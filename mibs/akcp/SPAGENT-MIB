--/***************************************************************************/
--/**                                                                        */
--/**               AKCP, Ltd                                                */
--/**               Proprietary and Confidential Information                 */
--/**                                                                        */
--/** This material contains, and is part of a computer software program     */
--/** which is, proprietary and confidential information owned by AKCP,Ltd   */
--/** The program, including this material,                                  */
--/** may not be duplicated, disclosed or reproduced in whole or in part for */
--/** any purpose without the express written authorization of AKCP, Ltd     */
--/** All authorized reproductions must be marked with this legend.          */
--/**                                                                        */
--/**                                                                        */
--/**                         Copyright (c) 1994-2025                        */
--/**                         AKCP, Ltd                                      */
--/**                         All rights reserved                            */
--/**                                                                        */
--/***************************************************************************/

--/***************************************************************************/
--/**                                                                        */
--/** This MIB is a superset which includes all of the features in the       */
--/** sensorProbe family. Some features may not be implemented in certain    */
--/** models.                                                                */
--/**                                                                        */
--/***************************************************************************/

SPAGENT-MIB DEFINITIONS ::= BEGIN

IMPORTS
        enterprises, IpAddress, Gauge, Opaque
                FROM RFC1155-SMI
        OBJECT-TYPE
                FROM RFC-1212
        DisplayString
                FROM RFC1213-MIB
        TRAP-TYPE
                FROM RFC-1215;


   akcp  OBJECT IDENTIFIER ::= { enterprises 3854 }
   sensorProbe OBJECT IDENTIFIER ::= { akcp 1 }


      spSummary OBJECT IDENTIFIER  ::=  {  sensorProbe 1   }

         spStatus OBJECT-TYPE
            SYNTAX  INTEGER {
               noStatus(1),
               normal(2),
               warning(3),
               critical(4),
               sensorError(5)
            }
            ACCESS  read-only
            STATUS  mandatory
            DESCRIPTION
            "The current status of this sensorProbe. The status of the sensorProbe is the worst status of all the sensors under the control of this sensorProbe."
            ::=  {  spSummary 2   }

         spManufName OBJECT-TYPE
            SYNTAX  DisplayString
            ACCESS  read-only
            STATUS  mandatory
            DESCRIPTION
            "The manufacturers name"
            ::=  {  spSummary 6   }

         spHelpUrl OBJECT-TYPE
            SYNTAX  DisplayString
            ACCESS  read-only
            STATUS  mandatory
            DESCRIPTION
            "The URL of the web based help"
            ::=  {  spSummary 7   }

         spProductName OBJECT-TYPE
            SYNTAX  DisplayString
            ACCESS  read-only
            STATUS  mandatory
            DESCRIPTION
            "The product name"
            ::=  {  spSummary 8   }

         spHostName OBJECT-TYPE
            SYNTAX  DisplayString
            ACCESS  read-only
            STATUS  mandatory
            DESCRIPTION
            "The hostname"
            ::=  {  spSummary 9   }
            
         spStatusEachModule OBJECT IDENTIFIER ::= { spSummary 10 }
            spStatusRJ45 OBJECT-TYPE
               SYNTAX  INTEGER {
                  noStatus(1),
                  normal(2),
                  warning(3),
                  critical(4),
                  sensorError(5)
               }
               ACCESS  read-only
               STATUS  mandatory
               DESCRIPTION
               "The status of the sensorProbe is the worst status of all sensors on RJ45 port"
               ::=  {  spStatusEachModule 1 }

            spStatusNoVideoSignal OBJECT-TYPE
               SYNTAX  INTEGER {
                  noStatus(1),
                  normal(2),
                  warning(3),
                  critical(4),
                  sensorError(5)
               }
               ACCESS  read-only
               STATUS  mandatory
               DESCRIPTION
               "The status of the sensorProbe is the worst status of all No Video Signal sensors"
               ::=  {  spStatusEachModule 2 }

            spStatusSoundDetector OBJECT-TYPE
               SYNTAX  INTEGER {
                  noStatus(1),
                  normal(2),
                  warning(3),
                  critical(4),
                  sensorError(5)
               }
               ACCESS  read-only
               STATUS  mandatory
               DESCRIPTION
               "The status of the sensorProbe is the worst status of Sound Detector sensors"
               ::=  {  spStatusEachModule 3 }

            spStatusVirtual OBJECT-TYPE
               SYNTAX  INTEGER {
                  noStatus(1),
                  normal(2),
                  warning(3),
                  critical(4),
                  sensorError(5)
               }
               ACCESS  read-only
               STATUS  mandatory
               DESCRIPTION
               "The status of the sensorProbe is the worst status of all Virtual sensors "
               ::=  {  spStatusEachModule 4 }

            spStatusSoftMotion OBJECT-TYPE
               SYNTAX  INTEGER {
                  noStatus(1),
                  normal(2),
                  warning(3),
                  critical(4),
                  sensorError(5)
               }
               ACCESS  read-only
               STATUS  mandatory
               DESCRIPTION
               "The status of the sensorProbe is the worst status of all Camera Motion Detector sensors "
               ::=  {  spStatusEachModule 5 }

      spSensor OBJECT IDENTIFIER  ::=  {  sensorProbe 2 }

         sensorProbeDetail OBJECT IDENTIFIER ::= { spSensor 2  }

            sensorProbeEntry OBJECT IDENTIFIER ::= { sensorProbeDetail 1  }

               sensorProbeHost OBJECT-TYPE
                  SYNTAX  IpAddress
                  ACCESS  read-write
                  STATUS  mandatory
                  DESCRIPTION
                  "The Host of this sensor, this is the IP address"
                  ::=  {  sensorProbeEntry 1   }

               sensorProbeUseDHCP OBJECT-TYPE
                  SYNTAX  INTEGER {
                     yes(1),
                     no(2)
                  }
                  ACCESS  read-write
                  STATUS  mandatory
                  DESCRIPTION
                  "To use DHCP enter a 1, to use a static IP address enter a 2"
                  ::=  {  sensorProbeEntry 2   }

               sensorProbeMAC OBJECT-TYPE
                  SYNTAX  DisplayString
                  ACCESS  read-only
                  STATUS  mandatory
                  DESCRIPTION
                  "The MAC address of this system"
                  ::=  {  sensorProbeEntry 3   }

               sensorProbeSetCommunity OBJECT-TYPE
                  SYNTAX  DisplayString
                  ACCESS  read-write
                  STATUS  mandatory
                  DESCRIPTION
                  "The sensorProbe community string used for snmp Sets"
                  ::=  {  sensorProbeEntry 4   }

               sensorProbeGetCommunity OBJECT-TYPE
                  SYNTAX  DisplayString
                  ACCESS  read-write
                  STATUS  mandatory
                  DESCRIPTION
                  "The sensorProbe community string used for snmp Gets"
                  ::=  {  sensorProbeEntry 5   }

               sensorProbeTempTable OBJECT-TYPE
                  SYNTAX  SEQUENCE OF SensorProbeTempEntry
                  ACCESS  not-accessible
                  STATUS  mandatory
                  DESCRIPTION
                  "This table contains the data for every Temperature Sensor in the SensorArray. Each row in the table contains data for a different Temperature Sensor."
                  ::=  {  sensorProbeEntry 16   }

               sensorProbeTempEntry OBJECT-TYPE
                  SYNTAX  SensorProbeTempEntry
                  ACCESS  not-accessible
                  STATUS  mandatory
                  DESCRIPTION
                  "This is an entry in the sensorProbeTempEntry Table"
                  INDEX         { sensorProbeTempIndex }
                  ::=  {  sensorProbeTempTable 1 }

                  SensorProbeTempEntry ::= SEQUENCE {
                     sensorProbeTempDescription
                        DisplayString,
                     sensorProbeTempLocation
                        DisplayString,
                     sensorProbeTempDegree
                        INTEGER,
                     sensorProbeTempStatus
                        INTEGER,
                     sensorProbeTempOnline
                        INTEGER,
                     sensorProbeTempGoOnline
                        INTEGER,
                     sensorProbeTempHighWarning
                        INTEGER,
                     sensorProbeTempHighCritical
                        INTEGER,
                     sensorProbeTempLowWarning
                        INTEGER,
                     sensorProbeTempLowCritical
                        INTEGER,
                     sensorProbeTempRearm
                        INTEGER,
                     sensorProbeTempDegreeType
                        INTEGER,
                     sensorProbeTempSensorType
                        INTEGER,
                     sensorProbeTempDegreeRaw
                        INTEGER,
                     sensorProbeTempEmailTrapLimit
                        INTEGER,
                     sensorProbeTempEmailTrapSchedule
                        DisplayString,
                     sensorProbeTempEmailTrapInterval
                        INTEGER,
                     sensorProbeTempSendNormalTrap
                        INTEGER,
                     sensorProbeTempDelayError
                        INTEGER,
                     sensorProbeTempDelayNormal
                        INTEGER,
                     sensorProbeTempIndex
                        INTEGER,
                     sensorProbeTempRelayCycleTime
                        INTEGER,
                     sensorProbeTempRelayOnPort
                        INTEGER,
                     sensorProbeTempRelayActiveStatus
                        INTEGER,
                     sensorProbeTempRelayAction
                        INTEGER,
                     sensorProbeTempEmailInterval
                        INTEGER,
                     sensorProbeTempIndexCount
                        INTEGER,
                     sensorProbeTempOffset
                        INTEGER,
                     sensorProbeTempSirenCycleTime
                        INTEGER,
                     sensorProbeTempSirenOnPort
                        INTEGER,
                     sensorProbeTempSirenActiveStatus
                        INTEGER,
                     sensorProbeTempSirenAction
                        INTEGER,
                     sensorProbeTempAcknowledgement
                        INTEGER,
                     sensorProbeTempSirenDelayAlarm
                        INTEGER,
                     sensorProbeTempURL
                        DisplayString,
                     sensorProbeTempOpenURL
                        INTEGER,
                     sensorProbeTempDatacollectType
                        INTEGER,
                     sensorProbeTempContTimeHighCritical
                        INTEGER,
                     sensorProbeTempContTimeHighWarning
                        INTEGER,
                     sensorProbeTempContTimeNormal
                        INTEGER,
                     sensorProbeTempContTimeLowWarning
                        INTEGER,
                     sensorProbeTempContTimeLowCritical
                        INTEGER,
                     sensorProbeTempContTimeSensorError
                        INTEGER,
                     sensorProbeTempCalendar
                        INTEGER,
                     sensorProbeThermostatIndex
                        INTEGER,
                     sensorProbeThermostatDescription
                        DisplayString,
                     sensorProbeThermostatValue
                        INTEGER,
                     sensorProbeThermostatOnline
                        INTEGER,
                     sensorProbeThermostatGoOnline
                        INTEGER,
                     sensorProbeThermostatMode
                        INTEGER,
                     sensorProbeThermostatRelayControlPort
                        INTEGER,
                     sensorProbeThermostatNormalAction1
                        INTEGER,
                     sensorProbeThermostatHighLimit1
                        INTEGER,
                     sensorProbeThermostatHighLimitAction1
                        INTEGER,
                     sensorProbeThermostatLowLimit1
                        INTEGER,
                     sensorProbeThermostatLowLimitAction1
                        INTEGER,
                     sensorProbeThermostatNormalAction2
                        INTEGER,
                     sensorProbeThermostatHighLimit2
                        INTEGER,
                     sensorProbeThermostatHighLimitAction2
                        INTEGER,
                     sensorProbeThermostatLowLimit2
                        INTEGER,
                     sensorProbeThermostatLowLimitAction2
                        INTEGER,
                     sensorProbeThermostatEnableTime
                        DisplayString,
                     sensorProbeTempSendNormalMail
                        INTEGER,
                     sensorProbeTempSendTrap
                        INTEGER,
                     sensorProbeTempSendMail
                        INTEGER
                  }
                  sensorProbeTempDescription OBJECT-TYPE
                     SYNTAX  DisplayString
                     ACCESS  read-write
                     STATUS  mandatory
                     DESCRIPTION
                     "A Description of this sensor"
                     ::=  {  sensorProbeTempEntry 1   }

                  sensorProbeTempLocation OBJECT-TYPE
                       SYNTAX  DisplayString
                       ACCESS  read-write
                       STATUS  mandatory
                       DESCRIPTION
                       "The physical location of this sensor"
                       ::=  {  sensorProbeTempEntry 2   }

                  sensorProbeTempDegree OBJECT-TYPE
                     SYNTAX  INTEGER
                     ACCESS  read-only
                     STATUS  mandatory
                     DESCRIPTION
                     "The degrees in this sensor"
                     ::=  {  sensorProbeTempEntry 3   }

                  sensorProbeTempStatus OBJECT-TYPE
                     SYNTAX  INTEGER {
                        noStatus(1),
                        normal(2),
                        highWarning(3),
                        highCritical(4),
                        lowWarning(5),
                        lowCritical(6),
                        sensorError(7)
                     }
                     ACCESS  read-only
                     STATUS  mandatory
                     DESCRIPTION
                     "The current status of this Sensor"
                     ::=  {  sensorProbeTempEntry 4   }
      
                  sensorProbeTempOnline OBJECT-TYPE
                     SYNTAX  INTEGER {
                        online(1),
                        offline(2)
                     }
                     ACCESS  read-only
                     STATUS  mandatory
                     DESCRIPTION
                     "If this Sensor is currently online"
                     ::=  {  sensorProbeTempEntry 5   }
   
                  sensorProbeTempGoOnline OBJECT-TYPE
                     SYNTAX  INTEGER {
                        goOnline(1),
                        goOffline(2)
                     }
                     ACCESS  read-write
                     STATUS  mandatory
                     DESCRIPTION
                     "To put online enter a 1, to take offline enter a 2"
                     ::=  {  sensorProbeTempEntry 6   }
         
                  sensorProbeTempHighWarning OBJECT-TYPE
                     SYNTAX  INTEGER
                     ACCESS  read-write
                     STATUS  mandatory
                     DESCRIPTION
                     "How hot this sensor gets before it sends a warning"
                     ::=  {  sensorProbeTempEntry 7   }
      
                  sensorProbeTempHighCritical OBJECT-TYPE
                     SYNTAX  INTEGER
                     ACCESS  read-write
                     STATUS  mandatory
                     DESCRIPTION
                     "How hot this sensor gets before it sends a critical event"
                     ::=  {  sensorProbeTempEntry 8   }
   
                  sensorProbeTempLowWarning OBJECT-TYPE
                     SYNTAX  INTEGER
                     ACCESS  read-write
                     STATUS  mandatory
                     DESCRIPTION
                     "How cold this sensor gets before it sends a warning"
                     ::=  {  sensorProbeTempEntry 9   }
   
                  sensorProbeTempLowCritical OBJECT-TYPE
                     SYNTAX  INTEGER
                     ACCESS  read-write
                     STATUS  mandatory
                     DESCRIPTION
                     "How cold this sensor gets before it sends a critical event"
                     ::=  {  sensorProbeTempEntry 10   }
      
                  sensorProbeTempRearm OBJECT-TYPE
                     SYNTAX  INTEGER
                     ACCESS  read-write
                     STATUS  mandatory
                     DESCRIPTION
                     "The number of degrees to rearm the status. For example if status goes from normal to warning, the temp must go down spTempRearm degrees below warning before the status goes to normal"
                     ::=  {  sensorProbeTempEntry 11   }
   
                  sensorProbeTempDegreeType OBJECT-TYPE
                     SYNTAX  INTEGER {
                        fahr(0),
                        celsius(1)
                     }
                     ACCESS  read-write
                     STATUS  mandatory
                     DESCRIPTION
                     "The degrees are in fahrenheit(0) or in celsius(1)"
                     ::=  {  sensorProbeTempEntry 12   }
      
                  sensorProbeTempSensorType OBJECT-TYPE
                       SYNTAX  INTEGER {
                          type1(0),
                          type2(1)
                       }
                       ACCESS  read-write
                       STATUS  mandatory
                       DESCRIPTION
                       "The type of temperture sensor"
                       ::=  {  sensorProbeTempEntry 13   }
         
                  sensorProbeTempDegreeRaw OBJECT-TYPE
                     SYNTAX  INTEGER 
                     ACCESS  read-only
                     STATUS  mandatory
                     DESCRIPTION
                     "SP Only: The raw degree data from the temperature sensor, slightly higher resolution"
                     ::=  {  sensorProbeTempEntry 14   }

                  sensorProbeTempEmailTrapLimit OBJECT-TYPE
                     SYNTAX  INTEGER {
                        disable(0),
                        enable(1)
                     }
                     ACCESS  read-write
                     STATUS  mandatory
                     DESCRIPTION
                     "Enable email/trap limit feature"
                     ::=  {  sensorProbeTempEntry 16   }

                  sensorProbeTempEmailTrapSchedule OBJECT-TYPE
                     SYNTAX  DisplayString
                     ACCESS  read-write
                     STATUS  mandatory
                     DESCRIPTION
                     "SP Only: Email/trap limit schedule for this sensor"
                     ::=  {  sensorProbeTempEntry 17   }

                  sensorProbeTempEmailTrapInterval OBJECT-TYPE
                     SYNTAX  INTEGER (0..60)
                     ACCESS  read-write
                     STATUS  mandatory
                     DESCRIPTION
                     "Minimum time between each [email/trap:SP, only trap:CP8] (can be from 0 to 60 minutes)."
                     ::=  {  sensorProbeTempEntry 18   }

                  sensorProbeTempSendNormalTrap OBJECT-TYPE
                     SYNTAX  INTEGER {
                        disable(0),
                        enable(1)
                     }
                     ACCESS  read-write
                     STATUS  mandatory
                     DESCRIPTION
                     "Enable sending email/trap when sensor goes to normal"
                     ::=  {  sensorProbeTempEntry 19   }

                  sensorProbeTempDelayError OBJECT-TYPE
                     SYNTAX  INTEGER (0..65534)
                     ACCESS  read-write
                     STATUS  mandatory
                     DESCRIPTION
                     "Time in seconds after the sensor has been in error status before report as an error"
                     ::=  {  sensorProbeTempEntry 20   }

                  sensorProbeTempDelayNormal OBJECT-TYPE
                     SYNTAX  INTEGER (0..65534)
                     ACCESS  read-write
                     STATUS  mandatory
                     DESCRIPTION
                     "Time in seconds after the sensor change from error to normal before report as normal"
                     ::=  {  sensorProbeTempEntry 21   }

                  sensorProbeTempIndex OBJECT-TYPE
                     SYNTAX  INTEGER (0..7)
                     ACCESS  read-only
                     STATUS  mandatory
                     DESCRIPTION
                     "The index into the temperature sensor table"
                     ::=  {  sensorProbeTempEntry 22   }
                     
                  sensorProbeTempRelayCycleTime OBJECT-TYPE
                     SYNTAX INTEGER (1..255)
                     ACCESS read-write
                     STATUS mandatory
                     DESCRIPTION
                     "Relay toggle period in seconds for Cycle action."
                     ::= {  sensorProbeTempEntry 23 }

                  sensorProbeTempRelayOnPort OBJECT-TYPE
                     SYNTAX INTEGER (0..255)
                     ACCESS read-write
                     STATUS mandatory
                     DESCRIPTION
                     "The sensor port that the relay will listen to. If this is set to 255, then the relay will not listen to any sensor ports"
                     ::= {  sensorProbeTempEntry 24 }

                  sensorProbeTempRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::= {  sensorProbeTempEntry 25 }

                  sensorProbeTempRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::= {  sensorProbeTempEntry 26 }

                  sensorProbeTempEmailInterval OBJECT-TYPE
                     SYNTAX  INTEGER (0..60)
                     ACCESS  read-write
                     STATUS  mandatory
                     DESCRIPTION
                     "CP8 Only: Minimum time between each email (can be from 0 to 60 minutes)"
                     ::=  {  sensorProbeTempEntry 27   }

                  sensorProbeTempIndexCount OBJECT-TYPE
                     SYNTAX  INTEGER
                     ACCESS  read-only
                     STATUS  mandatory
                     DESCRIPTION
                     "Number of Temperature sensor online"
                     ::=  {  sensorProbeTempEntry 28   }

                  sensorProbeTempOffset OBJECT-TYPE
                     SYNTAX  INTEGER
                     ACCESS  read-write
                     STATUS  mandatory
                     DESCRIPTION
                     "Temperature Offset reading"
                     ::=  {  sensorProbeTempEntry 29   }

                  sensorProbeTempSirenCycleTime OBJECT-TYPE
                     SYNTAX INTEGER (1..255)
                     ACCESS read-write
                     STATUS mandatory
                     DESCRIPTION
                     "Siren toggle period in seconds for Cycle action."
                     ::= {  sensorProbeTempEntry 30 }

                  sensorProbeTempSirenOnPort OBJECT-TYPE
                     SYNTAX INTEGER (0..255)
                     ACCESS read-write
                     STATUS mandatory
                     DESCRIPTION
                     "The sensor port that the siren will listen to. If this is set to 255, then the siren will not listen to any sensor ports"
                     ::= {  sensorProbeTempEntry 31 }

                  sensorProbeTempSirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::= {  sensorProbeTempEntry 32 }

                  sensorProbeTempSirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::= {  sensorProbeTempEntry 33 }

                  sensorProbeTempAcknowledgement OBJECT-TYPE
                     SYNTAX INTEGER {
                        ack(1)
                     }
                     ACCESS read-write
                     STATUS mandatory
                     DESCRIPTION
                     "Acknowledged sensor error and stop notification"
                     ::= {  sensorProbeTempEntry 34 }

                  sensorProbeTempSirenDelayAlarm OBJECT-TYPE
                     SYNTAX INTEGER (1..255)
                     ACCESS read-write
                     STATUS mandatory
                     DESCRIPTION
                     "Siren delay in seconds before start Alarm."
                     ::= {  sensorProbeTempEntry 35 }

                  sensorProbeTempURL OBJECT-TYPE
                     SYNTAX  DisplayString
                     ACCESS  read-write
                     STATUS  mandatory
                     DESCRIPTION
                     "Sensor URL link."
                     ::= {  sensorProbeTempEntry 36 }

                  sensorProbeTempOpenURL OBJECT-TYPE
                     SYNTAX INTEGER {
                        cur-window(0),
                        new-window(2)
                     }
                     ACCESS read-write
                     STATUS mandatory
                     DESCRIPTION
                     "Open URL in this browser or open in a new window."
                     ::= {  sensorProbeTempEntry 37 }

                  sensorProbeTempDatacollectType OBJECT-TYPE
                     SYNTAX INTEGER {
                        average(1),
                        highest(2),
                        lowest(3)
                     }
                     ACCESS read-write
                     STATUS mandatory
                     DESCRIPTION
                     "Type of datacollect to collect."
                     ::= {  sensorProbeTempEntry 38 }

                  sensorProbeTempContTimeHighCritical OBJECT-TYPE
                     SYNTAX INTEGER (0..65535)
                     ACCESS read-write
                     STATUS mandatory
                     DESCRIPTION
                     "Continuous time for this sensor to be in High Critical before accepting new Status."
                     ::= {  sensorProbeTempEntry 39 }

                  sensorProbeTempContTimeHighWarning OBJECT-TYPE
                     SYNTAX INTEGER (0..65535)
                     ACCESS read-write
                     STATUS mandatory
                     DESCRIPTION
                     "Continuous time for this sensor to be in High Warning before accepting new Status."
                     ::= {  sensorProbeTempEntry 40 }

                  sensorProbeTempContTimeNormal OBJECT-TYPE
                     SYNTAX INTEGER (0..65535)
                     ACCESS read-write
                     STATUS mandatory
                     DESCRIPTION
                     "Continuous time for this sensor to be in Normal before accepting new Status."
                     ::= {  sensorProbeTempEntry 41 }

                  sensorProbeTempContTimeLowWarning OBJECT-TYPE
                     SYNTAX INTEGER (0..65535)
                     ACCESS read-write
                     STATUS mandatory
                     DESCRIPTION
                     "Continuous time for this sensor to be in Low Warning before accepting new Status."
                     ::= {  sensorProbeTempEntry 42 }

                  sensorProbeTempContTimeLowCritical OBJECT-TYPE
                     SYNTAX INTEGER (0..65535)
                     ACCESS read-write
                     STATUS mandatory
                     DESCRIPTION
                     "Continuous time for this sensor to be in Low Critical before accepting new Status."
                     ::= {  sensorProbeTempEntry 43 }

                  sensorProbeTempContTimeSensorError OBJECT-TYPE
                     SYNTAX INTEGER (0..65535)
                     ACCESS read-write
                     STATUS mandatory
                     DESCRIPTION
                     "Continuous time for this sensor to be in Sensor Error before accepting new Status."
                     ::= {  sensorProbeTempEntry 44 }

                  sensorProbeTempCalendar OBJECT-TYPE
                     SYNTAX INTEGER {
                        disable(0),
                        enable(1)
                     }
                     ACCESS read-write
                     STATUS mandatory
                     DESCRIPTION
                     "Enable or disable the calendar filtering working hours of sensor."
                     ::= {  sensorProbeTempEntry 45 }

                  sensorProbeThermostatIndex OBJECT-TYPE
                     SYNTAX  INTEGER
                     ACCESS  read-only
                     STATUS  mandatory
                     DESCRIPTION
                     "A unique value for each sensor thermostat port."
                     ::= {  sensorProbeTempEntry 46 }

                  sensorProbeThermostatDescription OBJECT-TYPE
                     SYNTAX  DisplayString
                     ACCESS  read-write
                     STATUS  mandatory
                     DESCRIPTION
                     "A Description of this sensor thermostat"
                     ::= {  sensorProbeTempEntry 47 }

                  sensorProbeThermostatValue OBJECT-TYPE
                     SYNTAX  INTEGER
                     ACCESS  read-only
                     STATUS  mandatory
                     DESCRIPTION
                     "The value in this sensor"
                     ::= {  sensorProbeTempEntry 48 }

                  sensorProbeThermostatOnline OBJECT-TYPE
                     SYNTAX  INTEGER {
                        online(1),
                        offline(2)
                     }
                     ACCESS  read-only
                     STATUS  mandatory
                     DESCRIPTION
                     "If this Sensor is currently online"
                     ::= {  sensorProbeTempEntry 49 }

                  sensorProbeThermostatGoOnline OBJECT-TYPE
                     SYNTAX  INTEGER {
                        goOnline(1),
                        goOffline(2)
                     }
                     ACCESS  read-write
                     STATUS  mandatory
                     DESCRIPTION
                     "To put online enter a 1, to take offline enter a 2"
                     ::= {  sensorProbeTempEntry 50 }

                  sensorProbeThermostatMode OBJECT-TYPE
                     SYNTAX INTEGER {
                        normal(0),
                        time-bases(1)
                     }
                     ACCESS read-write
                     STATUS mandatory
                     DESCRIPTION
                     "To select the thermostat mode for working on time-bases(1) or normal(0)."
                     ::= {  sensorProbeTempEntry 51 }

                  sensorProbeThermostatRelayControlPort OBJECT-TYPE
                     SYNTAX INTEGER
                     ACCESS read-write
                     STATUS mandatory
                     DESCRIPTION
                     "To select a relay port to be controled by this thermostat sensor."
                     ::= {  sensorProbeTempEntry 52 }

                  sensorProbeThermostatNormalAction1 OBJECT-TYPE
                     SYNTAX INTEGER {
                        turn-on(0),
                        turn-off(1),
                        no-change(2)
                     }
                     ACCESS read-write
                     STATUS mandatory
                     DESCRIPTION
                     "Profile1: Thermostat normal action for controlling a relay sensor."
                     ::= {  sensorProbeTempEntry 53 }

                  sensorProbeThermostatHighLimit1 OBJECT-TYPE
                     SYNTAX INTEGER (-40..167)
                     ACCESS read-write
                     STATUS mandatory
                     DESCRIPTION
                     "Profile1: When this sersor higher than thermostat high limit, it will take a high limit action."
                     ::= {  sensorProbeTempEntry 54 }

                  sensorProbeThermostatHighLimitAction1 OBJECT-TYPE
                     SYNTAX INTEGER {
                        turn-on(0),
                        turn-off(1),
                        no-change(2)
                     }
                     ACCESS read-write
                     STATUS mandatory
                     DESCRIPTION
                     "Profile1: Thermostat high limit action for controlling a relay sensor."
                     ::= {  sensorProbeTempEntry 55 }

                  sensorProbeThermostatLowLimit1 OBJECT-TYPE
                     SYNTAX INTEGER (-40..167)
                     ACCESS read-write
                     STATUS mandatory
                     DESCRIPTION
                     "Profile1: When this sersor higher than thermostat low limit, it will take a normal limit action."
                     ::= {  sensorProbeTempEntry 56 }

                  sensorProbeThermostatLowLimitAction1 OBJECT-TYPE
                     SYNTAX INTEGER {
                        turn-on(0),
                        turn-off(1),
                        no-change(2)
                     }
                     ACCESS read-write
                     STATUS mandatory
                     DESCRIPTION
                     "Profile1: Thermostat low limit action for controlling a relay sensor."
                     ::= {  sensorProbeTempEntry 57 }

                  sensorProbeThermostatNormalAction2 OBJECT-TYPE
                     SYNTAX INTEGER {
                        turn-on(0),
                        turn-off(1),
                        no-change(2)
                     }
                     ACCESS read-write
                     STATUS mandatory
                     DESCRIPTION
                     "Profile2: Thermostat normal action for controlling a relay sensor."
                     ::= {  sensorProbeTempEntry 58 }

                  sensorProbeThermostatHighLimit2 OBJECT-TYPE
                     SYNTAX INTEGER (-40..167)
                     ACCESS read-write
                     STATUS mandatory
                     DESCRIPTION
                     "Profile2: When this sersor higher than thermostat high limit, it will take a high limit action."
                     ::= {  sensorProbeTempEntry 59 }

                  sensorProbeThermostatHighLimitAction2 OBJECT-TYPE
                     SYNTAX INTEGER {
                        turn-on(0),
                        turn-off(1),
                        no-change(2)
                     }
                     ACCESS read-write
                     STATUS mandatory
                     DESCRIPTION
                     "Profile2: Thermostat high limit action for controlling a relay sensor."
                     ::= {  sensorProbeTempEntry 60 }

                  sensorProbeThermostatLowLimit2 OBJECT-TYPE
                     SYNTAX INTEGER (-40..167)
                     ACCESS read-write
                     STATUS mandatory
                     DESCRIPTION
                     "Profile2: When this sersor higher than thermostat low limit, it will take a normal limit action."
                     ::= {  sensorProbeTempEntry 61 }

                  sensorProbeThermostatLowLimitAction2 OBJECT-TYPE
                     SYNTAX INTEGER {
                        turn-on(0),
                        turn-off(1),
                        no-change(2)
                     }
                     ACCESS read-write
                     STATUS mandatory
                     DESCRIPTION
                     "Profile2: Thermostat low limit action for controlling a relay sensor."
                     ::= {  sensorProbeTempEntry 62 }

                  sensorProbeThermostatEnableTime OBJECT-TYPE
                     SYNTAX  DisplayString
                     ACCESS  read-write
                     STATUS  mandatory
                     DESCRIPTION
                     "Time to enable on Thermostat"
                     ::=  {  sensorProbeTempEntry 63 }

                  sensorProbeTempSendNormalMail OBJECT-TYPE
                     SYNTAX  INTEGER {
                        disable(0),
                        enable(1)
                     }
                     ACCESS  read-write
                     STATUS  mandatory
                     DESCRIPTION
                     "Enable sending email when sensor goes to normal"
                     ::=  {  sensorProbeTempEntry 64 }

                  sensorProbeTempSendTrap OBJECT-TYPE
                     SYNTAX  INTEGER {
                        disable(0),
                        enable(1)
                     }
                     ACCESS  read-write
                     STATUS  mandatory
                     DESCRIPTION
                     "Enable sending trap when sensor change status"
                     ::=  {  sensorProbeTempEntry 65 }

                  sensorProbeTempSendMail OBJECT-TYPE
                     SYNTAX  INTEGER {
                        disable(0),
                        enable(1)
                     }
                     ACCESS  read-write
                     STATUS  mandatory
                     DESCRIPTION
                     "Enable sending email when sensor change status"
                     ::=  {  sensorProbeTempEntry 66 }

               sensorProbeHumidityTable OBJECT-TYPE
                  SYNTAX  SEQUENCE OF SensorProbeHumidityEntry
                  ACCESS  not-accessible
                  STATUS  mandatory
                  DESCRIPTION
                  "This table contains the data for every Humidity Sensor in the SensorArray. Each row in the table contains data for a different Humidity Sensor."
                  ::=  {  sensorProbeEntry 17   }

               sensorProbeHumidityEntry OBJECT-TYPE
                  SYNTAX  SensorProbeHumidityEntry
                  ACCESS  not-accessible
                  STATUS  mandatory
                  DESCRIPTION
                  "This is an entry in the sensorProbeHumidityEntry Table"
                  INDEX         { sensorProbeHumidityIndex }
                  ::=  { sensorProbeHumidityTable 1 }

                  SensorProbeHumidityEntry ::= SEQUENCE {
                     sensorProbeHumidityDescription
                        DisplayString,
                       sensorProbeHumidityLocation
                          DisplayString,
                     sensorProbeHumidityPercent
                        INTEGER,
                     sensorProbeHumidityStatus
                        INTEGER,
                     sensorProbeHumidityOnline
                        INTEGER,
                     sensorProbeHumidityGoOnline
                        INTEGER,
                     sensorProbeHumidityHighWarning
                        INTEGER,
                     sensorProbeHumidityHighCritical
                        INTEGER,
                     sensorProbeHumidityLowWarning
                        INTEGER,
                     sensorProbeHumidityLowCritical
                        INTEGER,
                     sensorProbeHumidityRearm
                        INTEGER,
                     sensorProbeHumidityRaw
                        INTEGER,
                     sensorProbeHumidityLowVoltage
                        INTEGER,
                     sensorProbeHumidityHighVoltage
                        INTEGER,
                     sensorProbeHumidityEmailTrapLimit
                        INTEGER,
                     sensorProbeHumidityEmailTrapSchedule
                        DisplayString,
                     sensorProbeHumidityEmailTrapInterval
                        INTEGER,
                     sensorProbeHumiditySendNormalTrap
                        INTEGER,
                     sensorProbeHumidityDelayError
                        INTEGER,
                     sensorProbeHumidityDelayNormal
                        INTEGER,
                     sensorProbeHumidityIndex
                        INTEGER,
                     sensorProbeHumidityAtoDAmountMaxVoltage
                        INTEGER,
                     sensorProbeHumidityAtoDAmountBaseVoltage
                        INTEGER,
                     sensorProbeHumidityAtoDTypeUnit
                        INTEGER,
                     sensorProbeHumidityDcUnit
                        DisplayString,
                     sensorProbeHumidityAtoDJumper
                        INTEGER,
                     sensorProbeHumidityRelayCycleTime
                        INTEGER,
                     sensorProbeHumidityRelayOnPort
                        INTEGER,
                     sensorProbeHumidityRelayActiveStatus
                        INTEGER,
                     sensorProbeHumidityRelayAction
                        INTEGER,
                     sensorProbeHumidityEmailInterval
                        INTEGER,
                     sensorProbeHumidity4to20mAUnit
                        DisplayString,
                     sensorProbeHumidityIndexCount
                        INTEGER,
                     sensorProbeHumidityOffset
                        INTEGER,
                     sensorProbeHumiditySirenCycleTime
                        INTEGER,
                     sensorProbeHumiditySirenOnPort
                        INTEGER,
                     sensorProbeHumiditySirenActiveStatus
                        INTEGER,
                     sensorProbeHumiditySirenAction
                        INTEGER,
                     sensorProbeHumidityAcknowledgement
                        INTEGER,
                     sensorProbeHumiditySirenDelayAlarm
                        INTEGER,
                     sensorProbeHumidityURL
                        DisplayString,
                     sensorProbeHumidityOpenURL
                        INTEGER,
                     sensorProbeHumidityDatacollectType
                        INTEGER,
                     sensorProbeHumidityContTimeHighCritical
                        INTEGER,
                     sensorProbeHumidityContTimeHighWarning
                        INTEGER,
                     sensorProbeHumidityContTimeNormal
                        INTEGER,
                     sensorProbeHumidityContTimeLowWarning
                        INTEGER,
                     sensorProbeHumidityContTimeLowCritical
                        INTEGER,
                     sensorProbeHumidityContTimeSensorError
                        INTEGER,
                     sensorProbeHumidityCalendar
                        INTEGER,
                     sensorProbeHumiditySendNormalMail
                        INTEGER,
                     sensorProbeHumiditySendTrap
                        INTEGER,
                     sensorProbeHumiditySendMail
                        INTEGER,
                     sensorProbeIDCVVoltateRatio
                        INTEGER,
                     sensorProbeIDCVErrorFlag
                        INTEGER,
                     sensorProbeIDCVCalibrate
                        INTEGER,
                     sensorProbeAirFlowProtocolType
                        INTEGER,
                     sensorProbeAirFlowSensitivity
                        INTEGER,
                     sensorProbeAirFlowNormalState
                        INTEGER,
                     sensorProbeAirFlowCalibrate
                        INTEGER
                  }
                  sensorProbeHumidityDescription OBJECT-TYPE
                     SYNTAX  DisplayString
                     ACCESS  read-write
                     STATUS  mandatory
                     DESCRIPTION
                     "A Description of this sensor"
                     ::=  {  sensorProbeHumidityEntry 1   }

                  sensorProbeHumidityLocation OBJECT-TYPE
                       SYNTAX  DisplayString
                       ACCESS  read-write
                       STATUS  mandatory
                       DESCRIPTION
                       "The physical location of this sensor"
                       ::=  {  sensorProbeHumidityEntry 2   }

                  sensorProbeHumidityPercent OBJECT-TYPE
                     SYNTAX  INTEGER (-32768..32767)
                     ACCESS  read-only
                     STATUS  mandatory
                     DESCRIPTION
                     "The relative humidity percentage measured by this sensor"
                     ::=  {  sensorProbeHumidityEntry 3   }

                  sensorProbeHumidityStatus OBJECT-TYPE
                     SYNTAX  INTEGER {
                        noStatus(1),
                        normal(2),
                        highWarning(3),
                        highCritical(4),
                        lowWarning(5),
                        lowCritical(6),
                        sensorError(7)
                     }
                     ACCESS  read-only
                     STATUS  mandatory
                     DESCRIPTION
                     "The current status of this Sensor"
                     ::=  {  sensorProbeHumidityEntry 4   }

                  sensorProbeHumidityOnline OBJECT-TYPE
                     SYNTAX  INTEGER {
                        online(1),
                        offline(2)
                     }
                     ACCESS  read-only
                     STATUS  mandatory
                     DESCRIPTION
                     "If this Sensor is currently online"
                        ::=  {  sensorProbeHumidityEntry 5   }

                  sensorProbeHumidityGoOnline OBJECT-TYPE
                     SYNTAX  INTEGER {
                        goOnline(1),
                        goOffline(2)
                     }
                     ACCESS  read-write
                     STATUS  mandatory
                     DESCRIPTION
                     "To put online enter a 1, to take offline enter a 2"
                     ::=  {  sensorProbeHumidityEntry 6   }

                  sensorProbeHumidityHighWarning OBJECT-TYPE
                     SYNTAX  INTEGER
                     ACCESS  read-write
                     STATUS  mandatory
                     DESCRIPTION
                     "How high the relative humidity this sensor measures before it sends a warning"
                     ::=  {  sensorProbeHumidityEntry 7   }

                  sensorProbeHumidityHighCritical OBJECT-TYPE
                     SYNTAX  INTEGER
                     ACCESS  read-write
                     STATUS  mandatory
                     DESCRIPTION
                     "How high the relative humidity this sensor measures before it becomes critical"
                     ::=  {  sensorProbeHumidityEntry 8   }

                  sensorProbeHumidityLowWarning OBJECT-TYPE
                     SYNTAX  INTEGER
                     ACCESS  read-write
                     STATUS  mandatory
                     DESCRIPTION
                     "How low the relative humidity this sensor measures before it sends a warning"
                     ::=  {  sensorProbeHumidityEntry 9   }

                  sensorProbeHumidityLowCritical OBJECT-TYPE
                     SYNTAX  INTEGER
                     ACCESS  read-write
                     STATUS  mandatory
                     DESCRIPTION
                     "How low the relative humidity this sensor measures before it becomes critical"
                     ::=  {  sensorProbeHumidityEntry 10   }

                  sensorProbeHumidityRearm OBJECT-TYPE
                     SYNTAX  INTEGER
                     ACCESS  read-write
                     STATUS  mandatory
                     DESCRIPTION
                     "The percent relative humidity to rearm the status. For example if status goes from normal to warning, the humidity must go down spAnalogueRearm below warning before the status goes to normal"
                     ::=  {  sensorProbeHumidityEntry 11   }

                  sensorProbeHumidityRaw OBJECT-TYPE
                     SYNTAX  INTEGER 
                     ACCESS  read-only
                     STATUS  mandatory
                     DESCRIPTION
                     "The unformatted, raw, A/D value in this sensor. Contains more resolution than the formated percentage. This number can go from 0 to 1023 depending on the input voltage"
                     ::=  {  sensorProbeHumidityEntry 13   }

                  sensorProbeHumidityLowVoltage OBJECT-TYPE
                     SYNTAX  INTEGER
                     ACCESS  read-write
                     STATUS  mandatory
                     DESCRIPTION
                     "SP Only: The low voltage range for use in AtoD conversion."
                     ::=  {  sensorProbeHumidityEntry 14   }

                  sensorProbeHumidityHighVoltage OBJECT-TYPE
                     SYNTAX  INTEGER
                     ACCESS  read-write
                     STATUS  mandatory
                     DESCRIPTION
                     "SP Only: The high voltage range for use in AtoD conversion."
                     ::=  {  sensorProbeHumidityEntry 15   }

                  sensorProbeHumidityEmailTrapLimit OBJECT-TYPE
                     SYNTAX  INTEGER {
                        disable(0),
                        enable(1)
                     }
                     ACCESS  read-write
                     STATUS  mandatory
                     DESCRIPTION
                     "Enable email/trap limit feature"
                     ::=  {  sensorProbeHumidityEntry 17   }

                  sensorProbeHumidityEmailTrapSchedule OBJECT-TYPE
                     SYNTAX  DisplayString
                     ACCESS  read-write
                     STATUS  mandatory
                     DESCRIPTION
                     "SP Only: Email/trap limit schedule for this sensor"
                     ::=  {  sensorProbeHumidityEntry 18   }

                  sensorProbeHumidityEmailTrapInterval OBJECT-TYPE
                     SYNTAX  INTEGER (0..60)
                     ACCESS  read-write
                     STATUS  mandatory
                     DESCRIPTION
                     "Minimum time between each [email/trap:SP, only trap:CP8] (can be from 0 to 60 minutes)"
                     ::=  {  sensorProbeHumidityEntry 19   }

                  sensorProbeHumiditySendNormalTrap OBJECT-TYPE
                     SYNTAX  INTEGER {
                        disable(0),
                        enable(1)
                     }
                     ACCESS  read-write
                     STATUS  mandatory
                     DESCRIPTION
                     "Enable sending email/trap when sensor goes to normal"
                     ::=  {  sensorProbeHumidityEntry 20   }

                  sensorProbeHumidityDelayError OBJECT-TYPE
                     SYNTAX  INTEGER (0..65534)
                     ACCESS  read-write
                     STATUS  mandatory
                     DESCRIPTION
                     "Time in seconds after the sensor has been in error status before report as an error"
                     ::=  {  sensorProbeHumidityEntry 21   }

                  sensorProbeHumidityDelayNormal OBJECT-TYPE
                     SYNTAX  INTEGER (0..65534)
                     ACCESS  read-write
                     STATUS  mandatory
                     DESCRIPTION
                     "Time in seconds after the sensor change from error to normal before report as normal"
                     ::=  {  sensorProbeHumidityEntry 22   }

                  sensorProbeHumidityIndex OBJECT-TYPE
                     SYNTAX  INTEGER (0..7)
                     ACCESS  read-only
                     STATUS  mandatory
                     DESCRIPTION
                     "The index into the Humidity sensor table"
                     ::=  {  sensorProbeHumidityEntry 23   }

                  sensorProbeHumidityAtoDAmountMaxVoltage OBJECT-TYPE
                     SYNTAX  INTEGER
                     ACCESS  read-write
                     STATUS  mandatory
                     DESCRIPTION
                     "The maximum scale of DC voltage conversion."
                     ::=  {  sensorProbeHumidityEntry 24   }

                  sensorProbeHumidityAtoDAmountBaseVoltage OBJECT-TYPE
                     SYNTAX  INTEGER
                     ACCESS  read-write
                     STATUS  mandatory
                     DESCRIPTION
                     "The base scale of DC voltage conversion."
                     ::=  {  sensorProbeHumidityEntry 25   }

                  sensorProbeHumidityAtoDTypeUnit OBJECT-TYPE
                     SYNTAX  INTEGER {
                        absolute(1),
                        percent(2)
                     }
                     ACCESS  read-write
                     STATUS  mandatory
                     DESCRIPTION
                     "Type of scale for use in DC voltage conversion."
                     ::=  {  sensorProbeHumidityEntry 26   }
                
                  sensorProbeHumidityDcUnit OBJECT-TYPE
                     SYNTAX  DisplayString
                     ACCESS  read-write
                     STATUS  mandatory
                     DESCRIPTION
                     "Display unit in DC voltage conversion."
                     ::=  {  sensorProbeHumidityEntry 27   }

                  sensorProbeHumidityAtoDJumper OBJECT-TYPE
                     SYNTAX  INTEGER {                 
                        jumperAt-60(-600),
                        jumperAt-40(-400),
                        jumperAt-30(-300),
                        jumperAt-20(-200),
                        jumperAt-10(-100),                        
                        jumperAt10(100),
                        jumperAt20(200),
                        jumperAt30(300),
                        jumperAt40(400),
                        jumperAt60(600)
                     }
                     ACCESS  read-write
                     STATUS  mandatory
                     DESCRIPTION
                     "Selected voltage scale (jumper 0) in DC voltage conversion."
                     ::=  {  sensorProbeHumidityEntry 28   }

                  sensorProbeHumidityRelayCycleTime OBJECT-TYPE
                     SYNTAX INTEGER (1..255)
                     ACCESS read-write
                     STATUS mandatory
                     DESCRIPTION
                     "Relay toggle period in seconds for Cycle action."
                     ::=  {  sensorProbeHumidityEntry 29   }

                  sensorProbeHumidityRelayOnPort OBJECT-TYPE
                     SYNTAX INTEGER (0..255)
                     ACCESS read-write
                     STATUS mandatory
                     DESCRIPTION
                     "The sensor port that the relay will listen to. If this is set to 255, then the relay will not listen to any sensor ports"
                     ::=  {  sensorProbeHumidityEntry 30   }

                  sensorProbeHumidityRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::=  {  sensorProbeHumidityEntry 31   }

                  sensorProbeHumidityRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::=  {  sensorProbeHumidityEntry 32   }

                  sensorProbeHumidityEmailInterval OBJECT-TYPE
                     SYNTAX  INTEGER (0..60)
                     ACCESS  read-write
                     STATUS  mandatory
                     DESCRIPTION
                     "CP8 Only: Minimum time between each emial (can be from 0 to 60 minutes)"
                     ::=  {  sensorProbeHumidityEntry 33   }

                  sensorProbeHumidity4to20mAUnit OBJECT-TYPE
                     SYNTAX  DisplayString
                     ACCESS  read-write
                     STATUS  mandatory
                     DESCRIPTION
                     "Display unit in DC voltage conversion."
                     ::=  {  sensorProbeHumidityEntry 34   }

                  sensorProbeHumidityIndexCount OBJECT-TYPE
                     SYNTAX  INTEGER
                     ACCESS   read-only
                     STATUS  mandatory
                     DESCRIPTION
                     "Number of Humidity sensor online"
                     ::=  {  sensorProbeHumidityEntry 35   }

                  sensorProbeHumidityOffset OBJECT-TYPE
                     SYNTAX  INTEGER
                     ACCESS  read-write
                     STATUS  mandatory
                     DESCRIPTION
                     "Humidity Offset reading"
                     ::=  {  sensorProbeHumidityEntry 36   }

                  sensorProbeHumiditySirenCycleTime OBJECT-TYPE
                     SYNTAX INTEGER (1..255)
                     ACCESS read-write
                     STATUS mandatory
                     DESCRIPTION
                     "Siren toggle period in seconds for Cycle action."
                     ::=  {  sensorProbeHumidityEntry 37   }

                  sensorProbeHumiditySirenOnPort OBJECT-TYPE
                     SYNTAX INTEGER (0..255)
                     ACCESS read-write
                     STATUS mandatory
                     DESCRIPTION
                     "The sensor port that the siren will listen to. If this is set to 255, then the siren will not listen to any sensor ports"
                     ::=  {  sensorProbeHumidityEntry 38   }

                  sensorProbeHumiditySirenActiveStatus OBJECT-TYPE
                     SYNTAX INTEGER {
                        highWarning(3),
                        highCritical(4),
                        lowWarning(5),
                        lowCritical(6),                        
                        anyError(7)
                     }
                     ACCESS read-write
                     STATUS mandatory
                     DESCRIPTION
                     "Sensor status that will activate the siren"
                     ::=  {  sensorProbeHumidityEntry 39   }

                  sensorProbeHumiditySirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::=  {  sensorProbeHumidityEntry 40   }

                  sensorProbeHumidityAcknowledgement OBJECT-TYPE
                     SYNTAX INTEGER {
                        ack(1)
                     }
                     ACCESS read-write
                     STATUS mandatory
                     DESCRIPTION
                     "Acknowledged sensor error and stop notification"
                     ::= {  sensorProbeHumidityEntry 41 }

                  sensorProbeHumiditySirenDelayAlarm OBJECT-TYPE
                     SYNTAX INTEGER (1..255)
                     ACCESS read-write
                     STATUS mandatory
                     DESCRIPTION
                     "Siren delay in seconds before start Alarm."
                     ::=  {  sensorProbeHumidityEntry 42 }

                  sensorProbeHumidityURL OBJECT-TYPE
                     SYNTAX  DisplayString
                     ACCESS  read-write
                     STATUS  mandatory
                     DESCRIPTION
                     "Sensor URL link."
                     ::=  {  sensorProbeHumidityEntry 43 }

                  sensorProbeHumidityOpenURL OBJECT-TYPE
                     SYNTAX INTEGER {
                        cur-window(0),
                        new-window(2)
                     }
                     ACCESS  read-write
                     STATUS  mandatory
                     DESCRIPTION
                     "Open URL in this browser or open in a new window."
                     ::=  {  sensorProbeHumidityEntry 44 }

                  sensorProbeHumidityDatacollectType OBJECT-TYPE
                     SYNTAX INTEGER {
                        average(1),
                        highest(2),
                        lowest(3)
                     }
                     ACCESS  read-write
                     STATUS  mandatory
                     DESCRIPTION
                     "Type of datacollect to collect."
                     ::=  {  sensorProbeHumidityEntry 45 }

                  sensorProbeHumidityContTimeHighCritical OBJECT-TYPE
                     SYNTAX INTEGER (0..65535)
                     ACCESS read-write
                     STATUS mandatory
                     DESCRIPTION
                     "Continuous time for this sensor to be in High Critical before accepting new Status."
                     ::= {  sensorProbeHumidityEntry 46 }

                  sensorProbeHumidityContTimeHighWarning OBJECT-TYPE
                     SYNTAX INTEGER (0..65535)
                     ACCESS read-write
                     STATUS mandatory
                     DESCRIPTION
                     "Continuous time for this sensor to be in High Warning before accepting new Status."
                     ::= {  sensorProbeHumidityEntry 47 }

                  sensorProbeHumidityContTimeNormal OBJECT-TYPE
                     SYNTAX INTEGER (0..65535)
                     ACCESS read-write
                     STATUS mandatory
                     DESCRIPTION
                     "Continuous time for this sensor to be in Normal before accepting new Status."
                     ::= {  sensorProbeHumidityEntry 48 }

                  sensorProbeHumidityContTimeLowWarning OBJECT-TYPE
                     SYNTAX INTEGER (0..65535)
                     ACCESS read-write
                     STATUS mandatory
                     DESCRIPTION
                     "Continuous time for this sensor to be in Low Warning before accepting new Status."
                     ::= {  sensorProbeHumidityEntry 49 }

                  sensorProbeHumidityContTimeLowCritical OBJECT-TYPE
                     SYNTAX INTEGER (0..65535)
                     ACCESS read-write
                     STATUS mandatory
                     DESCRIPTION
                     "Continuous time for this sensor to be in Low Critical before accepting new Status."
                     ::= {  sensorProbeHumidityEntry 50 }

                  sensorProbeHumidityContTimeSensorError OBJECT-TYPE
                     SYNTAX INTEGER (0..65535)
                     ACCESS read-write
                     STATUS mandatory
                     DESCRIPTION
                     "Continuous time for this sensor to be in Sensor Error before accepting new Status."
                     ::= {  sensorProbeHumidityEntry 51 }

                  sensorProbeHumidityCalendar OBJECT-TYPE
                     SYNTAX INTEGER {
                        disable(0),
                        enable(1)
                     }
                     ACCESS read-write
                     STATUS mandatory
                     DESCRIPTION
                     "Enable or disable the calendar filtering working hours of sensor."
                     ::= {  sensorProbeHumidityEntry 52 }

                  sensorProbeHumiditySendNormalMail OBJECT-TYPE
                     SYNTAX  INTEGER {
                        disable(0),
                        enable(1)
                     }
                     ACCESS  read-write
                     STATUS  mandatory
                     DESCRIPTION
                     "Enable sending email when sensor goes to normal"
                     ::=  {  sensorProbeHumidityEntry 53 }

                  sensorProbeHumiditySendTrap OBJECT-TYPE
                     SYNTAX  INTEGER {
                        disable(0),
                        enable(1)
                     }
                     ACCESS  read-write
                     STATUS  mandatory
                     DESCRIPTION
                     "Enable sending trap when sensor change status"
                     ::=  {  sensorProbeHumidityEntry 54 }

                  sensorProbeHumiditySendMail OBJECT-TYPE
                     SYNTAX  INTEGER {
                        disable(0),
                        enable(1)
                     }
                     ACCESS  read-write
                     STATUS  mandatory
                     DESCRIPTION
                     "Enable sending email when sensor change status"
                     ::=  {  sensorProbeHumidityEntry 55 }

                  sensorProbeIDCVVoltateRatio OBJECT-TYPE
                     SYNTAX INTEGER (0..65535)
                     ACCESS  read-write
                     STATUS  mandatory
                     DESCRIPTION
                     "iDCV calibrate voltate ratio"
                     ::=  {  sensorProbeHumidityEntry 56 }

                  sensorProbeIDCVErrorFlag OBJECT-TYPE
                     SYNTAX INTEGER (0..65535)
                     ACCESS  read-only
                     STATUS  mandatory
                     DESCRIPTION
                     "iDCV error flag"
                     ::=  {  sensorProbeHumidityEntry 57 }

                  sensorProbeIDCVCalibrate OBJECT-TYPE
                     SYNTAX INTEGER (0..65535)
                     ACCESS  read-write
                     STATUS  mandatory
                     DESCRIPTION
                     "iDCV calibrate"
                     ::=  {  sensorProbeHumidityEntry 58 }

                  sensorProbeAirFlowProtocolType OBJECT-TYPE
                     SYNTAX  INTEGER {
                        analogType(0),
                        i2cType(1)
                     }
                     ACCESS  read-only
                     STATUS  mandatory
                     DESCRIPTION
                     "Air flow protocol type"
                     ::=  {  sensorProbeHumidityEntry 59 }

                  sensorProbeAirFlowSensitivity OBJECT-TYPE
                     SYNTAX INTEGER (0..65535)
                     ACCESS  read-write
                     STATUS  mandatory
                     DESCRIPTION
                     "Air flow (AFS00) sensitivity"
                     ::=  {  sensorProbeHumidityEntry 60 }

                  sensorProbeAirFlowNormalState OBJECT-TYPE
                     SYNTAX  INTEGER {
                        presense(0),
                        absense(1)
                     }
                     ACCESS  read-write
                     STATUS  mandatory
                     DESCRIPTION
                     "Air flow (AFS00) normal state"
                     ::=  {  sensorProbeHumidityEntry 61 }

                  sensorProbeAirFlowCalibrate OBJECT-TYPE
                     SYNTAX INTEGER (0..65535)
                     ACCESS  read-write
                     STATUS  mandatory
                     DESCRIPTION
                     "Air flow (AFS00) normal state"
                     ::=  {  sensorProbeHumidityEntry 62 }


               sensorProbeSwitchTable OBJECT-TYPE
                  SYNTAX  SEQUENCE OF SensorProbeSwitchEntry
                  ACCESS  not-accessible
                  STATUS  mandatory
                  DESCRIPTION
                  "This table contains the data for every Switch Sensor in the SensorArray. Each row in the table contains data for a different Switch Sensor."
                  ::=  {  sensorProbeEntry 18   }

               sensorProbeSwitchEntry OBJECT-TYPE
                  SYNTAX  SensorProbeSwitchEntry
                  ACCESS  not-accessible
                  STATUS  mandatory
                  DESCRIPTION
                  "This is an entry in the sensorProbeSwitchEntry Table"
                  INDEX         { sensorProbeSwitchIndex }
                  ::=  { sensorProbeSwitchTable 1 }

                  SensorProbeSwitchEntry ::= SEQUENCE {
                     sensorProbeSwitchDescription
                        DisplayString,
                     sensorProbeSwitchLocation
                        DisplayString,
                     sensorProbeSwitchStatus
                        INTEGER,
                     sensorProbeSwitchOnline
                        INTEGER,
                     sensorProbeSwitchGoOnline
                        INTEGER,
                     sensorProbeSwitchDirection
                        INTEGER,
                     sensorProbeSwitchNormalState
                        INTEGER,
                     sensorProbeSwitchOutputLevel
                        INTEGER,
                     sensorProbeSensorType
                        INTEGER,
                     sensorProbeSwitchEmailTrapLimit
                        INTEGER,
                     sensorProbeSwitchEmailTrapSchedule
                        DisplayString,
                     sensorProbeSwitchEmailTrapInterval
                        INTEGER,
                     sensorProbeSwitchSendNormalTrap
                        INTEGER,
                     sensorProbeSwitchDelayError
                        INTEGER,
                     sensorProbeSwitchDelayNormal
                        INTEGER,
                     sensorProbeSwitchIndex
                        INTEGER,
                     sensorProbeSwitchRelayCycleTime
                        INTEGER,
                     sensorProbeSwitchRelayOnPort
                        INTEGER,
                     sensorProbeSwitchRelayActiveStatus
                        INTEGER,
                     sensorProbeSwitchRelayAction
                        INTEGER,
                     sensorProbeSwitchEmailInterval
                        INTEGER,
                     sensorProbeSwitchRelayOutputVoltStatus
                        INTEGER,
                     sensorProbeSwitchManualRelayCycleTime
                        INTEGER,
                     sensorProbeSwitchManualRelayAction
                        INTEGER,
                     sensorProbeSwitchRelayDescOn
                        DisplayString,
                     sensorProbeSwitchRelayDescOff
                        DisplayString,
                     sensorProbeSwitchIndexCount
                        INTEGER,
                     sensorProbeSwitchSirenCycleTime
                        INTEGER,
                     sensorProbeSwitchSirenOnPort
                        INTEGER,
                     sensorProbeSwitchSirenActiveStatus
                        INTEGER,
                     sensorProbeSwitchSirenAction
                        INTEGER,
                     sensorProbeSwitchAcknowledgement
                        INTEGER,
                     sensorProbeSwitchSirenDelayAlarm
                        INTEGER,
                     sensorProbeSwitchURL
                        DisplayString,
                     sensorProbeSwitchOpenURL
                        INTEGER,
                     sensorProbeSwitchContTimeHighCritical
                        INTEGER,
                     sensorProbeSwitchContTimeNormal
                        INTEGER,
                     sensorProbeSwitchCalendar
                        INTEGER,
                     sensorProbeSwitchRelayControlMode
                        INTEGER,
                     sensorProbeSwitchSirenControlMode
                        INTEGER,
                     sensorProbeSwitchSendNormalMail
                        INTEGER,
                     sensorProbeSwitchSendTrap
                        INTEGER,
                     sensorProbeSwitchSendMail
                        INTEGER,
                     sensorProbeSwitchWaterRopeLeakLocation
                        INTEGER,
                     sensorProbeSwitchWaterRopeLength
                        INTEGER,
                     sensorProbeSwitchWaterRopeUnit
                        INTEGER,
                     sensorProbeSwitchWaterRopeImpedance
                        INTEGER,
                     sensorProbeSwitchWaterRopeRaw
                        INTEGER,
                     sensorProbeSwitchWaterRopeType
                        INTEGER
                  }
                  sensorProbeSwitchDescription OBJECT-TYPE
                     SYNTAX  DisplayString
                     ACCESS  read-write
                     STATUS  mandatory
                     DESCRIPTION
                     "A Description of this sensor Switch"
                     ::=  {  sensorProbeSwitchEntry 1   }

                    sensorProbeSwitchLocation OBJECT-TYPE
                       SYNTAX  DisplayString
                       ACCESS  read-write
                       STATUS  mandatory
                       DESCRIPTION
                       "The physical location of this sensor Switch"
                       ::=  {  sensorProbeSwitchEntry 2   }

                  sensorProbeSwitchStatus OBJECT-TYPE
                     SYNTAX  INTEGER {
                        noStatus(1),
                        normal(2),
                        highCritical(4),
                        lowCritical(6),
                        sensorError(7),
                        relayOn(8),
                        relayOff(9)
                     }
                     ACCESS  read-only
                     STATUS  mandatory
                     DESCRIPTION
                     "The current status of this Sensor, only input switches have a status"
                     ::=  {  sensorProbeSwitchEntry 3  }

                  sensorProbeSwitchOnline OBJECT-TYPE
                     SYNTAX  INTEGER {
                        online(1),
                        offline(2)
                     }
                     ACCESS  read-only
                     STATUS  mandatory
                     DESCRIPTION
                     "If this Sensor is currently online"
                        ::=  {  sensorProbeSwitchEntry 4  }

                  sensorProbeSwitchGoOnline OBJECT-TYPE
                     SYNTAX  INTEGER {
                        goOnline(1),
                        goOffline(2)
                     }
                     ACCESS  read-write
                     STATUS  mandatory
                     DESCRIPTION
                     "To put online enter a 1, to take offline enter a 2"
                     ::=  {  sensorProbeSwitchEntry 5  }

                  sensorProbeSwitchDirection OBJECT-TYPE
                     SYNTAX  INTEGER {
                        input(0),
                        output(1)
                     }
                     ACCESS  read-write
                     STATUS  mandatory
                     DESCRIPTION
                     "To set a switch to input enter 0. To set a switch to output enter 1"
                     ::=  {  sensorProbeSwitchEntry 6  }

                  sensorProbeSwitchNormalState OBJECT-TYPE
                     SYNTAX  INTEGER {
                        closed(0),
                        open(1)
                     }
                     ACCESS  read-write
                     STATUS  mandatory
                     DESCRIPTION
                     "The normal state of an input switch. If an input switch is in this state it is normal, else it is critical. An open switch senses +5 volts. A closed switch senses 0 volts."
                     ::=  {  sensorProbeSwitchEntry 7  }
                     
                  sensorProbeSwitchOutputLevel OBJECT-TYPE
                     SYNTAX  INTEGER {
                        low(0),
                        high(1)
                     }
                     ACCESS  read-write
                     STATUS  mandatory
                     DESCRIPTION
                     "An output swith can be set to this level"
                     ::=  {  sensorProbeSwitchEntry 8  }
                     
                  sensorProbeSensorType OBJECT-TYPE
                     SYNTAX  INTEGER {
                        temperature(1),
                        fourTo20mA(2),
                        humidity(3),
                        water(4),
                        atod(5),
                        security(6),
                        airflow(8),
                        siren(9),
                        dryContact(10),
                        voltage(12),
                        relay(13),
                        motion(14)
                     }

                     ACCESS  read-write
                     STATUS  mandatory
                     DESCRIPTION
                     "Enter the type of this Sensor"
                     ::=  {  sensorProbeSwitchEntry 9  }

                  sensorProbeSwitchEmailTrapLimit OBJECT-TYPE
                     SYNTAX  INTEGER {
                        disable(0),
                        enable(1)
                     }
                     ACCESS  read-write
                     STATUS  mandatory
                     DESCRIPTION
                     "Enable email/trap limit feature"
                     ::=  {  sensorProbeSwitchEntry 11   }

                  sensorProbeSwitchEmailTrapSchedule OBJECT-TYPE
                     SYNTAX  DisplayString
                     ACCESS  read-write
                     STATUS  mandatory
                     DESCRIPTION
                     "SP Only: Email/trap limit schedule for this sensor"
                     ::=  {  sensorProbeSwitchEntry 12   }

                  sensorProbeSwitchEmailTrapInterval OBJECT-TYPE
                     SYNTAX  INTEGER (0..60)
                     ACCESS  read-write
                     STATUS  mandatory
                     DESCRIPTION
                     "Minimum time between each [email/trap:SP, only trap:CP8] (can be from 0 to 60 minutes)"
                     ::=  {  sensorProbeSwitchEntry 13   }

                  sensorProbeSwitchSendNormalTrap OBJECT-TYPE
                     SYNTAX  INTEGER {
                        disable(0),
                        enable(1)
                     }
                     ACCESS  read-write
                     STATUS  mandatory
                     DESCRIPTION
                     "Enable sending email/trap when sensor goes to normal"
                     ::=  {  sensorProbeSwitchEntry 14   }

                  sensorProbeSwitchDelayError OBJECT-TYPE
                     SYNTAX  INTEGER (0..65534)
                     ACCESS  read-write
                     STATUS  mandatory
                     DESCRIPTION
                     "Time in seconds after the sensor has been in error status before report as an error"
                     ::=  {  sensorProbeSwitchEntry 15   }

                  sensorProbeSwitchDelayNormal OBJECT-TYPE
                     SYNTAX  INTEGER (0..65534)
                     ACCESS  read-write
                     STATUS  mandatory
                     DESCRIPTION
                     "Time in seconds after the sensor change from error to normal before report as normal"
                     ::=  {  sensorProbeSwitchEntry 16   }

                  sensorProbeSwitchIndex OBJECT-TYPE
                     SYNTAX  INTEGER (0..67)
                     ACCESS  read-only
                     STATUS  mandatory
                     DESCRIPTION
                     "The index into the Switch sensor table"
                     ::=  {  sensorProbeSwitchEntry 17   }

                  sensorProbeSwitchRelayCycleTime OBJECT-TYPE
                     SYNTAX INTEGER (1..255)
                     ACCESS read-write
                     STATUS mandatory
                     DESCRIPTION
                     "Relay toggle period in seconds for Cycle action."
                     ::=  {  sensorProbeSwitchEntry 18   }

                  sensorProbeSwitchRelayOnPort OBJECT-TYPE
                     SYNTAX INTEGER (0..255)
                     ACCESS read-write
                     STATUS mandatory
                     DESCRIPTION
                     "The sensor port that the relay will listen to. If this is set to 255, then the relay will not listen to any sensor ports"
                     ::=  {  sensorProbeSwitchEntry 19   }

                  sensorProbeSwitchRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::=  {  sensorProbeSwitchEntry 20   }

                  sensorProbeSwitchRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::=  {  sensorProbeSwitchEntry 21   }

                  sensorProbeSwitchEmailInterval OBJECT-TYPE
                     SYNTAX  INTEGER (0..60)
                     ACCESS  read-write
                     STATUS  mandatory
                     DESCRIPTION
                     "CP8 Only: Minimum time between each email (can be from 0 to 60 minutes)"
                     ::=  {  sensorProbeSwitchEntry 22   }

                  sensorProbeSwitchRelayOutputVoltStatus OBJECT-TYPE
                     SYNTAX  INTEGER {
                        sensorError(7),
                        noVoltagePresent(10),
                        voltagePresent(11)
                     }
                     ACCESS  read-only
                     STATUS  mandatory
                     DESCRIPTION
                     "SP Only: The current voltage status of the relay"
                        ::=  {  sensorProbeSwitchEntry 23  }

                  sensorProbeSwitchManualRelayCycleTime OBJECT-TYPE
                     SYNTAX INTEGER (1..255)
                     ACCESS read-write
                     STATUS mandatory
                     DESCRIPTION
                     "Relay toggle period in seconds for Manual Cycle action."
                     ::= { sensorProbeSwitchEntry 24 }

                  sensorProbeSwitchManualRelayAction OBJECT-TYPE
                     SYNTAX INTEGER {
                        allow-sensor-control(1),
                        turn-on(3),
                        turn-off(4),
                        cycle-Off-On-Off(7),                        
                        cycle-On-Off-On(8)
                     }
                     ACCESS read-write
                     STATUS mandatory
                     DESCRIPTION
                     "Control the relay manualy"
                     ::= { sensorProbeSwitchEntry 25 }

                  sensorProbeSwitchRelayDescOn OBJECT-TYPE
                     SYNTAX  DisplayString
                     ACCESS  read-write
                     STATUS  mandatory
                     DESCRIPTION
                     "Description of relay On"
                     ::=  {  sensorProbeSwitchEntry 26   }

                  sensorProbeSwitchRelayDescOff OBJECT-TYPE
                     SYNTAX  DisplayString
                     ACCESS  read-write
                     STATUS  mandatory
                     DESCRIPTION
                     "Description of relay Off"
                     ::=  {  sensorProbeSwitchEntry 27   }

                  sensorProbeSwitchIndexCount OBJECT-TYPE
                     SYNTAX  INTEGER
                     ACCESS  read-only
                     STATUS  mandatory
                     DESCRIPTION
                     "Number of Switch sensor online"
                     ::=  {  sensorProbeSwitchEntry 28   }

                  sensorProbeSwitchSirenCycleTime OBJECT-TYPE
                     SYNTAX INTEGER (1..255)
                     ACCESS read-write
                     STATUS mandatory
                     DESCRIPTION
                     "Siren toggle period in seconds for Cycle action."
                     ::=  {  sensorProbeSwitchEntry 29   }

                  sensorProbeSwitchSirenOnPort OBJECT-TYPE
                     SYNTAX INTEGER (0..255)
                     ACCESS read-write
                     STATUS mandatory
                     DESCRIPTION
                     "The sensor port that the siren will listen to. If this is set to 255, then the siren will not listen to any sensor ports"
                     ::=  {  sensorProbeSwitchEntry 30   }

                  sensorProbeSwitchSirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::=  {  sensorProbeSwitchEntry 31   }

                  sensorProbeSwitchSirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::=  {  sensorProbeSwitchEntry 32   }

                  sensorProbeSwitchAcknowledgement OBJECT-TYPE
                     SYNTAX INTEGER {
                        ack(1)
                     }
                     ACCESS read-write
                     STATUS mandatory
                     DESCRIPTION
                     "Acknowledged sensor error and stop notification"
                     ::= {  sensorProbeSwitchEntry 33 }

                  sensorProbeSwitchSirenDelayAlarm OBJECT-TYPE
                     SYNTAX INTEGER (1..255)
                     ACCESS read-write
                     STATUS mandatory
                     DESCRIPTION
                     "Siren delay in seconds before start Alarm."
                     ::=  {  sensorProbeSwitchEntry 34   }

                  sensorProbeSwitchURL OBJECT-TYPE
                     SYNTAX  DisplayString
                     ACCESS  read-write
                     STATUS  mandatory
                     DESCRIPTION
                     "Sensor URL link."
                     ::=  {  sensorProbeSwitchEntry 35 }

                  sensorProbeSwitchOpenURL OBJECT-TYPE
                     SYNTAX  INTEGER {
                        cur-window(0),
                        new-window(2)
                     }
                     ACCESS  read-write
                     STATUS  mandatory
                     DESCRIPTION
                     "Open URL in this browser or open in a new window."
                     ::=  {  sensorProbeSwitchEntry 36 }

                  sensorProbeSwitchContTimeHighCritical OBJECT-TYPE
                     SYNTAX INTEGER (0..65535)
                     ACCESS read-write
                     STATUS mandatory
                     DESCRIPTION
                     "Continuous time for this sensor to be in High Critical before accepting new Status."
                     ::= {  sensorProbeSwitchEntry 37 }

                  sensorProbeSwitchContTimeNormal OBJECT-TYPE
                     SYNTAX INTEGER (0..65535)
                     ACCESS read-write
                     STATUS mandatory
                     DESCRIPTION
                     "Continuous time for this sensor to be in Normal before accepting new Status."
                     ::= {  sensorProbeSwitchEntry 39 }

                  sensorProbeSwitchCalendar OBJECT-TYPE
                     SYNTAX INTEGER {
                        disable(0),
                        enable(1)
                     }
                     ACCESS read-write
                     STATUS mandatory
                     DESCRIPTION
                     "Enable or disable the calendar filtering working hours of sensor."
                     ::= {  sensorProbeSwitchEntry 43 }

                  sensorProbeSwitchRelayControlMode OBJECT-TYPE
                     SYNTAX  INTEGER {
                        manual-control(0),
                        notification-control(1),
                        time-control(2),
                        thermostat-control(3)
                     }
                     ACCESS  read-write
                     STATUS  mandatory
                     DESCRIPTION
                     "Relay Control Mode used for selecting the mode to control a relay."
                     ::=  {  sensorProbeSwitchEntry 44  }

                  sensorProbeSwitchSirenControlMode OBJECT-TYPE
                     SYNTAX  INTEGER {
                        manual-control(0),
                        notification-control(1),
                        time-control(2)
                     }
                     ACCESS  read-write
                     STATUS  mandatory
                     DESCRIPTION
                     "Siren Control Mode used for selecting the mode to control a siren."
                     ::=  {  sensorProbeSwitchEntry 45  }

                  sensorProbeSwitchSendNormalMail OBJECT-TYPE
                     SYNTAX  INTEGER {
                        disable(0),
                        enable(1)
                     }
                     ACCESS  read-write
                     STATUS  mandatory
                     DESCRIPTION
                     "Enable sending email when sensor goes to normal"
                     ::=  {  sensorProbeSwitchEntry 46 }

                  sensorProbeSwitchSendTrap OBJECT-TYPE
                     SYNTAX  INTEGER {
                        disable(0),
                        enable(1)
                     }
                     ACCESS  read-write
                     STATUS  mandatory
                     DESCRIPTION
                     "Enable sending trap when sensor change status"
                     ::=  {  sensorProbeSwitchEntry 47 }

                  sensorProbeSwitchSendMail OBJECT-TYPE
                     SYNTAX  INTEGER {
                        disable(0),
                        enable(1)
                     }
                     ACCESS  read-write
                     STATUS  mandatory
                     DESCRIPTION
                     "Enable sending email when sensor change status"
                     ::=  {  sensorProbeSwitchEntry 48 }

                  sensorProbeSwitchWaterRopeLeakLocation OBJECT-TYPE
                     SYNTAX INTEGER
                     ACCESS read-only
                     STATUS mandatory
                     DESCRIPTION
                     "Location of leakage of water rope sensor."
                     ::= {  sensorProbeSwitchEntry 49 }

                  sensorProbeSwitchWaterRopeLength OBJECT-TYPE
                     SYNTAX INTEGER
                     ACCESS read-only
                     STATUS mandatory
                     DESCRIPTION
                     "Length of water rope sensor."
                     ::= {  sensorProbeSwitchEntry 50 }

                  sensorProbeSwitchWaterRopeUnit OBJECT-TYPE
                     SYNTAX  INTEGER {
                        meters(0),
                        feet(1)
                     }
                     ACCESS  read-write
                     STATUS  mandatory
                     DESCRIPTION
                     "Display unit of water rope sensor."
                     ::=  {  sensorProbeSwitchEntry 51   }

                  sensorProbeSwitchWaterRopeImpedance OBJECT-TYPE
                     SYNTAX INTEGER (0..65535)
                     ACCESS read-write
                     STATUS mandatory
                     DESCRIPTION
                     "Sensing wire impedance per meter value times 100"
                     ::= {  sensorProbeSwitchEntry 52 }

                  sensorProbeSwitchWaterRopeRaw OBJECT-TYPE
                     SYNTAX INTEGER
                     ACCESS read-only
                     STATUS mandatory
                     DESCRIPTION
                     "Raw value of location or length in ohms"
                     ::= {  sensorProbeSwitchEntry 53 }

                  sensorProbeSwitchWaterRopeType OBJECT-TYPE
                     SYNTAX  INTEGER {
                        custom(0),
                        water(1),
                        fuel(2)
                     }
                     ACCESS  read-write
                     STATUS  mandatory
                     DESCRIPTION
                     "Water rope sensing cable type"
                     ::=  {  sensorProbeSwitchEntry 55   }

               sensorProbeOtherSensor OBJECT IDENTIFIER ::= { sensorProbeEntry 19  }

                  sensorProbeIRMSSensor OBJECT IDENTIFIER ::= { sensorProbeOtherSensor 26  }

                     sensorProbeIRMSSensorNumber OBJECT-TYPE
                        SYNTAX INTEGER
                        ACCESS read-only
                        STATUS mandatory
                        DESCRIPTION
                        "The total number of RMS current Sensor port."
                        ::= {  sensorProbeIRMSSensor 1 }

                     sensorProbeIRMSSensorTable OBJECT-TYPE
                        SYNTAX  SEQUENCE OF SensorProbeIRMSSensorEntry
                        ACCESS  not-accessible
                        STATUS  mandatory
                        DESCRIPTION
                        "This table contains the data for every RMS current Sensor in the SensorArray. Each row in the table contains data for a different RMS current Sensor."
                        ::=  {  sensorProbeIRMSSensor 2   }

                        sensorProbeIRMSSensorEntry OBJECT-TYPE
                           SYNTAX  SensorProbeIRMSSensorEntry
                           ACCESS  not-accessible
                           STATUS  mandatory
                           DESCRIPTION
                           "This is an entry in the sensorProbeIRMSSensorEntry Table"
                           INDEX         { sensorProbeIRMSSensorIndex }
                           ::=  { sensorProbeIRMSSensorTable 1 }

                        SensorProbeIRMSSensorEntry ::= SEQUENCE {
                           sensorProbeIRMSSensorIndex
                              INTEGER,
                           sensorProbeIRMSDescription
                              DisplayString,
                           sensorProbeIRMSPercent
                              INTEGER,
                           sensorProbeIRMSStatus
                              INTEGER,
                           sensorProbeIRMSOnline
                              INTEGER,
                           sensorProbeIRMSGoOnline
                              INTEGER,
                           sensorProbeIRMSHighWarning
                              INTEGER,
                           sensorProbeIRMSHighCritical
                              INTEGER,
                           sensorProbeIRMSLowWarning
                              INTEGER,
                           sensorProbeIRMSLowCritical
                              INTEGER,
                           sensorProbeIRMSRearm
                              INTEGER,
                           sensorProbeIRMSRaw
                              INTEGER,
                           sensorProbeIRMSEmailTrapLimit
                              INTEGER,
                           sensorProbeIRMSDelayError
                              INTEGER,
                           sensorProbeIRMSDelayNormal
                              INTEGER,
                           sensorProbeIRMSRelayCycleTime
                              INTEGER,
                           sensorProbeIRMSRelayOnPort
                              INTEGER,
                           sensorProbeIRMSRelayActiveStatus
                              INTEGER,
                           sensorProbeIRMSRelayAction
                              INTEGER,
                           sensorProbeIRMSSirenCycleTime
                              INTEGER,
                           sensorProbeIRMSSirenOnPort
                              INTEGER,
                           sensorProbeIRMSSirenActiveStatus
                              INTEGER,
                           sensorProbeIRMSSirenAction
                              INTEGER,
                           sensorProbeIRMSAcknowledgement
                              INTEGER,
                           sensorProbeIRMSSirenDelayAlarm
                              INTEGER,
                           sensorProbeIRMSURL
                              DisplayString,
                           sensorProbeIRMSOpenURL
                              INTEGER,
                           sensorProbeIRMSDatacollectType
                              INTEGER,
                           sensorProbeIRMSContTimeHighCritical
                              INTEGER,
                           sensorProbeIRMSContTimeHighWarning
                              INTEGER,
                           sensorProbeIRMSContTimeNormal
                              INTEGER,
                           sensorProbeIRMSContTimeLowWarning
                              INTEGER,
                           sensorProbeIRMSContTimeLowCritical
                              INTEGER,
                           sensorProbeIRMSContTimeSensorError
                              INTEGER,
                           sensorProbeIRMSCalendar
                              INTEGER
                        }

                          sensorProbeIRMSSensorIndex OBJECT-TYPE
                              SYNTAX  INTEGER (0..7)
                              ACCESS  read-only
                              STATUS  mandatory
                              DESCRIPTION
                              "A unique value for each IRMS sensor port."
                              ::=  {  sensorProbeIRMSSensorEntry 1   }

                          sensorProbeIRMSDescription OBJECT-TYPE
                              SYNTAX  DisplayString
                              ACCESS  read-write
                              STATUS  mandatory
                              DESCRIPTION
                              "A Description of this sensor IRMS"
                              ::=  {  sensorProbeIRMSSensorEntry 2   }

                          sensorProbeIRMSPercent OBJECT-TYPE
                              SYNTAX  INTEGER (-32768..32767)
                              ACCESS  read-only
                              STATUS  mandatory
                              DESCRIPTION
                              "The relative IRMS percentage measured by this sensor"
                              ::=  {  sensorProbeIRMSSensorEntry 3   }

                           sensorProbeIRMSStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeIRMSSensorEntry 4   }

                           sensorProbeIRMSOnline OBJECT-TYPE
                              SYNTAX  INTEGER {
                                 online(1),
                                 offline(2)
                              }
                              ACCESS  read-only
                              STATUS  mandatory
                              DESCRIPTION
                              "If this Sensor is currently online"
                                 ::=  {  sensorProbeIRMSSensorEntry 5   }

                           sensorProbeIRMSGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeIRMSSensorEntry 6   }

                           sensorProbeIRMSHighWarning OBJECT-TYPE
                              SYNTAX  INTEGER
                              ACCESS  read-write
                              STATUS  mandatory
                              DESCRIPTION
                              "How high the relative IRMS this sensor measures before it sends a warning"
                              ::=  {  sensorProbeIRMSSensorEntry 7   }

                           sensorProbeIRMSHighCritical OBJECT-TYPE
                              SYNTAX  INTEGER
                              ACCESS  read-write
                              STATUS  mandatory
                              DESCRIPTION
                              "How high the relative IRMS this sensor measures before it becomes critical"
                              ::=  {  sensorProbeIRMSSensorEntry 8   }

                           sensorProbeIRMSLowWarning OBJECT-TYPE
                              SYNTAX  INTEGER
                              ACCESS  read-write
                              STATUS  mandatory
                              DESCRIPTION
                              "How low the relative IRMS this sensor measures before it sends a warning"
                              ::=  {  sensorProbeIRMSSensorEntry 9   }

                           sensorProbeIRMSLowCritical OBJECT-TYPE
                              SYNTAX  INTEGER
                              ACCESS  read-write
                              STATUS  mandatory
                              DESCRIPTION
                              "How low the relative IRMS this sensor measures before it becomes critical"
                              ::=  {  sensorProbeIRMSSensorEntry 10   }

                           sensorProbeIRMSRearm OBJECT-TYPE
                              SYNTAX  INTEGER
                              ACCESS  read-write
                              STATUS  mandatory
                              DESCRIPTION
                              "The percent relative IRMS to rearm the status. For example if status goes from normal to warning, the IRMS must go down spAnalogueRearm below warning before the status goes to normal"
                              ::=  {  sensorProbeIRMSSensorEntry 11   }

                           sensorProbeIRMSRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeIRMSSensorEntry 13   }

                           sensorProbeIRMSEmailTrapLimit OBJECT-TYPE
                              SYNTAX  INTEGER {
                                 disable(0),
                                 enable(1)
                              }
                              ACCESS  read-write
                              STATUS  mandatory
                              DESCRIPTION
                              "Enable email/trap limit feature"
                              ::=  {  sensorProbeIRMSSensorEntry 17   }

                           sensorProbeIRMSDelayError OBJECT-TYPE
                              SYNTAX  INTEGER (0..65534)
                              ACCESS  read-write
                              STATUS  mandatory
                              DESCRIPTION
                              "Time in seconds after the sensor has been in error status before report as an error"
                              ::=  {  sensorProbeIRMSSensorEntry 21   }

                           sensorProbeIRMSDelayNormal OBJECT-TYPE
                              SYNTAX  INTEGER (0..65534)
                              ACCESS  read-write
                              STATUS  mandatory
                              DESCRIPTION
                              "Time in seconds after the sensor change from error to normal before report as normal"
                              ::=  {  sensorProbeIRMSSensorEntry 22   }

                           sensorProbeIRMSRelayCycleTime OBJECT-TYPE
                              SYNTAX INTEGER (1..255)
                              ACCESS read-write
                              STATUS mandatory
                              DESCRIPTION
                              "Relay toggle period in seconds for Cycle action."
                              ::=  {  sensorProbeIRMSSensorEntry 29   }

                           sensorProbeIRMSRelayOnPort OBJECT-TYPE
                              SYNTAX INTEGER (0..255)
                              ACCESS read-write
                              STATUS mandatory
                              DESCRIPTION
                              "The sensor port that the relay will listen to. If this is set to 255, then the relay will not listen to any sensor ports"
                              ::=  {  sensorProbeIRMSSensorEntry 30   }

                           sensorProbeIRMSRelayActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the relay"
                              ::=  {  sensorProbeIRMSSensorEntry 31   }

                           sensorProbeIRMSRelayAction OBJECT-TYPE
                              SYNTAX INTEGER {
                                 cycle(2),
                                 turn-on(3),
                                 turn-off(4)
                              }
                              ACCESS read-write
                              STATUS mandatory
                              DESCRIPTION
                              "What the relay will do when the listened to port status turns to the specified active status."
                              ::=  {  sensorProbeIRMSSensorEntry 32   }

                           sensorProbeIRMSSirenCycleTime OBJECT-TYPE
                              SYNTAX INTEGER (1..255)
                              ACCESS read-write
                              STATUS mandatory
                              DESCRIPTION
                              "Siren toggle period in seconds for Cycle action."
                              ::=  {  sensorProbeIRMSSensorEntry 37   }

                           sensorProbeIRMSSirenOnPort OBJECT-TYPE
                              SYNTAX INTEGER (0..255)
                              ACCESS read-write
                              STATUS mandatory
                              DESCRIPTION
                              "The sensor port that the siren will listen to. If this is set to 255, then the siren will not listen to any sensor ports"
                              ::=  {  sensorProbeIRMSSensorEntry 38   }

                           sensorProbeIRMSSirenActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the siren"
                              ::=  {  sensorProbeIRMSSensorEntry 39   }

                           sensorProbeIRMSSirenAction OBJECT-TYPE
                              SYNTAX INTEGER {
                                 cycle(2),
                                 turn-on(3),
                                 turn-off(4)
                              }
                              ACCESS read-write
                              STATUS mandatory
                              DESCRIPTION
                              "What the siren will do when the listened to port status turns to the specified active status."
                              ::=  {  sensorProbeIRMSSensorEntry 40   }

                           sensorProbeIRMSAcknowledgement OBJECT-TYPE
                              SYNTAX INTEGER {
                                 ack(1)
                              }
                              ACCESS read-write
                              STATUS mandatory
                              DESCRIPTION
                              "Acknowledged sensor error and stop notification"
                              ::= {  sensorProbeIRMSSensorEntry 41 }

                           sensorProbeIRMSSirenDelayAlarm OBJECT-TYPE
                              SYNTAX INTEGER (1..255)
                              ACCESS read-write
                              STATUS mandatory
                              DESCRIPTION
                              "Siren delay in seconds before start Alarm."
                              ::=  {  sensorProbeIRMSSensorEntry 42   }

                           sensorProbeIRMSURL OBJECT-TYPE
                              SYNTAX DisplayString
                              ACCESS read-write
                              STATUS mandatory
                              DESCRIPTION
                              "Sensor URL link."
                              ::=  {  sensorProbeIRMSSensorEntry 43   }

                           sensorProbeIRMSOpenURL OBJECT-TYPE
                              SYNTAX INTEGER {
                                 cur-window(0),
                                 new-window(2)
                              }
                              ACCESS read-write
                              STATUS mandatory
                              DESCRIPTION
                              "Open URL in this browser or open in a new window."
                              ::=  {  sensorProbeIRMSSensorEntry 44   }

                           sensorProbeIRMSDatacollectType OBJECT-TYPE
                              SYNTAX INTEGER {
                                 average(1),
                                 highest(2),
                                 lowest(3)
                              }
                              ACCESS read-write
                              STATUS mandatory
                              DESCRIPTION
                              "Type of datacollect to collect."
                              ::=  {  sensorProbeIRMSSensorEntry 45   }

                           sensorProbeIRMSContTimeHighCritical OBJECT-TYPE
                              SYNTAX INTEGER (0..65535)
                              ACCESS read-write
                              STATUS mandatory
                              DESCRIPTION
                              "Continuous time for this sensor to be in High Critical before accepting new Status."
                              ::= {  sensorProbeIRMSSensorEntry 46 }

                           sensorProbeIRMSContTimeHighWarning OBJECT-TYPE
                              SYNTAX INTEGER (0..65535)
                              ACCESS read-write
                              STATUS mandatory
                              DESCRIPTION
                              "Continuous time for this sensor to be in High Warning before accepting new Status."
                              ::= {  sensorProbeIRMSSensorEntry 47 }

                           sensorProbeIRMSContTimeNormal OBJECT-TYPE
                              SYNTAX INTEGER (0..65535)
                              ACCESS read-write
                              STATUS mandatory
                              DESCRIPTION
                              "Continuous time for this sensor to be in Normal before accepting new Status."
                              ::= {  sensorProbeIRMSSensorEntry 48 }

                           sensorProbeIRMSContTimeLowWarning OBJECT-TYPE
                              SYNTAX INTEGER (0..65535)
                              ACCESS read-write
                              STATUS mandatory
                              DESCRIPTION
                              "Continuous time for this sensor to be in Low Warning before accepting new Status."
                              ::= {  sensorProbeIRMSSensorEntry 49 }

                           sensorProbeIRMSContTimeLowCritical OBJECT-TYPE
                              SYNTAX INTEGER (0..65535)
                              ACCESS read-write
                              STATUS mandatory
                              DESCRIPTION
                              "Continuous time for this sensor to be in Low Critical before accepting new Status."
                              ::= {  sensorProbeIRMSSensorEntry 50 }

                           sensorProbeIRMSContTimeSensorError OBJECT-TYPE
                              SYNTAX INTEGER (0..65535)
                              ACCESS read-write
                              STATUS mandatory
                              DESCRIPTION
                              "Continuous time for this sensor to be in Sensor Error before accepting new Status."
                              ::= {  sensorProbeIRMSSensorEntry 51 }

                           sensorProbeIRMSCalendar OBJECT-TYPE
                              SYNTAX INTEGER {
                                 disable(0),
                                 enable(1)
                              }
                              ACCESS read-write
                              STATUS mandatory
                              DESCRIPTION
                              "Enable or disable the calendar filtering working hours of sensor."
                              ::= {  sensorProbeIRMSSensorEntry 52 }

                  sensorProbeVRMSSensor OBJECT IDENTIFIER ::= { sensorProbeOtherSensor 27  }

                     sensorProbeVRMSSensorNumber OBJECT-TYPE
                        SYNTAX INTEGER
                        ACCESS read-only
                        STATUS mandatory
                        DESCRIPTION
                        "The total number of RMS voltage Sensor port."
                        ::= {  sensorProbeVRMSSensor 1 }

                     sensorProbeVRMSSensorTable OBJECT-TYPE
                        SYNTAX  SEQUENCE OF SensorProbeVRMSSensorEntry
                        ACCESS  not-accessible
                        STATUS  mandatory
                        DESCRIPTION
                        "This table contains the data for every RMS voltage Sensor in the SensorArray. Each row in the table contains data for a different RMS voltage Sensor."
                        ::=  {  sensorProbeVRMSSensor 2   }

                        sensorProbeVRMSSensorEntry OBJECT-TYPE
                           SYNTAX  SensorProbeVRMSSensorEntry
                           ACCESS  not-accessible
                           STATUS  mandatory
                           DESCRIPTION
                           "This is an entry in the sensorProbeVRMSSensorEntry Table"
                           INDEX         { sensorProbeVRMSSensorIndex }
                           ::=  { sensorProbeVRMSSensorTable 1 }

                        SensorProbeVRMSSensorEntry ::= SEQUENCE {
                           sensorProbeVRMSSensorIndex
                              INTEGER,
                           sensorProbeVRMSDescription
                              DisplayString,
                           sensorProbeVRMSPercent
                              INTEGER,
                           sensorProbeVRMSStatus
                              INTEGER,
                           sensorProbeVRMSOnline
                              INTEGER,
                           sensorProbeVRMSGoOnline
                              INTEGER,
                           sensorProbeVRMSHighWarning
                              INTEGER,
                           sensorProbeVRMSHighCritical
                              INTEGER,
                           sensorProbeVRMSLowWarning
                              INTEGER,
                           sensorProbeVRMSLowCritical
                              INTEGER,
                           sensorProbeVRMSRearm
                              INTEGER,
                           sensorProbeVRMSRaw
                              INTEGER,
                           sensorProbeVRMSEmailTrapLimit
                              INTEGER,
                           sensorProbeVRMSDelayError
                              INTEGER,
                           sensorProbeVRMSDelayNormal
                              INTEGER,
                           sensorProbeVRMSRelayCycleTime
                              INTEGER,
                           sensorProbeVRMSRelayOnPort
                              INTEGER,
                           sensorProbeVRMSRelayActiveStatus
                              INTEGER,
                           sensorProbeVRMSRelayAction
                              INTEGER,
                           sensorProbeVRMSSirenCycleTime
                              INTEGER,
                           sensorProbeVRMSSirenOnPort
                              INTEGER,
                           sensorProbeVRMSSirenActiveStatus
                              INTEGER,
                           sensorProbeVRMSSirenAction
                              INTEGER,
                           sensorProbeVRMSAcknowledgement
                              INTEGER,
                           sensorProbeVRMSSirenDelayAlarm
                              INTEGER,
                           sensorProbeVRMSvoltageMode
                              INTEGER,
                           sensorProbeVRMSURL
                              DisplayString,
                           sensorProbeVRMSOpenURL
                              INTEGER,
                           sensorProbeVRMSDatacollectType
                              INTEGER,
                           sensorProbeVRMSContTimeHighCritical
                              INTEGER,
                           sensorProbeVRMSContTimeHighWarning
                              INTEGER,
                           sensorProbeVRMSContTimeNormal
                              INTEGER,
                           sensorProbeVRMSContTimeLowWarning
                              INTEGER,
                           sensorProbeVRMSContTimeLowCritical
                              INTEGER,
                           sensorProbeVRMSContTimeSensorError
                              INTEGER,
                           sensorProbeVRMSCalendar
                              INTEGER
                        }

                          sensorProbeVRMSSensorIndex OBJECT-TYPE
                              SYNTAX  INTEGER (0..7)
                              ACCESS  read-only
                              STATUS  mandatory
                              DESCRIPTION
                              "A unique value for each VRMS sensor port."
                              ::=  {  sensorProbeVRMSSensorEntry 1   }

                          sensorProbeVRMSDescription OBJECT-TYPE
                              SYNTAX  DisplayString
                              ACCESS  read-write
                              STATUS  mandatory
                              DESCRIPTION
                              "A Description of this sensor VRMS"
                              ::=  {  sensorProbeVRMSSensorEntry 2   }

                          sensorProbeVRMSPercent OBJECT-TYPE
                              SYNTAX  INTEGER (-32768..32767)
                              ACCESS  read-only
                              STATUS  mandatory
                              DESCRIPTION
                              "The relative VRMS percentage measured by this sensor"
                              ::=  {  sensorProbeVRMSSensorEntry 3   }

                           sensorProbeVRMSStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeVRMSSensorEntry 4   }

                           sensorProbeVRMSOnline OBJECT-TYPE
                              SYNTAX  INTEGER {
                                 online(1),
                                 offline(2)
                              }
                              ACCESS  read-only
                              STATUS  mandatory
                              DESCRIPTION
                              "If this Sensor is currently online"
                                 ::=  {  sensorProbeVRMSSensorEntry 5   }

                           sensorProbeVRMSGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeVRMSSensorEntry 6   }

                           sensorProbeVRMSHighWarning OBJECT-TYPE
                              SYNTAX  INTEGER
                              ACCESS  read-write
                              STATUS  mandatory
                              DESCRIPTION
                              "How high the relative VRMS this sensor measures before it sends a warning"
                              ::=  {  sensorProbeVRMSSensorEntry 7   }

                           sensorProbeVRMSHighCritical OBJECT-TYPE
                              SYNTAX  INTEGER
                              ACCESS  read-write
                              STATUS  mandatory
                              DESCRIPTION
                              "How high the relative VRMS this sensor measures before it becomes critical"
                              ::=  {  sensorProbeVRMSSensorEntry 8   }

                           sensorProbeVRMSLowWarning OBJECT-TYPE
                              SYNTAX  INTEGER
                              ACCESS  read-write
                              STATUS  mandatory
                              DESCRIPTION
                              "How low the relative VRMS this sensor measures before it sends a warning"
                              ::=  {  sensorProbeVRMSSensorEntry 9   }

                           sensorProbeVRMSLowCritical OBJECT-TYPE
                              SYNTAX  INTEGER
                              ACCESS  read-write
                              STATUS  mandatory
                              DESCRIPTION
                              "How low the relative VRMS this sensor measures before it becomes critical"
                              ::=  {  sensorProbeVRMSSensorEntry 10   }

                           sensorProbeVRMSRearm OBJECT-TYPE
                              SYNTAX  INTEGER
                              ACCESS  read-write
                              STATUS  mandatory
                              DESCRIPTION
                              "The percent relative VRMS to rearm the status. For example if status goes from normal to warning, the VRMS must go down spAnalogueRearm below warning before the status goes to normal"
                              ::=  {  sensorProbeVRMSSensorEntry 11   }

                           sensorProbeVRMSRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeVRMSSensorEntry 13   }

                           sensorProbeVRMSEmailTrapLimit OBJECT-TYPE
                              SYNTAX  INTEGER {
                                 disable(0),
                                 enable(1)
                              }
                              ACCESS  read-write
                              STATUS  mandatory
                              DESCRIPTION
                              "Enable email/trap limit feature"
                              ::=  {  sensorProbeVRMSSensorEntry 17   }

                           sensorProbeVRMSDelayError OBJECT-TYPE
                              SYNTAX  INTEGER (0..65534)
                              ACCESS  read-write
                              STATUS  mandatory
                              DESCRIPTION
                              "Time in seconds after the sensor has been in error status before report as an error"
                              ::=  {  sensorProbeVRMSSensorEntry 21   }

                           sensorProbeVRMSDelayNormal OBJECT-TYPE
                              SYNTAX  INTEGER (0..65534)
                              ACCESS  read-write
                              STATUS  mandatory
                              DESCRIPTION
                              "Time in seconds after the sensor change from error to normal before report as normal"
                              ::=  {  sensorProbeVRMSSensorEntry 22   }

                           sensorProbeVRMSRelayCycleTime OBJECT-TYPE
                              SYNTAX INTEGER (1..255)
                              ACCESS read-write
                              STATUS mandatory
                              DESCRIPTION
                              "Relay toggle period in seconds for Cycle action."
                              ::=  {  sensorProbeVRMSSensorEntry 29   }

                           sensorProbeVRMSRelayOnPort OBJECT-TYPE
                              SYNTAX INTEGER (0..255)
                              ACCESS read-write
                              STATUS mandatory
                              DESCRIPTION
                              "The sensor port that the relay will listen to. If this is set to 255, then the relay will not listen to any sensor ports"
                              ::=  {  sensorProbeVRMSSensorEntry 30   }

                           sensorProbeVRMSRelayActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the relay"
                              ::=  {  sensorProbeVRMSSensorEntry 31   }

                           sensorProbeVRMSRelayAction OBJECT-TYPE
                              SYNTAX INTEGER {
                                 cycle(2),
                                 turn-on(3),
                                 turn-off(4)
                              }
                              ACCESS read-write
                              STATUS mandatory
                              DESCRIPTION
                              "What the relay will do when the listened to port status turns to the specified active status."
                              ::=  {  sensorProbeVRMSSensorEntry 32   }

                           sensorProbeVRMSSirenCycleTime OBJECT-TYPE
                              SYNTAX INTEGER (1..255)
                              ACCESS read-write
                              STATUS mandatory
                              DESCRIPTION
                              "Siren toggle period in seconds for Cycle action."
                              ::=  {  sensorProbeVRMSSensorEntry 37   }

                           sensorProbeVRMSSirenOnPort OBJECT-TYPE
                              SYNTAX INTEGER (0..255)
                              ACCESS read-write
                              STATUS mandatory
                              DESCRIPTION
                              "The sensor port that the siren will listen to. If this is set to 255, then the siren will not listen to any sensor ports"
                              ::=  {  sensorProbeVRMSSensorEntry 38   }

                           sensorProbeVRMSSirenActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the siren"
                              ::=  {  sensorProbeVRMSSensorEntry 39   }

                           sensorProbeVRMSSirenAction OBJECT-TYPE
                              SYNTAX INTEGER {
                                 cycle(2),
                                 turn-on(3),
                                 turn-off(4)
                              }
                              ACCESS read-write
                              STATUS mandatory
                              DESCRIPTION
                              "What the siren will do when the listened to port status turns to the specified active status."
                              ::=  {  sensorProbeVRMSSensorEntry 40   }

                           sensorProbeVRMSAcknowledgement OBJECT-TYPE
                              SYNTAX INTEGER {
                                 ack(1)
                              }
                              ACCESS read-write
                              STATUS mandatory
                              DESCRIPTION
                              "Acknowledged sensor error and stop notification"
                              ::= {  sensorProbeVRMSSensorEntry 41 }

                           sensorProbeVRMSSirenDelayAlarm OBJECT-TYPE
                              SYNTAX INTEGER (1..255)
                              ACCESS read-write
                              STATUS mandatory
                              DESCRIPTION
                              "Siren delay in seconds before start Alarm."
                              ::=  {  sensorProbeVRMSSensorEntry 42   }

                           sensorProbeVRMSvoltageMode OBJECT-TYPE
                              SYNTAX INTEGER {
                                 ac-110(110),
                                 ac-220(220)
                              }
                              ACCESS read-write
                              STATUS mandatory
                              DESCRIPTION
                              "VRMS Voltage Mode."
                              ::=  {  sensorProbeVRMSSensorEntry 43   }

                           sensorProbeVRMSURL OBJECT-TYPE
                              SYNTAX DisplayString
                              ACCESS read-write
                              STATUS mandatory
                              DESCRIPTION
                              "Sensor URL link."
                              ::=  {  sensorProbeVRMSSensorEntry 44   }

                           sensorProbeVRMSOpenURL OBJECT-TYPE
                              SYNTAX INTEGER {
                                 cur-window(0),
                                 new-window(2)
                              }
                              ACCESS read-write
                              STATUS mandatory
                              DESCRIPTION
                              "Open URL in this browser or open in a new window."
                              ::=  {  sensorProbeVRMSSensorEntry 45   }

                           sensorProbeVRMSDatacollectType OBJECT-TYPE
                              SYNTAX INTEGER {
                                 average(1),
                                 highest(2),
                                 lowest(3)
                              }
                              ACCESS read-write
                              STATUS mandatory
                              DESCRIPTION
                              "Type of datacollect to collect."
                              ::=  {  sensorProbeVRMSSensorEntry 46   }

                           sensorProbeVRMSContTimeHighCritical OBJECT-TYPE
                              SYNTAX INTEGER (0..65535)
                              ACCESS read-write
                              STATUS mandatory
                              DESCRIPTION
                              "Continuous time for this sensor to be in High Critical before accepting new Status."
                              ::= {  sensorProbeVRMSSensorEntry 47 }

                           sensorProbeVRMSContTimeHighWarning OBJECT-TYPE
                              SYNTAX INTEGER (0..65535)
                              ACCESS read-write
                              STATUS mandatory
                              DESCRIPTION
                              "Continuous time for this sensor to be in High Warning before accepting new Status."
                              ::= {  sensorProbeVRMSSensorEntry 48 }

                           sensorProbeVRMSContTimeNormal OBJECT-TYPE
                              SYNTAX INTEGER (0..65535)
                              ACCESS read-write
                              STATUS mandatory
                              DESCRIPTION
                              "Continuous time for this sensor to be in Normal before accepting new Status."
                              ::= {  sensorProbeVRMSSensorEntry 49 }

                           sensorProbeVRMSContTimeLowWarning OBJECT-TYPE
                              SYNTAX INTEGER (0..65535)
                              ACCESS read-write
                              STATUS mandatory
                              DESCRIPTION
                              "Continuous time for this sensor to be in Low Warning before accepting new Status."
                              ::= {  sensorProbeVRMSSensorEntry 50 }

                           sensorProbeVRMSContTimeLowCritical OBJECT-TYPE
                              SYNTAX INTEGER (0..65535)
                              ACCESS read-write
                              STATUS mandatory
                              DESCRIPTION
                              "Continuous time for this sensor to be in Low Critical before accepting new Status."
                              ::= {  sensorProbeVRMSSensorEntry 51 }

                           sensorProbeVRMSContTimeSensorError OBJECT-TYPE
                              SYNTAX INTEGER (0..65535)
                              ACCESS read-write
                              STATUS mandatory
                              DESCRIPTION
                              "Continuous time for this sensor to be in Sensor Error before accepting new Status."
                              ::= {  sensorProbeVRMSSensorEntry 52 }

                           sensorProbeVRMSCalendar OBJECT-TYPE
                              SYNTAX INTEGER {
                                 disable(0),
                                 enable(1)
                              }
                              ACCESS read-write
                              STATUS mandatory
                              DESCRIPTION
                              "Enable or disable the calendar filtering working hours of sensor."
                              ::= {  sensorProbeVRMSSensorEntry 53 }

                  sensorProbeEnergySensor OBJECT IDENTIFIER ::= { sensorProbeOtherSensor 28  }

                     sensorProbeEnergySensorNumber OBJECT-TYPE
                        SYNTAX INTEGER
                        ACCESS read-only
                        STATUS mandatory
                        DESCRIPTION
                        "The total number of Energy Sensor port."
                        ::= {  sensorProbeEnergySensor 1 }

                     sensorProbeEnergySensorTable OBJECT-TYPE
                        SYNTAX  SEQUENCE OF SensorProbeEnergySensorEntry
                        ACCESS  not-accessible
                        STATUS  mandatory
                        DESCRIPTION
                        "This table contains the data for every Energy Sensor in the SensorArray. Each row in the table contains data for a different Energy Sensor."
                        ::=  {  sensorProbeEnergySensor 2   }

                        sensorProbeEnergySensorEntry OBJECT-TYPE
                           SYNTAX  SensorProbeEnergySensorEntry
                           ACCESS  not-accessible
                           STATUS  mandatory
                           DESCRIPTION
                           "This is an entry in the sensorProbeEnergySensorEntry Table"
                           INDEX         { sensorProbeEnergySensorIndex }
                           ::=  { sensorProbeEnergySensorTable 1 }

                        SensorProbeEnergySensorEntry ::= SEQUENCE {
                           sensorProbeEnergySensorIndex
                              INTEGER,
                           sensorProbeEnergyDescription
                              DisplayString,
                           sensorProbeEnergyPercent
                              INTEGER,
                           sensorProbeEnergyStatus
                              INTEGER,
                           sensorProbeEnergyOnline
                              INTEGER,
                           sensorProbeEnergyGoOnline
                              INTEGER,
                           sensorProbeEnergyHighWarning
                              INTEGER,
                           sensorProbeEnergyHighCritical
                              INTEGER,
                           sensorProbeEnergyLowWarning
                              INTEGER,
                           sensorProbeEnergyLowCritical
                              INTEGER,
                           sensorProbeEnergyRearm
                              INTEGER,
                           sensorProbeEnergyRaw
                              INTEGER,
                           sensorProbeEnergyEmailTrapLimit
                              INTEGER,
                           sensorProbeEnergyDelayError
                              INTEGER,
                           sensorProbeEnergyDelayNormal
                              INTEGER,
                           sensorProbeEnergyRelayCycleTime
                              INTEGER,
                           sensorProbeEnergyRelayOnPort
                              INTEGER,
                           sensorProbeEnergyRelayActiveStatus
                              INTEGER,
                           sensorProbeEnergyRelayAction
                              INTEGER,
                           sensorProbeEnergySirenCycleTime
                              INTEGER,
                           sensorProbeEnergySirenOnPort
                              INTEGER,
                           sensorProbeEnergySirenActiveStatus
                              INTEGER,
                           sensorProbeEnergySirenAction
                              INTEGER,
                           sensorProbeEnergyAcknowledgement
                              INTEGER,
                           sensorProbeEnergySirenDelayAlarm
                              INTEGER,
                           sensorProbeEnergyReadingMode
                              INTEGER,
                           sensorProbeEnergyURL
                              DisplayString,
                           sensorProbeEnergyOpenURL
                              INTEGER,
                           sensorProbeEnergyDatacollectType
                              INTEGER,
                           sensorProbeEnergyContTimeHighCritical
                              INTEGER,
                           sensorProbeEnergyContTimeHighWarning
                              INTEGER,
                           sensorProbeEnergyContTimeNormal
                              INTEGER,
                           sensorProbeEnergyContTimeLowWarning
                              INTEGER,
                           sensorProbeEnergyContTimeLowCritical
                              INTEGER,
                           sensorProbeEnergyContTimeSensorError
                              INTEGER,
                           sensorProbeEnergyCalendar
                              INTEGER
                        }

                          sensorProbeEnergySensorIndex OBJECT-TYPE
                              SYNTAX  INTEGER (0..7)
                              ACCESS  read-only
                              STATUS  mandatory
                              DESCRIPTION
                              "A unique value for each Energy sensor port."
                              ::=  {  sensorProbeEnergySensorEntry 1   }

                          sensorProbeEnergyDescription OBJECT-TYPE
                              SYNTAX  DisplayString
                              ACCESS  read-write
                              STATUS  mandatory
                              DESCRIPTION
                              "A Description of this sensor Energy"
                              ::=  {  sensorProbeEnergySensorEntry 2   }

                          sensorProbeEnergyPercent OBJECT-TYPE
                              SYNTAX  INTEGER (-32768..32767)
                              ACCESS  read-only
                              STATUS  mandatory
                              DESCRIPTION
                              "The relative Energy percentage measured by this sensor"
                              ::=  {  sensorProbeEnergySensorEntry 3   }

                           sensorProbeEnergyStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeEnergySensorEntry 4   }

                           sensorProbeEnergyOnline OBJECT-TYPE
                              SYNTAX  INTEGER {
                                 online(1),
                                 offline(2)
                              }
                              ACCESS  read-only
                              STATUS  mandatory
                              DESCRIPTION
                              "If this Sensor is currently online"
                                 ::=  {  sensorProbeEnergySensorEntry 5   }

                           sensorProbeEnergyGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeEnergySensorEntry 6   }

                           sensorProbeEnergyHighWarning OBJECT-TYPE
                              SYNTAX  INTEGER
                              ACCESS  read-write
                              STATUS  mandatory
                              DESCRIPTION
                              "How high the relative Energy this sensor measures before it sends a warning"
                              ::=  {  sensorProbeEnergySensorEntry 7   }

                           sensorProbeEnergyHighCritical OBJECT-TYPE
                              SYNTAX  INTEGER
                              ACCESS  read-write
                              STATUS  mandatory
                              DESCRIPTION
                              "How high the relative Energy this sensor measures before it becomes critical"
                              ::=  {  sensorProbeEnergySensorEntry 8   }

                           sensorProbeEnergyLowWarning OBJECT-TYPE
                              SYNTAX  INTEGER
                              ACCESS  read-write
                              STATUS  mandatory
                              DESCRIPTION
                              "How low the relative Energy this sensor measures before it sends a warning"
                              ::=  {  sensorProbeEnergySensorEntry 9   }

                           sensorProbeEnergyLowCritical OBJECT-TYPE
                              SYNTAX  INTEGER
                              ACCESS  read-write
                              STATUS  mandatory
                              DESCRIPTION
                              "How low the relative Energy this sensor measures before it becomes critical"
                              ::=  {  sensorProbeEnergySensorEntry 10   }

                           sensorProbeEnergyRearm OBJECT-TYPE
                              SYNTAX  INTEGER
                              ACCESS  read-write
                              STATUS  mandatory
                              DESCRIPTION
                              "The percent relative Energy to rearm the status. For example if status goes from normal to warning, the Energy must go down spAnalogueRearm below warning before the status goes to normal"
                              ::=  {  sensorProbeEnergySensorEntry 11   }

                           sensorProbeEnergyRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeEnergySensorEntry 13   }

                           sensorProbeEnergyEmailTrapLimit OBJECT-TYPE
                              SYNTAX  INTEGER {
                                 disable(0),
                                 enable(1)
                              }
                              ACCESS  read-write
                              STATUS  mandatory
                              DESCRIPTION
                              "Enable email/trap limit feature"
                              ::=  {  sensorProbeEnergySensorEntry 17   }

                           sensorProbeEnergyDelayError OBJECT-TYPE
                              SYNTAX  INTEGER (0..65534)
                              ACCESS  read-write
                              STATUS  mandatory
                              DESCRIPTION
                              "Time in seconds after the sensor has been in error status before report as an error"
                              ::=  {  sensorProbeEnergySensorEntry 21   }

                           sensorProbeEnergyDelayNormal OBJECT-TYPE
                              SYNTAX  INTEGER (0..65534)
                              ACCESS  read-write
                              STATUS  mandatory
                              DESCRIPTION
                              "Time in seconds after the sensor change from error to normal before report as normal"
                              ::=  {  sensorProbeEnergySensorEntry 22   }

                           sensorProbeEnergyRelayCycleTime OBJECT-TYPE
                              SYNTAX INTEGER (1..255)
                              ACCESS read-write
                              STATUS mandatory
                              DESCRIPTION
                              "Relay toggle period in seconds for Cycle action."
                              ::=  {  sensorProbeEnergySensorEntry 29   }

                           sensorProbeEnergyRelayOnPort OBJECT-TYPE
                              SYNTAX INTEGER (0..255)
                              ACCESS read-write
                              STATUS mandatory
                              DESCRIPTION
                              "The sensor port that the relay will listen to. If this is set to 255, then the relay will not listen to any sensor ports"
                              ::=  {  sensorProbeEnergySensorEntry 30   }

                           sensorProbeEnergyRelayActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the relay"
                              ::=  {  sensorProbeEnergySensorEntry 31   }

                           sensorProbeEnergyRelayAction OBJECT-TYPE
                              SYNTAX INTEGER {
                                 cycle(2),
                                 turn-on(3),
                                 turn-off(4)
                              }
                              ACCESS read-write
                              STATUS mandatory
                              DESCRIPTION
                              "What the relay will do when the listened to port status turns to the specified active status."
                              ::=  {  sensorProbeEnergySensorEntry 32   }

                           sensorProbeEnergySirenCycleTime OBJECT-TYPE
                              SYNTAX INTEGER (1..255)
                              ACCESS read-write
                              STATUS mandatory
                              DESCRIPTION
                              "Siren toggle period in seconds for Cycle action."
                              ::=  {  sensorProbeEnergySensorEntry 37   }

                           sensorProbeEnergySirenOnPort OBJECT-TYPE
                              SYNTAX INTEGER (0..255)
                              ACCESS read-write
                              STATUS mandatory
                              DESCRIPTION
                              "The sensor port that the siren will listen to. If this is set to 255, then the siren will not listen to any sensor ports"
                              ::=  {  sensorProbeEnergySensorEntry 38   }

                           sensorProbeEnergySirenActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the siren"
                              ::=  {  sensorProbeEnergySensorEntry 39   }

                           sensorProbeEnergySirenAction OBJECT-TYPE
                              SYNTAX INTEGER {
                                 cycle(2),
                                 turn-on(3),
                                 turn-off(4)
                              }
                              ACCESS read-write
                              STATUS mandatory
                              DESCRIPTION
                              "What the siren will do when the listened to port status turns to the specified active status."
                              ::=  {  sensorProbeEnergySensorEntry 40   }

                           sensorProbeEnergyAcknowledgement OBJECT-TYPE
                              SYNTAX INTEGER {
                                 ack(1)
                              }
                              ACCESS read-write
                              STATUS mandatory
                              DESCRIPTION
                              "Acknowledged sensor error and stop notification"
                              ::= {  sensorProbeEnergySensorEntry 41 }

                           sensorProbeEnergySirenDelayAlarm OBJECT-TYPE
                              SYNTAX INTEGER (1..255)
                              ACCESS read-write
                              STATUS mandatory
                              DESCRIPTION
                              "Siren delay in seconds before start Alarm."
                              ::=  {  sensorProbeEnergySensorEntry 42   }

                           sensorProbeEnergyReadingMode OBJECT-TYPE
                              SYNTAX INTEGER {
                                 active(0),
                                 apparent(1)
                              }
                              ACCESS read-write
                              STATUS mandatory
                              DESCRIPTION
                              "Energy Meter Reading Mode."
                              ::=  {  sensorProbeEnergySensorEntry 43   }

                           sensorProbeEnergyURL OBJECT-TYPE
                              SYNTAX DisplayString
                              ACCESS read-write
                              STATUS mandatory
                              DESCRIPTION
                              "Sensor URL link."
                              ::=  {  sensorProbeEnergySensorEntry 44   }

                           sensorProbeEnergyOpenURL OBJECT-TYPE
                              SYNTAX INTEGER {
                                 cur-window(0),
                                 new-window(2)
                              }
                              ACCESS read-write
                              STATUS mandatory
                              DESCRIPTION
                              "Open URL in this browser or open in a new window."
                              ::=  {  sensorProbeEnergySensorEntry 45   }

                           sensorProbeEnergyDatacollectType OBJECT-TYPE
                              SYNTAX INTEGER {
                                 average(1),
                                 highest(2),
                                 lowest(3)
                              }
                              ACCESS read-write
                              STATUS mandatory
                              DESCRIPTION
                              "Type of datacollect to collect."
                              ::=  {  sensorProbeEnergySensorEntry 46   }

                           sensorProbeEnergyContTimeHighCritical OBJECT-TYPE
                              SYNTAX INTEGER (0..65535)
                              ACCESS read-write
                              STATUS mandatory
                              DESCRIPTION
                              "Continuous time for this sensor to be in High Critical before accepting new Status."
                              ::= {  sensorProbeEnergySensorEntry 47 }

                           sensorProbeEnergyContTimeHighWarning OBJECT-TYPE
                              SYNTAX INTEGER (0..65535)
                              ACCESS read-write
                              STATUS mandatory
                              DESCRIPTION
                              "Continuous time for this sensor to be in High Warning before accepting new Status."
                              ::= {  sensorProbeEnergySensorEntry 48 }

                           sensorProbeEnergyContTimeNormal OBJECT-TYPE
                              SYNTAX INTEGER (0..65535)
                              ACCESS read-write
                              STATUS mandatory
                              DESCRIPTION
                              "Continuous time for this sensor to be in Normal before accepting new Status."
                              ::= {  sensorProbeEnergySensorEntry 49 }

                           sensorProbeEnergyContTimeLowWarning OBJECT-TYPE
                              SYNTAX INTEGER (0..65535)
                              ACCESS read-write
                              STATUS mandatory
                              DESCRIPTION
                              "Continuous time for this sensor to be in Low Warning before accepting new Status."
                              ::= {  sensorProbeEnergySensorEntry 50 }

                           sensorProbeEnergyContTimeLowCritical OBJECT-TYPE
                              SYNTAX INTEGER (0..65535)
                              ACCESS read-write
                              STATUS mandatory
                              DESCRIPTION
                              "Continuous time for this sensor to be in Low Critical before accepting new Status."
                              ::= {  sensorProbeEnergySensorEntry 51 }

                           sensorProbeEnergyContTimeSensorError OBJECT-TYPE
                              SYNTAX INTEGER (0..65535)
                              ACCESS read-write
                              STATUS mandatory
                              DESCRIPTION
                              "Continuous time for this sensor to be in Sensor Error before accepting new Status."
                              ::= {  sensorProbeEnergySensorEntry 52 }

                           sensorProbeEnergyCalendar OBJECT-TYPE
                              SYNTAX INTEGER {
                                 disable(0),
                                 enable(1)
                              }
                              ACCESS read-write
                              STATUS mandatory
                              DESCRIPTION
                              "Enable or disable the calendar filtering working hours of sensor."
                              ::= {  sensorProbeEnergySensorEntry 53 }

                        sensorProbeRelayArraySensor OBJECT IDENTIFIER ::= { sensorProbeOtherSensor 29  }

                           sensorProbeRelayArrayPort1 OBJECT IDENTIFIER ::= { sensorProbeRelayArraySensor 1  }
                              sensorProbeRelayArrayPort1Number OBJECT-TYPE
                                 SYNTAX INTEGER
                                 ACCESS read-only
                                 STATUS mandatory
                                 DESCRIPTION
                                 "The total number of port on the RelayArray."
                                 ::=  {  sensorProbeRelayArrayPort1 1   }

                              sensorProbeRelayArrayPort1Table OBJECT-TYPE
                                 SYNTAX  SEQUENCE OF SensorProbeRelayArrayPort1Entry
                                 ACCESS  not-accessible
                                 STATUS  mandatory
                                 DESCRIPTION
                                 "This table contains the data for every Switch Sensor in the SensorArray. Each row in the table contains data for a different Switch Sensor."
                                 ::=  {  sensorProbeRelayArrayPort1 2   }

                                 sensorProbeRelayArrayPort1Entry OBJECT-TYPE
                                    SYNTAX  SensorProbeRelayArrayPort1Entry
                                    ACCESS  not-accessible
                                    STATUS  mandatory
                                    DESCRIPTION
                                    "This is an entry in the sensorProbeRelayArrayPort1 Table"
                                    INDEX         { sensorProbeRelayArrayPort1Index }
                                    ::=  { sensorProbeRelayArrayPort1Table 1 }

                                    SensorProbeRelayArrayPort1Entry ::= SEQUENCE {
                                       sensorProbeRelayArrayPort1Index
                                          INTEGER,
                                       sensorProbeRelayArrayPort1Description
                                          DisplayString,
                                       sensorProbeRelayArrayPort1Status
                                          INTEGER,
                                       sensorProbeRelayArrayPort1Online
                                          INTEGER,
                                       sensorProbeRelayArrayPort1GoOnline
                                          INTEGER,
                                       sensorProbeRelayArrayPort1NormalState
                                          INTEGER,
                                       sensorProbeRelayArrayPort1RelayCycleTime
                                          INTEGER,
                                       sensorProbeRelayArrayPort1RelayAction
                                          INTEGER,
                                       sensorProbeRelayArrayPort1ManualRelayCycleTime
                                          INTEGER,
                                       sensorProbeRelayArrayPort1ManualRelayAction
                                          INTEGER,
                                       sensorProbeRelayArrayPort1RelayDescOn
                                          DisplayString,
                                       sensorProbeRelayArrayPort1RelayDescOff
                                          DisplayString,
                                       sensorProbeRelayArrayPort1URL
                                          DisplayString,
                                       sensorProbeRelayArrayPort1OpenURL
                                          INTEGER,
                                       sensorProbeRelayArrayPort1ControlMode
                                          INTEGER
                                    }

                                    sensorProbeRelayArrayPort1Index OBJECT-TYPE
                                       SYNTAX  INTEGER (0..7)
                                       ACCESS  read-only
                                       STATUS  mandatory
                                       DESCRIPTION
                                       "A unique value for each sensor RelayArray port."
                                       ::=  {  sensorProbeRelayArrayPort1Entry 1   }

                                    sensorProbeRelayArrayPort1Description OBJECT-TYPE
                                       SYNTAX  DisplayString
                                       ACCESS  read-write
                                       STATUS  mandatory
                                       DESCRIPTION
                                       "A Description of this sensor RelayArray"
                                       ::=  {  sensorProbeRelayArrayPort1Entry 2   }

                                    sensorProbeRelayArrayPort1Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort1Entry 4  }

                                    sensorProbeRelayArrayPort1Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort1Entry 5  }

                                    sensorProbeRelayArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort1Entry 6  }

                                    sensorProbeRelayArrayPort1NormalState OBJECT-TYPE
                                       SYNTAX  INTEGER {
                                          closed(0),
                                          open(1)
                                       }
                                       ACCESS  read-write
                                       STATUS  mandatory
                                       DESCRIPTION
                                       "The normal state of RelayArray"
                                       ::=  {  sensorProbeRelayArrayPort1Entry 7  }

                                    sensorProbeRelayArrayPort1RelayCycleTime OBJECT-TYPE
                                       SYNTAX INTEGER (1..255)
                                       ACCESS read-write
                                       STATUS mandatory
                                       DESCRIPTION
                                       "Relay toggle period in seconds for Cycle action."
                                       ::=  {  sensorProbeRelayArrayPort1Entry 18   }

                                    sensorProbeRelayArrayPort1RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort1Entry 21   }

                                    sensorProbeRelayArrayPort1ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort1Entry 24 }

                                    sensorProbeRelayArrayPort1ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort1Entry 25 }

                                    sensorProbeRelayArrayPort1RelayDescOn OBJECT-TYPE
                                       SYNTAX  DisplayString
                                       ACCESS  read-write
                                       STATUS  mandatory
                                       DESCRIPTION
                                       "Description of relay On"
                                       ::=  {  sensorProbeRelayArrayPort1Entry 26   }

                                    sensorProbeRelayArrayPort1RelayDescOff OBJECT-TYPE
                                       SYNTAX  DisplayString
                                       ACCESS  read-write
                                       STATUS  mandatory
                                       DESCRIPTION
                                       "Description of relay Off"
                                       ::=  {  sensorProbeRelayArrayPort1Entry 27   }

                                    sensorProbeRelayArrayPort1URL OBJECT-TYPE
                                       SYNTAX  DisplayString
                                       ACCESS  read-write
                                       STATUS  mandatory
                                       DESCRIPTION
                                       "Sersor URL link."
                                       ::=  {  sensorProbeRelayArrayPort1Entry 28   }

                                    sensorProbeRelayArrayPort1OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort1Entry 29   }

                                    sensorProbeRelayArrayPort1ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort1Entry 30  }

                           sensorProbeRelayArrayPort2 OBJECT IDENTIFIER ::= { sensorProbeRelayArraySensor 2  }
                              sensorProbeRelayArrayPort2Number OBJECT-TYPE
                                 SYNTAX INTEGER
                                 ACCESS read-only
                                 STATUS mandatory
                                 DESCRIPTION
                                 "The total number of port on the RelayArray."
                                 ::=  {  sensorProbeRelayArrayPort2 1   }

                              sensorProbeRelayArrayPort2Table OBJECT-TYPE
                                 SYNTAX  SEQUENCE OF SensorProbeRelayArrayPort2Entry
                                 ACCESS  not-accessible
                                 STATUS  mandatory
                                 DESCRIPTION
                                 "This table contains the data for every Switch Sensor in the SensorArray. Each row in the table contains data for a different Switch Sensor."
                                 ::=  {  sensorProbeRelayArrayPort2 2   }

                                 sensorProbeRelayArrayPort2Entry OBJECT-TYPE
                                    SYNTAX  SensorProbeRelayArrayPort2Entry
                                    ACCESS  not-accessible
                                    STATUS  mandatory
                                    DESCRIPTION
                                    "This is an entry in the sensorProbeRelayArrayPort2 Table"
                                    INDEX         { sensorProbeRelayArrayPort2Index }
                                    ::=  { sensorProbeRelayArrayPort2Table 1 }

                                    SensorProbeRelayArrayPort2Entry ::= SEQUENCE {
                                       sensorProbeRelayArrayPort2Index
                                          INTEGER,
                                       sensorProbeRelayArrayPort2Description
                                          DisplayString,
                                       sensorProbeRelayArrayPort2Status
                                          INTEGER,
                                       sensorProbeRelayArrayPort2Online
                                          INTEGER,
                                       sensorProbeRelayArrayPort2GoOnline
                                          INTEGER,
                                       sensorProbeRelayArrayPort2NormalState
                                          INTEGER,
                                       sensorProbeRelayArrayPort2RelayCycleTime
                                          INTEGER,
                                       sensorProbeRelayArrayPort2RelayAction
                                          INTEGER,
                                       sensorProbeRelayArrayPort2ManualRelayCycleTime
                                          INTEGER,
                                       sensorProbeRelayArrayPort2ManualRelayAction
                                          INTEGER,
                                       sensorProbeRelayArrayPort2RelayDescOn
                                          DisplayString,
                                       sensorProbeRelayArrayPort2RelayDescOff
                                          DisplayString,
                                       sensorProbeRelayArrayPort2URL
                                          DisplayString,
                                       sensorProbeRelayArrayPort2OpenURL
                                          INTEGER,
                                       sensorProbeRelayArrayPort2ControlMode
                                          INTEGER
                                    }

                                    sensorProbeRelayArrayPort2Index OBJECT-TYPE
                                       SYNTAX  INTEGER (0..7)
                                       ACCESS  read-only
                                       STATUS  mandatory
                                       DESCRIPTION
                                       "A unique value for each sensor RelayArray port."
                                       ::=  {  sensorProbeRelayArrayPort2Entry 1   }

                                    sensorProbeRelayArrayPort2Description OBJECT-TYPE
                                       SYNTAX  DisplayString
                                       ACCESS  read-write
                                       STATUS  mandatory
                                       DESCRIPTION
                                       "A Description of this sensor RelayArray"
                                       ::=  {  sensorProbeRelayArrayPort2Entry 2   }

                                    sensorProbeRelayArrayPort2Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort2Entry 4  }

                                    sensorProbeRelayArrayPort2Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort2Entry 5  }

                                    sensorProbeRelayArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort2Entry 6  }

                                    sensorProbeRelayArrayPort2NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort2Entry 7  }

                                    sensorProbeRelayArrayPort2RelayCycleTime OBJECT-TYPE
                                       SYNTAX INTEGER (1..255)
                                       ACCESS read-write
                                       STATUS mandatory
                                       DESCRIPTION
                                       "Relay toggle period in seconds for Cycle action."
                                       ::=  {  sensorProbeRelayArrayPort2Entry 18   }

                                    sensorProbeRelayArrayPort2RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort2Entry 21   }

                                    sensorProbeRelayArrayPort2ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort2Entry 24 }

                                    sensorProbeRelayArrayPort2ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort2Entry 25 }

                                    sensorProbeRelayArrayPort2RelayDescOn OBJECT-TYPE
                                       SYNTAX  DisplayString
                                       ACCESS  read-write
                                       STATUS  mandatory
                                       DESCRIPTION
                                       "Description of relay On"
                                       ::=  {  sensorProbeRelayArrayPort2Entry 26   }

                                    sensorProbeRelayArrayPort2RelayDescOff OBJECT-TYPE
                                       SYNTAX  DisplayString
                                       ACCESS  read-write
                                       STATUS  mandatory
                                       DESCRIPTION
                                       "Description of relay Off"
                                       ::=  {  sensorProbeRelayArrayPort2Entry 27   }

                                    sensorProbeRelayArrayPort2URL OBJECT-TYPE
                                       SYNTAX  DisplayString
                                       ACCESS  read-write
                                       STATUS  mandatory
                                       DESCRIPTION
                                       "Sensor URL link"
                                       ::=  {  sensorProbeRelayArrayPort2Entry 28   }

                                    sensorProbeRelayArrayPort2OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort2Entry 29   }

                                    sensorProbeRelayArrayPort2ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort2Entry 30  }

                           sensorProbeRelayArrayPort3 OBJECT IDENTIFIER ::= { sensorProbeRelayArraySensor 3  }
                              sensorProbeRelayArrayPort3Number OBJECT-TYPE
                                 SYNTAX INTEGER
                                 ACCESS read-only
                                 STATUS mandatory
                                 DESCRIPTION
                                 "The total number of port on the RelayArray."
                                 ::=  {  sensorProbeRelayArrayPort3 1   }

                              sensorProbeRelayArrayPort3Table OBJECT-TYPE
                                 SYNTAX  SEQUENCE OF SensorProbeRelayArrayPort3Entry
                                 ACCESS  not-accessible
                                 STATUS  mandatory
                                 DESCRIPTION
                                 "This table contains the data for every Switch Sensor in the SensorArray. Each row in the table contains data for a different Switch Sensor."
                                 ::=  {  sensorProbeRelayArrayPort3 2   }

                                 sensorProbeRelayArrayPort3Entry OBJECT-TYPE
                                    SYNTAX  SensorProbeRelayArrayPort3Entry
                                    ACCESS  not-accessible
                                    STATUS  mandatory
                                    DESCRIPTION
                                    "This is an entry in the sensorProbeRelayArrayPort3 Table"
                                    INDEX         { sensorProbeRelayArrayPort3Index }
                                    ::=  { sensorProbeRelayArrayPort3Table 1 }

                                    SensorProbeRelayArrayPort3Entry ::= SEQUENCE {
                                       sensorProbeRelayArrayPort3Index
                                          INTEGER,
                                       sensorProbeRelayArrayPort3Description
                                          DisplayString,
                                       sensorProbeRelayArrayPort3Status
                                          INTEGER,
                                       sensorProbeRelayArrayPort3Online
                                          INTEGER,
                                       sensorProbeRelayArrayPort3GoOnline
                                          INTEGER,
                                       sensorProbeRelayArrayPort3NormalState
                                          INTEGER,
                                       sensorProbeRelayArrayPort3RelayCycleTime
                                          INTEGER,
                                       sensorProbeRelayArrayPort3RelayAction
                                          INTEGER,
                                       sensorProbeRelayArrayPort3ManualRelayCycleTime
                                          INTEGER,
                                       sensorProbeRelayArrayPort3ManualRelayAction
                                          INTEGER,
                                       sensorProbeRelayArrayPort3RelayDescOn
                                          DisplayString,
                                       sensorProbeRelayArrayPort3RelayDescOff
                                          DisplayString,
                                       sensorProbeRelayArrayPort3URL
                                          DisplayString,
                                       sensorProbeRelayArrayPort3OpenURL
                                          INTEGER,
                                       sensorProbeRelayArrayPort3ControlMode
                                          INTEGER
                                    }

                                    sensorProbeRelayArrayPort3Index OBJECT-TYPE
                                       SYNTAX  INTEGER (0..7)
                                       ACCESS  read-only
                                       STATUS  mandatory
                                       DESCRIPTION
                                       "A unique value for each sensor RelayArray port."
                                       ::=  {  sensorProbeRelayArrayPort3Entry 1   }

                                    sensorProbeRelayArrayPort3Description OBJECT-TYPE
                                       SYNTAX  DisplayString
                                       ACCESS  read-write
                                       STATUS  mandatory
                                       DESCRIPTION
                                       "A Description of this sensor RelayArray"
                                       ::=  {  sensorProbeRelayArrayPort3Entry 2   }

                                    sensorProbeRelayArrayPort3Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort3Entry 4  }

                                    sensorProbeRelayArrayPort3Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort3Entry 5  }

                                    sensorProbeRelayArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort3Entry 6  }

                                    sensorProbeRelayArrayPort3NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort3Entry 7  }

                                    sensorProbeRelayArrayPort3RelayCycleTime OBJECT-TYPE
                                       SYNTAX INTEGER (1..255)
                                       ACCESS read-write
                                       STATUS mandatory
                                       DESCRIPTION
                                       "Relay toggle period in seconds for Cycle action."
                                       ::=  {  sensorProbeRelayArrayPort3Entry 18   }

                                    sensorProbeRelayArrayPort3RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort3Entry 21   }

                                    sensorProbeRelayArrayPort3ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort3Entry 24 }

                                    sensorProbeRelayArrayPort3ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort3Entry 25 }

                                    sensorProbeRelayArrayPort3RelayDescOn OBJECT-TYPE
                                       SYNTAX  DisplayString
                                       ACCESS  read-write
                                       STATUS  mandatory
                                       DESCRIPTION
                                       "Description of relay On"
                                       ::=  {  sensorProbeRelayArrayPort3Entry 26   }

                                    sensorProbeRelayArrayPort3RelayDescOff OBJECT-TYPE
                                       SYNTAX  DisplayString
                                       ACCESS  read-write
                                       STATUS  mandatory
                                       DESCRIPTION
                                       "Description of relay Off"
                                       ::=  {  sensorProbeRelayArrayPort3Entry 27   }

                                    sensorProbeRelayArrayPort3URL OBJECT-TYPE
                                       SYNTAX  DisplayString
                                       ACCESS  read-write
                                       STATUS  mandatory
                                       DESCRIPTION
                                       "Sensor URL link."
                                       ::=  {  sensorProbeRelayArrayPort3Entry 28   }

                                    sensorProbeRelayArrayPort3OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort3Entry 29   }

                                    sensorProbeRelayArrayPort3ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort3Entry 30  }

                           sensorProbeRelayArrayPort4 OBJECT IDENTIFIER ::= { sensorProbeRelayArraySensor 4  }
                              sensorProbeRelayArrayPort4Number OBJECT-TYPE
                                 SYNTAX INTEGER
                                 ACCESS read-only
                                 STATUS mandatory
                                 DESCRIPTION
                                 "The total number of port on the RelayArray."
                                 ::=  {  sensorProbeRelayArrayPort4 1   }

                              sensorProbeRelayArrayPort4Table OBJECT-TYPE
                                 SYNTAX  SEQUENCE OF SensorProbeRelayArrayPort4Entry
                                 ACCESS  not-accessible
                                 STATUS  mandatory
                                 DESCRIPTION
                                 "This table contains the data for every Switch Sensor in the SensorArray. Each row in the table contains data for a different Switch Sensor."
                                 ::=  {  sensorProbeRelayArrayPort4 2   }

                                 sensorProbeRelayArrayPort4Entry OBJECT-TYPE
                                    SYNTAX  SensorProbeRelayArrayPort4Entry
                                    ACCESS  not-accessible
                                    STATUS  mandatory
                                    DESCRIPTION
                                    "This is an entry in the sensorProbeRelayArrayPort4 Table"
                                    INDEX         { sensorProbeRelayArrayPort4Index }
                                    ::=  { sensorProbeRelayArrayPort4Table 1 }

                                    SensorProbeRelayArrayPort4Entry ::= SEQUENCE {
                                       sensorProbeRelayArrayPort4Index
                                          INTEGER,
                                       sensorProbeRelayArrayPort4Description
                                          DisplayString,
                                       sensorProbeRelayArrayPort4Status
                                          INTEGER,
                                       sensorProbeRelayArrayPort4Online
                                          INTEGER,
                                       sensorProbeRelayArrayPort4GoOnline
                                          INTEGER,
                                       sensorProbeRelayArrayPort4NormalState
                                          INTEGER,
                                       sensorProbeRelayArrayPort4RelayCycleTime
                                          INTEGER,
                                       sensorProbeRelayArrayPort4RelayAction
                                          INTEGER,
                                       sensorProbeRelayArrayPort4ManualRelayCycleTime
                                          INTEGER,
                                       sensorProbeRelayArrayPort4ManualRelayAction
                                          INTEGER,
                                       sensorProbeRelayArrayPort4RelayDescOn
                                          DisplayString,
                                       sensorProbeRelayArrayPort4RelayDescOff
                                          DisplayString,
                                       sensorProbeRelayArrayPort4URL
                                          DisplayString,
                                       sensorProbeRelayArrayPort4OpenURL
                                          INTEGER,
                                       sensorProbeRelayArrayPort4ControlMode
                                          INTEGER
                                    }

                                    sensorProbeRelayArrayPort4Index OBJECT-TYPE
                                       SYNTAX  INTEGER (0..7)
                                       ACCESS  read-only
                                       STATUS  mandatory
                                       DESCRIPTION
                                       "A unique value for each sensor RelayArray port."
                                       ::=  {  sensorProbeRelayArrayPort4Entry 1   }

                                    sensorProbeRelayArrayPort4Description OBJECT-TYPE
                                       SYNTAX  DisplayString
                                       ACCESS  read-write
                                       STATUS  mandatory
                                       DESCRIPTION
                                       "A Description of this sensor RelayArray"
                                       ::=  {  sensorProbeRelayArrayPort4Entry 2   }

                                    sensorProbeRelayArrayPort4Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort4Entry 4  }

                                    sensorProbeRelayArrayPort4Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort4Entry 5  }

                                    sensorProbeRelayArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort4Entry 6  }

                                    sensorProbeRelayArrayPort4NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort4Entry 7  }

                                    sensorProbeRelayArrayPort4RelayCycleTime OBJECT-TYPE
                                       SYNTAX INTEGER (1..255)
                                       ACCESS read-write
                                       STATUS mandatory
                                       DESCRIPTION
                                       "Relay toggle period in seconds for Cycle action."
                                       ::=  {  sensorProbeRelayArrayPort4Entry 18   }

                                    sensorProbeRelayArrayPort4RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort4Entry 21   }

                                    sensorProbeRelayArrayPort4ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort4Entry 24 }

                                    sensorProbeRelayArrayPort4ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort4Entry 25 }

                                    sensorProbeRelayArrayPort4RelayDescOn OBJECT-TYPE
                                       SYNTAX  DisplayString
                                       ACCESS  read-write
                                       STATUS  mandatory
                                       DESCRIPTION
                                       "Description of relay On"
                                       ::=  {  sensorProbeRelayArrayPort4Entry 26   }

                                    sensorProbeRelayArrayPort4RelayDescOff OBJECT-TYPE
                                       SYNTAX  DisplayString
                                       ACCESS  read-write
                                       STATUS  mandatory
                                       DESCRIPTION
                                       "Description of relay Off"
                                       ::=  {  sensorProbeRelayArrayPort4Entry 27   }

                                    sensorProbeRelayArrayPort4URL OBJECT-TYPE
                                       SYNTAX  DisplayString
                                       ACCESS  read-write
                                       STATUS  mandatory
                                       DESCRIPTION
                                       "Sensor URL link."
                                       ::=  {  sensorProbeRelayArrayPort4Entry 28   }

                                    sensorProbeRelayArrayPort4OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort4Entry 29   }

                                    sensorProbeRelayArrayPort4ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort4Entry 30  }

                           sensorProbeRelayArrayPort5 OBJECT IDENTIFIER ::= { sensorProbeRelayArraySensor 5  }
                              sensorProbeRelayArrayPort5Number OBJECT-TYPE
                                 SYNTAX INTEGER
                                 ACCESS read-only
                                 STATUS mandatory
                                 DESCRIPTION
                                 "The total number of port on the RelayArray."
                                 ::=  {  sensorProbeRelayArrayPort5 1   }

                              sensorProbeRelayArrayPort5Table OBJECT-TYPE
                                 SYNTAX  SEQUENCE OF SensorProbeRelayArrayPort5Entry
                                 ACCESS  not-accessible
                                 STATUS  mandatory
                                 DESCRIPTION
                                 "This table contains the data for every Switch Sensor in the SensorArray. Each row in the table contains data for a different Switch Sensor."
                                 ::=  {  sensorProbeRelayArrayPort5 2   }

                                 sensorProbeRelayArrayPort5Entry OBJECT-TYPE
                                    SYNTAX  SensorProbeRelayArrayPort5Entry
                                    ACCESS  not-accessible
                                    STATUS  mandatory
                                    DESCRIPTION
                                    "This is an entry in the sensorProbeRelayArrayPort5 Table"
                                    INDEX         { sensorProbeRelayArrayPort5Index }
                                    ::=  { sensorProbeRelayArrayPort5Table 1 }

                                    SensorProbeRelayArrayPort5Entry ::= SEQUENCE {
                                       sensorProbeRelayArrayPort5Index
                                          INTEGER,
                                       sensorProbeRelayArrayPort5Description
                                          DisplayString,
                                       sensorProbeRelayArrayPort5Status
                                          INTEGER,
                                       sensorProbeRelayArrayPort5Online
                                          INTEGER,
                                       sensorProbeRelayArrayPort5GoOnline
                                          INTEGER,
                                       sensorProbeRelayArrayPort5NormalState
                                          INTEGER,
                                       sensorProbeRelayArrayPort5RelayCycleTime
                                          INTEGER,
                                       sensorProbeRelayArrayPort5RelayAction
                                          INTEGER,
                                       sensorProbeRelayArrayPort5ManualRelayCycleTime
                                          INTEGER,
                                       sensorProbeRelayArrayPort5ManualRelayAction
                                          INTEGER,
                                       sensorProbeRelayArrayPort5RelayDescOn
                                          DisplayString,
                                       sensorProbeRelayArrayPort5RelayDescOff
                                          DisplayString,
                                       sensorProbeRelayArrayPort5URL
                                          DisplayString,
                                       sensorProbeRelayArrayPort5OpenURL
                                          INTEGER,
                                       sensorProbeRelayArrayPort5ControlMode
                                          INTEGER
                                    }

                                    sensorProbeRelayArrayPort5Index OBJECT-TYPE
                                       SYNTAX  INTEGER (0..7)
                                       ACCESS  read-only
                                       STATUS  mandatory
                                       DESCRIPTION
                                       "A unique value for each sensor RelayArray port."
                                       ::=  {  sensorProbeRelayArrayPort5Entry 1   }

                                    sensorProbeRelayArrayPort5Description OBJECT-TYPE
                                       SYNTAX  DisplayString
                                       ACCESS  read-write
                                       STATUS  mandatory
                                       DESCRIPTION
                                       "A Description of this sensor RelayArray"
                                       ::=  {  sensorProbeRelayArrayPort5Entry 2   }

                                    sensorProbeRelayArrayPort5Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort5Entry 4  }

                                    sensorProbeRelayArrayPort5Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort5Entry 5  }

                                    sensorProbeRelayArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort5Entry 6  }

                                    sensorProbeRelayArrayPort5NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort5Entry 7  }

                                    sensorProbeRelayArrayPort5RelayCycleTime OBJECT-TYPE
                                       SYNTAX INTEGER (1..255)
                                       ACCESS read-write
                                       STATUS mandatory
                                       DESCRIPTION
                                       "Relay toggle period in seconds for Cycle action."
                                       ::=  {  sensorProbeRelayArrayPort5Entry 18   }

                                    sensorProbeRelayArrayPort5RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort5Entry 21   }

                                    sensorProbeRelayArrayPort5ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort5Entry 24 }

                                    sensorProbeRelayArrayPort5ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort5Entry 25 }

                                    sensorProbeRelayArrayPort5RelayDescOn OBJECT-TYPE
                                       SYNTAX  DisplayString
                                       ACCESS  read-write
                                       STATUS  mandatory
                                       DESCRIPTION
                                       "Description of relay On"
                                       ::=  {  sensorProbeRelayArrayPort5Entry 26   }

                                    sensorProbeRelayArrayPort5RelayDescOff OBJECT-TYPE
                                       SYNTAX  DisplayString
                                       ACCESS  read-write
                                       STATUS  mandatory
                                       DESCRIPTION
                                       "Description of relay Off"
                                       ::=  {  sensorProbeRelayArrayPort5Entry 27   }

                                    sensorProbeRelayArrayPort5URL OBJECT-TYPE
                                       SYNTAX  DisplayString
                                       ACCESS  read-write
                                       STATUS  mandatory
                                       DESCRIPTION
                                       "Sensor URL link."
                                       ::=  {  sensorProbeRelayArrayPort5Entry 28   }

                                    sensorProbeRelayArrayPort5OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort5Entry 29   }

                                    sensorProbeRelayArrayPort5ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort5Entry 30  }

                           sensorProbeRelayArrayPort6 OBJECT IDENTIFIER ::= { sensorProbeRelayArraySensor 6  }
                              sensorProbeRelayArrayPort6Number OBJECT-TYPE
                                 SYNTAX INTEGER
                                 ACCESS read-only
                                 STATUS mandatory
                                 DESCRIPTION
                                 "The total number of port on the RelayArray."
                                 ::=  {  sensorProbeRelayArrayPort6 1   }

                              sensorProbeRelayArrayPort6Table OBJECT-TYPE
                                 SYNTAX  SEQUENCE OF SensorProbeRelayArrayPort6Entry
                                 ACCESS  not-accessible
                                 STATUS  mandatory
                                 DESCRIPTION
                                 "This table contains the data for every Switch Sensor in the SensorArray. Each row in the table contains data for a different Switch Sensor."
                                 ::=  {  sensorProbeRelayArrayPort6 2   }

                                 sensorProbeRelayArrayPort6Entry OBJECT-TYPE
                                    SYNTAX  SensorProbeRelayArrayPort6Entry
                                    ACCESS  not-accessible
                                    STATUS  mandatory
                                    DESCRIPTION
                                    "This is an entry in the sensorProbeRelayArrayPort6 Table"
                                    INDEX         { sensorProbeRelayArrayPort6Index }
                                    ::=  { sensorProbeRelayArrayPort6Table 1 }

                                    SensorProbeRelayArrayPort6Entry ::= SEQUENCE {
                                       sensorProbeRelayArrayPort6Index
                                          INTEGER,
                                       sensorProbeRelayArrayPort6Description
                                          DisplayString,
                                       sensorProbeRelayArrayPort6Status
                                          INTEGER,
                                       sensorProbeRelayArrayPort6Online
                                          INTEGER,
                                       sensorProbeRelayArrayPort6GoOnline
                                          INTEGER,
                                       sensorProbeRelayArrayPort6NormalState
                                          INTEGER,
                                       sensorProbeRelayArrayPort6RelayCycleTime
                                          INTEGER,
                                       sensorProbeRelayArrayPort6RelayAction
                                          INTEGER,
                                       sensorProbeRelayArrayPort6ManualRelayCycleTime
                                          INTEGER,
                                       sensorProbeRelayArrayPort6ManualRelayAction
                                          INTEGER,
                                       sensorProbeRelayArrayPort6RelayDescOn
                                          DisplayString,
                                       sensorProbeRelayArrayPort6RelayDescOff
                                          DisplayString,
                                       sensorProbeRelayArrayPort6URL
                                          DisplayString,
                                       sensorProbeRelayArrayPort6OpenURL
                                          INTEGER,
                                       sensorProbeRelayArrayPort6ControlMode
                                          INTEGER
                                    }

                                    sensorProbeRelayArrayPort6Index OBJECT-TYPE
                                       SYNTAX  INTEGER (0..7)
                                       ACCESS  read-only
                                       STATUS  mandatory
                                       DESCRIPTION
                                       "A unique value for each sensor RelayArray port."
                                       ::=  {  sensorProbeRelayArrayPort6Entry 1   }

                                    sensorProbeRelayArrayPort6Description OBJECT-TYPE
                                       SYNTAX  DisplayString
                                       ACCESS  read-write
                                       STATUS  mandatory
                                       DESCRIPTION
                                       "A Description of this sensor RelayArray"
                                       ::=  {  sensorProbeRelayArrayPort6Entry 2   }

                                    sensorProbeRelayArrayPort6Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort6Entry 4  }

                                    sensorProbeRelayArrayPort6Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort6Entry 5  }

                                    sensorProbeRelayArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort6Entry 6  }

                                    sensorProbeRelayArrayPort6NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort6Entry 7  }

                                    sensorProbeRelayArrayPort6RelayCycleTime OBJECT-TYPE
                                       SYNTAX INTEGER (1..255)
                                       ACCESS read-write
                                       STATUS mandatory
                                       DESCRIPTION
                                       "Relay toggle period in seconds for Cycle action."
                                       ::=  {  sensorProbeRelayArrayPort6Entry 18   }

                                    sensorProbeRelayArrayPort6RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort6Entry 21   }

                                    sensorProbeRelayArrayPort6ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort6Entry 24 }

                                    sensorProbeRelayArrayPort6ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort6Entry 25 }

                                    sensorProbeRelayArrayPort6RelayDescOn OBJECT-TYPE
                                       SYNTAX  DisplayString
                                       ACCESS  read-write
                                       STATUS  mandatory
                                       DESCRIPTION
                                       "Description of relay On"
                                       ::=  {  sensorProbeRelayArrayPort6Entry 26   }

                                    sensorProbeRelayArrayPort6RelayDescOff OBJECT-TYPE
                                       SYNTAX  DisplayString
                                       ACCESS  read-write
                                       STATUS  mandatory
                                       DESCRIPTION
                                       "Description of relay Off"
                                       ::=  {  sensorProbeRelayArrayPort6Entry 27   }

                                    sensorProbeRelayArrayPort6URL OBJECT-TYPE
                                       SYNTAX  DisplayString
                                       ACCESS  read-write
                                       STATUS  mandatory
                                       DESCRIPTION
                                       "Sensor URL link."
                                       ::=  {  sensorProbeRelayArrayPort6Entry 28   }

                                    sensorProbeRelayArrayPort6OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort6Entry 29   }

                                    sensorProbeRelayArrayPort6ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort6Entry 30  }

                           sensorProbeRelayArrayPort7 OBJECT IDENTIFIER ::= { sensorProbeRelayArraySensor 7  }
                              sensorProbeRelayArrayPort7Number OBJECT-TYPE
                                 SYNTAX INTEGER
                                 ACCESS read-only
                                 STATUS mandatory
                                 DESCRIPTION
                                 "The total number of port on the RelayArray."
                                 ::=  {  sensorProbeRelayArrayPort7 1   }

                              sensorProbeRelayArrayPort7Table OBJECT-TYPE
                                 SYNTAX  SEQUENCE OF SensorProbeRelayArrayPort7Entry
                                 ACCESS  not-accessible
                                 STATUS  mandatory
                                 DESCRIPTION
                                 "This table contains the data for every Switch Sensor in the SensorArray. Each row in the table contains data for a different Switch Sensor."
                                 ::=  {  sensorProbeRelayArrayPort7 2   }

                                 sensorProbeRelayArrayPort7Entry OBJECT-TYPE
                                    SYNTAX  SensorProbeRelayArrayPort7Entry
                                    ACCESS  not-accessible
                                    STATUS  mandatory
                                    DESCRIPTION
                                    "This is an entry in the sensorProbeRelayArrayPort7 Table"
                                    INDEX         { sensorProbeRelayArrayPort7Index }
                                    ::=  { sensorProbeRelayArrayPort7Table 1 }

                                    SensorProbeRelayArrayPort7Entry ::= SEQUENCE {
                                       sensorProbeRelayArrayPort7Index
                                          INTEGER,
                                       sensorProbeRelayArrayPort7Description
                                          DisplayString,
                                       sensorProbeRelayArrayPort7Status
                                          INTEGER,
                                       sensorProbeRelayArrayPort7Online
                                          INTEGER,
                                       sensorProbeRelayArrayPort7GoOnline
                                          INTEGER,
                                       sensorProbeRelayArrayPort7NormalState
                                          INTEGER,
                                       sensorProbeRelayArrayPort7RelayCycleTime
                                          INTEGER,
                                       sensorProbeRelayArrayPort7RelayAction
                                          INTEGER,
                                       sensorProbeRelayArrayPort7ManualRelayCycleTime
                                          INTEGER,
                                       sensorProbeRelayArrayPort7ManualRelayAction
                                          INTEGER,
                                       sensorProbeRelayArrayPort7RelayDescOn
                                          DisplayString,
                                       sensorProbeRelayArrayPort7RelayDescOff
                                          DisplayString,
                                       sensorProbeRelayArrayPort7URL
                                          DisplayString,
                                       sensorProbeRelayArrayPort7OpenURL
                                          INTEGER,
                                       sensorProbeRelayArrayPort7ControlMode
                                          INTEGER
                                    }

                                    sensorProbeRelayArrayPort7Index OBJECT-TYPE
                                       SYNTAX  INTEGER (0..7)
                                       ACCESS  read-only
                                       STATUS  mandatory
                                       DESCRIPTION
                                       "A unique value for each sensor RelayArray port."
                                       ::=  {  sensorProbeRelayArrayPort7Entry 1   }

                                    sensorProbeRelayArrayPort7Description OBJECT-TYPE
                                       SYNTAX  DisplayString
                                       ACCESS  read-write
                                       STATUS  mandatory
                                       DESCRIPTION
                                       "A Description of this sensor RelayArray"
                                       ::=  {  sensorProbeRelayArrayPort7Entry 2   }

                                    sensorProbeRelayArrayPort7Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort7Entry 4  }

                                    sensorProbeRelayArrayPort7Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort7Entry 5  }

                                    sensorProbeRelayArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort7Entry 6  }

                                    sensorProbeRelayArrayPort7NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort7Entry 7  }

                                    sensorProbeRelayArrayPort7RelayCycleTime OBJECT-TYPE
                                       SYNTAX INTEGER (1..255)
                                       ACCESS read-write
                                       STATUS mandatory
                                       DESCRIPTION
                                       "Relay toggle period in seconds for Cycle action."
                                       ::=  {  sensorProbeRelayArrayPort7Entry 18   }

                                    sensorProbeRelayArrayPort7RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort7Entry 21   }

                                    sensorProbeRelayArrayPort7ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort7Entry 24 }

                                    sensorProbeRelayArrayPort7ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort7Entry 25 }

                                    sensorProbeRelayArrayPort7RelayDescOn OBJECT-TYPE
                                       SYNTAX  DisplayString
                                       ACCESS  read-write
                                       STATUS  mandatory
                                       DESCRIPTION
                                       "Description of relay On"
                                       ::=  {  sensorProbeRelayArrayPort7Entry 26   }

                                    sensorProbeRelayArrayPort7RelayDescOff OBJECT-TYPE
                                       SYNTAX  DisplayString
                                       ACCESS  read-write
                                       STATUS  mandatory
                                       DESCRIPTION
                                       "Description of relay Off"
                                       ::=  {  sensorProbeRelayArrayPort7Entry 27   }

                                    sensorProbeRelayArrayPort7URL OBJECT-TYPE
                                       SYNTAX  DisplayString
                                       ACCESS  read-write
                                       STATUS  mandatory
                                       DESCRIPTION
                                       "Sensor URL link."
                                       ::=  {  sensorProbeRelayArrayPort7Entry 28   }

                                    sensorProbeRelayArrayPort7OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort7Entry 29   }

                                    sensorProbeRelayArrayPort7ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort7Entry 30  }

                           sensorProbeRelayArrayPort8 OBJECT IDENTIFIER ::= { sensorProbeRelayArraySensor 8  }
                              sensorProbeRelayArrayPort8Number OBJECT-TYPE
                                 SYNTAX INTEGER
                                 ACCESS read-only
                                 STATUS mandatory
                                 DESCRIPTION
                                 "The total number of port on the RelayArray."
                                 ::=  {  sensorProbeRelayArrayPort8 1   }

                              sensorProbeRelayArrayPort8Table OBJECT-TYPE
                                 SYNTAX  SEQUENCE OF SensorProbeRelayArrayPort8Entry
                                 ACCESS  not-accessible
                                 STATUS  mandatory
                                 DESCRIPTION
                                 "This table contains the data for every Switch Sensor in the SensorArray. Each row in the table contains data for a different Switch Sensor."
                                 ::=  {  sensorProbeRelayArrayPort8 2   }

                                 sensorProbeRelayArrayPort8Entry OBJECT-TYPE
                                    SYNTAX  SensorProbeRelayArrayPort8Entry
                                    ACCESS  not-accessible
                                    STATUS  mandatory
                                    DESCRIPTION
                                    "This is an entry in the sensorProbeRelayArrayPort8 Table"
                                    INDEX         { sensorProbeRelayArrayPort8Index }
                                    ::=  { sensorProbeRelayArrayPort8Table 1 }

                                    SensorProbeRelayArrayPort8Entry ::= SEQUENCE {
                                       sensorProbeRelayArrayPort8Index
                                          INTEGER,
                                       sensorProbeRelayArrayPort8Description
                                          DisplayString,
                                       sensorProbeRelayArrayPort8Status
                                          INTEGER,
                                       sensorProbeRelayArrayPort8Online
                                          INTEGER,
                                       sensorProbeRelayArrayPort8GoOnline
                                          INTEGER,
                                       sensorProbeRelayArrayPort8NormalState
                                          INTEGER,
                                       sensorProbeRelayArrayPort8RelayCycleTime
                                          INTEGER,
                                       sensorProbeRelayArrayPort8RelayAction
                                          INTEGER,
                                       sensorProbeRelayArrayPort8ManualRelayCycleTime
                                          INTEGER,
                                       sensorProbeRelayArrayPort8ManualRelayAction
                                          INTEGER,
                                       sensorProbeRelayArrayPort8RelayDescOn
                                          DisplayString,
                                       sensorProbeRelayArrayPort8RelayDescOff
                                          DisplayString,
                                       sensorProbeRelayArrayPort8URL
                                          DisplayString,
                                       sensorProbeRelayArrayPort8OpenURL
                                          INTEGER,
                                       sensorProbeRelayArrayPort8ControlMode
                                          INTEGER
                                    }

                                    sensorProbeRelayArrayPort8Index OBJECT-TYPE
                                       SYNTAX  INTEGER (0..7)
                                       ACCESS  read-only
                                       STATUS  mandatory
                                       DESCRIPTION
                                       "A unique value for each sensor RelayArray port."
                                       ::=  {  sensorProbeRelayArrayPort8Entry 1   }

                                    sensorProbeRelayArrayPort8Description OBJECT-TYPE
                                       SYNTAX  DisplayString
                                       ACCESS  read-write
                                       STATUS  mandatory
                                       DESCRIPTION
                                       "A Description of this sensor RelayArray"
                                       ::=  {  sensorProbeRelayArrayPort8Entry 2   }

                                    sensorProbeRelayArrayPort8Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort8Entry 4  }

                                    sensorProbeRelayArrayPort8Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort8Entry 5  }

                                    sensorProbeRelayArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort8Entry 6  }

                                    sensorProbeRelayArrayPort8NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort8Entry 7  }

                                    sensorProbeRelayArrayPort8RelayCycleTime OBJECT-TYPE
                                       SYNTAX INTEGER (1..255)
                                       ACCESS read-write
                                       STATUS mandatory
                                       DESCRIPTION
                                       "Relay toggle period in seconds for Cycle action."
                                       ::=  {  sensorProbeRelayArrayPort8Entry 18   }

                                    sensorProbeRelayArrayPort8RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort8Entry 21   }

                                    sensorProbeRelayArrayPort8ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort8Entry 24 }

                                    sensorProbeRelayArrayPort8ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort8Entry 25 }

                                    sensorProbeRelayArrayPort8RelayDescOn OBJECT-TYPE
                                       SYNTAX  DisplayString
                                       ACCESS  read-write
                                       STATUS  mandatory
                                       DESCRIPTION
                                       "Description of relay On"
                                       ::=  {  sensorProbeRelayArrayPort8Entry 26   }

                                    sensorProbeRelayArrayPort8RelayDescOff OBJECT-TYPE
                                       SYNTAX  DisplayString
                                       ACCESS  read-write
                                       STATUS  mandatory
                                       DESCRIPTION
                                       "Description of relay Off"
                                       ::=  {  sensorProbeRelayArrayPort8Entry 27   }

                                    sensorProbeRelayArrayPort8URL OBJECT-TYPE
                                       SYNTAX  DisplayString
                                       ACCESS  read-write
                                       STATUS  mandatory
                                       DESCRIPTION
                                       "Sensor URL link."
                                       ::=  {  sensorProbeRelayArrayPort8Entry 28   }

                                    sensorProbeRelayArrayPort8OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort8Entry 29   }

                                    sensorProbeRelayArrayPort8ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort8Entry 30  }

                  sensorProbeVirtualAnalogSensor OBJECT IDENTIFIER ::= { sensorProbeOtherSensor 30  }

                     sensorProbeVirtualAnalogSensorNumber OBJECT-TYPE
                        SYNTAX INTEGER
                        ACCESS read-only
                        STATUS mandatory
                        DESCRIPTION
                        "The total number of VirtualAnalog Sensor port."
                        ::= {  sensorProbeVirtualAnalogSensor 1 }

                     sensorProbeVirtualAnalogSensorTable OBJECT-TYPE
                        SYNTAX  SEQUENCE OF SensorProbeVirtualAnalogSensorEntry
                        ACCESS  not-accessible
                        STATUS  mandatory
                        DESCRIPTION
                        "This table contains the data for every VirtualAnalog Sensor in the SensorArray. Each row in the table contains data for a different VirtualAnalog Sensor."
                        ::=  {  sensorProbeVirtualAnalogSensor 2   }

                        sensorProbeVirtualAnalogSensorEntry OBJECT-TYPE
                           SYNTAX  SensorProbeVirtualAnalogSensorEntry
                           ACCESS  not-accessible
                           STATUS  mandatory
                           DESCRIPTION
                           "This is an entry in the sensorProbeVirtualAnalogSensorEntry Table"
                           INDEX         { sensorProbeVirtualAnalogSensorIndex }
                           ::=  { sensorProbeVirtualAnalogSensorTable 1 }

                        SensorProbeVirtualAnalogSensorEntry ::= SEQUENCE {
                           sensorProbeVirtualAnalogSensorIndex
                              INTEGER,
                           sensorProbeVirtualAnalogDescription
                              DisplayString,
                           sensorProbeVirtualAnalogStatus
                              INTEGER,
                           sensorProbeVirtualAnalogOnline
                              INTEGER,
                           sensorProbeVirtualAnalogGoOnline
                              INTEGER,
                           sensorProbeVirtualAnalogHighWarning
                              INTEGER,
                           sensorProbeVirtualAnalogHighCritical
                              INTEGER,
                           sensorProbeVirtualAnalogLowWarning
                              INTEGER,
                           sensorProbeVirtualAnalogLowCritical
                              INTEGER,
                           sensorProbeVirtualAnalogRearm
                              INTEGER,
                           sensorProbeVirtualAnalogRaw
                              INTEGER,
                           sensorProbeVirtualAnalogEmailTrapLimit
                              INTEGER,
                           sensorProbeVirtualAnalogDelayError
                              INTEGER,
                           sensorProbeVirtualAnalogDelayNormal
                              INTEGER,
                           sensorProbeVirtualAnalogUnit
                              DisplayString,
                           sensorProbeVirtualAnalogAcknowledgement
                              INTEGER,
                           sensorProbeVirtualAnalogURL
                              DisplayString,
                           sensorProbeVirtualAnalogOpenURL
                              INTEGER,
                           sensorProbeVirtualAnalogContTimeHighCritical
                              INTEGER,
                           sensorProbeVirtualAnalogContTimeHighWarning
                              INTEGER,
                           sensorProbeVirtualAnalogContTimeNormal
                              INTEGER,
                           sensorProbeVirtualAnalogContTimeLowWarning
                              INTEGER,
                           sensorProbeVirtualAnalogContTimeLowCritical
                              INTEGER,
                           sensorProbeVirtualAnalogContTimeSensorError
                              INTEGER,
                           sensorProbeVirtualAnalogCalendar
                              INTEGER,
                           sensorProbeVirtualAnalogValueFactor
                              INTEGER
                        }

                          sensorProbeVirtualAnalogSensorIndex OBJECT-TYPE
                              SYNTAX  INTEGER (0..67)
                              ACCESS  read-only
                              STATUS  mandatory
                              DESCRIPTION
                              "A unique value for each VirtualAnalog sensor port."
                              ::=  {  sensorProbeVirtualAnalogSensorEntry 1   }

                          sensorProbeVirtualAnalogDescription OBJECT-TYPE
                              SYNTAX  DisplayString
                              ACCESS  read-write
                              STATUS  mandatory
                              DESCRIPTION
                              "A Description of this sensor"
                              ::=  {  sensorProbeVirtualAnalogSensorEntry 2   }

                           sensorProbeVirtualAnalogStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeVirtualAnalogSensorEntry 4   }

                           sensorProbeVirtualAnalogOnline OBJECT-TYPE
                              SYNTAX  INTEGER {
                                 online(1),
                                 offline(2)
                              }
                              ACCESS  read-only
                              STATUS  mandatory
                              DESCRIPTION
                              "If this Sensor is currently online"
                                 ::=  {  sensorProbeVirtualAnalogSensorEntry 5   }

                           sensorProbeVirtualAnalogGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeVirtualAnalogSensorEntry 6   }

                           sensorProbeVirtualAnalogHighWarning OBJECT-TYPE
                              SYNTAX  INTEGER
                              ACCESS  read-write
                              STATUS  mandatory
                              DESCRIPTION
                              "How high the relative VirtualAnalog this sensor measures before it sends a warning"
                              ::=  {  sensorProbeVirtualAnalogSensorEntry 7   }

                           sensorProbeVirtualAnalogHighCritical OBJECT-TYPE
                              SYNTAX  INTEGER
                              ACCESS  read-write
                              STATUS  mandatory
                              DESCRIPTION
                              "How high the relative VirtualAnalog this sensor measures before it becomes critical"
                              ::=  {  sensorProbeVirtualAnalogSensorEntry 8   }

                           sensorProbeVirtualAnalogLowWarning OBJECT-TYPE
                              SYNTAX  INTEGER
                              ACCESS  read-write
                              STATUS  mandatory
                              DESCRIPTION
                              "How low the relative VirtualAnalog this sensor measures before it sends a warning"
                              ::=  {  sensorProbeVirtualAnalogSensorEntry 9   }

                           sensorProbeVirtualAnalogLowCritical OBJECT-TYPE
                              SYNTAX  INTEGER
                              ACCESS  read-write
                              STATUS  mandatory
                              DESCRIPTION
                              "How low the relative VirtualAnalog this sensor measures before it becomes critical"
                              ::=  {  sensorProbeVirtualAnalogSensorEntry 10   }

                           sensorProbeVirtualAnalogRearm OBJECT-TYPE
                              SYNTAX  INTEGER
                              ACCESS  read-write
                              STATUS  mandatory
                              DESCRIPTION
                              "The percent relative VirtualAnalog to rearm the status. For example if status goes from normal to warning, the VirtualAnalog must go down spAnalogueRearm below warning before the status goes to normal"
                              ::=  {  sensorProbeVirtualAnalogSensorEntry 11   }

                           sensorProbeVirtualAnalogRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeVirtualAnalogSensorEntry 13   }

                           sensorProbeVirtualAnalogEmailTrapLimit OBJECT-TYPE
                              SYNTAX  INTEGER {
                                 disable(0),
                                 enable(1)
                              }
                              ACCESS  read-write
                              STATUS  mandatory
                              DESCRIPTION
                              "Enable email/trap limit feature"
                              ::=  {  sensorProbeVirtualAnalogSensorEntry 17   }

                           sensorProbeVirtualAnalogDelayError OBJECT-TYPE
                              SYNTAX  INTEGER (0..65534)
                              ACCESS  read-write
                              STATUS  mandatory
                              DESCRIPTION
                              "Time in seconds after the sensor has been in error status before report as an error"
                              ::=  {  sensorProbeVirtualAnalogSensorEntry 21   }

                           sensorProbeVirtualAnalogDelayNormal OBJECT-TYPE
                              SYNTAX  INTEGER (0..65534)
                              ACCESS  read-write
                              STATUS  mandatory
                              DESCRIPTION
                              "Time in seconds after the sensor change from error to normal before report as normal"
                              ::=  {  sensorProbeVirtualAnalogSensorEntry 22   }

                           sensorProbeVirtualAnalogUnit OBJECT-TYPE
                              SYNTAX  DisplayString
                              ACCESS  read-write
                              STATUS  mandatory
                              DESCRIPTION
                              "Display unit in VirtualAnalog."
                              ::=  {  sensorProbeVirtualAnalogSensorEntry 27   }

                           sensorProbeVirtualAnalogAcknowledgement OBJECT-TYPE
                              SYNTAX INTEGER {
                                 ack(1)
                              }
                              ACCESS read-write
                              STATUS mandatory
                              DESCRIPTION
                              "Acknowledged sensor error and stop notification"
                              ::= {  sensorProbeVirtualAnalogSensorEntry 41 }

                           sensorProbeVirtualAnalogURL OBJECT-TYPE
                              SYNTAX DisplayString
                              ACCESS read-write
                              STATUS mandatory
                              DESCRIPTION
                              "Sensor URL link."
                              ::=  {  sensorProbeVirtualAnalogSensorEntry 43   }

                           sensorProbeVirtualAnalogOpenURL OBJECT-TYPE
                              SYNTAX INTEGER {
                                 cur-window(0),
                                 new-window(2)
                              }
                              ACCESS read-write
                              STATUS mandatory
                              DESCRIPTION
                              "Open URL in this browser or open in a new window."
                              ::=  {  sensorProbeVirtualAnalogSensorEntry 44   }

                           sensorProbeVirtualAnalogContTimeHighCritical OBJECT-TYPE
                              SYNTAX INTEGER (0..65535)
                              ACCESS read-write
                              STATUS mandatory
                              DESCRIPTION
                              "Continuous time for this sensor to be in High Critical before accepting new Status."
                              ::= {  sensorProbeVirtualAnalogSensorEntry 45 }

                           sensorProbeVirtualAnalogContTimeHighWarning OBJECT-TYPE
                              SYNTAX INTEGER (0..65535)
                              ACCESS read-write
                              STATUS mandatory
                              DESCRIPTION
                              "Continuous time for this sensor to be in High Warning before accepting new Status."
                              ::= {  sensorProbeVirtualAnalogSensorEntry 46 }

                           sensorProbeVirtualAnalogContTimeNormal OBJECT-TYPE
                              SYNTAX INTEGER (0..65535)
                              ACCESS read-write
                              STATUS mandatory
                              DESCRIPTION
                              "Continuous time for this sensor to be in Normal before accepting new Status."
                              ::= {  sensorProbeVirtualAnalogSensorEntry 47 }

                           sensorProbeVirtualAnalogContTimeLowWarning OBJECT-TYPE
                              SYNTAX INTEGER (0..65535)
                              ACCESS read-write
                              STATUS mandatory
                              DESCRIPTION
                              "Continuous time for this sensor to be in Low Warning before accepting new Status."
                              ::= {  sensorProbeVirtualAnalogSensorEntry 48 }

                           sensorProbeVirtualAnalogContTimeLowCritical OBJECT-TYPE
                              SYNTAX INTEGER (0..65535)
                              ACCESS read-write
                              STATUS mandatory
                              DESCRIPTION
                              "Continuous time for this sensor to be in Low Critical before accepting new Status."
                              ::= {  sensorProbeVirtualAnalogSensorEntry 49 }

                           sensorProbeVirtualAnalogContTimeSensorError OBJECT-TYPE
                              SYNTAX INTEGER (0..65535)
                              ACCESS read-write
                              STATUS mandatory
                              DESCRIPTION
                              "Continuous time for this sensor to be in Sensor Error before accepting new Status."
                              ::= {  sensorProbeVirtualAnalogSensorEntry 50 }

                           sensorProbeVirtualAnalogCalendar OBJECT-TYPE
                              SYNTAX INTEGER {
                                 disable(0),
                                 enable(1)
                              }
                              ACCESS read-write
                              STATUS mandatory
                              DESCRIPTION
                              "Enable or disable the calendar filtering working hours of sensor."
                              ::= {  sensorProbeVirtualAnalogSensorEntry 51 }

                           sensorProbeVirtualAnalogValueFactor OBJECT-TYPE
                              SYNTAX INTEGER {
                                 x1(1),
                                 x0-1(10),
                                 x0-01(100),
                                 x0-001(1000)
                              }
                              ACCESS read-write
                              STATUS mandatory
                              DESCRIPTION
                              "To change the ratio of value."
                              ::= {  sensorProbeVirtualAnalogSensorEntry 52 }

                  sensorProbeVirtualSwitchSensor OBJECT IDENTIFIER ::= { sensorProbeOtherSensor 31  }

                     sensorProbeVirtualSwitchSensorNumber OBJECT-TYPE
                        SYNTAX INTEGER
                        ACCESS read-only
                        STATUS mandatory
                        DESCRIPTION
                        "The total number of VirtualSwitch Sensor port."
                        ::= {  sensorProbeVirtualSwitchSensor 1 }

                     sensorProbeVirtualSwitchSensorTable OBJECT-TYPE
                        SYNTAX  SEQUENCE OF SensorProbeVirtualSwitchSensorEntry
                        ACCESS  not-accessible
                        STATUS  mandatory
                        DESCRIPTION
                        "This table contains the data for every VirtualSwitch Sensor in the SensorArray. Each row in the table contains data for a different VirtualSwitch Sensor."
                        ::=  {  sensorProbeVirtualSwitchSensor 2   }

                        sensorProbeVirtualSwitchSensorEntry OBJECT-TYPE
                           SYNTAX  SensorProbeVirtualSwitchSensorEntry
                           ACCESS  not-accessible
                           STATUS  mandatory
                           DESCRIPTION
                           "This is an entry in the sensorProbeVirtualSwitchSensorEntry Table"
                           INDEX         { sensorProbeVirtualSwitchSensorIndex }
                           ::=  { sensorProbeVirtualSwitchSensorTable 1 }

                        SensorProbeVirtualSwitchSensorEntry ::= SEQUENCE {
                           sensorProbeVirtualSwitchSensorIndex
                              INTEGER,
                           sensorProbeVirtualSwitchDescription
                              DisplayString,
                           sensorProbeVirtualSwitchStatus
                              INTEGER,
                           sensorProbeVirtualSwitchOnline
                              INTEGER,
                           sensorProbeVirtualSwitchGoOnline
                              INTEGER,
                           sensorProbeVirtualSwitchEmailTrapLimit
                              INTEGER,
                           sensorProbeVirtualSwitchContTimeHighCritical
                              INTEGER,
                           sensorProbeVirtualSwitchContTimeNormal
                              INTEGER,                         
                           sensorProbeVirtualSwitchDescriptionCritical
                              DisplayString,
                           sensorProbeVirtualSwitchDescriptionNormal
                              DisplayString,                           
                           sensorProbeVirtualSwitchAcknowledgement
                              INTEGER,                             
                           sensorProbeVirtualSwitchURL
                              DisplayString,
                           sensorProbeVirtualSwitchOpenURL
                              INTEGER,
                           sensorProbeVirtualSwitchCalendar
                              INTEGER,
                           sensorProbeVirtualSwitchNormalState
                              INTEGER
                        }

                          sensorProbeVirtualSwitchSensorIndex OBJECT-TYPE
                              SYNTAX  INTEGER (0..67)
                              ACCESS  read-only
                              STATUS  mandatory
                              DESCRIPTION
                              "A unique value for each VirtualSwitch sensor port."
                              ::=  {  sensorProbeVirtualSwitchSensorEntry 1   }

                          sensorProbeVirtualSwitchDescription OBJECT-TYPE
                              SYNTAX  DisplayString
                              ACCESS  read-write
                              STATUS  mandatory
                              DESCRIPTION
                              "A Description of this sensor"
                              ::=  {  sensorProbeVirtualSwitchSensorEntry 2   }

                           sensorProbeVirtualSwitchStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeVirtualSwitchSensorEntry 4   }

                           sensorProbeVirtualSwitchOnline OBJECT-TYPE
                              SYNTAX  INTEGER {
                                 online(1),
                                 offline(2)
                              }
                              ACCESS  read-only
                              STATUS  mandatory
                              DESCRIPTION
                              "If this Sensor is currently online"
                                 ::=  {  sensorProbeVirtualSwitchSensorEntry 5   }

                           sensorProbeVirtualSwitchGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeVirtualSwitchSensorEntry 6   }

                           sensorProbeVirtualSwitchEmailTrapLimit OBJECT-TYPE
                              SYNTAX  INTEGER {
                                 disable(0),
                                 enable(1)
                              }
                              ACCESS  read-write
                              STATUS  mandatory
                              DESCRIPTION
                              "Enable email/trap limit feature"
                              ::=  {  sensorProbeVirtualSwitchSensorEntry 17   }

                           sensorProbeVirtualSwitchContTimeHighCritical OBJECT-TYPE
                              SYNTAX  INTEGER (0..65534)
                              ACCESS  read-write
                              STATUS  mandatory
                              DESCRIPTION
                              "Continuous time for this sensor to be in High Critical before accepting new Status."
                              ::=  {  sensorProbeVirtualSwitchSensorEntry 21   }

                           sensorProbeVirtualSwitchContTimeNormal OBJECT-TYPE
                              SYNTAX INTEGER (0..65535)
                              ACCESS read-write
                              STATUS mandatory
                              DESCRIPTION
                              "Continuous time for this sensor to be in Normal before accepting new Status."
                              ::=  {  sensorProbeVirtualSwitchSensorEntry 22   }

                           sensorProbeVirtualSwitchDescriptionCritical OBJECT-TYPE
                              SYNTAX DisplayString
                              ACCESS read-write
                              STATUS mandatory
                              DESCRIPTION
                              "Description of status when the virsual switch is critical"
                              ::=  {  sensorProbeVirtualSwitchSensorEntry 26   }

                           sensorProbeVirtualSwitchDescriptionNormal OBJECT-TYPE
                              SYNTAX DisplayString
                              ACCESS read-write
                              STATUS mandatory
                              DESCRIPTION
                              "Description of status when the virsual switch is normal"
                              ::=  {  sensorProbeVirtualSwitchSensorEntry 27   }

                           sensorProbeVirtualSwitchAcknowledgement OBJECT-TYPE
                              SYNTAX INTEGER {
                                 ack(1)
                              }
                              ACCESS read-write
                              STATUS mandatory
                              DESCRIPTION
                              "Acknowledged sensor error and stop notification"
                              ::= {  sensorProbeVirtualSwitchSensorEntry 41 }

                           sensorProbeVirtualSwitchURL OBJECT-TYPE
                              SYNTAX DisplayString
                              ACCESS read-write
                              STATUS mandatory
                              DESCRIPTION
                              "Sensor URL link."
                              ::=  {  sensorProbeVirtualSwitchSensorEntry 43   }

                           sensorProbeVirtualSwitchOpenURL OBJECT-TYPE
                              SYNTAX INTEGER {
                                 cur-window(0),
                                 new-window(2)
                              }
                              ACCESS read-write
                              STATUS mandatory
                              DESCRIPTION
                              "Open URL in this browser or open in a new window."
                              ::=  {  sensorProbeVirtualSwitchSensorEntry 44   }

                           sensorProbeVirtualSwitchCalendar OBJECT-TYPE
                              SYNTAX INTEGER {
                                 disable(0),
                                 enable(1)
                              }
                              ACCESS read-write
                              STATUS mandatory
                              DESCRIPTION
                              "Enable or disable the calendar filtering working hours of sensor."
                              ::= {  sensorProbeVirtualSwitchSensorEntry 45 }

                           sensorProbeVirtualSwitchNormalState OBJECT-TYPE
                              SYNTAX INTEGER
                              ACCESS read-write
                              STATUS mandatory
                              DESCRIPTION
                              "The normal state of a return of the virsual switch. If a return of the virsual switch is equal this normal state value, it is normal. Otherwise, it is critical."
                              ::= {  sensorProbeVirtualSwitchSensorEntry 46 }

                  sensorProbeWattHoursSensor OBJECT IDENTIFIER ::= { sensorProbeOtherSensor 32  }

                     sensorProbeWattHoursSensorNumber OBJECT-TYPE
                        SYNTAX INTEGER
                        ACCESS read-only
                        STATUS mandatory
                        DESCRIPTION
                        "The total number of WattHours Sensor port."
                        ::= {  sensorProbeWattHoursSensor 1 }

                     sensorProbeWattHoursSensorTable OBJECT-TYPE
                        SYNTAX  SEQUENCE OF SensorProbeWattHoursSensorEntry
                        ACCESS  not-accessible
                        STATUS  mandatory
                        DESCRIPTION
                        "This table contains the data for every WattHours Sensor in the SensorArray. Each row in the table contains data for a different WattHours Sensor."
                        ::=  {  sensorProbeWattHoursSensor 2   }

                        sensorProbeWattHoursSensorEntry OBJECT-TYPE
                           SYNTAX  SensorProbeWattHoursSensorEntry
                           ACCESS  not-accessible
                           STATUS  mandatory
                           DESCRIPTION
                           "This is an entry in the sensorProbeWattHoursSensorEntry Table"
                           INDEX         { sensorProbeWattHoursSensorIndex }
                           ::=  { sensorProbeWattHoursSensorTable 1 }

                        SensorProbeWattHoursSensorEntry ::= SEQUENCE {
                           sensorProbeWattHoursSensorIndex
                              INTEGER,
                           sensorProbeWattHoursDescription
                              DisplayString,
                           sensorProbeWattHoursPercent
                              INTEGER,
                           sensorProbeWattHoursReset
                              INTEGER
                        }

                          sensorProbeWattHoursSensorIndex OBJECT-TYPE
                              SYNTAX  INTEGER (0..7)
                              ACCESS  read-only
                              STATUS  mandatory
                              DESCRIPTION
                              "A unique value for each WattHours sensor port."
                              ::=  {  sensorProbeWattHoursSensorEntry 1  }

                          sensorProbeWattHoursDescription OBJECT-TYPE
                              SYNTAX  DisplayString
                              ACCESS  read-write
                              STATUS  mandatory
                              DESCRIPTION
                              "A Description of this sensor"
                              ::=  {  sensorProbeWattHoursSensorEntry 2   }

                          sensorProbeWattHoursPercent OBJECT-TYPE
                              SYNTAX  INTEGER (-32768..32767)
                              ACCESS  read-only
                              STATUS  mandatory
                              DESCRIPTION
                              "The relative WattHours percentage measured by this sensor"
                              ::=  {  sensorProbeWattHoursSensorEntry 3   }

                          sensorProbeWattHoursReset OBJECT-TYPE
                              SYNTAX  INTEGER (1)
                              ACCESS  read-write
                              STATUS  mandatory
                              DESCRIPTION
                              "The relative WattHours percentage measured by this sensor"
                              ::=  {  sensorProbeWattHoursSensorEntry 43   }

                        sensorProbeTemperatureArraySensor OBJECT IDENTIFIER ::= { sensorProbeOtherSensor 33  }

                           sensorProbeTemperatureArrayPort1 OBJECT IDENTIFIER ::= { sensorProbeTemperatureArraySensor 1  }
                              sensorProbeTemperatureArrayPort1Number OBJECT-TYPE
                                 SYNTAX INTEGER
                                 ACCESS read-only
                                 STATUS mandatory
                                 DESCRIPTION
                                 "The total number of port on the TemperatureArray."
                                 ::=  {  sensorProbeTemperatureArrayPort1 1   }

                              sensorProbeTemperatureArrayPort1Table OBJECT-TYPE
                                 SYNTAX  SEQUENCE OF SensorProbeTemperatureArrayPort1Entry
                                 ACCESS  not-accessible
                                 STATUS  mandatory
                                 DESCRIPTION
                                 "This table contains the data for every Switch Sensor in the SensorArray. Each row in the table contains data for a different Switch Sensor."
                                 ::=  {  sensorProbeTemperatureArrayPort1 2   }

                                 sensorProbeTemperatureArrayPort1Entry OBJECT-TYPE
                                    SYNTAX  SensorProbeTemperatureArrayPort1Entry
                                    ACCESS  not-accessible
                                    STATUS  mandatory
                                    DESCRIPTION
                                    "This is an entry in the sensorProbeTemperatureArrayPort1 Table"
                                    INDEX         { sensorProbeTemperatureArrayPort1Index }
                                    ::=  { sensorProbeTemperatureArrayPort1Table 1 }

                                    SensorProbeTemperatureArrayPort1Entry ::= SEQUENCE {
                                       sensorProbeTemperatureArrayPort1Index
                                          INTEGER,
                                       sensorProbeTemperatureArrayPort1Description
                                          DisplayString,
                                       sensorProbeTemperatureArrayPort1Value
                                          INTEGER,
                                       sensorProbeTemperatureArrayPort1Status
                                          INTEGER,
                                       sensorProbeTemperatureArrayPort1Online
                                          INTEGER,
                                       sensorProbeTemperatureArrayPort1GoOnline
                                          INTEGER,
                                       sensorProbeTemperatureArrayPort1HighWarning
                                          INTEGER,
                                       sensorProbeTemperatureArrayPort1HighCritical
                                          INTEGER,
                                       sensorProbeTemperatureArrayPort1LowWarning
                                          INTEGER,
                                       sensorProbeTemperatureArrayPort1LowCritical
                                          INTEGER,
                                       sensorProbeTemperatureArrayPort1Rearm
                                          INTEGER,
                                       sensorProbeTemperatureArrayPort1DegreeType
                                          INTEGER,
                                       sensorProbeTemperatureArrayPort1DegreeRaw
                                          INTEGER,
                                       sensorProbeTemperatureArrayPort1Offset
                                          INTEGER,
                                       sensorProbeTemperatureArrayPort1URL
                                          DisplayString,
                                       sensorProbeTemperatureArrayPort1OpenURL
                                          INTEGER,
                                       sensorProbeTemperatureArrayPort1DatacollectType
                                          INTEGER,
                                       sensorProbeTemperatureArrayPort1ContTimeHighCritical
                                          INTEGER,
                                       sensorProbeTemperatureArrayPort1ContTimeHighWarning
                                          INTEGER,
                                       sensorProbeTemperatureArrayPort1ContTimeNormal
                                          INTEGER,
                                       sensorProbeTemperatureArrayPort1ContTimeLowWarning
                                          INTEGER,
                                       sensorProbeTemperatureArrayPort1ContTimeLowCritical
                                          INTEGER,
                                       sensorProbeTemperatureArrayPort1ContTimeSensorError
                                          INTEGER,
                                       sensorProbeTemperatureArrayPort1Calendar
                                          INTEGER,
                                       sensorProbeThermostatTemperatureArrayPort1Index
                                          INTEGER,
                                       sensorProbeThermostatTemperatureArrayPort1Description
                                          DisplayString,
                                       sensorProbeThermostatTemperatureArrayPort1Value
                                          INTEGER,
                                       sensorProbeThermostatTemperatureArrayPort1Online
                                          INTEGER,
                                       sensorProbeThermostatTemperatureArrayPort1GoOnline
                                          INTEGER,
                                       sensorProbeThermostatTemperatureArrayPort1Mode
                                          INTEGER,
                                       sensorProbeThermostatTemperatureArrayPort1RelayControlPort
                                          INTEGER,
                                       sensorProbeThermostatTemperatureArrayPort1NormalAction1
                                          INTEGER,
                                       sensorProbeThermostatTemperatureArrayPort1HighLimit1
                                          INTEGER,
                                       sensorProbeThermostatTemperatureArrayPort1HighLimitAction1
                                          INTEGER,
                                       sensorProbeThermostatTemperatureArrayPort1LowLimit1
                                          INTEGER,
                                       sensorProbeThermostatTemperatureArrayPort1LowLimitAction1
                                          INTEGER,
                                       sensorProbeThermostatTemperatureArrayPort1NormalAction2
                                          INTEGER,
                                       sensorProbeThermostatTemperatureArrayPort1HighLimit2
                                          INTEGER,
                                       sensorProbeThermostatTemperatureArrayPort1HighLimitAction2
                                          INTEGER,
                                       sensorProbeThermostatTemperatureArrayPort1LowLimit2
                                          INTEGER,
                                       sensorProbeThermostatTemperatureArrayPort1LowLimitAction2
                                          INTEGER,
                                       sensorProbeThermostatTemperatureArrayPort1EnableTime
                                          DisplayString
                                    }

                                    sensorProbeTemperatureArrayPort1Index OBJECT-TYPE
                                       SYNTAX  INTEGER (0..7)
                                       ACCESS  read-only
                                       STATUS  mandatory
                                       DESCRIPTION
                                       "A unique value for each sensor TemperatureArray port."
                                       ::=  {  sensorProbeTemperatureArrayPort1Entry 1   }

                                    sensorProbeTemperatureArrayPort1Description OBJECT-TYPE
                                       SYNTAX  DisplayString
                                       ACCESS  read-write
                                       STATUS  mandatory
                                       DESCRIPTION
                                       "A Description of this sensor TemperatureArray"
                                       ::=  {  sensorProbeTemperatureArrayPort1Entry 2   }

                                    sensorProbeTemperatureArrayPort1Value OBJECT-TYPE
                                       SYNTAX  INTEGER
                                       ACCESS  read-only
                                       STATUS  mandatory
                                       DESCRIPTION
                                       "The value in this sensor"
                                       ::=  {  sensorProbeTemperatureArrayPort1Entry 3   }

                                    sensorProbeTemperatureArrayPort1Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort1Entry 4   }

                                    sensorProbeTemperatureArrayPort1Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort1Entry 5   }

                                    sensorProbeTemperatureArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort1Entry 6   }

                                    sensorProbeTemperatureArrayPort1HighWarning OBJECT-TYPE
                                       SYNTAX  INTEGER
                                       ACCESS  read-write
                                       STATUS  mandatory
                                       DESCRIPTION
                                       "How hot this  sensor gets before it sends a warning"
                                       ::=  {  sensorProbeTemperatureArrayPort1Entry 7   }

                                    sensorProbeTemperatureArrayPort1HighCritical OBJECT-TYPE
                                       SYNTAX  INTEGER
                                       ACCESS  read-write
                                       STATUS  mandatory
                                       DESCRIPTION
                                       "How hot this sensor gets before it sends a critical event"
                                       ::=  {  sensorProbeTemperatureArrayPort1Entry 8   }

                                    sensorProbeTemperatureArrayPort1LowWarning OBJECT-TYPE
                                       SYNTAX  INTEGER
                                       ACCESS  read-write
                                       STATUS  mandatory
                                       DESCRIPTION
                                       "How cold this sensor gets before it sends a warning"
                                       ::=  {  sensorProbeTemperatureArrayPort1Entry 9   }

                                    sensorProbeTemperatureArrayPort1LowCritical OBJECT-TYPE
                                       SYNTAX  INTEGER
                                       ACCESS  read-write
                                       STATUS  mandatory
                                       DESCRIPTION
                                       "How cold this sensor gets before it sends a critical event"
                                       ::=  {  sensorProbeTemperatureArrayPort1Entry 10   }

                                    sensorProbeTemperatureArrayPort1Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort1Entry 11   }

                                    sensorProbeTemperatureArrayPort1DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort1Entry 12   }

                                    sensorProbeTemperatureArrayPort1DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort1Entry 14   }

                                    sensorProbeTemperatureArrayPort1Offset OBJECT-TYPE
                                       SYNTAX  INTEGER
                                       ACCESS  read-write
                                       STATUS  mandatory
                                       DESCRIPTION
                                       "Offset reading"
                                       ::=  {  sensorProbeTemperatureArrayPort1Entry 15   }

                                    sensorProbeTemperatureArrayPort1URL OBJECT-TYPE
                                       SYNTAX  DisplayString
                                       ACCESS  read-write
                                       STATUS  mandatory
                                       DESCRIPTION
                                       "Sensor URL link."
                                       ::=  {  sensorProbeTemperatureArrayPort1Entry 16   }

                                    sensorProbeTemperatureArrayPort1OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort1Entry 17   }

                                    sensorProbeTemperatureArrayPort1DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort1Entry 18   }

                                    sensorProbeTemperatureArrayPort1ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort1Entry 19 }

                                    sensorProbeTemperatureArrayPort1ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort1Entry 20 }

                                    sensorProbeTemperatureArrayPort1ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort1Entry 21 }

                                    sensorProbeTemperatureArrayPort1ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort1Entry 22 }

                                    sensorProbeTemperatureArrayPort1ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort1Entry 23 }

                                    sensorProbeTemperatureArrayPort1ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort1Entry 24 }

                                    sensorProbeTemperatureArrayPort1Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort1Entry 25 }

                                    sensorProbeThermostatTemperatureArrayPort1Index OBJECT-TYPE
                                       SYNTAX  INTEGER
                                       ACCESS  read-only
                                       STATUS  mandatory
                                       DESCRIPTION
                                       "A unique value for each sensor thermostat port."
                                       ::= {  sensorProbeTemperatureArrayPort1Entry 26 }

                                    sensorProbeThermostatTemperatureArrayPort1Description OBJECT-TYPE
                                       SYNTAX  DisplayString
                                       ACCESS  read-write
                                       STATUS  mandatory
                                       DESCRIPTION
                                       "A Description of this sensor thermostat"
                                       ::= {  sensorProbeTemperatureArrayPort1Entry 27 }

                                    sensorProbeThermostatTemperatureArrayPort1Value OBJECT-TYPE
                                       SYNTAX  INTEGER
                                       ACCESS  read-only
                                       STATUS  mandatory
                                       DESCRIPTION
                                       "The value in this sensor"
                                       ::= {  sensorProbeTemperatureArrayPort1Entry 28 }

                                    sensorProbeThermostatTemperatureArrayPort1Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort1Entry 29 }

                                    sensorProbeThermostatTemperatureArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort1Entry 30 }

                                    sensorProbeThermostatTemperatureArrayPort1Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort1Entry 31 }

                                    sensorProbeThermostatTemperatureArrayPort1RelayControlPort OBJECT-TYPE
                                       SYNTAX INTEGER
                                       ACCESS read-write
                                       STATUS mandatory
                                       DESCRIPTION
                                       "To select a relay port to be controled by this thermostat sensor."
                                       ::= {  sensorProbeTemperatureArrayPort1Entry 32 }

                                    sensorProbeThermostatTemperatureArrayPort1NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort1Entry 33 }

                                    sensorProbeThermostatTemperatureArrayPort1HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort1Entry 34 }

                                    sensorProbeThermostatTemperatureArrayPort1HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort1Entry 35 }

                                    sensorProbeThermostatTemperatureArrayPort1LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort1Entry 36 }

                                    sensorProbeThermostatTemperatureArrayPort1LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort1Entry 37 }

                                    sensorProbeThermostatTemperatureArrayPort1NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort1Entry 38 }

                                    sensorProbeThermostatTemperatureArrayPort1HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort1Entry 39 }

                                    sensorProbeThermostatTemperatureArrayPort1HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort1Entry 40 }

                                    sensorProbeThermostatTemperatureArrayPort1LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort1Entry 41 }

                                    sensorProbeThermostatTemperatureArrayPort1LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort1Entry 42 }

                                    sensorProbeThermostatTemperatureArrayPort1EnableTime OBJECT-TYPE
                                       SYNTAX  DisplayString
                                       ACCESS  read-write
                                       STATUS  mandatory
                                       DESCRIPTION
                                       "Time to enable on Thermostat"
                                       ::=  {  sensorProbeTemperatureArrayPort1Entry 43 }

                           sensorProbeTemperatureArrayPort2 OBJECT IDENTIFIER ::= { sensorProbeTemperatureArraySensor 2  }
                              sensorProbeTemperatureArrayPort2Number OBJECT-TYPE
                                 SYNTAX INTEGER
                                 ACCESS read-only
                                 STATUS mandatory
                                 DESCRIPTION
                                 "The total number of port on the TemperatureArray."
                                 ::=  {  sensorProbeTemperatureArrayPort2 1   }

                              sensorProbeTemperatureArrayPort2Table OBJECT-TYPE
                                 SYNTAX  SEQUENCE OF SensorProbeTemperatureArrayPort2Entry
                                 ACCESS  not-accessible
                                 STATUS  mandatory
                                 DESCRIPTION
                                 "This table contains the data for every Switch Sensor in the SensorArray. Each row in the table contains data for a different Switch Sensor."
                                 ::=  {  sensorProbeTemperatureArrayPort2 2   }

                                 sensorProbeTemperatureArrayPort2Entry OBJECT-TYPE
                                    SYNTAX  SensorProbeTemperatureArrayPort2Entry
                                    ACCESS  not-accessible
                                    STATUS  mandatory
                                    DESCRIPTION
                                    "This is an entry in the sensorProbeTemperatureArrayPort2 Table"
                                    INDEX         { sensorProbeTemperatureArrayPort2Index }
                                    ::=  { sensorProbeTemperatureArrayPort2Table 1 }

                                    SensorProbeTemperatureArrayPort2Entry ::= SEQUENCE {
                                       sensorProbeTemperatureArrayPort2Index
                                          INTEGER,
                                       sensorProbeTemperatureArrayPort2Description
                                          DisplayString,
                                       sensorProbeTemperatureArrayPort2Value
                                          INTEGER,
                                       sensorProbeTemperatureArrayPort2Status
                                          INTEGER,
                                       sensorProbeTemperatureArrayPort2Online
                                          INTEGER,
                                       sensorProbeTemperatureArrayPort2GoOnline
                                          INTEGER,
                                       sensorProbeTemperatureArrayPort2HighWarning
                                          INTEGER,
                                       sensorProbeTemperatureArrayPort2HighCritical
                                          INTEGER,
                                       sensorProbeTemperatureArrayPort2LowWarning
                                          INTEGER,
                                       sensorProbeTemperatureArrayPort2LowCritical
                                          INTEGER,
                                       sensorProbeTemperatureArrayPort2Rearm
                                          INTEGER,
                                       sensorProbeTemperatureArrayPort2DegreeType
                                          INTEGER,
                                       sensorProbeTemperatureArrayPort2DegreeRaw
                                          INTEGER,
                                       sensorProbeTemperatureArrayPort2Offset
                                          INTEGER,
                                       sensorProbeTemperatureArrayPort2URL
                                          DisplayString,
                                       sensorProbeTemperatureArrayPort2OpenURL
                                          INTEGER,
                                       sensorProbeTemperatureArrayPort2DatacollectType
                                          INTEGER,
                                       sensorProbeTemperatureArrayPort2ContTimeHighCritical
                                          INTEGER,
                                       sensorProbeTemperatureArrayPort2ContTimeHighWarning
                                          INTEGER,
                                       sensorProbeTemperatureArrayPort2ContTimeNormal
                                          INTEGER,
                                       sensorProbeTemperatureArrayPort2ContTimeLowWarning
                                          INTEGER,
                                       sensorProbeTemperatureArrayPort2ContTimeLowCritical
                                          INTEGER,
                                       sensorProbeTemperatureArrayPort2ContTimeSensorError
                                          INTEGER,
                                       sensorProbeTemperatureArrayPort2Calendar
                                          INTEGER,
                                       sensorProbeThermostatTemperatureArrayPort2Index
                                          INTEGER,
                                       sensorProbeThermostatTemperatureArrayPort2Description
                                          DisplayString,
                                       sensorProbeThermostatTemperatureArrayPort2Value
                                          INTEGER,
                                       sensorProbeThermostatTemperatureArrayPort2Online
                                          INTEGER,
                                       sensorProbeThermostatTemperatureArrayPort2GoOnline
                                          INTEGER,
                                       sensorProbeThermostatTemperatureArrayPort2Mode
                                          INTEGER,
                                       sensorProbeThermostatTemperatureArrayPort2RelayControlPort
                                          INTEGER,
                                       sensorProbeThermostatTemperatureArrayPort2NormalAction1
                                          INTEGER,
                                       sensorProbeThermostatTemperatureArrayPort2HighLimit1
                                          INTEGER,
                                       sensorProbeThermostatTemperatureArrayPort2HighLimitAction1
                                          INTEGER,
                                       sensorProbeThermostatTemperatureArrayPort2LowLimit1
                                          INTEGER,
                                       sensorProbeThermostatTemperatureArrayPort2LowLimitAction1
                                          INTEGER,
                                       sensorProbeThermostatTemperatureArrayPort2NormalAction2
                                          INTEGER,
                                       sensorProbeThermostatTemperatureArrayPort2HighLimit2
                                          INTEGER,
                                       sensorProbeThermostatTemperatureArrayPort2HighLimitAction2
                                          INTEGER,
                                       sensorProbeThermostatTemperatureArrayPort2LowLimit2
                                          INTEGER,
                                       sensorProbeThermostatTemperatureArrayPort2LowLimitAction2
                                          INTEGER,
                                       sensorProbeThermostatTemperatureArrayPort2EnableTime
                                          DisplayString
                                    }

                                    sensorProbeTemperatureArrayPort2Index OBJECT-TYPE
                                       SYNTAX  INTEGER (0..7)
                                       ACCESS  read-only
                                       STATUS  mandatory
                                       DESCRIPTION
                                       "A unique value for each sensor TemperatureArray port."
                                       ::=  {  sensorProbeTemperatureArrayPort2Entry 1   }

                                    sensorProbeTemperatureArrayPort2Description OBJECT-TYPE
                                       SYNTAX  DisplayString
                                       ACCESS  read-write
                                       STATUS  mandatory
                                       DESCRIPTION
                                       "A Description of this sensor TemperatureArray"
                                       ::=  {  sensorProbeTemperatureArrayPort2Entry 2   }

                                    sensorProbeTemperatureArrayPort2Value OBJECT-TYPE
                                       SYNTAX  INTEGER
                                       ACCESS  read-only
                                       STATUS  mandatory
                                       DESCRIPTION
                                       "The value in this sensor"
                                       ::=  {  sensorProbeTemperatureArrayPort2Entry 3   }

                                    sensorProbeTemperatureArrayPort2Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort2Entry 4   }

                                    sensorProbeTemperatureArrayPort2Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort2Entry 5   }

                                    sensorProbeTemperatureArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort2Entry 6   }

                                    sensorProbeTemperatureArrayPort2HighWarning OBJECT-TYPE
                                       SYNTAX  INTEGER
                                       ACCESS  read-write
                                       STATUS  mandatory
                                       DESCRIPTION
                                       "How hot this  sensor gets before it sends a warning"
                                       ::=  {  sensorProbeTemperatureArrayPort2Entry 7   }

                                    sensorProbeTemperatureArrayPort2HighCritical OBJECT-TYPE
                                       SYNTAX  INTEGER
                                       ACCESS  read-write
                                       STATUS  mandatory
                                       DESCRIPTION
                                       "How hot this sensor gets before it sends a critical event"
                                       ::=  {  sensorProbeTemperatureArrayPort2Entry 8   }

                                    sensorProbeTemperatureArrayPort2LowWarning OBJECT-TYPE
                                       SYNTAX  INTEGER
                                       ACCESS  read-write
                                       STATUS  mandatory
                                       DESCRIPTION
                                       "How cold this sensor gets before it sends a warning"
                                       ::=  {  sensorProbeTemperatureArrayPort2Entry 9   }

                                    sensorProbeTemperatureArrayPort2LowCritical OBJECT-TYPE
                                       SYNTAX  INTEGER
                                       ACCESS  read-write
                                       STATUS  mandatory
                                       DESCRIPTION
                                       "How cold this sensor gets before it sends a critical event"
                                       ::=  {  sensorProbeTemperatureArrayPort2Entry 10   }

                                    sensorProbeTemperatureArrayPort2Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort2Entry 11   }

                                    sensorProbeTemperatureArrayPort2DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort2Entry 12   }

                                    sensorProbeTemperatureArrayPort2DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort2Entry 14   }

                                    sensorProbeTemperatureArrayPort2Offset OBJECT-TYPE
                                       SYNTAX  INTEGER
                                       ACCESS  read-write
                                       STATUS  mandatory
                                       DESCRIPTION
                                       "Offset reading"
                                       ::=  {  sensorProbeTemperatureArrayPort2Entry 15   }

                                    sensorProbeTemperatureArrayPort2URL OBJECT-TYPE
                                       SYNTAX  DisplayString
                                       ACCESS  read-write
                                       STATUS  mandatory
                                       DESCRIPTION
                                       "Sensor URL link."
                                       ::=  {  sensorProbeTemperatureArrayPort2Entry 16   }

                                    sensorProbeTemperatureArrayPort2OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort2Entry 17   }

                                    sensorProbeTemperatureArrayPort2DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort2Entry 18   }

                                    sensorProbeTemperatureArrayPort2ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort2Entry 19 }

                                    sensorProbeTemperatureArrayPort2ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort2Entry 20 }

                                    sensorProbeTemperatureArrayPort2ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort2Entry 21 }

                                    sensorProbeTemperatureArrayPort2ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort2Entry 22 }

                                    sensorProbeTemperatureArrayPort2ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort2Entry 23 }

                                    sensorProbeTemperatureArrayPort2ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort2Entry 24 }

                                    sensorProbeTemperatureArrayPort2Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort2Entry 25 }

                                    sensorProbeThermostatTemperatureArrayPort2Index OBJECT-TYPE
                                       SYNTAX  INTEGER
                                       ACCESS  read-only
                                       STATUS  mandatory
                                       DESCRIPTION
                                       "A unique value for each sensor thermostat port."
                                       ::= {  sensorProbeTemperatureArrayPort2Entry 26 }

                                    sensorProbeThermostatTemperatureArrayPort2Description OBJECT-TYPE
                                       SYNTAX  DisplayString
                                       ACCESS  read-write
                                       STATUS  mandatory
                                       DESCRIPTION
                                       "A Description of this sensor thermostat"
                                       ::= {  sensorProbeTemperatureArrayPort2Entry 27 }

                                    sensorProbeThermostatTemperatureArrayPort2Value OBJECT-TYPE
                                       SYNTAX  INTEGER
                                       ACCESS  read-only
                                       STATUS  mandatory
                                       DESCRIPTION
                                       "The value in this sensor"
                                       ::= {  sensorProbeTemperatureArrayPort2Entry 28 }

                                    sensorProbeThermostatTemperatureArrayPort2Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort2Entry 29 }

                                    sensorProbeThermostatTemperatureArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort2Entry 30 }

                                    sensorProbeThermostatTemperatureArrayPort2Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort2Entry 31 }

                                    sensorProbeThermostatTemperatureArrayPort2RelayControlPort OBJECT-TYPE
                                       SYNTAX INTEGER
                                       ACCESS read-write
                                       STATUS mandatory
                                       DESCRIPTION
                                       "To select a relay port to be controled by this thermostat sensor."
                                       ::= {  sensorProbeTemperatureArrayPort2Entry 32 }

                                    sensorProbeThermostatTemperatureArrayPort2NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort2Entry 33 }

                                    sensorProbeThermostatTemperatureArrayPort2HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort2Entry 34 }

                                    sensorProbeThermostatTemperatureArrayPort2HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort2Entry 35 }

                                    sensorProbeThermostatTemperatureArrayPort2LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort2Entry 36 }

                                    sensorProbeThermostatTemperatureArrayPort2LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort2Entry 37 }

                                    sensorProbeThermostatTemperatureArrayPort2NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort2Entry 38 }

                                    sensorProbeThermostatTemperatureArrayPort2HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort2Entry 39 }

                                    sensorProbeThermostatTemperatureArrayPort2HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort2Entry 40 }

                                    sensorProbeThermostatTemperatureArrayPort2LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort2Entry 41 }

                                    sensorProbeThermostatTemperatureArrayPort2LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort2Entry 42 }

                                    sensorProbeThermostatTemperatureArrayPort2EnableTime OBJECT-TYPE
                                       SYNTAX  DisplayString
                                       ACCESS  read-write
                                       STATUS  mandatory
                                       DESCRIPTION
                                       "Time to enable on Thermostat"
                                       ::=  {  sensorProbeTemperatureArrayPort2Entry 43 }

                           sensorProbeTemperatureArrayPort3 OBJECT IDENTIFIER ::= { sensorProbeTemperatureArraySensor 3  }
                              sensorProbeTemperatureArrayPort3Number OBJECT-TYPE
                                 SYNTAX INTEGER
                                 ACCESS read-only
                                 STATUS mandatory
                                 DESCRIPTION
                                 "The total number of port on the TemperatureArray."
                                 ::=  {  sensorProbeTemperatureArrayPort3 1   }

                              sensorProbeTemperatureArrayPort3Table OBJECT-TYPE
                                 SYNTAX  SEQUENCE OF SensorProbeTemperatureArrayPort3Entry
                                 ACCESS  not-accessible
                                 STATUS  mandatory
                                 DESCRIPTION
                                 "This table contains the data for every Switch Sensor in the SensorArray. Each row in the table contains data for a different Switch Sensor."
                                 ::=  {  sensorProbeTemperatureArrayPort3 2   }

                                 sensorProbeTemperatureArrayPort3Entry OBJECT-TYPE
                                    SYNTAX  SensorProbeTemperatureArrayPort3Entry
                                    ACCESS  not-accessible
                                    STATUS  mandatory
                                    DESCRIPTION
                                    "This is an entry in the sensorProbeTemperatureArrayPort3 Table"
                                    INDEX         { sensorProbeTemperatureArrayPort3Index }
                                    ::=  { sensorProbeTemperatureArrayPort3Table 1 }

                                    SensorProbeTemperatureArrayPort3Entry ::= SEQUENCE {
                                       sensorProbeTemperatureArrayPort3Index
                                          INTEGER,
                                       sensorProbeTemperatureArrayPort3Description
                                          DisplayString,
                                       sensorProbeTemperatureArrayPort3Value
                                          INTEGER,
                                       sensorProbeTemperatureArrayPort3Status
                                          INTEGER,
                                       sensorProbeTemperatureArrayPort3Online
                                          INTEGER,
                                       sensorProbeTemperatureArrayPort3GoOnline
                                          INTEGER,
                                       sensorProbeTemperatureArrayPort3HighWarning
                                          INTEGER,
                                       sensorProbeTemperatureArrayPort3HighCritical
                                          INTEGER,
                                       sensorProbeTemperatureArrayPort3LowWarning
                                          INTEGER,
                                       sensorProbeTemperatureArrayPort3LowCritical
                                          INTEGER,
                                       sensorProbeTemperatureArrayPort3Rearm
                                          INTEGER,
                                       sensorProbeTemperatureArrayPort3DegreeType
                                          INTEGER,
                                       sensorProbeTemperatureArrayPort3DegreeRaw
                                          INTEGER,
                                       sensorProbeTemperatureArrayPort3Offset
                                          INTEGER,
                                       sensorProbeTemperatureArrayPort3URL
                                          DisplayString,
                                       sensorProbeTemperatureArrayPort3OpenURL
                                          INTEGER,
                                       sensorProbeTemperatureArrayPort3DatacollectType
                                          INTEGER,
                                       sensorProbeTemperatureArrayPort3ContTimeHighCritical
                                          INTEGER,
                                       sensorProbeTemperatureArrayPort3ContTimeHighWarning
                                          INTEGER,
                                       sensorProbeTemperatureArrayPort3ContTimeNormal
                                          INTEGER,
                                       sensorProbeTemperatureArrayPort3ContTimeLowWarning
                                          INTEGER,
                                       sensorProbeTemperatureArrayPort3ContTimeLowCritical
                                          INTEGER,
                                       sensorProbeTemperatureArrayPort3ContTimeSensorError
                                          INTEGER,
                                       sensorProbeTemperatureArrayPort3Calendar
                                          INTEGER,
                                       sensorProbeThermostatTemperatureArrayPort3Index
                                          INTEGER,
                                       sensorProbeThermostatTemperatureArrayPort3Description
                                          DisplayString,
                                       sensorProbeThermostatTemperatureArrayPort3Value
                                          INTEGER,
                                       sensorProbeThermostatTemperatureArrayPort3Online
                                          INTEGER,
                                       sensorProbeThermostatTemperatureArrayPort3GoOnline
                                          INTEGER,
                                       sensorProbeThermostatTemperatureArrayPort3Mode
                                          INTEGER,
                                       sensorProbeThermostatTemperatureArrayPort3RelayControlPort
                                          INTEGER,
                                       sensorProbeThermostatTemperatureArrayPort3NormalAction1
                                          INTEGER,
                                       sensorProbeThermostatTemperatureArrayPort3HighLimit1
                                          INTEGER,
                                       sensorProbeThermostatTemperatureArrayPort3HighLimitAction1
                                          INTEGER,
                                       sensorProbeThermostatTemperatureArrayPort3LowLimit1
                                          INTEGER,
                                       sensorProbeThermostatTemperatureArrayPort3LowLimitAction1
                                          INTEGER,
                                       sensorProbeThermostatTemperatureArrayPort3NormalAction2
                                          INTEGER,
                                       sensorProbeThermostatTemperatureArrayPort3HighLimit2
                                          INTEGER,
                                       sensorProbeThermostatTemperatureArrayPort3HighLimitAction2
                                          INTEGER,
                                       sensorProbeThermostatTemperatureArrayPort3LowLimit2
                                          INTEGER,
                                       sensorProbeThermostatTemperatureArrayPort3LowLimitAction2
                                          INTEGER,
                                       sensorProbeThermostatTemperatureArrayPort3EnableTime
                                          DisplayString
                                    }

                                    sensorProbeTemperatureArrayPort3Index OBJECT-TYPE
                                       SYNTAX  INTEGER (0..7)
                                       ACCESS  read-only
                                       STATUS  mandatory
                                       DESCRIPTION
                                       "A unique value for each sensor TemperatureArray port."
                                       ::=  {  sensorProbeTemperatureArrayPort3Entry 1   }

                                    sensorProbeTemperatureArrayPort3Description OBJECT-TYPE
                                       SYNTAX  DisplayString
                                       ACCESS  read-write
                                       STATUS  mandatory
                                       DESCRIPTION
                                       "A Description of this sensor TemperatureArray"
                                       ::=  {  sensorProbeTemperatureArrayPort3Entry 2   }

                                    sensorProbeTemperatureArrayPort3Value OBJECT-TYPE
                                       SYNTAX  INTEGER
                                       ACCESS  read-only
                                       STATUS  mandatory
                                       DESCRIPTION
                                       "The value in this sensor"
                                       ::=  {  sensorProbeTemperatureArrayPort3Entry 3   }

                                    sensorProbeTemperatureArrayPort3Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort3Entry 4   }

                                    sensorProbeTemperatureArrayPort3Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort3Entry 5   }

                                    sensorProbeTemperatureArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort3Entry 6   }

                                    sensorProbeTemperatureArrayPort3HighWarning OBJECT-TYPE
                                       SYNTAX  INTEGER
                                       ACCESS  read-write
                                       STATUS  mandatory
                                       DESCRIPTION
                                       "How hot this  sensor gets before it sends a warning"
                                       ::=  {  sensorProbeTemperatureArrayPort3Entry 7   }

                                    sensorProbeTemperatureArrayPort3HighCritical OBJECT-TYPE
                                       SYNTAX  INTEGER
                                       ACCESS  read-write
                                       STATUS  mandatory
                                       DESCRIPTION
                                       "How hot this sensor gets before it sends a critical event"
                                       ::=  {  sensorProbeTemperatureArrayPort3Entry 8   }

                                    sensorProbeTemperatureArrayPort3LowWarning OBJECT-TYPE
                                       SYNTAX  INTEGER
                                       ACCESS  read-write
                                       STATUS  mandatory
                                       DESCRIPTION
                                       "How cold this sensor gets before it sends a warning"
                                       ::=  {  sensorProbeTemperatureArrayPort3Entry 9   }

                                    sensorProbeTemperatureArrayPort3LowCritical OBJECT-TYPE
                                       SYNTAX  INTEGER
                                       ACCESS  read-write
                                       STATUS  mandatory
                                       DESCRIPTION
                                       "How cold this sensor gets before it sends a critical event"
                                       ::=  {  sensorProbeTemperatureArrayPort3Entry 10   }

                                    sensorProbeTemperatureArrayPort3Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort3Entry 11   }

                                    sensorProbeTemperatureArrayPort3DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort3Entry 12   }

                                    sensorProbeTemperatureArrayPort3DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort3Entry 14   }

                                    sensorProbeTemperatureArrayPort3Offset OBJECT-TYPE
                                       SYNTAX  INTEGER
                                       ACCESS  read-write
                                       STATUS  mandatory
                                       DESCRIPTION
                                       "Offset reading"
                                       ::=  {  sensorProbeTemperatureArrayPort3Entry 15   }

                                    sensorProbeTemperatureArrayPort3URL OBJECT-TYPE
                                       SYNTAX  DisplayString
                                       ACCESS  read-write
                                       STATUS  mandatory
                                       DESCRIPTION
                                       "Sensor URL link."
                                       ::=  {  sensorProbeTemperatureArrayPort3Entry 16   }

                                    sensorProbeTemperatureArrayPort3OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort3Entry 17   }

                                    sensorProbeTemperatureArrayPort3DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort3Entry 18   }

                                    sensorProbeTemperatureArrayPort3ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort3Entry 19 }

                                    sensorProbeTemperatureArrayPort3ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort3Entry 20 }

                                    sensorProbeTemperatureArrayPort3ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort3Entry 21 }

                                    sensorProbeTemperatureArrayPort3ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort3Entry 22 }

                                    sensorProbeTemperatureArrayPort3ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort3Entry 23 }

                                    sensorProbeTemperatureArrayPort3ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort3Entry 24 }

                                    sensorProbeTemperatureArrayPort3Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort3Entry 25 }

                                    sensorProbeThermostatTemperatureArrayPort3Index OBJECT-TYPE
                                       SYNTAX  INTEGER
                                       ACCESS  read-only
                                       STATUS  mandatory
                                       DESCRIPTION
                                       "A unique value for each sensor thermostat port."
                                       ::= {  sensorProbeTemperatureArrayPort3Entry 26 }

                                    sensorProbeThermostatTemperatureArrayPort3Description OBJECT-TYPE
                                       SYNTAX  DisplayString
                                       ACCESS  read-write
                                       STATUS  mandatory
                                       DESCRIPTION
                                       "A Description of this sensor thermostat"
                                       ::= {  sensorProbeTemperatureArrayPort3Entry 27 }

                                    sensorProbeThermostatTemperatureArrayPort3Value OBJECT-TYPE
                                       SYNTAX  INTEGER
                                       ACCESS  read-only
                                       STATUS  mandatory
                                       DESCRIPTION
                                       "The value in this sensor"
                                       ::= {  sensorProbeTemperatureArrayPort3Entry 28 }

                                    sensorProbeThermostatTemperatureArrayPort3Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort3Entry 29 }

                                    sensorProbeThermostatTemperatureArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort3Entry 30 }

                                    sensorProbeThermostatTemperatureArrayPort3Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort3Entry 31 }

                                    sensorProbeThermostatTemperatureArrayPort3RelayControlPort OBJECT-TYPE
                                       SYNTAX INTEGER
                                       ACCESS read-write
                                       STATUS mandatory
                                       DESCRIPTION
                                       "To select a relay port to be controled by this thermostat sensor."
                                       ::= {  sensorProbeTemperatureArrayPort3Entry 32 }

                                    sensorProbeThermostatTemperatureArrayPort3NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort3Entry 33 }

                                    sensorProbeThermostatTemperatureArrayPort3HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort3Entry 34 }

                                    sensorProbeThermostatTemperatureArrayPort3HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort3Entry 35 }

                                    sensorProbeThermostatTemperatureArrayPort3LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort3Entry 36 }

                                    sensorProbeThermostatTemperatureArrayPort3LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort3Entry 37 }

                                    sensorProbeThermostatTemperatureArrayPort3NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort3Entry 38 }

                                    sensorProbeThermostatTemperatureArrayPort3HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort3Entry 39 }

                                    sensorProbeThermostatTemperatureArrayPort3HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort3Entry 40 }

                                    sensorProbeThermostatTemperatureArrayPort3LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort3Entry 41 }

                                    sensorProbeThermostatTemperatureArrayPort3LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort3Entry 42 }

                                    sensorProbeThermostatTemperatureArrayPort3EnableTime OBJECT-TYPE
                                       SYNTAX  DisplayString
                                       ACCESS  read-write
                                       STATUS  mandatory
                                       DESCRIPTION
                                       "Time to enable on Thermostat"
                                       ::=  {  sensorProbeTemperatureArrayPort3Entry 43 }


                           sensorProbeTemperatureArrayPort4 OBJECT IDENTIFIER ::= { sensorProbeTemperatureArraySensor 4  }
                              sensorProbeTemperatureArrayPort4Number OBJECT-TYPE
                                 SYNTAX INTEGER
                                 ACCESS read-only
                                 STATUS mandatory
                                 DESCRIPTION
                                 "The total number of port on the TemperatureArray."
                                 ::=  {  sensorProbeTemperatureArrayPort4 1   }

                              sensorProbeTemperatureArrayPort4Table OBJECT-TYPE
                                 SYNTAX  SEQUENCE OF SensorProbeTemperatureArrayPort4Entry
                                 ACCESS  not-accessible
                                 STATUS  mandatory
                                 DESCRIPTION
                                 "This table contains the data for every Switch Sensor in the SensorArray. Each row in the table contains data for a different Switch Sensor."
                                 ::=  {  sensorProbeTemperatureArrayPort4 2   }

                                 sensorProbeTemperatureArrayPort4Entry OBJECT-TYPE
                                    SYNTAX  SensorProbeTemperatureArrayPort4Entry
                                    ACCESS  not-accessible
                                    STATUS  mandatory
                                    DESCRIPTION
                                    "This is an entry in the sensorProbeTemperatureArrayPort4 Table"
                                    INDEX         { sensorProbeTemperatureArrayPort4Index }
                                    ::=  { sensorProbeTemperatureArrayPort4Table 1 }

                                    SensorProbeTemperatureArrayPort4Entry ::= SEQUENCE {
                                       sensorProbeTemperatureArrayPort4Index
                                          INTEGER,
                                       sensorProbeTemperatureArrayPort4Description
                                          DisplayString,
                                       sensorProbeTemperatureArrayPort4Value
                                          INTEGER,
                                       sensorProbeTemperatureArrayPort4Status
                                          INTEGER,
                                       sensorProbeTemperatureArrayPort4Online
                                          INTEGER,
                                       sensorProbeTemperatureArrayPort4GoOnline
                                          INTEGER,
                                       sensorProbeTemperatureArrayPort4HighWarning
                                          INTEGER,
                                       sensorProbeTemperatureArrayPort4HighCritical
                                          INTEGER,
                                       sensorProbeTemperatureArrayPort4LowWarning
                                          INTEGER,
                                       sensorProbeTemperatureArrayPort4LowCritical
                                          INTEGER,
                                       sensorProbeTemperatureArrayPort4Rearm
                                          INTEGER,
                                       sensorProbeTemperatureArrayPort4DegreeType
                                          INTEGER,
                                       sensorProbeTemperatureArrayPort4DegreeRaw
                                          INTEGER,
                                       sensorProbeTemperatureArrayPort4Offset
                                          INTEGER,
                                       sensorProbeTemperatureArrayPort4URL
                                          DisplayString,
                                       sensorProbeTemperatureArrayPort4OpenURL
                                          INTEGER,
                                       sensorProbeTemperatureArrayPort4DatacollectType
                                          INTEGER,
                                       sensorProbeTemperatureArrayPort4ContTimeHighCritical
                                          INTEGER,
                                       sensorProbeTemperatureArrayPort4ContTimeHighWarning
                                          INTEGER,
                                       sensorProbeTemperatureArrayPort4ContTimeNormal
                                          INTEGER,
                                       sensorProbeTemperatureArrayPort4ContTimeLowWarning
                                          INTEGER,
                                       sensorProbeTemperatureArrayPort4ContTimeLowCritical
                                          INTEGER,
                                       sensorProbeTemperatureArrayPort4ContTimeSensorError
                                          INTEGER,
                                       sensorProbeTemperatureArrayPort4Calendar
                                          INTEGER,
                                       sensorProbeThermostatTemperatureArrayPort4Index
                                          INTEGER,
                                       sensorProbeThermostatTemperatureArrayPort4Description
                                          DisplayString,
                                       sensorProbeThermostatTemperatureArrayPort4Value
                                          INTEGER,
                                       sensorProbeThermostatTemperatureArrayPort4Online
                                          INTEGER,
                                       sensorProbeThermostatTemperatureArrayPort4GoOnline
                                          INTEGER,
                                       sensorProbeThermostatTemperatureArrayPort4Mode
                                          INTEGER,
                                       sensorProbeThermostatTemperatureArrayPort4RelayControlPort
                                          INTEGER,
                                       sensorProbeThermostatTemperatureArrayPort4NormalAction1
                                          INTEGER,
                                       sensorProbeThermostatTemperatureArrayPort4HighLimit1
                                          INTEGER,
                                       sensorProbeThermostatTemperatureArrayPort4HighLimitAction1
                                          INTEGER,
                                       sensorProbeThermostatTemperatureArrayPort4LowLimit1
                                          INTEGER,
                                       sensorProbeThermostatTemperatureArrayPort4LowLimitAction1
                                          INTEGER,
                                       sensorProbeThermostatTemperatureArrayPort4NormalAction2
                                          INTEGER,
                                       sensorProbeThermostatTemperatureArrayPort4HighLimit2
                                          INTEGER,
                                       sensorProbeThermostatTemperatureArrayPort4HighLimitAction2
                                          INTEGER,
                                       sensorProbeThermostatTemperatureArrayPort4LowLimit2
                                          INTEGER,
                                       sensorProbeThermostatTemperatureArrayPort4LowLimitAction2
                                          INTEGER,
                                       sensorProbeThermostatTemperatureArrayPort4EnableTime
                                          DisplayString
                                    }

                                    sensorProbeTemperatureArrayPort4Index OBJECT-TYPE
                                       SYNTAX  INTEGER (0..7)
                                       ACCESS  read-only
                                       STATUS  mandatory
                                       DESCRIPTION
                                       "A unique value for each sensor TemperatureArray port."
                                       ::=  {  sensorProbeTemperatureArrayPort4Entry 1   }

                                    sensorProbeTemperatureArrayPort4Description OBJECT-TYPE
                                       SYNTAX  DisplayString
                                       ACCESS  read-write
                                       STATUS  mandatory
                                       DESCRIPTION
                                       "A Description of this sensor TemperatureArray"
                                       ::=  {  sensorProbeTemperatureArrayPort4Entry 2   }

                                    sensorProbeTemperatureArrayPort4Value OBJECT-TYPE
                                       SYNTAX  INTEGER
                                       ACCESS  read-only
                                       STATUS  mandatory
                                       DESCRIPTION
                                       "The value in this sensor"
                                       ::=  {  sensorProbeTemperatureArrayPort4Entry 3   }

                                    sensorProbeTemperatureArrayPort4Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort4Entry 4   }

                                    sensorProbeTemperatureArrayPort4Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort4Entry 5   }

                                    sensorProbeTemperatureArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort4Entry 6   }

                                    sensorProbeTemperatureArrayPort4HighWarning OBJECT-TYPE
                                       SYNTAX  INTEGER
                                       ACCESS  read-write
                                       STATUS  mandatory
                                       DESCRIPTION
                                       "How hot this  sensor gets before it sends a warning"
                                       ::=  {  sensorProbeTemperatureArrayPort4Entry 7   }

                                    sensorProbeTemperatureArrayPort4HighCritical OBJECT-TYPE
                                       SYNTAX  INTEGER
                                       ACCESS  read-write
                                       STATUS  mandatory
                                       DESCRIPTION
                                       "How hot this sensor gets before it sends a critical event"
                                       ::=  {  sensorProbeTemperatureArrayPort4Entry 8   }

                                    sensorProbeTemperatureArrayPort4LowWarning OBJECT-TYPE
                                       SYNTAX  INTEGER
                                       ACCESS  read-write
                                       STATUS  mandatory
                                       DESCRIPTION
                                       "How cold this sensor gets before it sends a warning"
                                       ::=  {  sensorProbeTemperatureArrayPort4Entry 9   }

                                    sensorProbeTemperatureArrayPort4LowCritical OBJECT-TYPE
                                       SYNTAX  INTEGER
                                       ACCESS  read-write
                                       STATUS  mandatory
                                       DESCRIPTION
                                       "How cold this sensor gets before it sends a critical event"
                                       ::=  {  sensorProbeTemperatureArrayPort4Entry 10   }

                                    sensorProbeTemperatureArrayPort4Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort4Entry 11   }

                                    sensorProbeTemperatureArrayPort4DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort4Entry 12   }

                                    sensorProbeTemperatureArrayPort4DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort4Entry 14   }

                                    sensorProbeTemperatureArrayPort4Offset OBJECT-TYPE
                                       SYNTAX  INTEGER
                                       ACCESS  read-write
                                       STATUS  mandatory
                                       DESCRIPTION
                                       "Offset reading"
                                       ::=  {  sensorProbeTemperatureArrayPort4Entry 15   }

                                    sensorProbeTemperatureArrayPort4URL OBJECT-TYPE
                                       SYNTAX  DisplayString
                                       ACCESS  read-write
                                       STATUS  mandatory
                                       DESCRIPTION
                                       "Sensor URL link."
                                       ::=  {  sensorProbeTemperatureArrayPort4Entry 16   }

                                    sensorProbeTemperatureArrayPort4OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort4Entry 17   }

                                    sensorProbeTemperatureArrayPort4DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort4Entry 18   }

                                    sensorProbeTemperatureArrayPort4ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort4Entry 19 }

                                    sensorProbeTemperatureArrayPort4ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort4Entry 20 }

                                    sensorProbeTemperatureArrayPort4ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort4Entry 21 }

                                    sensorProbeTemperatureArrayPort4ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort4Entry 22 }

                                    sensorProbeTemperatureArrayPort4ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort4Entry 23 }

                                    sensorProbeTemperatureArrayPort4ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort4Entry 24 }

                                    sensorProbeTemperatureArrayPort4Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort4Entry 25 }

                                    sensorProbeThermostatTemperatureArrayPort4Index OBJECT-TYPE
                                       SYNTAX  INTEGER
                                       ACCESS  read-only
                                       STATUS  mandatory
                                       DESCRIPTION
                                       "A unique value for each sensor thermostat port."
                                       ::= {  sensorProbeTemperatureArrayPort4Entry 26 }

                                    sensorProbeThermostatTemperatureArrayPort4Description OBJECT-TYPE
                                       SYNTAX  DisplayString
                                       ACCESS  read-write
                                       STATUS  mandatory
                                       DESCRIPTION
                                       "A Description of this sensor thermostat"
                                       ::= {  sensorProbeTemperatureArrayPort4Entry 27 }

                                    sensorProbeThermostatTemperatureArrayPort4Value OBJECT-TYPE
                                       SYNTAX  INTEGER
                                       ACCESS  read-only
                                       STATUS  mandatory
                                       DESCRIPTION
                                       "The value in this sensor"
                                       ::= {  sensorProbeTemperatureArrayPort4Entry 28 }

                                    sensorProbeThermostatTemperatureArrayPort4Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort4Entry 29 }

                                    sensorProbeThermostatTemperatureArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort4Entry 30 }

                                    sensorProbeThermostatTemperatureArrayPort4Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort4Entry 31 }

                                    sensorProbeThermostatTemperatureArrayPort4RelayControlPort OBJECT-TYPE
                                       SYNTAX INTEGER
                                       ACCESS read-write
                                       STATUS mandatory
                                       DESCRIPTION
                                       "To select a relay port to be controled by this thermostat sensor."
                                       ::= {  sensorProbeTemperatureArrayPort4Entry 32 }

                                    sensorProbeThermostatTemperatureArrayPort4NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort4Entry 33 }

                                    sensorProbeThermostatTemperatureArrayPort4HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort4Entry 34 }

                                    sensorProbeThermostatTemperatureArrayPort4HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort4Entry 35 }

                                    sensorProbeThermostatTemperatureArrayPort4LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort4Entry 36 }

                                    sensorProbeThermostatTemperatureArrayPort4LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort4Entry 37 }

                                    sensorProbeThermostatTemperatureArrayPort4NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort4Entry 38 }

                                    sensorProbeThermostatTemperatureArrayPort4HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort4Entry 39 }

                                    sensorProbeThermostatTemperatureArrayPort4HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort4Entry 40 }

                                    sensorProbeThermostatTemperatureArrayPort4LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort4Entry 41 }

                                    sensorProbeThermostatTemperatureArrayPort4LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort4Entry 42 }

                                    sensorProbeThermostatTemperatureArrayPort4EnableTime OBJECT-TYPE
                                       SYNTAX  DisplayString
                                       ACCESS  read-write
                                       STATUS  mandatory
                                       DESCRIPTION
                                       "Time to enable on Thermostat"
                                       ::=  {  sensorProbeTemperatureArrayPort4Entry 43 }

                           sensorProbeTemperatureArrayPort5 OBJECT IDENTIFIER ::= { sensorProbeTemperatureArraySensor 5  }
                              sensorProbeTemperatureArrayPort5Number OBJECT-TYPE
                                 SYNTAX INTEGER
                                 ACCESS read-only
                                 STATUS mandatory
                                 DESCRIPTION
                                 "The total number of port on the TemperatureArray."
                                 ::=  {  sensorProbeTemperatureArrayPort5 1   }

                              sensorProbeTemperatureArrayPort5Table OBJECT-TYPE
                                 SYNTAX  SEQUENCE OF SensorProbeTemperatureArrayPort5Entry
                                 ACCESS  not-accessible
                                 STATUS  mandatory
                                 DESCRIPTION
                                 "This table contains the data for every Switch Sensor in the SensorArray. Each row in the table contains data for a different Switch Sensor."
                                 ::=  {  sensorProbeTemperatureArrayPort5 2   }

                                 sensorProbeTemperatureArrayPort5Entry OBJECT-TYPE
                                    SYNTAX  SensorProbeTemperatureArrayPort5Entry
                                    ACCESS  not-accessible
                                    STATUS  mandatory
                                    DESCRIPTION
                                    "This is an entry in the sensorProbeTemperatureArrayPort5 Table"
                                    INDEX         { sensorProbeTemperatureArrayPort5Index }
                                    ::=  { sensorProbeTemperatureArrayPort5Table 1 }

                                    SensorProbeTemperatureArrayPort5Entry ::= SEQUENCE {
                                       sensorProbeTemperatureArrayPort5Index
                                          INTEGER,
                                       sensorProbeTemperatureArrayPort5Description
                                          DisplayString,
                                       sensorProbeTemperatureArrayPort5Value
                                          INTEGER,
                                       sensorProbeTemperatureArrayPort5Status
                                          INTEGER,
                                       sensorProbeTemperatureArrayPort5Online
                                          INTEGER,
                                       sensorProbeTemperatureArrayPort5GoOnline
                                          INTEGER,
                                       sensorProbeTemperatureArrayPort5HighWarning
                                          INTEGER,
                                       sensorProbeTemperatureArrayPort5HighCritical
                                          INTEGER,
                                       sensorProbeTemperatureArrayPort5LowWarning
                                          INTEGER,
                                       sensorProbeTemperatureArrayPort5LowCritical
                                          INTEGER,
                                       sensorProbeTemperatureArrayPort5Rearm
                                          INTEGER,
                                       sensorProbeTemperatureArrayPort5DegreeType
                                          INTEGER,
                                       sensorProbeTemperatureArrayPort5DegreeRaw
                                          INTEGER,
                                       sensorProbeTemperatureArrayPort5Offset
                                          INTEGER,
                                       sensorProbeTemperatureArrayPort5URL
                                          DisplayString,
                                       sensorProbeTemperatureArrayPort5OpenURL
                                          INTEGER,
                                       sensorProbeTemperatureArrayPort5DatacollectType
                                          INTEGER,
                                       sensorProbeTemperatureArrayPort5ContTimeHighCritical
                                          INTEGER,
                                       sensorProbeTemperatureArrayPort5ContTimeHighWarning
                                          INTEGER,
                                       sensorProbeTemperatureArrayPort5ContTimeNormal
                                          INTEGER,
                                       sensorProbeTemperatureArrayPort5ContTimeLowWarning
                                          INTEGER,
                                       sensorProbeTemperatureArrayPort5ContTimeLowCritical
                                          INTEGER,
                                       sensorProbeTemperatureArrayPort5ContTimeSensorError
                                          INTEGER,
                                       sensorProbeTemperatureArrayPort5Calendar
                                          INTEGER,
                                       sensorProbeThermostatTemperatureArrayPort5Index
                                          INTEGER,
                                       sensorProbeThermostatTemperatureArrayPort5Description
                                          DisplayString,
                                       sensorProbeThermostatTemperatureArrayPort5Value
                                          INTEGER,
                                       sensorProbeThermostatTemperatureArrayPort5Online
                                          INTEGER,
                                       sensorProbeThermostatTemperatureArrayPort5GoOnline
                                          INTEGER,
                                       sensorProbeThermostatTemperatureArrayPort5Mode
                                          INTEGER,
                                       sensorProbeThermostatTemperatureArrayPort5RelayControlPort
                                          INTEGER,
                                       sensorProbeThermostatTemperatureArrayPort5NormalAction1
                                          INTEGER,
                                       sensorProbeThermostatTemperatureArrayPort5HighLimit1
                                          INTEGER,
                                       sensorProbeThermostatTemperatureArrayPort5HighLimitAction1
                                          INTEGER,
                                       sensorProbeThermostatTemperatureArrayPort5LowLimit1
                                          INTEGER,
                                       sensorProbeThermostatTemperatureArrayPort5LowLimitAction1
                                          INTEGER,
                                       sensorProbeThermostatTemperatureArrayPort5NormalAction2
                                          INTEGER,
                                       sensorProbeThermostatTemperatureArrayPort5HighLimit2
                                          INTEGER,
                                       sensorProbeThermostatTemperatureArrayPort5HighLimitAction2
                                          INTEGER,
                                       sensorProbeThermostatTemperatureArrayPort5LowLimit2
                                          INTEGER,
                                       sensorProbeThermostatTemperatureArrayPort5LowLimitAction2
                                          INTEGER,
                                       sensorProbeThermostatTemperatureArrayPort5EnableTime
                                          DisplayString
                                    }

                                    sensorProbeTemperatureArrayPort5Index OBJECT-TYPE
                                       SYNTAX  INTEGER (0..7)
                                       ACCESS  read-only
                                       STATUS  mandatory
                                       DESCRIPTION
                                       "A unique value for each sensor TemperatureArray port."
                                       ::=  {  sensorProbeTemperatureArrayPort5Entry 1   }

                                    sensorProbeTemperatureArrayPort5Description OBJECT-TYPE
                                       SYNTAX  DisplayString
                                       ACCESS  read-write
                                       STATUS  mandatory
                                       DESCRIPTION
                                       "A Description of this sensor TemperatureArray"
                                       ::=  {  sensorProbeTemperatureArrayPort5Entry 2   }

                                    sensorProbeTemperatureArrayPort5Value OBJECT-TYPE
                                       SYNTAX  INTEGER
                                       ACCESS  read-only
                                       STATUS  mandatory
                                       DESCRIPTION
                                       "The value in this sensor"
                                       ::=  {  sensorProbeTemperatureArrayPort5Entry 3   }

                                    sensorProbeTemperatureArrayPort5Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort5Entry 4   }

                                    sensorProbeTemperatureArrayPort5Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort5Entry 5   }

                                    sensorProbeTemperatureArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort5Entry 6   }

                                    sensorProbeTemperatureArrayPort5HighWarning OBJECT-TYPE
                                       SYNTAX  INTEGER
                                       ACCESS  read-write
                                       STATUS  mandatory
                                       DESCRIPTION
                                       "How hot this  sensor gets before it sends a warning"
                                       ::=  {  sensorProbeTemperatureArrayPort5Entry 7   }

                                    sensorProbeTemperatureArrayPort5HighCritical OBJECT-TYPE
                                       SYNTAX  INTEGER
                                       ACCESS  read-write
                                       STATUS  mandatory
                                       DESCRIPTION
                                       "How hot this sensor gets before it sends a critical event"
                                       ::=  {  sensorProbeTemperatureArrayPort5Entry 8   }

                                    sensorProbeTemperatureArrayPort5LowWarning OBJECT-TYPE
                                       SYNTAX  INTEGER
                                       ACCESS  read-write
                                       STATUS  mandatory
                                       DESCRIPTION
                                       "How cold this sensor gets before it sends a warning"
                                       ::=  {  sensorProbeTemperatureArrayPort5Entry 9   }

                                    sensorProbeTemperatureArrayPort5LowCritical OBJECT-TYPE
                                       SYNTAX  INTEGER
                                       ACCESS  read-write
                                       STATUS  mandatory
                                       DESCRIPTION
                                       "How cold this sensor gets before it sends a critical event"
                                       ::=  {  sensorProbeTemperatureArrayPort5Entry 10   }

                                    sensorProbeTemperatureArrayPort5Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort5Entry 11   }

                                    sensorProbeTemperatureArrayPort5DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort5Entry 12   }

                                    sensorProbeTemperatureArrayPort5DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort5Entry 14   }

                                    sensorProbeTemperatureArrayPort5Offset OBJECT-TYPE
                                       SYNTAX  INTEGER
                                       ACCESS  read-write
                                       STATUS  mandatory
                                       DESCRIPTION
                                       "Offset reading"
                                       ::=  {  sensorProbeTemperatureArrayPort5Entry 15   }

                                    sensorProbeTemperatureArrayPort5URL OBJECT-TYPE
                                       SYNTAX  DisplayString
                                       ACCESS  read-write
                                       STATUS  mandatory
                                       DESCRIPTION
                                       "Sensor URL link."
                                       ::=  {  sensorProbeTemperatureArrayPort5Entry 16   }

                                    sensorProbeTemperatureArrayPort5OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort5Entry 17   }

                                    sensorProbeTemperatureArrayPort5DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort5Entry 18   }

                                    sensorProbeTemperatureArrayPort5ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort5Entry 19 }

                                    sensorProbeTemperatureArrayPort5ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort5Entry 20 }

                                    sensorProbeTemperatureArrayPort5ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort5Entry 21 }

                                    sensorProbeTemperatureArrayPort5ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort5Entry 22 }

                                    sensorProbeTemperatureArrayPort5ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort5Entry 23 }

                                    sensorProbeTemperatureArrayPort5ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort5Entry 24 }

                                    sensorProbeTemperatureArrayPort5Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort5Entry 25 }

                                    sensorProbeThermostatTemperatureArrayPort5Index OBJECT-TYPE
                                       SYNTAX  INTEGER
                                       ACCESS  read-only
                                       STATUS  mandatory
                                       DESCRIPTION
                                       "A unique value for each sensor thermostat port."
                                       ::= {  sensorProbeTemperatureArrayPort5Entry 26 }

                                    sensorProbeThermostatTemperatureArrayPort5Description OBJECT-TYPE
                                       SYNTAX  DisplayString
                                       ACCESS  read-write
                                       STATUS  mandatory
                                       DESCRIPTION
                                       "A Description of this sensor thermostat"
                                       ::= {  sensorProbeTemperatureArrayPort5Entry 27 }

                                    sensorProbeThermostatTemperatureArrayPort5Value OBJECT-TYPE
                                       SYNTAX  INTEGER
                                       ACCESS  read-only
                                       STATUS  mandatory
                                       DESCRIPTION
                                       "The value in this sensor"
                                       ::= {  sensorProbeTemperatureArrayPort5Entry 28 }

                                    sensorProbeThermostatTemperatureArrayPort5Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort5Entry 29 }

                                    sensorProbeThermostatTemperatureArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort5Entry 30 }

                                    sensorProbeThermostatTemperatureArrayPort5Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort5Entry 31 }

                                    sensorProbeThermostatTemperatureArrayPort5RelayControlPort OBJECT-TYPE
                                       SYNTAX INTEGER
                                       ACCESS read-write
                                       STATUS mandatory
                                       DESCRIPTION
                                       "To select a relay port to be controled by this thermostat sensor."
                                       ::= {  sensorProbeTemperatureArrayPort5Entry 32 }

                                    sensorProbeThermostatTemperatureArrayPort5NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort5Entry 33 }

                                    sensorProbeThermostatTemperatureArrayPort5HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort5Entry 34 }

                                    sensorProbeThermostatTemperatureArrayPort5HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort5Entry 35 }

                                    sensorProbeThermostatTemperatureArrayPort5LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort5Entry 36 }

                                    sensorProbeThermostatTemperatureArrayPort5LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort5Entry 37 }

                                    sensorProbeThermostatTemperatureArrayPort5NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort5Entry 38 }

                                    sensorProbeThermostatTemperatureArrayPort5HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort5Entry 39 }

                                    sensorProbeThermostatTemperatureArrayPort5HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort5Entry 40 }

                                    sensorProbeThermostatTemperatureArrayPort5LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort5Entry 41 }

                                    sensorProbeThermostatTemperatureArrayPort5LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort5Entry 42 }

                                    sensorProbeThermostatTemperatureArrayPort5EnableTime OBJECT-TYPE
                                       SYNTAX  DisplayString
                                       ACCESS  read-write
                                       STATUS  mandatory
                                       DESCRIPTION
                                       "Time to enable on Thermostat"
                                       ::=  {  sensorProbeTemperatureArrayPort5Entry 43 }

                           sensorProbeTemperatureArrayPort6 OBJECT IDENTIFIER ::= { sensorProbeTemperatureArraySensor 6  }
                              sensorProbeTemperatureArrayPort6Number OBJECT-TYPE
                                 SYNTAX INTEGER
                                 ACCESS read-only
                                 STATUS mandatory
                                 DESCRIPTION
                                 "The total number of port on the TemperatureArray."
                                 ::=  {  sensorProbeTemperatureArrayPort6 1   }

                              sensorProbeTemperatureArrayPort6Table OBJECT-TYPE
                                 SYNTAX  SEQUENCE OF SensorProbeTemperatureArrayPort6Entry
                                 ACCESS  not-accessible
                                 STATUS  mandatory
                                 DESCRIPTION
                                 "This table contains the data for every Switch Sensor in the SensorArray. Each row in the table contains data for a different Switch Sensor."
                                 ::=  {  sensorProbeTemperatureArrayPort6 2   }

                                 sensorProbeTemperatureArrayPort6Entry OBJECT-TYPE
                                    SYNTAX  SensorProbeTemperatureArrayPort6Entry
                                    ACCESS  not-accessible
                                    STATUS  mandatory
                                    DESCRIPTION
                                    "This is an entry in the sensorProbeTemperatureArrayPort6 Table"
                                    INDEX         { sensorProbeTemperatureArrayPort6Index }
                                    ::=  { sensorProbeTemperatureArrayPort6Table 1 }

                                    SensorProbeTemperatureArrayPort6Entry ::= SEQUENCE {
                                       sensorProbeTemperatureArrayPort6Index
                                          INTEGER,
                                       sensorProbeTemperatureArrayPort6Description
                                          DisplayString,
                                       sensorProbeTemperatureArrayPort6Value
                                          INTEGER,
                                       sensorProbeTemperatureArrayPort6Status
                                          INTEGER,
                                       sensorProbeTemperatureArrayPort6Online
                                          INTEGER,
                                       sensorProbeTemperatureArrayPort6GoOnline
                                          INTEGER,
                                       sensorProbeTemperatureArrayPort6HighWarning
                                          INTEGER,
                                       sensorProbeTemperatureArrayPort6HighCritical
                                          INTEGER,
                                       sensorProbeTemperatureArrayPort6LowWarning
                                          INTEGER,
                                       sensorProbeTemperatureArrayPort6LowCritical
                                          INTEGER,
                                       sensorProbeTemperatureArrayPort6Rearm
                                          INTEGER,
                                       sensorProbeTemperatureArrayPort6DegreeType
                                          INTEGER,
                                       sensorProbeTemperatureArrayPort6DegreeRaw
                                          INTEGER,
                                       sensorProbeTemperatureArrayPort6Offset
                                          INTEGER,
                                       sensorProbeTemperatureArrayPort6URL
                                          DisplayString,
                                       sensorProbeTemperatureArrayPort6OpenURL
                                          INTEGER,
                                       sensorProbeTemperatureArrayPort6DatacollectType
                                          INTEGER,
                                       sensorProbeTemperatureArrayPort6ContTimeHighCritical
                                          INTEGER,
                                       sensorProbeTemperatureArrayPort6ContTimeHighWarning
                                          INTEGER,
                                       sensorProbeTemperatureArrayPort6ContTimeNormal
                                          INTEGER,
                                       sensorProbeTemperatureArrayPort6ContTimeLowWarning
                                          INTEGER,
                                       sensorProbeTemperatureArrayPort6ContTimeLowCritical
                                          INTEGER,
                                       sensorProbeTemperatureArrayPort6ContTimeSensorError
                                          INTEGER,
                                       sensorProbeTemperatureArrayPort6Calendar
                                          INTEGER,
                                       sensorProbeThermostatTemperatureArrayPort6Index
                                          INTEGER,
                                       sensorProbeThermostatTemperatureArrayPort6Description
                                          DisplayString,
                                       sensorProbeThermostatTemperatureArrayPort6Value
                                          INTEGER,
                                       sensorProbeThermostatTemperatureArrayPort6Online
                                          INTEGER,
                                       sensorProbeThermostatTemperatureArrayPort6GoOnline
                                          INTEGER,
                                       sensorProbeThermostatTemperatureArrayPort6Mode
                                          INTEGER,
                                       sensorProbeThermostatTemperatureArrayPort6RelayControlPort
                                          INTEGER,
                                       sensorProbeThermostatTemperatureArrayPort6NormalAction1
                                          INTEGER,
                                       sensorProbeThermostatTemperatureArrayPort6HighLimit1
                                          INTEGER,
                                       sensorProbeThermostatTemperatureArrayPort6HighLimitAction1
                                          INTEGER,
                                       sensorProbeThermostatTemperatureArrayPort6LowLimit1
                                          INTEGER,
                                       sensorProbeThermostatTemperatureArrayPort6LowLimitAction1
                                          INTEGER,
                                       sensorProbeThermostatTemperatureArrayPort6NormalAction2
                                          INTEGER,
                                       sensorProbeThermostatTemperatureArrayPort6HighLimit2
                                          INTEGER,
                                       sensorProbeThermostatTemperatureArrayPort6HighLimitAction2
                                          INTEGER,
                                       sensorProbeThermostatTemperatureArrayPort6LowLimit2
                                          INTEGER,
                                       sensorProbeThermostatTemperatureArrayPort6LowLimitAction2
                                          INTEGER,
                                       sensorProbeThermostatTemperatureArrayPort6EnableTime
                                          DisplayString
                                    }

                                    sensorProbeTemperatureArrayPort6Index OBJECT-TYPE
                                       SYNTAX  INTEGER (0..7)
                                       ACCESS  read-only
                                       STATUS  mandatory
                                       DESCRIPTION
                                       "A unique value for each sensor TemperatureArray port."
                                       ::=  {  sensorProbeTemperatureArrayPort6Entry 1   }

                                    sensorProbeTemperatureArrayPort6Description OBJECT-TYPE
                                       SYNTAX  DisplayString
                                       ACCESS  read-write
                                       STATUS  mandatory
                                       DESCRIPTION
                                       "A Description of this sensor TemperatureArray"
                                       ::=  {  sensorProbeTemperatureArrayPort6Entry 2   }

                                    sensorProbeTemperatureArrayPort6Value OBJECT-TYPE
                                       SYNTAX  INTEGER
                                       ACCESS  read-only
                                       STATUS  mandatory
                                       DESCRIPTION
                                       "The value in this sensor"
                                       ::=  {  sensorProbeTemperatureArrayPort6Entry 3   }

                                    sensorProbeTemperatureArrayPort6Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort6Entry 4   }

                                    sensorProbeTemperatureArrayPort6Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort6Entry 5   }

                                    sensorProbeTemperatureArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort6Entry 6   }

                                    sensorProbeTemperatureArrayPort6HighWarning OBJECT-TYPE
                                       SYNTAX  INTEGER
                                       ACCESS  read-write
                                       STATUS  mandatory
                                       DESCRIPTION
                                       "How hot this  sensor gets before it sends a warning"
                                       ::=  {  sensorProbeTemperatureArrayPort6Entry 7   }

                                    sensorProbeTemperatureArrayPort6HighCritical OBJECT-TYPE
                                       SYNTAX  INTEGER
                                       ACCESS  read-write
                                       STATUS  mandatory
                                       DESCRIPTION
                                       "How hot this sensor gets before it sends a critical event"
                                       ::=  {  sensorProbeTemperatureArrayPort6Entry 8   }

                                    sensorProbeTemperatureArrayPort6LowWarning OBJECT-TYPE
                                       SYNTAX  INTEGER
                                       ACCESS  read-write
                                       STATUS  mandatory
                                       DESCRIPTION
                                       "How cold this sensor gets before it sends a warning"
                                       ::=  {  sensorProbeTemperatureArrayPort6Entry 9   }

                                    sensorProbeTemperatureArrayPort6LowCritical OBJECT-TYPE
                                       SYNTAX  INTEGER
                                       ACCESS  read-write
                                       STATUS  mandatory
                                       DESCRIPTION
                                       "How cold this sensor gets before it sends a critical event"
                                       ::=  {  sensorProbeTemperatureArrayPort6Entry 10   }

                                    sensorProbeTemperatureArrayPort6Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort6Entry 11   }

                                    sensorProbeTemperatureArrayPort6DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort6Entry 12   }

                                    sensorProbeTemperatureArrayPort6DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort6Entry 14   }

                                    sensorProbeTemperatureArrayPort6Offset OBJECT-TYPE
                                       SYNTAX  INTEGER
                                       ACCESS  read-write
                                       STATUS  mandatory
                                       DESCRIPTION
                                       "Offset reading"
                                       ::=  {  sensorProbeTemperatureArrayPort6Entry 15   }

                                    sensorProbeTemperatureArrayPort6URL OBJECT-TYPE
                                       SYNTAX  DisplayString
                                       ACCESS  read-write
                                       STATUS  mandatory
                                       DESCRIPTION
                                       "Sensor URL link."
                                       ::=  {  sensorProbeTemperatureArrayPort6Entry 16   }

                                    sensorProbeTemperatureArrayPort6OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort6Entry 17   }

                                    sensorProbeTemperatureArrayPort6DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort6Entry 18   }

                                    sensorProbeTemperatureArrayPort6ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort6Entry 19 }

                                    sensorProbeTemperatureArrayPort6ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort6Entry 20 }

                                    sensorProbeTemperatureArrayPort6ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort6Entry 21 }

                                    sensorProbeTemperatureArrayPort6ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort6Entry 22 }

                                    sensorProbeTemperatureArrayPort6ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort6Entry 23 }

                                    sensorProbeTemperatureArrayPort6ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort6Entry 24 }

                                    sensorProbeTemperatureArrayPort6Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort6Entry 25 }

                                    sensorProbeThermostatTemperatureArrayPort6Index OBJECT-TYPE
                                       SYNTAX  INTEGER
                                       ACCESS  read-only
                                       STATUS  mandatory
                                       DESCRIPTION
                                       "A unique value for each sensor thermostat port."
                                       ::= {  sensorProbeTemperatureArrayPort6Entry 26 }

                                    sensorProbeThermostatTemperatureArrayPort6Description OBJECT-TYPE
                                       SYNTAX  DisplayString
                                       ACCESS  read-write
                                       STATUS  mandatory
                                       DESCRIPTION
                                       "A Description of this sensor thermostat"
                                       ::= {  sensorProbeTemperatureArrayPort6Entry 27 }

                                    sensorProbeThermostatTemperatureArrayPort6Value OBJECT-TYPE
                                       SYNTAX  INTEGER
                                       ACCESS  read-only
                                       STATUS  mandatory
                                       DESCRIPTION
                                       "The value in this sensor"
                                       ::= {  sensorProbeTemperatureArrayPort6Entry 28 }

                                    sensorProbeThermostatTemperatureArrayPort6Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort6Entry 29 }

                                    sensorProbeThermostatTemperatureArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort6Entry 30 }

                                    sensorProbeThermostatTemperatureArrayPort6Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort6Entry 31 }

                                    sensorProbeThermostatTemperatureArrayPort6RelayControlPort OBJECT-TYPE
                                       SYNTAX INTEGER
                                       ACCESS read-write
                                       STATUS mandatory
                                       DESCRIPTION
                                       "To select a relay port to be controled by this thermostat sensor."
                                       ::= {  sensorProbeTemperatureArrayPort6Entry 32 }

                                    sensorProbeThermostatTemperatureArrayPort6NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort6Entry 33 }

                                    sensorProbeThermostatTemperatureArrayPort6HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort6Entry 34 }

                                    sensorProbeThermostatTemperatureArrayPort6HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort6Entry 35 }

                                    sensorProbeThermostatTemperatureArrayPort6LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort6Entry 36 }

                                    sensorProbeThermostatTemperatureArrayPort6LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort6Entry 37 }

                                    sensorProbeThermostatTemperatureArrayPort6NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort6Entry 38 }

                                    sensorProbeThermostatTemperatureArrayPort6HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort6Entry 39 }

                                    sensorProbeThermostatTemperatureArrayPort6HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort6Entry 40 }

                                    sensorProbeThermostatTemperatureArrayPort6LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort6Entry 41 }

                                    sensorProbeThermostatTemperatureArrayPort6LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort6Entry 42 }

                                    sensorProbeThermostatTemperatureArrayPort6EnableTime OBJECT-TYPE
                                       SYNTAX  DisplayString
                                       ACCESS  read-write
                                       STATUS  mandatory
                                       DESCRIPTION
                                       "Time to enable on Thermostat"
                                       ::=  {  sensorProbeTemperatureArrayPort6Entry 43 }

                           sensorProbeTemperatureArrayPort7 OBJECT IDENTIFIER ::= { sensorProbeTemperatureArraySensor 7  }
                              sensorProbeTemperatureArrayPort7Number OBJECT-TYPE
                                 SYNTAX INTEGER
                                 ACCESS read-only
                                 STATUS mandatory
                                 DESCRIPTION
                                 "The total number of port on the TemperatureArray."
                                 ::=  {  sensorProbeTemperatureArrayPort7 1   }

                              sensorProbeTemperatureArrayPort7Table OBJECT-TYPE
                                 SYNTAX  SEQUENCE OF SensorProbeTemperatureArrayPort7Entry
                                 ACCESS  not-accessible
                                 STATUS  mandatory
                                 DESCRIPTION
                                 "This table contains the data for every Switch Sensor in the SensorArray. Each row in the table contains data for a different Switch Sensor."
                                 ::=  {  sensorProbeTemperatureArrayPort7 2   }

                                 sensorProbeTemperatureArrayPort7Entry OBJECT-TYPE
                                    SYNTAX  SensorProbeTemperatureArrayPort7Entry
                                    ACCESS  not-accessible
                                    STATUS  mandatory
                                    DESCRIPTION
                                    "This is an entry in the sensorProbeTemperatureArrayPort7 Table"
                                    INDEX         { sensorProbeTemperatureArrayPort7Index }
                                    ::=  { sensorProbeTemperatureArrayPort7Table 1 }

                                    SensorProbeTemperatureArrayPort7Entry ::= SEQUENCE {
                                       sensorProbeTemperatureArrayPort7Index
                                          INTEGER,
                                       sensorProbeTemperatureArrayPort7Description
                                          DisplayString,
                                       sensorProbeTemperatureArrayPort7Value
                                          INTEGER,
                                       sensorProbeTemperatureArrayPort7Status
                                          INTEGER,
                                       sensorProbeTemperatureArrayPort7Online
                                          INTEGER,
                                       sensorProbeTemperatureArrayPort7GoOnline
                                          INTEGER,
                                       sensorProbeTemperatureArrayPort7HighWarning
                                          INTEGER,
                                       sensorProbeTemperatureArrayPort7HighCritical
                                          INTEGER,
                                       sensorProbeTemperatureArrayPort7LowWarning
                                          INTEGER,
                                       sensorProbeTemperatureArrayPort7LowCritical
                                          INTEGER,
                                       sensorProbeTemperatureArrayPort7Rearm
                                          INTEGER,
                                       sensorProbeTemperatureArrayPort7DegreeType
                                          INTEGER,
                                       sensorProbeTemperatureArrayPort7DegreeRaw
                                          INTEGER,
                                       sensorProbeTemperatureArrayPort7Offset
                                          INTEGER,
                                       sensorProbeTemperatureArrayPort7URL
                                          DisplayString,
                                       sensorProbeTemperatureArrayPort7OpenURL
                                          INTEGER,
                                       sensorProbeTemperatureArrayPort7DatacollectType
                                          INTEGER,
                                       sensorProbeTemperatureArrayPort7ContTimeHighCritical
                                          INTEGER,
                                       sensorProbeTemperatureArrayPort7ContTimeHighWarning
                                          INTEGER,
                                       sensorProbeTemperatureArrayPort7ContTimeNormal
                                          INTEGER,
                                       sensorProbeTemperatureArrayPort7ContTimeLowWarning
                                          INTEGER,
                                       sensorProbeTemperatureArrayPort7ContTimeLowCritical
                                          INTEGER,
                                       sensorProbeTemperatureArrayPort7ContTimeSensorError
                                          INTEGER,
                                       sensorProbeTemperatureArrayPort7Calendar
                                          INTEGER,
                                       sensorProbeThermostatTemperatureArrayPort7Index
                                          INTEGER,
                                       sensorProbeThermostatTemperatureArrayPort7Description
                                          DisplayString,
                                       sensorProbeThermostatTemperatureArrayPort7Value
                                          INTEGER,
                                       sensorProbeThermostatTemperatureArrayPort7Online
                                          INTEGER,
                                       sensorProbeThermostatTemperatureArrayPort7GoOnline
                                          INTEGER,
                                       sensorProbeThermostatTemperatureArrayPort7Mode
                                          INTEGER,
                                       sensorProbeThermostatTemperatureArrayPort7RelayControlPort
                                          INTEGER,
                                       sensorProbeThermostatTemperatureArrayPort7NormalAction1
                                          INTEGER,
                                       sensorProbeThermostatTemperatureArrayPort7HighLimit1
                                          INTEGER,
                                       sensorProbeThermostatTemperatureArrayPort7HighLimitAction1
                                          INTEGER,
                                       sensorProbeThermostatTemperatureArrayPort7LowLimit1
                                          INTEGER,
                                       sensorProbeThermostatTemperatureArrayPort7LowLimitAction1
                                          INTEGER,
                                       sensorProbeThermostatTemperatureArrayPort7NormalAction2
                                          INTEGER,
                                       sensorProbeThermostatTemperatureArrayPort7HighLimit2
                                          INTEGER,
                                       sensorProbeThermostatTemperatureArrayPort7HighLimitAction2
                                          INTEGER,
                                       sensorProbeThermostatTemperatureArrayPort7LowLimit2
                                          INTEGER,
                                       sensorProbeThermostatTemperatureArrayPort7LowLimitAction2
                                          INTEGER,
                                       sensorProbeThermostatTemperatureArrayPort7EnableTime
                                          DisplayString
                                    }

                                    sensorProbeTemperatureArrayPort7Index OBJECT-TYPE
                                       SYNTAX  INTEGER (0..7)
                                       ACCESS  read-only
                                       STATUS  mandatory
                                       DESCRIPTION
                                       "A unique value for each sensor TemperatureArray port."
                                       ::=  {  sensorProbeTemperatureArrayPort7Entry 1   }

                                    sensorProbeTemperatureArrayPort7Description OBJECT-TYPE
                                       SYNTAX  DisplayString
                                       ACCESS  read-write
                                       STATUS  mandatory
                                       DESCRIPTION
                                       "A Description of this sensor TemperatureArray"
                                       ::=  {  sensorProbeTemperatureArrayPort7Entry 2   }

                                    sensorProbeTemperatureArrayPort7Value OBJECT-TYPE
                                       SYNTAX  INTEGER
                                       ACCESS  read-only
                                       STATUS  mandatory
                                       DESCRIPTION
                                       "The value in this sensor"
                                       ::=  {  sensorProbeTemperatureArrayPort7Entry 3   }

                                    sensorProbeTemperatureArrayPort7Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort7Entry 4   }

                                    sensorProbeTemperatureArrayPort7Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort7Entry 5   }

                                    sensorProbeTemperatureArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort7Entry 6   }

                                    sensorProbeTemperatureArrayPort7HighWarning OBJECT-TYPE
                                       SYNTAX  INTEGER
                                       ACCESS  read-write
                                       STATUS  mandatory
                                       DESCRIPTION
                                       "How hot this  sensor gets before it sends a warning"
                                       ::=  {  sensorProbeTemperatureArrayPort7Entry 7   }

                                    sensorProbeTemperatureArrayPort7HighCritical OBJECT-TYPE
                                       SYNTAX  INTEGER
                                       ACCESS  read-write
                                       STATUS  mandatory
                                       DESCRIPTION
                                       "How hot this sensor gets before it sends a critical event"
                                       ::=  {  sensorProbeTemperatureArrayPort7Entry 8   }

                                    sensorProbeTemperatureArrayPort7LowWarning OBJECT-TYPE
                                       SYNTAX  INTEGER
                                       ACCESS  read-write
                                       STATUS  mandatory
                                       DESCRIPTION
                                       "How cold this sensor gets before it sends a warning"
                                       ::=  {  sensorProbeTemperatureArrayPort7Entry 9   }

                                    sensorProbeTemperatureArrayPort7LowCritical OBJECT-TYPE
                                       SYNTAX  INTEGER
                                       ACCESS  read-write
                                       STATUS  mandatory
                                       DESCRIPTION
                                       "How cold this sensor gets before it sends a critical event"
                                       ::=  {  sensorProbeTemperatureArrayPort7Entry 10   }

                                    sensorProbeTemperatureArrayPort7Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort7Entry 11   }

                                    sensorProbeTemperatureArrayPort7DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort7Entry 12   }

                                    sensorProbeTemperatureArrayPort7DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort7Entry 14   }

                                    sensorProbeTemperatureArrayPort7Offset OBJECT-TYPE
                                       SYNTAX  INTEGER
                                       ACCESS  read-write
                                       STATUS  mandatory
                                       DESCRIPTION
                                       "Offset reading"
                                       ::=  {  sensorProbeTemperatureArrayPort7Entry 15   }

                                    sensorProbeTemperatureArrayPort7URL OBJECT-TYPE
                                       SYNTAX  DisplayString
                                       ACCESS  read-write
                                       STATUS  mandatory
                                       DESCRIPTION
                                       "Sensor URL link."
                                       ::=  {  sensorProbeTemperatureArrayPort7Entry 16   }

                                    sensorProbeTemperatureArrayPort7OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort7Entry 17   }

                                    sensorProbeTemperatureArrayPort7DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort7Entry 18   }

                                    sensorProbeTemperatureArrayPort7ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort7Entry 19 }

                                    sensorProbeTemperatureArrayPort7ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort7Entry 20 }

                                    sensorProbeTemperatureArrayPort7ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort7Entry 21 }

                                    sensorProbeTemperatureArrayPort7ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort7Entry 22 }

                                    sensorProbeTemperatureArrayPort7ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort7Entry 23 }

                                    sensorProbeTemperatureArrayPort7ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort7Entry 24 }

                                    sensorProbeTemperatureArrayPort7Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort7Entry 25 }

                                    sensorProbeThermostatTemperatureArrayPort7Index OBJECT-TYPE
                                       SYNTAX  INTEGER
                                       ACCESS  read-only
                                       STATUS  mandatory
                                       DESCRIPTION
                                       "A unique value for each sensor thermostat port."
                                       ::= {  sensorProbeTemperatureArrayPort7Entry 26 }

                                    sensorProbeThermostatTemperatureArrayPort7Description OBJECT-TYPE
                                       SYNTAX  DisplayString
                                       ACCESS  read-write
                                       STATUS  mandatory
                                       DESCRIPTION
                                       "A Description of this sensor thermostat"
                                       ::= {  sensorProbeTemperatureArrayPort7Entry 27 }

                                    sensorProbeThermostatTemperatureArrayPort7Value OBJECT-TYPE
                                       SYNTAX  INTEGER
                                       ACCESS  read-only
                                       STATUS  mandatory
                                       DESCRIPTION
                                       "The value in this sensor"
                                       ::= {  sensorProbeTemperatureArrayPort7Entry 28 }

                                    sensorProbeThermostatTemperatureArrayPort7Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort7Entry 29 }

                                    sensorProbeThermostatTemperatureArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort7Entry 30 }

                                    sensorProbeThermostatTemperatureArrayPort7Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort7Entry 31 }

                                    sensorProbeThermostatTemperatureArrayPort7RelayControlPort OBJECT-TYPE
                                       SYNTAX INTEGER
                                       ACCESS read-write
                                       STATUS mandatory
                                       DESCRIPTION
                                       "To select a relay port to be controled by this thermostat sensor."
                                       ::= {  sensorProbeTemperatureArrayPort7Entry 32 }

                                    sensorProbeThermostatTemperatureArrayPort7NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort7Entry 33 }

                                    sensorProbeThermostatTemperatureArrayPort7HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort7Entry 34 }

                                    sensorProbeThermostatTemperatureArrayPort7HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort7Entry 35 }

                                    sensorProbeThermostatTemperatureArrayPort7LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort7Entry 36 }

                                    sensorProbeThermostatTemperatureArrayPort7LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort7Entry 37 }

                                    sensorProbeThermostatTemperatureArrayPort7NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort7Entry 38 }

                                    sensorProbeThermostatTemperatureArrayPort7HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort7Entry 39 }

                                    sensorProbeThermostatTemperatureArrayPort7HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort7Entry 40 }

                                    sensorProbeThermostatTemperatureArrayPort7LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort7Entry 41 }

                                    sensorProbeThermostatTemperatureArrayPort7LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort7Entry 42 }

                                    sensorProbeThermostatTemperatureArrayPort7EnableTime OBJECT-TYPE
                                       SYNTAX  DisplayString
                                       ACCESS  read-write
                                       STATUS  mandatory
                                       DESCRIPTION
                                       "Time to enable on Thermostat"
                                       ::=  {  sensorProbeTemperatureArrayPort7Entry 43 }

                           sensorProbeTemperatureArrayPort8 OBJECT IDENTIFIER ::= { sensorProbeTemperatureArraySensor 8  }
                              sensorProbeTemperatureArrayPort8Number OBJECT-TYPE
                                 SYNTAX INTEGER
                                 ACCESS read-only
                                 STATUS mandatory
                                 DESCRIPTION
                                 "The total number of port on the TemperatureArray."
                                 ::=  {  sensorProbeTemperatureArrayPort8 1   }

                              sensorProbeTemperatureArrayPort8Table OBJECT-TYPE
                                 SYNTAX  SEQUENCE OF SensorProbeTemperatureArrayPort8Entry
                                 ACCESS  not-accessible
                                 STATUS  mandatory
                                 DESCRIPTION
                                 "This table contains the data for every Switch Sensor in the SensorArray. Each row in the table contains data for a different Switch Sensor."
                                 ::=  {  sensorProbeTemperatureArrayPort8 2   }

                                 sensorProbeTemperatureArrayPort8Entry OBJECT-TYPE
                                    SYNTAX  SensorProbeTemperatureArrayPort8Entry
                                    ACCESS  not-accessible
                                    STATUS  mandatory
                                    DESCRIPTION
                                    "This is an entry in the sensorProbeTemperatureArrayPort8 Table"
                                    INDEX         { sensorProbeTemperatureArrayPort8Index }
                                    ::=  { sensorProbeTemperatureArrayPort8Table 1 }

                                    SensorProbeTemperatureArrayPort8Entry ::= SEQUENCE {
                                       sensorProbeTemperatureArrayPort8Index
                                          INTEGER,
                                       sensorProbeTemperatureArrayPort8Description
                                          DisplayString,
                                       sensorProbeTemperatureArrayPort8Value
                                          INTEGER,
                                       sensorProbeTemperatureArrayPort8Status
                                          INTEGER,
                                       sensorProbeTemperatureArrayPort8Online
                                          INTEGER,
                                       sensorProbeTemperatureArrayPort8GoOnline
                                          INTEGER,
                                       sensorProbeTemperatureArrayPort8HighWarning
                                          INTEGER,
                                       sensorProbeTemperatureArrayPort8HighCritical
                                          INTEGER,
                                       sensorProbeTemperatureArrayPort8LowWarning
                                          INTEGER,
                                       sensorProbeTemperatureArrayPort8LowCritical
                                          INTEGER,
                                       sensorProbeTemperatureArrayPort8Rearm
                                          INTEGER,
                                       sensorProbeTemperatureArrayPort8DegreeType
                                          INTEGER,
                                       sensorProbeTemperatureArrayPort8DegreeRaw
                                          INTEGER,
                                       sensorProbeTemperatureArrayPort8Offset
                                          INTEGER,
                                       sensorProbeTemperatureArrayPort8URL
                                          DisplayString,
                                       sensorProbeTemperatureArrayPort8OpenURL
                                          INTEGER,
                                       sensorProbeTemperatureArrayPort8DatacollectType
                                          INTEGER,
                                       sensorProbeTemperatureArrayPort8ContTimeHighCritical
                                          INTEGER,
                                       sensorProbeTemperatureArrayPort8ContTimeHighWarning
                                          INTEGER,
                                       sensorProbeTemperatureArrayPort8ContTimeNormal
                                          INTEGER,
                                       sensorProbeTemperatureArrayPort8ContTimeLowWarning
                                          INTEGER,
                                       sensorProbeTemperatureArrayPort8ContTimeLowCritical
                                          INTEGER,
                                       sensorProbeTemperatureArrayPort8ContTimeSensorError
                                          INTEGER,
                                       sensorProbeTemperatureArrayPort8Calendar
                                          INTEGER,
                                       sensorProbeThermostatTemperatureArrayPort8Index
                                          INTEGER,
                                       sensorProbeThermostatTemperatureArrayPort8Description
                                          DisplayString,
                                       sensorProbeThermostatTemperatureArrayPort8Value
                                          INTEGER,
                                       sensorProbeThermostatTemperatureArrayPort8Online
                                          INTEGER,
                                       sensorProbeThermostatTemperatureArrayPort8GoOnline
                                          INTEGER,
                                       sensorProbeThermostatTemperatureArrayPort8Mode
                                          INTEGER,
                                       sensorProbeThermostatTemperatureArrayPort8RelayControlPort
                                          INTEGER,
                                       sensorProbeThermostatTemperatureArrayPort8NormalAction1
                                          INTEGER,
                                       sensorProbeThermostatTemperatureArrayPort8HighLimit1
                                          INTEGER,
                                       sensorProbeThermostatTemperatureArrayPort8HighLimitAction1
                                          INTEGER,
                                       sensorProbeThermostatTemperatureArrayPort8LowLimit1
                                          INTEGER,
                                       sensorProbeThermostatTemperatureArrayPort8LowLimitAction1
                                          INTEGER,
                                       sensorProbeThermostatTemperatureArrayPort8NormalAction2
                                          INTEGER,
                                       sensorProbeThermostatTemperatureArrayPort8HighLimit2
                                          INTEGER,
                                       sensorProbeThermostatTemperatureArrayPort8HighLimitAction2
                                          INTEGER,
                                       sensorProbeThermostatTemperatureArrayPort8LowLimit2
                                          INTEGER,
                                       sensorProbeThermostatTemperatureArrayPort8LowLimitAction2
                                          INTEGER,
                                       sensorProbeThermostatTemperatureArrayPort8EnableTime
                                          DisplayString
                                    }

                                    sensorProbeTemperatureArrayPort8Index OBJECT-TYPE
                                       SYNTAX  INTEGER (0..7)
                                       ACCESS  read-only
                                       STATUS  mandatory
                                       DESCRIPTION
                                       "A unique value for each sensor TemperatureArray port."
                                       ::=  {  sensorProbeTemperatureArrayPort8Entry 1   }

                                    sensorProbeTemperatureArrayPort8Description OBJECT-TYPE
                                       SYNTAX  DisplayString
                                       ACCESS  read-write
                                       STATUS  mandatory
                                       DESCRIPTION
                                       "A Description of this sensor TemperatureArray"
                                       ::=  {  sensorProbeTemperatureArrayPort8Entry 2   }

                                    sensorProbeTemperatureArrayPort8Value OBJECT-TYPE
                                       SYNTAX  INTEGER
                                       ACCESS  read-only
                                       STATUS  mandatory
                                       DESCRIPTION
                                       "The value in this sensor"
                                       ::=  {  sensorProbeTemperatureArrayPort8Entry 3   }

                                    sensorProbeTemperatureArrayPort8Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort8Entry 4   }

                                    sensorProbeTemperatureArrayPort8Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort8Entry 5   }

                                    sensorProbeTemperatureArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort8Entry 6   }

                                    sensorProbeTemperatureArrayPort8HighWarning OBJECT-TYPE
                                       SYNTAX  INTEGER
                                       ACCESS  read-write
                                       STATUS  mandatory
                                       DESCRIPTION
                                       "How hot this  sensor gets before it sends a warning"
                                       ::=  {  sensorProbeTemperatureArrayPort8Entry 7   }

                                    sensorProbeTemperatureArrayPort8HighCritical OBJECT-TYPE
                                       SYNTAX  INTEGER
                                       ACCESS  read-write
                                       STATUS  mandatory
                                       DESCRIPTION
                                       "How hot this sensor gets before it sends a critical event"
                                       ::=  {  sensorProbeTemperatureArrayPort8Entry 8   }

                                    sensorProbeTemperatureArrayPort8LowWarning OBJECT-TYPE
                                       SYNTAX  INTEGER
                                       ACCESS  read-write
                                       STATUS  mandatory
                                       DESCRIPTION
                                       "How cold this sensor gets before it sends a warning"
                                       ::=  {  sensorProbeTemperatureArrayPort8Entry 9   }

                                    sensorProbeTemperatureArrayPort8LowCritical OBJECT-TYPE
                                       SYNTAX  INTEGER
                                       ACCESS  read-write
                                       STATUS  mandatory
                                       DESCRIPTION
                                       "How cold this sensor gets before it sends a critical event"
                                       ::=  {  sensorProbeTemperatureArrayPort8Entry 10   }

                                    sensorProbeTemperatureArrayPort8Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort8Entry 11   }

                                    sensorProbeTemperatureArrayPort8DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort8Entry 12   }

                                    sensorProbeTemperatureArrayPort8DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort8Entry 14   }

                                    sensorProbeTemperatureArrayPort8Offset OBJECT-TYPE
                                       SYNTAX  INTEGER
                                       ACCESS  read-write
                                       STATUS  mandatory
                                       DESCRIPTION
                                       "Offset reading"
                                       ::=  {  sensorProbeTemperatureArrayPort8Entry 15   }

                                    sensorProbeTemperatureArrayPort8URL OBJECT-TYPE
                                       SYNTAX  DisplayString
                                       ACCESS  read-write
                                       STATUS  mandatory
                                       DESCRIPTION
                                       "Sensor URL link."
                                       ::=  {  sensorProbeTemperatureArrayPort8Entry 16   }

                                    sensorProbeTemperatureArrayPort8OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort8Entry 17   }

                                    sensorProbeTemperatureArrayPort8DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort8Entry 18   }

                                    sensorProbeTemperatureArrayPort8ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort8Entry 19 }

                                    sensorProbeTemperatureArrayPort8ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort8Entry 20 }

                                    sensorProbeTemperatureArrayPort8ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort8Entry 21 }

                                    sensorProbeTemperatureArrayPort8ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort8Entry 22 }

                                    sensorProbeTemperatureArrayPort8ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort8Entry 23 }

                                    sensorProbeTemperatureArrayPort8ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort8Entry 24 }

                                    sensorProbeTemperatureArrayPort8Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort8Entry 25 }

                                    sensorProbeThermostatTemperatureArrayPort8Index OBJECT-TYPE
                                       SYNTAX  INTEGER
                                       ACCESS  read-only
                                       STATUS  mandatory
                                       DESCRIPTION
                                       "A unique value for each sensor thermostat port."
                                       ::= {  sensorProbeTemperatureArrayPort8Entry 26 }

                                    sensorProbeThermostatTemperatureArrayPort8Description OBJECT-TYPE
                                       SYNTAX  DisplayString
                                       ACCESS  read-write
                                       STATUS  mandatory
                                       DESCRIPTION
                                       "A Description of this sensor thermostat"
                                       ::= {  sensorProbeTemperatureArrayPort8Entry 27 }

                                    sensorProbeThermostatTemperatureArrayPort8Value OBJECT-TYPE
                                       SYNTAX  INTEGER
                                       ACCESS  read-only
                                       STATUS  mandatory
                                       DESCRIPTION
                                       "The value in this sensor"
                                       ::= {  sensorProbeTemperatureArrayPort8Entry 28 }

                                    sensorProbeThermostatTemperatureArrayPort8Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort8Entry 29 }

                                    sensorProbeThermostatTemperatureArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort8Entry 30 }

                                    sensorProbeThermostatTemperatureArrayPort8Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort8Entry 31 }

                                    sensorProbeThermostatTemperatureArrayPort8RelayControlPort OBJECT-TYPE
                                       SYNTAX INTEGER
                                       ACCESS read-write
                                       STATUS mandatory
                                       DESCRIPTION
                                       "To select a relay port to be controled by this thermostat sensor."
                                       ::= {  sensorProbeTemperatureArrayPort8Entry 32 }

                                    sensorProbeThermostatTemperatureArrayPort8NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort8Entry 33 }

                                    sensorProbeThermostatTemperatureArrayPort8HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort8Entry 34 }

                                    sensorProbeThermostatTemperatureArrayPort8HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort8Entry 35 }

                                    sensorProbeThermostatTemperatureArrayPort8LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort8Entry 36 }

                                    sensorProbeThermostatTemperatureArrayPort8LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort8Entry 37 }

                                    sensorProbeThermostatTemperatureArrayPort8NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort8Entry 38 }

                                    sensorProbeThermostatTemperatureArrayPort8HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort8Entry 39 }

                                    sensorProbeThermostatTemperatureArrayPort8HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort8Entry 40 }

                                    sensorProbeThermostatTemperatureArrayPort8LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort8Entry 41 }

                                    sensorProbeThermostatTemperatureArrayPort8LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort8Entry 42 }

                                    sensorProbeThermostatTemperatureArrayPort8EnableTime OBJECT-TYPE
                                       SYNTAX  DisplayString
                                       ACCESS  read-write
                                       STATUS  mandatory
                                       DESCRIPTION
                                       "Time to enable on Thermostat"
                                       ::=  {  sensorProbeTemperatureArrayPort8Entry 43 }

                  sensorProbeNoCameraSensor OBJECT IDENTIFIER ::= { sensorProbeOtherSensor 34  }

                     sensorProbeNoCameraSensorNumber OBJECT-TYPE
                        SYNTAX INTEGER
                        ACCESS read-only
                        STATUS mandatory
                        DESCRIPTION
                        "The total number of no camera sensor port."
                        ::= {  sensorProbeNoCameraSensor 1 }

                     sensorProbeNoCameraSensorTable OBJECT-TYPE
                        SYNTAX  SEQUENCE OF SensorProbeNoCameraSensorEntry
                        ACCESS  not-accessible
                        STATUS  mandatory
                        DESCRIPTION
                        "This table contains the data for every no camera Sensor. Each row in the table contains data for a different NoCamera Sensor."
                        ::=  {  sensorProbeNoCameraSensor 2   }

                        sensorProbeNoCameraSensorEntry OBJECT-TYPE
                           SYNTAX  SensorProbeNoCameraSensorEntry
                           ACCESS  not-accessible
                           STATUS  mandatory
                           DESCRIPTION
                           "This is an entry in the sensorProbeNoCameraSensorEntry Table"
                           INDEX         { sensorProbeNoCameraSensorIndex }
                           ::=  { sensorProbeNoCameraSensorTable 1 }

                        SensorProbeNoCameraSensorEntry ::= SEQUENCE {
                           sensorProbeNoCameraSensorIndex
                              INTEGER,
                           sensorProbeNoCameraDescription
                              DisplayString,
                           sensorProbeNoCameraStatus
                              INTEGER,
                           sensorProbeNoCameraOnline
                              INTEGER,
                           sensorProbeNoCameraGoOnline
                              INTEGER,
                           sensorProbeNoCameraContTimeHighCritical
                              INTEGER,
                           sensorProbeNoCameraContTimeNormal
                              INTEGER,
                           sensorProbeNoCameraCalendar
                              INTEGER
                        }

                           sensorProbeNoCameraSensorIndex OBJECT-TYPE
                              SYNTAX  INTEGER (0..3)
                              ACCESS  read-only
                              STATUS  mandatory
                              DESCRIPTION
                              "A unique value for each no camera sensor port."
                              ::=  {  sensorProbeNoCameraSensorEntry 1  }

                           sensorProbeNoCameraDescription OBJECT-TYPE
                              SYNTAX  DisplayString
                              ACCESS  read-write
                              STATUS  mandatory
                              DESCRIPTION
                              "A Description of this sensor"
                              ::=  {  sensorProbeNoCameraSensorEntry 2   }

                           sensorProbeNoCameraStatus OBJECT-TYPE
                              SYNTAX  INTEGER {
                                 noStatus(1),
                                 normal(2),
                                 highCritical(4),
                                 lowCritical(6),
                                 sensorError(7),
                                 relayOn(8),
                                 relayOff(9)
                              }
                              ACCESS  read-only
                              STATUS  mandatory
                              DESCRIPTION
                              "The current status of this Sensor."
                              ::=  {  sensorProbeNoCameraSensorEntry 4  }

                           sensorProbeNoCameraOnline OBJECT-TYPE
                              SYNTAX  INTEGER {
                                 online(1),
                                 offline(2)
                              }
                              ACCESS  read-only
                              STATUS  mandatory
                              DESCRIPTION
                              "If this Sensor is currently online"
                                 ::=  {  sensorProbeNoCameraSensorEntry 5  }

                           sensorProbeNoCameraGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeNoCameraSensorEntry 6  }

                           sensorProbeNoCameraContTimeHighCritical OBJECT-TYPE
                              SYNTAX INTEGER (0..65535)
                              ACCESS read-write
                              STATUS mandatory
                              DESCRIPTION
                              "Continuous time for this sensor to be in High Critical before accepting new Status."
                              ::= {  sensorProbeNoCameraSensorEntry 7 }

                           sensorProbeNoCameraContTimeNormal OBJECT-TYPE
                              SYNTAX INTEGER (0..65535)
                              ACCESS read-write
                              STATUS mandatory
                              DESCRIPTION
                              "Continuous time for this sensor to be in Normal before accepting new Status."
                              ::= {  sensorProbeNoCameraSensorEntry 8 }

                           sensorProbeNoCameraCalendar OBJECT-TYPE
                              SYNTAX INTEGER {
                                 disable(0),
                                 enable(1)
                              }
                              ACCESS read-write
                              STATUS mandatory
                              DESCRIPTION
                              "Enable or disable the calendar filtering working hours of sensor."
                              ::= {  sensorProbeNoCameraSensorEntry 9 }

                  sensorProbeSoftMotionSensor OBJECT IDENTIFIER ::= { sensorProbeOtherSensor 35  }

                     sensorProbeSoftMotionSensorNumber OBJECT-TYPE
                        SYNTAX INTEGER
                        ACCESS read-only
                        STATUS mandatory
                        DESCRIPTION
                        "The total number of SoftMotionSensor port."
                        ::= {  sensorProbeSoftMotionSensor 1 }

                     sensorProbeSoftMotionSensorTable OBJECT-TYPE
                        SYNTAX  SEQUENCE OF SensorProbeSoftMotionSensorEntry
                        ACCESS  not-accessible
                        STATUS  mandatory
                        DESCRIPTION
                        "This table contains the data for every SoftMotion Sensor. Each row in the table contains data for a different SoftMotion Sensor."
                        ::=  {  sensorProbeSoftMotionSensor 2   }

                        sensorProbeSoftMotionSensorEntry OBJECT-TYPE
                           SYNTAX  SensorProbeSoftMotionSensorEntry
                           ACCESS  not-accessible
                           STATUS  mandatory
                           DESCRIPTION
                           "This is an entry in the sensorProbeSoftMotionSensorEntry Table"
                           INDEX         { sensorProbeSoftMotionSensorIndex }
                           ::=  { sensorProbeSoftMotionSensorTable 1 }

                        SensorProbeSoftMotionSensorEntry ::= SEQUENCE {
                           sensorProbeSoftMotionSensorIndex
                              INTEGER,
                           sensorProbeSoftMotionDescription
                              DisplayString,
                           sensorProbeSoftMotionStatus
                              INTEGER,
                           sensorProbeSoftMotionOnline
                              INTEGER,
                           sensorProbeSoftMotionGoOnline
                              INTEGER,
                           sensorProbeSoftMotionPercentSensitivity
                              INTEGER,
                           sensorProbeSoftMotionURL
                              DisplayString,
                           sensorProbeSoftMotionOpenURL
                              INTEGER,
                           sensorProbeSoftMotionContTimeHighCritical
                              INTEGER,
                           sensorProbeSoftMotionContTimeNormal
                              INTEGER,
                           sensorProbeSoftMotionCalendar
                              INTEGER,
                           sensorProbeSoftMotionMask
                              INTEGER
                        }

                           sensorProbeSoftMotionSensorIndex OBJECT-TYPE
                              SYNTAX  INTEGER (0..3)
                              ACCESS  read-only
                              STATUS  mandatory
                              DESCRIPTION
                              "A unique value for each soft motion sensor port."
                              ::=  {  sensorProbeSoftMotionSensorEntry 1  }

                           sensorProbeSoftMotionDescription OBJECT-TYPE
                              SYNTAX  DisplayString
                              ACCESS  read-write
                              STATUS  mandatory
                              DESCRIPTION
                              "A Description of this sensor"
                              ::=  {  sensorProbeSoftMotionSensorEntry 2   }

                           sensorProbeSoftMotionStatus OBJECT-TYPE
                              SYNTAX  INTEGER {
                                 noStatus(1),
                                 normal(2),
                                 highCritical(4),
                                 lowCritical(6),
                                 sensorError(7),
                                 relayOn(8),
                                 relayOff(9)
                              }
                              ACCESS  read-only
                              STATUS  mandatory
                              DESCRIPTION
                              "The current status of this Sensor."
                              ::=  {  sensorProbeSoftMotionSensorEntry 4  }

                           sensorProbeSoftMotionOnline OBJECT-TYPE
                              SYNTAX  INTEGER {
                                 online(1),
                                 offline(2)
                              }
                              ACCESS  read-only
                              STATUS  mandatory
                              DESCRIPTION
                              "If this Sensor is currently online"
                                 ::=  {  sensorProbeSoftMotionSensorEntry 5  }

                           sensorProbeSoftMotionGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeSoftMotionSensorEntry 6  }

                           sensorProbeSoftMotionPercentSensitivity OBJECT-TYPE
                              SYNTAX INTEGER (0..100)
                              ACCESS read-write
                              STATUS mandatory
                              DESCRIPTION
                              "The percent of sensitivity uses for setting the sentisitivity of motion detector."
                              ::= {  sensorProbeSoftMotionSensorEntry 7 }

                           sensorProbeSoftMotionURL OBJECT-TYPE
                              SYNTAX  DisplayString
                              ACCESS  read-write
                              STATUS  mandatory
                              DESCRIPTION
                              "Sensor URL link."
                              ::=  {  sensorProbeSoftMotionSensorEntry 8   }

                           sensorProbeSoftMotionOpenURL OBJECT-TYPE
                              SYNTAX  INTEGER {
                                 cur-window(0),
                                 new-window(2)
                              }
                              ACCESS  read-write
                              STATUS  mandatory
                              DESCRIPTION
                              "Open URL in this browser or open in a new window."
                              ::=  {  sensorProbeSoftMotionSensorEntry 9   }

                           sensorProbeSoftMotionContTimeHighCritical OBJECT-TYPE
                              SYNTAX INTEGER (0..65535)
                              ACCESS read-write
                              STATUS mandatory
                              DESCRIPTION
                              "Continuous time for this sensor to be in High Critical before accepting new Status."
                              ::= {  sensorProbeSoftMotionSensorEntry 10 }

                           sensorProbeSoftMotionContTimeNormal OBJECT-TYPE
                              SYNTAX INTEGER (0..65535)
                              ACCESS read-write
                              STATUS mandatory
                              DESCRIPTION
                              "Continuous time for this sensor to be in Normal before accepting new Status."
                              ::= {  sensorProbeSoftMotionSensorEntry 11 }

                           sensorProbeSoftMotionCalendar OBJECT-TYPE
                              SYNTAX INTEGER {
                                 disable(0),
                                 enable(1)
                              }
                              ACCESS read-write
                              STATUS mandatory
                              DESCRIPTION
                              "Enable or disable the calendar filtering working hours of sensor."
                              ::= {  sensorProbeSoftMotionSensorEntry 12 }

                           sensorProbeSoftMotionMask OBJECT-TYPE
                              SYNTAX INTEGER (0..33554431)
                              ACCESS read-write
                              STATUS mandatory
                              DESCRIPTION
                              "Mask of enable or disable of SoftMotion."
                              ::= {  sensorProbeSoftMotionSensorEntry 13 }

                  sensorProbeSoundDetectorSensor OBJECT IDENTIFIER ::= { sensorProbeOtherSensor 36  }

                     sensorProbeSoundDetectorSensorNumber OBJECT-TYPE
                        SYNTAX INTEGER
                        ACCESS read-only
                        STATUS mandatory
                        DESCRIPTION
                        "The total number of SoundDetectorSensor port."
                        ::= {  sensorProbeSoundDetectorSensor 1 }

                     sensorProbeSoundDetectorSensorTable OBJECT-TYPE
                        SYNTAX  SEQUENCE OF SensorProbeSoundDetectorSensorEntry
                        ACCESS  not-accessible
                        STATUS  mandatory
                        DESCRIPTION
                        "This table contains the data for every SoundDetectorSensor Sensor. Each row in the table contains data for a different SoundDetectorSensor Sensor."
                        ::=  {  sensorProbeSoundDetectorSensor 2   }

                        sensorProbeSoundDetectorSensorEntry OBJECT-TYPE
                           SYNTAX  SensorProbeSoundDetectorSensorEntry
                           ACCESS  not-accessible
                           STATUS  mandatory
                           DESCRIPTION
                           "This is an entry in the sensorProbeSoundDetectorSensorEntry Table"
                           INDEX         { sensorProbeSoundDetectorIndex }
                           ::=  { sensorProbeSoundDetectorSensorTable 1 }

                        SensorProbeSoundDetectorSensorEntry ::= SEQUENCE {
                           sensorProbeSoundDetectorIndex
                              INTEGER,
                           sensorProbeSoundDetectorDescription
                              DisplayString,
                           sensorProbeSoundDetectorValue
                              INTEGER,
                           sensorProbeSoundDetectorStatus
                              INTEGER,
                           sensorProbeSoundDetectorOnline
                              INTEGER,
                           sensorProbeSoundDetectorGoOnline
                              INTEGER,
                           sensorProbeSoundDetectorHighWarning
                              INTEGER,
                           sensorProbeSoundDetectorHighCritical
                              INTEGER,
                           sensorProbeSoundDetectorLowWarning
                              INTEGER,
                           sensorProbeSoundDetectorLowCritical
                              INTEGER,
                           sensorProbeSoundDetectorRearm
                              INTEGER,
                           sensorProbeSoundDetectorRecordingSource
                              INTEGER,
                           sensorProbeSoundDetectorMicBoost
                              INTEGER,
                           sensorProbeSoundDetectorMicSensitivity
                              INTEGER,
                           sensorProbeSoundDetectorPulseLength
                              INTEGER,
                           sensorProbeSoundDetectorURL
                              DisplayString,
                           sensorProbeSoundDetectorOpenURL
                              INTEGER,
                           sensorProbeSoundDetectorDatacollectType
                              INTEGER,
                           sensorProbeSoundDetectorContTimeHighCritical
                              INTEGER,
                           sensorProbeSoundDetectorContTimeHighWarning
                              INTEGER,
                           sensorProbeSoundDetectorContTimeNormal
                              INTEGER,
                           sensorProbeSoundDetectorContTimeLowWarning
                              INTEGER,
                           sensorProbeSoundDetectorContTimeLowCritical
                              INTEGER,
                           sensorProbeSoundDetectorContTimeSensorError
                              INTEGER,
                           sensorProbeSoundDetectorCalendar
                              INTEGER
                        }

                           sensorProbeSoundDetectorIndex OBJECT-TYPE
                              SYNTAX  INTEGER (0)
                              ACCESS  read-only
                              STATUS  mandatory
                              DESCRIPTION
                              "A unique value for each sound detector sensor port."
                              ::=  {  sensorProbeSoundDetectorSensorEntry 1  }

                           sensorProbeSoundDetectorDescription OBJECT-TYPE
                              SYNTAX  DisplayString
                              ACCESS  read-write
                              STATUS  mandatory
                              DESCRIPTION
                              "A Description of this sensor"
                              ::=  {  sensorProbeSoundDetectorSensorEntry 2   }

                           sensorProbeSoundDetectorValue OBJECT-TYPE
                              SYNTAX  INTEGER
                              ACCESS  read-only
                              STATUS  mandatory
                              DESCRIPTION
                              "The value in this sensor"
                              ::=  {  sensorProbeSoundDetectorSensorEntry 3   }

                           sensorProbeSoundDetectorStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeSoundDetectorSensorEntry 4   }

                           sensorProbeSoundDetectorOnline OBJECT-TYPE
                              SYNTAX  INTEGER {
                                 online(1),
                                 offline(2)
                              }
                              ACCESS  read-only
                              STATUS  mandatory
                              DESCRIPTION
                              "If this Sensor is currently online"
                              ::=  {  sensorProbeSoundDetectorSensorEntry 5   }

                           sensorProbeSoundDetectorGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeSoundDetectorSensorEntry 6   }

                           sensorProbeSoundDetectorHighWarning OBJECT-TYPE
                              SYNTAX  INTEGER
                              ACCESS  read-write
                              STATUS  mandatory
                              DESCRIPTION
                              "How hot this  sensor gets before it sends a warning"
                              ::=  {  sensorProbeSoundDetectorSensorEntry 7   }

                           sensorProbeSoundDetectorHighCritical OBJECT-TYPE
                              SYNTAX  INTEGER
                              ACCESS  read-write
                              STATUS  mandatory
                              DESCRIPTION
                              "How hot this sensor gets before it sends a critical event"
                              ::=  {  sensorProbeSoundDetectorSensorEntry 8   }

                           sensorProbeSoundDetectorLowWarning OBJECT-TYPE
                              SYNTAX  INTEGER
                              ACCESS  read-write
                              STATUS  mandatory
                              DESCRIPTION
                              "How cold this sensor gets before it sends a warning"
                              ::=  {  sensorProbeSoundDetectorSensorEntry 9   }

                           sensorProbeSoundDetectorLowCritical OBJECT-TYPE
                              SYNTAX  INTEGER
                              ACCESS  read-write
                              STATUS  mandatory
                              DESCRIPTION
                              "How cold this sensor gets before it sends a critical event"
                              ::=  {  sensorProbeSoundDetectorSensorEntry 10   }

                           sensorProbeSoundDetectorRearm OBJECT-TYPE
                              SYNTAX  INTEGER
                              ACCESS  read-write
                              STATUS  mandatory
                              DESCRIPTION
                              "The number of degrees to rearm the status. For example if status goes from normal to warning, the temp must go down Rearm degrees below warning before the status goes to normal"
                              ::=  {  sensorProbeSoundDetectorSensorEntry 11   }

                           sensorProbeSoundDetectorRecordingSource OBJECT-TYPE
                              SYNTAX  INTEGER {
                                 internal-mic(0),
                                 line-in(1)
                              }
                              ACCESS  read-write
                              STATUS  mandatory
                              DESCRIPTION
                              "To select a recording source being in internal microphone(0) or in line-in(1)."
                              ::=  {  sensorProbeSoundDetectorSensorEntry 12   }

                           sensorProbeSoundDetectorMicBoost OBJECT-TYPE
                              SYNTAX  INTEGER {
                                 off(0),
                                 on(1)
                              }
                              ACCESS  read-write
                              STATUS  mandatory
                              DESCRIPTION
                              "Enable or disable a microphone boost(+20 db)."
                              ::=  {  sensorProbeSoundDetectorSensorEntry 13   }

                           sensorProbeSoundDetectorMicSensitivity OBJECT-TYPE
                              SYNTAX  INTEGER {
                                 i0(0),
                                 i20(20),
                                 i40(40),
                                 i60(60),
                                 i80(80),
                                 i100(100)
                              }
                              ACCESS  read-write
                              STATUS  mandatory
                              DESCRIPTION
                              "The sensitivity of microphone to detect sound."
                              ::=  {  sensorProbeSoundDetectorSensorEntry 14   }

                           sensorProbeSoundDetectorPulseLength OBJECT-TYPE
                              SYNTAX  INTEGER
                              ACCESS  read-write
                              STATUS  mandatory
                              DESCRIPTION
                              "Continuous time for detecting before changing status."
                              ::=  {  sensorProbeSoundDetectorSensorEntry 15   }

                           sensorProbeSoundDetectorURL OBJECT-TYPE
                              SYNTAX  DisplayString
                              ACCESS  read-write
                              STATUS  mandatory
                              DESCRIPTION
                              "Sensor URL link."
                              ::=  {  sensorProbeSoundDetectorSensorEntry 16   }

                           sensorProbeSoundDetectorOpenURL OBJECT-TYPE
                              SYNTAX  INTEGER {
                                 cur-window(0),
                                 new-window(2)
                              }
                              ACCESS  read-write
                              STATUS  mandatory
                              DESCRIPTION
                              "Open URL in this browser or open in a new window."
                              ::=  {  sensorProbeSoundDetectorSensorEntry 17   }

                           sensorProbeSoundDetectorDatacollectType OBJECT-TYPE
                              SYNTAX  INTEGER {
                                 average(1),
                                 highest(2),
                                 lowest(3)
                              }
                              ACCESS  read-write
                              STATUS  mandatory
                              DESCRIPTION
                              "Type of datacollect to collect."
                              ::=  {  sensorProbeSoundDetectorSensorEntry 18   }

                           sensorProbeSoundDetectorContTimeHighCritical OBJECT-TYPE
                              SYNTAX INTEGER (0..65535)
                              ACCESS read-write
                              STATUS mandatory
                              DESCRIPTION
                              "Continuous time for this sensor to be in High Critical before accepting new Status."
                              ::= {  sensorProbeSoundDetectorSensorEntry 19 }

                           sensorProbeSoundDetectorContTimeHighWarning OBJECT-TYPE
                              SYNTAX INTEGER (0..65535)
                              ACCESS read-write
                              STATUS mandatory
                              DESCRIPTION
                              "Continuous time for this sensor to be in High Warning before accepting new Status."
                              ::= {  sensorProbeSoundDetectorSensorEntry 20 }

                           sensorProbeSoundDetectorContTimeNormal OBJECT-TYPE
                              SYNTAX INTEGER (0..65535)
                              ACCESS read-write
                              STATUS mandatory
                              DESCRIPTION
                              "Continuous time for this sensor to be in Normal before accepting new Status."
                              ::= {  sensorProbeSoundDetectorSensorEntry 21 }

                           sensorProbeSoundDetectorContTimeLowWarning OBJECT-TYPE
                              SYNTAX INTEGER (0..65535)
                              ACCESS read-write
                              STATUS mandatory
                              DESCRIPTION
                              "Continuous time for this sensor to be in Low Warning before accepting new Status."
                              ::= {  sensorProbeSoundDetectorSensorEntry 22 }

                           sensorProbeSoundDetectorContTimeLowCritical OBJECT-TYPE
                              SYNTAX INTEGER (0..65535)
                              ACCESS read-write
                              STATUS mandatory
                              DESCRIPTION
                              "Continuous time for this sensor to be in Low Critical before accepting new Status."
                              ::= {  sensorProbeSoundDetectorSensorEntry 23 }

                           sensorProbeSoundDetectorContTimeSensorError OBJECT-TYPE
                              SYNTAX INTEGER (0..65535)
                              ACCESS read-write
                              STATUS mandatory
                              DESCRIPTION
                              "Continuous time for this sensor to be in Sensor Error before accepting new Status."
                              ::= {  sensorProbeSoundDetectorSensorEntry 24 }

                           sensorProbeSoundDetectorCalendar OBJECT-TYPE
                              SYNTAX INTEGER {
                                 disable(0),
                                 enable(1)
                              }
                              ACCESS read-write
                              STATUS mandatory
                              DESCRIPTION
                              "Enable or disable the calendar filtering working hours of sensor."
                              ::= {  sensorProbeSoundDetectorSensorEntry 25 }

                        sensorProbeDrycontactArraySensor OBJECT IDENTIFIER ::= { sensorProbeOtherSensor 37  }

                           sensorProbeDrycontactArrayPort1 OBJECT IDENTIFIER ::= { sensorProbeDrycontactArraySensor 1  }
                              sensorProbeDrycontactArrayPort1Number OBJECT-TYPE
                                 SYNTAX INTEGER
                                 ACCESS read-only
                                 STATUS mandatory
                                 DESCRIPTION
                                 "The total number of port on the DrycontactArray."
                                 ::=  {  sensorProbeDrycontactArrayPort1 1   }

                              sensorProbeDrycontactArrayPort1Table OBJECT-TYPE
                                 SYNTAX  SEQUENCE OF SensorProbeDrycontactArrayPort1Entry
                                 ACCESS  not-accessible
                                 STATUS  mandatory
                                 DESCRIPTION
                                 "This table contains the data for every Drycontact Sensor in the SensorArray. Each row in the table contains data for a different Drycontact Sensor."
                                 ::=  {  sensorProbeDrycontactArrayPort1 2   }

                                 sensorProbeDrycontactArrayPort1Entry OBJECT-TYPE
                                    SYNTAX  SensorProbeDrycontactArrayPort1Entry
                                    ACCESS  not-accessible
                                    STATUS  mandatory
                                    DESCRIPTION
                                    "This is an entry in the sensorProbeDrycontactArrayPort1 Table"
                                    INDEX         { sensorProbeDrycontactArrayPort1Index }
                                    ::=  { sensorProbeDrycontactArrayPort1Table 1 }

                                    SensorProbeDrycontactArrayPort1Entry ::= SEQUENCE {
                                       sensorProbeDrycontactArrayPort1Index
                                          INTEGER,
                                       sensorProbeDrycontactArrayPort1Description
                                          DisplayString,
                                       sensorProbeDrycontactArrayPort1Status
                                          INTEGER,
                                       sensorProbeDrycontactArrayPort1Online
                                          INTEGER,
                                       sensorProbeDrycontactArrayPort1GoOnline
                                          INTEGER,
                                       sensorProbeDrycontactArrayPort1NormalState
                                          INTEGER,
                                       sensorProbeDrycontactArrayPort1Direction
                                          INTEGER,
                                       sensorProbeDrycontactArrayPort1ContTimeCritical
                                          INTEGER,
                                       sensorProbeDrycontactArrayPort1ContTimeNormal
                                          INTEGER,
                                       sensorProbeDrycontactArrayPort1ManualOutputCycleTime
                                          INTEGER,
                                       sensorProbeDrycontactArrayPort1ManualOutputAction
                                          INTEGER,
                                       sensorProbeDrycontactArrayPort1OutputDescOn
                                          DisplayString,
                                       sensorProbeDrycontactArrayPort1OutputDescOff
                                          DisplayString,
                                       sensorProbeDrycontactArrayPort1URL
                                          DisplayString,
                                       sensorProbeDrycontactArrayPort1OpenURL
                                          INTEGER,
                                       sensorProbeDrycontactArrayPort1ControlMode
                                          INTEGER
                                    }

                                    sensorProbeDrycontactArrayPort1Index OBJECT-TYPE
                                       SYNTAX  INTEGER (0..7)
                                       ACCESS  read-only
                                       STATUS  mandatory
                                       DESCRIPTION
                                       "A unique value for each sensor DrycontactArray port."
                                       ::=  {  sensorProbeDrycontactArrayPort1Entry 1   }

                                    sensorProbeDrycontactArrayPort1Description OBJECT-TYPE
                                       SYNTAX  DisplayString
                                       ACCESS  read-write
                                       STATUS  mandatory
                                       DESCRIPTION
                                       "A Description of this sensor DrycontactArray"
                                       ::=  {  sensorProbeDrycontactArrayPort1Entry 2   }

                                    sensorProbeDrycontactArrayPort1Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort1Entry 4  }

                                    sensorProbeDrycontactArrayPort1Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort1Entry 5  }

                                    sensorProbeDrycontactArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort1Entry 6  }

                                    sensorProbeDrycontactArrayPort1NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort1Entry 7  }

                                    sensorProbeDrycontactArrayPort1Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort1Entry 8  }

                                    sensorProbeDrycontactArrayPort1ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort1Entry 9   }

                                    sensorProbeDrycontactArrayPort1ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort1Entry 10   }

                                    sensorProbeDrycontactArrayPort1ManualOutputCycleTime OBJECT-TYPE
                                       SYNTAX INTEGER (1..255)
                                       ACCESS read-write
                                       STATUS mandatory
                                       DESCRIPTION
                                       "Drycontact output toggle period in seconds for Manual Cycle action."
                                       ::= { sensorProbeDrycontactArrayPort1Entry 24 }

                                    sensorProbeDrycontactArrayPort1ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the drycontact output manualy"
                                       ::=  {  sensorProbeDrycontactArrayPort1Entry 25 }

                                    sensorProbeDrycontactArrayPort1OutputDescOn OBJECT-TYPE
                                       SYNTAX  DisplayString
                                       ACCESS  read-write
                                       STATUS  mandatory
                                       DESCRIPTION
                                       "Description of Drycontact output On"
                                       ::=  {  sensorProbeDrycontactArrayPort1Entry 26   }

                                    sensorProbeDrycontactArrayPort1OutputDescOff OBJECT-TYPE
                                       SYNTAX  DisplayString
                                       ACCESS  read-write
                                       STATUS  mandatory
                                       DESCRIPTION
                                       "Description of Drycontact output Off"
                                       ::=  {  sensorProbeDrycontactArrayPort1Entry 27   }

                                    sensorProbeDrycontactArrayPort1URL OBJECT-TYPE
                                       SYNTAX  DisplayString
                                       ACCESS  read-write
                                       STATUS  mandatory
                                       DESCRIPTION
                                       "Sersor URL link."
                                       ::=  {  sensorProbeDrycontactArrayPort1Entry 28   }

                                    sensorProbeDrycontactArrayPort1OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort1Entry 29   }

                                    sensorProbeDrycontactArrayPort1ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a drycontact output."
                                       ::=  {  sensorProbeDrycontactArrayPort1Entry 30  }

                           sensorProbeDrycontactArrayPort2 OBJECT IDENTIFIER ::= { sensorProbeDrycontactArraySensor 2  }
                              sensorProbeDrycontactArrayPort2Number OBJECT-TYPE
                                 SYNTAX INTEGER
                                 ACCESS read-only
                                 STATUS mandatory
                                 DESCRIPTION
                                 "The total number of port on the DrycontactArray."
                                 ::=  {  sensorProbeDrycontactArrayPort2 1   }

                              sensorProbeDrycontactArrayPort2Table OBJECT-TYPE
                                 SYNTAX  SEQUENCE OF SensorProbeDrycontactArrayPort2Entry
                                 ACCESS  not-accessible
                                 STATUS  mandatory
                                 DESCRIPTION
                                 "This table contains the data for every Drycontact Sensor in the SensorArray. Each row in the table contains data for a different Drycontact Sensor."
                                 ::=  {  sensorProbeDrycontactArrayPort2 2   }

                                 sensorProbeDrycontactArrayPort2Entry OBJECT-TYPE
                                    SYNTAX  SensorProbeDrycontactArrayPort2Entry
                                    ACCESS  not-accessible
                                    STATUS  mandatory
                                    DESCRIPTION
                                    "This is an entry in the sensorProbeDrycontactArrayPort2 Table"
                                    INDEX         { sensorProbeDrycontactArrayPort2Index }
                                    ::=  { sensorProbeDrycontactArrayPort2Table 1 }

                                    SensorProbeDrycontactArrayPort2Entry ::= SEQUENCE {
                                       sensorProbeDrycontactArrayPort2Index
                                          INTEGER,
                                       sensorProbeDrycontactArrayPort2Description
                                          DisplayString,
                                       sensorProbeDrycontactArrayPort2Status
                                          INTEGER,
                                       sensorProbeDrycontactArrayPort2Online
                                          INTEGER,
                                       sensorProbeDrycontactArrayPort2GoOnline
                                          INTEGER,
                                       sensorProbeDrycontactArrayPort2NormalState
                                          INTEGER,
                                       sensorProbeDrycontactArrayPort2Direction
                                          INTEGER,
                                       sensorProbeDrycontactArrayPort2ContTimeCritical
                                          INTEGER,
                                       sensorProbeDrycontactArrayPort2ContTimeNormal
                                          INTEGER,
                                       sensorProbeDrycontactArrayPort2ManualOutputCycleTime
                                          INTEGER,
                                       sensorProbeDrycontactArrayPort2ManualOutputAction
                                          INTEGER,
                                       sensorProbeDrycontactArrayPort2OutputDescOn
                                          DisplayString,
                                       sensorProbeDrycontactArrayPort2OutputDescOff
                                          DisplayString,
                                       sensorProbeDrycontactArrayPort2URL
                                          DisplayString,
                                       sensorProbeDrycontactArrayPort2OpenURL
                                          INTEGER,
                                       sensorProbeDrycontactArrayPort2ControlMode
                                          INTEGER
                                    }

                                    sensorProbeDrycontactArrayPort2Index OBJECT-TYPE
                                       SYNTAX  INTEGER (0..7)
                                       ACCESS  read-only
                                       STATUS  mandatory
                                       DESCRIPTION
                                       "A unique value for each sensor DrycontactArray port."
                                       ::=  {  sensorProbeDrycontactArrayPort2Entry 1   }

                                    sensorProbeDrycontactArrayPort2Description OBJECT-TYPE
                                       SYNTAX  DisplayString
                                       ACCESS  read-write
                                       STATUS  mandatory
                                       DESCRIPTION
                                       "A Description of this sensor DrycontactArray"
                                       ::=  {  sensorProbeDrycontactArrayPort2Entry 2   }

                                    sensorProbeDrycontactArrayPort2Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort2Entry 4  }

                                    sensorProbeDrycontactArrayPort2Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort2Entry 5  }

                                    sensorProbeDrycontactArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort2Entry 6  }

                                    sensorProbeDrycontactArrayPort2NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort2Entry 7  }

                                    sensorProbeDrycontactArrayPort2Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort2Entry 8  }

                                    sensorProbeDrycontactArrayPort2ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort2Entry 9   }

                                    sensorProbeDrycontactArrayPort2ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort2Entry 10   }

                                    sensorProbeDrycontactArrayPort2ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort2Entry 24 }

                                    sensorProbeDrycontactArrayPort2ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort2Entry 25 }

                                    sensorProbeDrycontactArrayPort2OutputDescOn OBJECT-TYPE
                                       SYNTAX  DisplayString
                                       ACCESS  read-write
                                       STATUS  mandatory
                                       DESCRIPTION
                                       "Description of Drycontact output On"
                                       ::=  {  sensorProbeDrycontactArrayPort2Entry 26   }

                                    sensorProbeDrycontactArrayPort2OutputDescOff OBJECT-TYPE
                                       SYNTAX  DisplayString
                                       ACCESS  read-write
                                       STATUS  mandatory
                                       DESCRIPTION
                                       "Description of Drycontact output Off"
                                       ::=  {  sensorProbeDrycontactArrayPort2Entry 27   }

                                    sensorProbeDrycontactArrayPort2URL OBJECT-TYPE
                                       SYNTAX  DisplayString
                                       ACCESS  read-write
                                       STATUS  mandatory
                                       DESCRIPTION
                                       "Sensor URL link"
                                       ::=  {  sensorProbeDrycontactArrayPort2Entry 28   }

                                    sensorProbeDrycontactArrayPort2OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort2Entry 29   }

                                    sensorProbeDrycontactArrayPort2ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort2Entry 30  }

                           sensorProbeDrycontactArrayPort3 OBJECT IDENTIFIER ::= { sensorProbeDrycontactArraySensor 3  }
                              sensorProbeDrycontactArrayPort3Number OBJECT-TYPE
                                 SYNTAX INTEGER
                                 ACCESS read-only
                                 STATUS mandatory
                                 DESCRIPTION
                                 "The total number of port on the DrycontactArray."
                                 ::=  {  sensorProbeDrycontactArrayPort3 1   }

                              sensorProbeDrycontactArrayPort3Table OBJECT-TYPE
                                 SYNTAX  SEQUENCE OF SensorProbeDrycontactArrayPort3Entry
                                 ACCESS  not-accessible
                                 STATUS  mandatory
                                 DESCRIPTION
                                 "This table contains the data for every Drycontact Sensor in the SensorArray. Each row in the table contains data for a different Drycontact Sensor."
                                 ::=  {  sensorProbeDrycontactArrayPort3 2   }

                                 sensorProbeDrycontactArrayPort3Entry OBJECT-TYPE
                                    SYNTAX  SensorProbeDrycontactArrayPort3Entry
                                    ACCESS  not-accessible
                                    STATUS  mandatory
                                    DESCRIPTION
                                    "This is an entry in the sensorProbeDrycontactArrayPort3 Table"
                                    INDEX         { sensorProbeDrycontactArrayPort3Index }
                                    ::=  { sensorProbeDrycontactArrayPort3Table 1 }

                                    SensorProbeDrycontactArrayPort3Entry ::= SEQUENCE {
                                       sensorProbeDrycontactArrayPort3Index
                                          INTEGER,
                                       sensorProbeDrycontactArrayPort3Description
                                          DisplayString,
                                       sensorProbeDrycontactArrayPort3Status
                                          INTEGER,
                                       sensorProbeDrycontactArrayPort3Online
                                          INTEGER,
                                       sensorProbeDrycontactArrayPort3GoOnline
                                          INTEGER,
                                       sensorProbeDrycontactArrayPort3NormalState
                                          INTEGER,
                                       sensorProbeDrycontactArrayPort3Direction
                                          INTEGER,
                                       sensorProbeDrycontactArrayPort3ContTimeCritical
                                          INTEGER,
                                       sensorProbeDrycontactArrayPort3ContTimeNormal
                                          INTEGER,
                                       sensorProbeDrycontactArrayPort3ManualOutputCycleTime
                                          INTEGER,
                                       sensorProbeDrycontactArrayPort3ManualOutputAction
                                          INTEGER,
                                       sensorProbeDrycontactArrayPort3OutputDescOn
                                          DisplayString,
                                       sensorProbeDrycontactArrayPort3OutputDescOff
                                          DisplayString,
                                       sensorProbeDrycontactArrayPort3URL
                                          DisplayString,
                                       sensorProbeDrycontactArrayPort3OpenURL
                                          INTEGER,
                                       sensorProbeDrycontactArrayPort3ControlMode
                                          INTEGER
                                    }

                                    sensorProbeDrycontactArrayPort3Index OBJECT-TYPE
                                       SYNTAX  INTEGER (0..7)
                                       ACCESS  read-only
                                       STATUS  mandatory
                                       DESCRIPTION
                                       "A unique value for each sensor DrycontactArray port."
                                       ::=  {  sensorProbeDrycontactArrayPort3Entry 1   }

                                    sensorProbeDrycontactArrayPort3Description OBJECT-TYPE
                                       SYNTAX  DisplayString
                                       ACCESS  read-write
                                       STATUS  mandatory
                                       DESCRIPTION
                                       "A Description of this sensor DrycontactArray"
                                       ::=  {  sensorProbeDrycontactArrayPort3Entry 2   }

                                    sensorProbeDrycontactArrayPort3Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort3Entry 4  }

                                    sensorProbeDrycontactArrayPort3Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort3Entry 5  }

                                    sensorProbeDrycontactArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort3Entry 6  }

                                    sensorProbeDrycontactArrayPort3NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort3Entry 7  }

                                    sensorProbeDrycontactArrayPort3Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort3Entry 8  }

                                    sensorProbeDrycontactArrayPort3ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort3Entry 9   }

                                    sensorProbeDrycontactArrayPort3ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort3Entry 10   }

                                    sensorProbeDrycontactArrayPort3ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort3Entry 24 }

                                    sensorProbeDrycontactArrayPort3ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort3Entry 25 }

                                    sensorProbeDrycontactArrayPort3OutputDescOn OBJECT-TYPE
                                       SYNTAX  DisplayString
                                       ACCESS  read-write
                                       STATUS  mandatory
                                       DESCRIPTION
                                       "Description of Drycontact output On"
                                       ::=  {  sensorProbeDrycontactArrayPort3Entry 26   }

                                    sensorProbeDrycontactArrayPort3OutputDescOff OBJECT-TYPE
                                       SYNTAX  DisplayString
                                       ACCESS  read-write
                                       STATUS  mandatory
                                       DESCRIPTION
                                       "Description of Drycontact output Off"
                                       ::=  {  sensorProbeDrycontactArrayPort3Entry 27   }

                                    sensorProbeDrycontactArrayPort3URL OBJECT-TYPE
                                       SYNTAX  DisplayString
                                       ACCESS  read-write
                                       STATUS  mandatory
                                       DESCRIPTION
                                       "Sensor URL link."
                                       ::=  {  sensorProbeDrycontactArrayPort3Entry 28   }

                                    sensorProbeDrycontactArrayPort3OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort3Entry 29   }

                                    sensorProbeDrycontactArrayPort3ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort3Entry 30  }

                           sensorProbeDrycontactArrayPort4 OBJECT IDENTIFIER ::= { sensorProbeDrycontactArraySensor 4  }
                              sensorProbeDrycontactArrayPort4Number OBJECT-TYPE
                                 SYNTAX INTEGER
                                 ACCESS read-only
                                 STATUS mandatory
                                 DESCRIPTION
                                 "The total number of port on the DrycontactArray."
                                 ::=  {  sensorProbeDrycontactArrayPort4 1   }

                              sensorProbeDrycontactArrayPort4Table OBJECT-TYPE
                                 SYNTAX  SEQUENCE OF SensorProbeDrycontactArrayPort4Entry
                                 ACCESS  not-accessible
                                 STATUS  mandatory
                                 DESCRIPTION
                                 "This table contains the data for every Drycontact Sensor in the SensorArray. Each row in the table contains data for a different Drycontact Sensor."
                                 ::=  {  sensorProbeDrycontactArrayPort4 2   }

                                 sensorProbeDrycontactArrayPort4Entry OBJECT-TYPE
                                    SYNTAX  SensorProbeDrycontactArrayPort4Entry
                                    ACCESS  not-accessible
                                    STATUS  mandatory
                                    DESCRIPTION
                                    "This is an entry in the sensorProbeDrycontactArrayPort4 Table"
                                    INDEX         { sensorProbeDrycontactArrayPort4Index }
                                    ::=  { sensorProbeDrycontactArrayPort4Table 1 }

                                    SensorProbeDrycontactArrayPort4Entry ::= SEQUENCE {
                                       sensorProbeDrycontactArrayPort4Index
                                          INTEGER,
                                       sensorProbeDrycontactArrayPort4Description
                                          DisplayString,
                                       sensorProbeDrycontactArrayPort4Status
                                          INTEGER,
                                       sensorProbeDrycontactArrayPort4Online
                                          INTEGER,
                                       sensorProbeDrycontactArrayPort4GoOnline
                                          INTEGER,
                                       sensorProbeDrycontactArrayPort4NormalState
                                          INTEGER,
                                       sensorProbeDrycontactArrayPort4Direction
                                          INTEGER,
                                       sensorProbeDrycontactArrayPort4ContTimeCritical
                                          INTEGER,
                                       sensorProbeDrycontactArrayPort4ContTimeNormal
                                          INTEGER,
                                       sensorProbeDrycontactArrayPort4ManualOutputCycleTime
                                          INTEGER,
                                       sensorProbeDrycontactArrayPort4ManualOutputAction
                                          INTEGER,
                                       sensorProbeDrycontactArrayPort4OutputDescOn
                                          DisplayString,
                                       sensorProbeDrycontactArrayPort4OutputDescOff
                                          DisplayString,
                                       sensorProbeDrycontactArrayPort4URL
                                          DisplayString,
                                       sensorProbeDrycontactArrayPort4OpenURL
                                          INTEGER,
                                       sensorProbeDrycontactArrayPort4ControlMode
                                          INTEGER
                                    }

                                    sensorProbeDrycontactArrayPort4Index OBJECT-TYPE
                                       SYNTAX  INTEGER (0..7)
                                       ACCESS  read-only
                                       STATUS  mandatory
                                       DESCRIPTION
                                       "A unique value for each sensor DrycontactArray port."
                                       ::=  {  sensorProbeDrycontactArrayPort4Entry 1   }

                                    sensorProbeDrycontactArrayPort4Description OBJECT-TYPE
                                       SYNTAX  DisplayString
                                       ACCESS  read-write
                                       STATUS  mandatory
                                       DESCRIPTION
                                       "A Description of this sensor DrycontactArray"
                                       ::=  {  sensorProbeDrycontactArrayPort4Entry 2   }

                                    sensorProbeDrycontactArrayPort4Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort4Entry 4  }

                                    sensorProbeDrycontactArrayPort4Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort4Entry 5  }

                                    sensorProbeDrycontactArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort4Entry 6  }

                                    sensorProbeDrycontactArrayPort4NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort4Entry 7  }

                                    sensorProbeDrycontactArrayPort4Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort4Entry 8  }

                                    sensorProbeDrycontactArrayPort4ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort4Entry 9   }

                                    sensorProbeDrycontactArrayPort4ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort4Entry 10   }

                                    sensorProbeDrycontactArrayPort4ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort4Entry 24 }

                                    sensorProbeDrycontactArrayPort4ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort4Entry 25 }

                                    sensorProbeDrycontactArrayPort4OutputDescOn OBJECT-TYPE
                                       SYNTAX  DisplayString
                                       ACCESS  read-write
                                       STATUS  mandatory
                                       DESCRIPTION
                                       "Description of Drycontact output On"
                                       ::=  {  sensorProbeDrycontactArrayPort4Entry 26   }

                                    sensorProbeDrycontactArrayPort4OutputDescOff OBJECT-TYPE
                                       SYNTAX  DisplayString
                                       ACCESS  read-write
                                       STATUS  mandatory
                                       DESCRIPTION
                                       "Description of Drycontact output Off"
                                       ::=  {  sensorProbeDrycontactArrayPort4Entry 27   }

                                    sensorProbeDrycontactArrayPort4URL OBJECT-TYPE
                                       SYNTAX  DisplayString
                                       ACCESS  read-write
                                       STATUS  mandatory
                                       DESCRIPTION
                                       "Sensor URL link."
                                       ::=  {  sensorProbeDrycontactArrayPort4Entry 28   }

                                    sensorProbeDrycontactArrayPort4OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort4Entry 29   }

                                    sensorProbeDrycontactArrayPort4ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort4Entry 30  }

                           sensorProbeDrycontactArrayPort5 OBJECT IDENTIFIER ::= { sensorProbeDrycontactArraySensor 5  }
                              sensorProbeDrycontactArrayPort5Number OBJECT-TYPE
                                 SYNTAX INTEGER
                                 ACCESS read-only
                                 STATUS mandatory
                                 DESCRIPTION
                                 "The total number of port on the DrycontactArray."
                                 ::=  {  sensorProbeDrycontactArrayPort5 1   }

                              sensorProbeDrycontactArrayPort5Table OBJECT-TYPE
                                 SYNTAX  SEQUENCE OF SensorProbeDrycontactArrayPort5Entry
                                 ACCESS  not-accessible
                                 STATUS  mandatory
                                 DESCRIPTION
                                 "This table contains the data for every Drycontact Sensor in the SensorArray. Each row in the table contains data for a different Drycontact Sensor."
                                 ::=  {  sensorProbeDrycontactArrayPort5 2   }

                                 sensorProbeDrycontactArrayPort5Entry OBJECT-TYPE
                                    SYNTAX  SensorProbeDrycontactArrayPort5Entry
                                    ACCESS  not-accessible
                                    STATUS  mandatory
                                    DESCRIPTION
                                    "This is an entry in the sensorProbeDrycontactArrayPort5 Table"
                                    INDEX         { sensorProbeDrycontactArrayPort5Index }
                                    ::=  { sensorProbeDrycontactArrayPort5Table 1 }

                                    SensorProbeDrycontactArrayPort5Entry ::= SEQUENCE {
                                       sensorProbeDrycontactArrayPort5Index
                                          INTEGER,
                                       sensorProbeDrycontactArrayPort5Description
                                          DisplayString,
                                       sensorProbeDrycontactArrayPort5Status
                                          INTEGER,
                                       sensorProbeDrycontactArrayPort5Online
                                          INTEGER,
                                       sensorProbeDrycontactArrayPort5GoOnline
                                          INTEGER,
                                       sensorProbeDrycontactArrayPort5NormalState
                                          INTEGER,
                                       sensorProbeDrycontactArrayPort5Direction
                                          INTEGER,
                                       sensorProbeDrycontactArrayPort5ContTimeCritical
                                          INTEGER,
                                       sensorProbeDrycontactArrayPort5ContTimeNormal
                                          INTEGER,
                                       sensorProbeDrycontactArrayPort5ManualOutputCycleTime
                                          INTEGER,
                                       sensorProbeDrycontactArrayPort5ManualOutputAction
                                          INTEGER,
                                       sensorProbeDrycontactArrayPort5OutputDescOn
                                          DisplayString,
                                       sensorProbeDrycontactArrayPort5OutputDescOff
                                          DisplayString,
                                       sensorProbeDrycontactArrayPort5URL
                                          DisplayString,
                                       sensorProbeDrycontactArrayPort5OpenURL
                                          INTEGER,
                                       sensorProbeDrycontactArrayPort5ControlMode
                                          INTEGER
                                    }

                                    sensorProbeDrycontactArrayPort5Index OBJECT-TYPE
                                       SYNTAX  INTEGER (0..7)
                                       ACCESS  read-only
                                       STATUS  mandatory
                                       DESCRIPTION
                                       "A unique value for each sensor DrycontactArray port."
                                       ::=  {  sensorProbeDrycontactArrayPort5Entry 1   }

                                    sensorProbeDrycontactArrayPort5Description OBJECT-TYPE
                                       SYNTAX  DisplayString
                                       ACCESS  read-write
                                       STATUS  mandatory
                                       DESCRIPTION
                                       "A Description of this sensor DrycontactArray"
                                       ::=  {  sensorProbeDrycontactArrayPort5Entry 2   }

                                    sensorProbeDrycontactArrayPort5Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort5Entry 4  }

                                    sensorProbeDrycontactArrayPort5Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort5Entry 5  }

                                    sensorProbeDrycontactArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort5Entry 6  }

                                    sensorProbeDrycontactArrayPort5NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort5Entry 7  }

                                    sensorProbeDrycontactArrayPort5Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort5Entry 8  }

                                    sensorProbeDrycontactArrayPort5ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort5Entry 9   }

                                    sensorProbeDrycontactArrayPort5ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort5Entry 10   }

                                    sensorProbeDrycontactArrayPort5ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort5Entry 24 }

                                    sensorProbeDrycontactArrayPort5ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort5Entry 25 }

                                    sensorProbeDrycontactArrayPort5OutputDescOn OBJECT-TYPE
                                       SYNTAX  DisplayString
                                       ACCESS  read-write
                                       STATUS  mandatory
                                       DESCRIPTION
                                       "Description of Drycontact output On"
                                       ::=  {  sensorProbeDrycontactArrayPort5Entry 26   }

                                    sensorProbeDrycontactArrayPort5OutputDescOff OBJECT-TYPE
                                       SYNTAX  DisplayString
                                       ACCESS  read-write
                                       STATUS  mandatory
                                       DESCRIPTION
                                       "Description of Drycontact output Off"
                                       ::=  {  sensorProbeDrycontactArrayPort5Entry 27   }

                                    sensorProbeDrycontactArrayPort5URL OBJECT-TYPE
                                       SYNTAX  DisplayString
                                       ACCESS  read-write
                                       STATUS  mandatory
                                       DESCRIPTION
                                       "Sensor URL link."
                                       ::=  {  sensorProbeDrycontactArrayPort5Entry 28   }

                                    sensorProbeDrycontactArrayPort5OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort5Entry 29   }

                                    sensorProbeDrycontactArrayPort5ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort5Entry 30  }

                           sensorProbeDrycontactArrayPort6 OBJECT IDENTIFIER ::= { sensorProbeDrycontactArraySensor 6  }
                              sensorProbeDrycontactArrayPort6Number OBJECT-TYPE
                                 SYNTAX INTEGER
                                 ACCESS read-only
                                 STATUS mandatory
                                 DESCRIPTION
                                 "The total number of port on the DrycontactArray."
                                 ::=  {  sensorProbeDrycontactArrayPort6 1   }

                              sensorProbeDrycontactArrayPort6Table OBJECT-TYPE
                                 SYNTAX  SEQUENCE OF SensorProbeDrycontactArrayPort6Entry
                                 ACCESS  not-accessible
                                 STATUS  mandatory
                                 DESCRIPTION
                                 "This table contains the data for every Drycontact Sensor in the SensorArray. Each row in the table contains data for a different Drycontact Sensor."
                                 ::=  {  sensorProbeDrycontactArrayPort6 2   }

                                 sensorProbeDrycontactArrayPort6Entry OBJECT-TYPE
                                    SYNTAX  SensorProbeDrycontactArrayPort6Entry
                                    ACCESS  not-accessible
                                    STATUS  mandatory
                                    DESCRIPTION
                                    "This is an entry in the sensorProbeDrycontactArrayPort6 Table"
                                    INDEX         { sensorProbeDrycontactArrayPort6Index }
                                    ::=  { sensorProbeDrycontactArrayPort6Table 1 }

                                    SensorProbeDrycontactArrayPort6Entry ::= SEQUENCE {
                                       sensorProbeDrycontactArrayPort6Index
                                          INTEGER,
                                       sensorProbeDrycontactArrayPort6Description
                                          DisplayString,
                                       sensorProbeDrycontactArrayPort6Status
                                          INTEGER,
                                       sensorProbeDrycontactArrayPort6Online
                                          INTEGER,
                                       sensorProbeDrycontactArrayPort6GoOnline
                                          INTEGER,
                                       sensorProbeDrycontactArrayPort6NormalState
                                          INTEGER,
                                       sensorProbeDrycontactArrayPort6Direction
                                          INTEGER,
                                       sensorProbeDrycontactArrayPort6ContTimeCritical
                                          INTEGER,
                                       sensorProbeDrycontactArrayPort6ContTimeNormal
                                          INTEGER,
                                       sensorProbeDrycontactArrayPort6ManualOutputCycleTime
                                          INTEGER,
                                       sensorProbeDrycontactArrayPort6ManualOutputAction
                                          INTEGER,
                                       sensorProbeDrycontactArrayPort6OutputDescOn
                                          DisplayString,
                                       sensorProbeDrycontactArrayPort6OutputDescOff
                                          DisplayString,
                                       sensorProbeDrycontactArrayPort6URL
                                          DisplayString,
                                       sensorProbeDrycontactArrayPort6OpenURL
                                          INTEGER,
                                       sensorProbeDrycontactArrayPort6ControlMode
                                          INTEGER
                                    }

                                    sensorProbeDrycontactArrayPort6Index OBJECT-TYPE
                                       SYNTAX  INTEGER (0..7)
                                       ACCESS  read-only
                                       STATUS  mandatory
                                       DESCRIPTION
                                       "A unique value for each sensor DrycontactArray port."
                                       ::=  {  sensorProbeDrycontactArrayPort6Entry 1   }

                                    sensorProbeDrycontactArrayPort6Description OBJECT-TYPE
                                       SYNTAX  DisplayString
                                       ACCESS  read-write
                                       STATUS  mandatory
                                       DESCRIPTION
                                       "A Description of this sensor DrycontactArray"
                                       ::=  {  sensorProbeDrycontactArrayPort6Entry 2   }

                                    sensorProbeDrycontactArrayPort6Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort6Entry 4  }

                                    sensorProbeDrycontactArrayPort6Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort6Entry 5  }

                                    sensorProbeDrycontactArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort6Entry 6  }

                                    sensorProbeDrycontactArrayPort6NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort6Entry 7  }

                                    sensorProbeDrycontactArrayPort6Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort6Entry 8  }

                                    sensorProbeDrycontactArrayPort6ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort6Entry 9   }

                                    sensorProbeDrycontactArrayPort6ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort6Entry 10   }

                                    sensorProbeDrycontactArrayPort6ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort6Entry 24 }

                                    sensorProbeDrycontactArrayPort6ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort6Entry 25 }

                                    sensorProbeDrycontactArrayPort6OutputDescOn OBJECT-TYPE
                                       SYNTAX  DisplayString
                                       ACCESS  read-write
                                       STATUS  mandatory
                                       DESCRIPTION
                                       "Description of Drycontact output On"
                                       ::=  {  sensorProbeDrycontactArrayPort6Entry 26   }

                                    sensorProbeDrycontactArrayPort6OutputDescOff OBJECT-TYPE
                                       SYNTAX  DisplayString
                                       ACCESS  read-write
                                       STATUS  mandatory
                                       DESCRIPTION
                                       "Description of Drycontact output Off"
                                       ::=  {  sensorProbeDrycontactArrayPort6Entry 27   }

                                    sensorProbeDrycontactArrayPort6URL OBJECT-TYPE
                                       SYNTAX  DisplayString
                                       ACCESS  read-write
                                       STATUS  mandatory
                                       DESCRIPTION
                                       "Sensor URL link."
                                       ::=  {  sensorProbeDrycontactArrayPort6Entry 28   }

                                    sensorProbeDrycontactArrayPort6OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort6Entry 29   }

                                    sensorProbeDrycontactArrayPort6ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort6Entry 30  }

                           sensorProbeDrycontactArrayPort7 OBJECT IDENTIFIER ::= { sensorProbeDrycontactArraySensor 7  }
                              sensorProbeDrycontactArrayPort7Number OBJECT-TYPE
                                 SYNTAX INTEGER
                                 ACCESS read-only
                                 STATUS mandatory
                                 DESCRIPTION
                                 "The total number of port on the DrycontactArray."
                                 ::=  {  sensorProbeDrycontactArrayPort7 1   }

                              sensorProbeDrycontactArrayPort7Table OBJECT-TYPE
                                 SYNTAX  SEQUENCE OF SensorProbeDrycontactArrayPort7Entry
                                 ACCESS  not-accessible
                                 STATUS  mandatory
                                 DESCRIPTION
                                 "This table contains the data for every Drycontact Sensor in the SensorArray. Each row in the table contains data for a different Drycontact Sensor."
                                 ::=  {  sensorProbeDrycontactArrayPort7 2   }

                                 sensorProbeDrycontactArrayPort7Entry OBJECT-TYPE
                                    SYNTAX  SensorProbeDrycontactArrayPort7Entry
                                    ACCESS  not-accessible
                                    STATUS  mandatory
                                    DESCRIPTION
                                    "This is an entry in the sensorProbeDrycontactArrayPort7 Table"
                                    INDEX         { sensorProbeDrycontactArrayPort7Index }
                                    ::=  { sensorProbeDrycontactArrayPort7Table 1 }

                                    SensorProbeDrycontactArrayPort7Entry ::= SEQUENCE {
                                       sensorProbeDrycontactArrayPort7Index
                                          INTEGER,
                                       sensorProbeDrycontactArrayPort7Description
                                          DisplayString,
                                       sensorProbeDrycontactArrayPort7Status
                                          INTEGER,
                                       sensorProbeDrycontactArrayPort7Online
                                          INTEGER,
                                       sensorProbeDrycontactArrayPort7GoOnline
                                          INTEGER,
                                       sensorProbeDrycontactArrayPort7NormalState
                                          INTEGER,
                                       sensorProbeDrycontactArrayPort7Direction
                                          INTEGER,
                                       sensorProbeDrycontactArrayPort7ContTimeCritical
                                          INTEGER,
                                       sensorProbeDrycontactArrayPort7ContTimeNormal
                                          INTEGER,
                                       sensorProbeDrycontactArrayPort7ManualOutputCycleTime
                                          INTEGER,
                                       sensorProbeDrycontactArrayPort7ManualOutputAction
                                          INTEGER,
                                       sensorProbeDrycontactArrayPort7OutputDescOn
                                          DisplayString,
                                       sensorProbeDrycontactArrayPort7OutputDescOff
                                          DisplayString,
                                       sensorProbeDrycontactArrayPort7URL
                                          DisplayString,
                                       sensorProbeDrycontactArrayPort7OpenURL
                                          INTEGER,
                                       sensorProbeDrycontactArrayPort7ControlMode
                                          INTEGER
                                    }

                                    sensorProbeDrycontactArrayPort7Index OBJECT-TYPE
                                       SYNTAX  INTEGER (0..7)
                                       ACCESS  read-only
                                       STATUS  mandatory
                                       DESCRIPTION
                                       "A unique value for each sensor DrycontactArray port."
                                       ::=  {  sensorProbeDrycontactArrayPort7Entry 1   }

                                    sensorProbeDrycontactArrayPort7Description OBJECT-TYPE
                                       SYNTAX  DisplayString
                                       ACCESS  read-write
                                       STATUS  mandatory
                                       DESCRIPTION
                                       "A Description of this sensor DrycontactArray"
                                       ::=  {  sensorProbeDrycontactArrayPort7Entry 2   }

                                    sensorProbeDrycontactArrayPort7Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort7Entry 4  }

                                    sensorProbeDrycontactArrayPort7Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort7Entry 5  }

                                    sensorProbeDrycontactArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort7Entry 6  }

                                    sensorProbeDrycontactArrayPort7NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort7Entry 7  }

                                    sensorProbeDrycontactArrayPort7Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort7Entry 8  }

                                    sensorProbeDrycontactArrayPort7ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort7Entry 9   }

                                    sensorProbeDrycontactArrayPort7ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort7Entry 10   }

                                    sensorProbeDrycontactArrayPort7ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort7Entry 24 }

                                    sensorProbeDrycontactArrayPort7ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort7Entry 25 }

                                    sensorProbeDrycontactArrayPort7OutputDescOn OBJECT-TYPE
                                       SYNTAX  DisplayString
                                       ACCESS  read-write
                                       STATUS  mandatory
                                       DESCRIPTION
                                       "Description of Drycontact output On"
                                       ::=  {  sensorProbeDrycontactArrayPort7Entry 26   }

                                    sensorProbeDrycontactArrayPort7OutputDescOff OBJECT-TYPE
                                       SYNTAX  DisplayString
                                       ACCESS  read-write
                                       STATUS  mandatory
                                       DESCRIPTION
                                       "Description of Drycontact output Off"
                                       ::=  {  sensorProbeDrycontactArrayPort7Entry 27   }

                                    sensorProbeDrycontactArrayPort7URL OBJECT-TYPE
                                       SYNTAX  DisplayString
                                       ACCESS  read-write
                                       STATUS  mandatory
                                       DESCRIPTION
                                       "Sensor URL link."
                                       ::=  {  sensorProbeDrycontactArrayPort7Entry 28   }

                                    sensorProbeDrycontactArrayPort7OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort7Entry 29   }

                                    sensorProbeDrycontactArrayPort7ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort7Entry 30  }

                           sensorProbeDrycontactArrayPort8 OBJECT IDENTIFIER ::= { sensorProbeDrycontactArraySensor 8  }
                              sensorProbeDrycontactArrayPort8Number OBJECT-TYPE
                                 SYNTAX INTEGER
                                 ACCESS read-only
                                 STATUS mandatory
                                 DESCRIPTION
                                 "The total number of port on the DrycontactArray."
                                 ::=  {  sensorProbeDrycontactArrayPort8 1   }

                              sensorProbeDrycontactArrayPort8Table OBJECT-TYPE
                                 SYNTAX  SEQUENCE OF SensorProbeDrycontactArrayPort8Entry
                                 ACCESS  not-accessible
                                 STATUS  mandatory
                                 DESCRIPTION
                                 "This table contains the data for every Drycontact Sensor in the SensorArray. Each row in the table contains data for a different Drycontact Sensor."
                                 ::=  {  sensorProbeDrycontactArrayPort8 2   }

                                 sensorProbeDrycontactArrayPort8Entry OBJECT-TYPE
                                    SYNTAX  SensorProbeDrycontactArrayPort8Entry
                                    ACCESS  not-accessible
                                    STATUS  mandatory
                                    DESCRIPTION
                                    "This is an entry in the sensorProbeDrycontactArrayPort8 Table"
                                    INDEX         { sensorProbeDrycontactArrayPort8Index }
                                    ::=  { sensorProbeDrycontactArrayPort8Table 1 }

                                    SensorProbeDrycontactArrayPort8Entry ::= SEQUENCE {
                                       sensorProbeDrycontactArrayPort8Index
                                          INTEGER,
                                       sensorProbeDrycontactArrayPort8Description
                                          DisplayString,
                                       sensorProbeDrycontactArrayPort8Status
                                          INTEGER,
                                       sensorProbeDrycontactArrayPort8Online
                                          INTEGER,
                                       sensorProbeDrycontactArrayPort8GoOnline
                                          INTEGER,
                                       sensorProbeDrycontactArrayPort8NormalState
                                          INTEGER,
                                       sensorProbeDrycontactArrayPort8Direction
                                          INTEGER,
                                       sensorProbeDrycontactArrayPort8ContTimeCritical
                                          INTEGER,
                                       sensorProbeDrycontactArrayPort8ContTimeNormal
                                          INTEGER,
                                       sensorProbeDrycontactArrayPort8ManualOutputCycleTime
                                          INTEGER,
                                       sensorProbeDrycontactArrayPort8ManualOutputAction
                                          INTEGER,
                                       sensorProbeDrycontactArrayPort8OutputDescOn
                                          DisplayString,
                                       sensorProbeDrycontactArrayPort8OutputDescOff
                                          DisplayString,
                                       sensorProbeDrycontactArrayPort8URL
                                          DisplayString,
                                       sensorProbeDrycontactArrayPort8OpenURL
                                          INTEGER,
                                       sensorProbeDrycontactArrayPort8ControlMode
                                          INTEGER
                                    }

                                    sensorProbeDrycontactArrayPort8Index OBJECT-TYPE
                                       SYNTAX  INTEGER (0..7)
                                       ACCESS  read-only
                                       STATUS  mandatory
                                       DESCRIPTION
                                       "A unique value for each sensor DrycontactArray port."
                                       ::=  {  sensorProbeDrycontactArrayPort8Entry 1   }

                                    sensorProbeDrycontactArrayPort8Description OBJECT-TYPE
                                       SYNTAX  DisplayString
                                       ACCESS  read-write
                                       STATUS  mandatory
                                       DESCRIPTION
                                       "A Description of this sensor DrycontactArray"
                                       ::=  {  sensorProbeDrycontactArrayPort8Entry 2   }

                                    sensorProbeDrycontactArrayPort8Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort8Entry 4  }

                                    sensorProbeDrycontactArrayPort8Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort8Entry 5  }

                                    sensorProbeDrycontactArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort8Entry 6  }

                                    sensorProbeDrycontactArrayPort8NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort8Entry 7  }

                                    sensorProbeDrycontactArrayPort8Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort8Entry 8  }

                                    sensorProbeDrycontactArrayPort8ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort8Entry 9   }

                                    sensorProbeDrycontactArrayPort8ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort8Entry 10   }

                                    sensorProbeDrycontactArrayPort8ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort8Entry 24 }

                                    sensorProbeDrycontactArrayPort8ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort8Entry 25 }

                                    sensorProbeDrycontactArrayPort8OutputDescOn OBJECT-TYPE
                                       SYNTAX  DisplayString
                                       ACCESS  read-write
                                       STATUS  mandatory
                                       DESCRIPTION
                                       "Description of Drycontact output On"
                                       ::=  {  sensorProbeDrycontactArrayPort8Entry 26   }

                                    sensorProbeDrycontactArrayPort8OutputDescOff OBJECT-TYPE
                                       SYNTAX  DisplayString
                                       ACCESS  read-write
                                       STATUS  mandatory
                                       DESCRIPTION
                                       "Description of Drycontact output Off"
                                       ::=  {  sensorProbeDrycontactArrayPort8Entry 27   }

                                    sensorProbeDrycontactArrayPort8URL OBJECT-TYPE
                                       SYNTAX  DisplayString
                                       ACCESS  read-write
                                       STATUS  mandatory
                                       DESCRIPTION
                                       "Sensor URL link."
                                       ::=  {  sensorProbeDrycontactArrayPort8Entry 28   }

                                    sensorProbeDrycontactArrayPort8OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort8Entry 29   }

                                    sensorProbeDrycontactArrayPort8ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort8Entry 30  }

               sensorProbeDebug OBJECT-TYPE
                  SYNTAX  INTEGER {
                     off(0),
                     on(1)
                  }
                  ACCESS  read-write
                  STATUS  mandatory
                  DESCRIPTION
                  "SP only: Turn on or off debug messages"
                  ::=  {  sensorProbeEntry 20  }

               sensorProbeTrapResend OBJECT-TYPE
                  SYNTAX  INTEGER {
                     off(0),
                     on(1)
                  }
                  ACCESS  read-write
                  STATUS  mandatory
                  DESCRIPTION
                  "If traps for Warning or Error should be resent. Traps for Normal status are sent once"
                  ::=  {  sensorProbeEntry 22  }

               sensorProbeTrapResendInterval OBJECT-TYPE
                  SYNTAX  INTEGER
                  ACCESS  read-write
                  STATUS  mandatory
                  DESCRIPTION
                  "How often to resend mail or Traps. Enter the number of seconds from 15 to 65535. Mail for WARNING and ERROR are resent at this interval. Traps for Normal status are sent once"
                  ::=  {  sensorProbeEntry 23  }

               sensorProbeSendTraps OBJECT-TYPE
                  SYNTAX  INTEGER {
                     on(1),
                     off(2)
                  }
                  ACCESS  read-write
                  STATUS  mandatory
                  DESCRIPTION
                  "Turn on or off the sending of traps"
                  ::=  {  sensorProbeEntry 24  }

               sensorProbeTrapDestination OBJECT-TYPE
                  SYNTAX  IpAddress
                  ACCESS  read-write
                  STATUS  mandatory
                  DESCRIPTION
                  "The IP address of the trap destination"
                  ::=  {  sensorProbeEntry 25  }

               sensorProbeTrapCommunity OBJECT-TYPE
                  SYNTAX  DisplayString
                  ACCESS  read-write
                  STATUS  mandatory
                  DESCRIPTION
                  "The community string of the trap destination"
                  ::=  {  sensorProbeEntry 26  }

               sensorProbeDefaultGateway OBJECT-TYPE
                  SYNTAX  IpAddress
                  ACCESS  read-write
                  STATUS  mandatory
                  DESCRIPTION
                  "If the destination is on another network, enter the IP address of the router"
                  ::=  {  sensorProbeEntry 27  }

               sensorProbeSubnetMask OBJECT-TYPE
                  SYNTAX  IpAddress
                  ACCESS  read-write
                  STATUS  mandatory
                  DESCRIPTION
                  "If the trap destination uses the default gateway"
                  ::=  {  sensorProbeEntry 28  }

               sensorProbeRouteAdd OBJECT-TYPE
                  SYNTAX  DisplayString
                  ACCESS  read-write
                  STATUS  mandatory
                  DESCRIPTION
                  "SP only: Up to 4, Manual additions to the routing table in the form, Network IP Address, Netmask, Gateway IP address"
                  ::=  {  sensorProbeEntry 29  }


               sensorProbeSendMail OBJECT-TYPE
                  SYNTAX  INTEGER {
                     on(1),
                     off(2)
                  }
                  ACCESS  read-write
                  STATUS  mandatory
                  DESCRIPTION
                  "Turn on or off the sending of Mail"
                  ::=  {  sensorProbeEntry 30  }

               sensorProbeMailRecpt OBJECT-TYPE
                  SYNTAX  DisplayString
                  ACCESS  read-write
                  STATUS  mandatory
                  DESCRIPTION
                  "The email address of the Recipient"
                  ::=  {  sensorProbeEntry 31  }

               sensorProbeMailFrom OBJECT-TYPE
                  SYNTAX  DisplayString
                  ACCESS  read-write
                  STATUS  mandatory
                  DESCRIPTION
                  "The email address of the Sender"
                  ::=  {  sensorProbeEntry 32  }

               sensorProbeMailSMTP OBJECT-TYPE
                  SYNTAX  DisplayString
                  ACCESS  read-write
                  STATUS  mandatory
                  DESCRIPTION
                  "The Address of the SMTP server"
                  ::=  {  sensorProbeEntry 33  }

               sensorProbeMailJpgInline OBJECT-TYPE
                  SYNTAX  INTEGER {
                     inline(1),
                     link(2)
                  }
                  ACCESS  read-write
                  STATUS  mandatory
                  DESCRIPTION
                  "If the jpg for this event is sent as an http link or is included with mail as an attachment"
                  ::=  {  sensorProbeEntry 34  }

               sensorProbeMailResendInterval OBJECT-TYPE
                  SYNTAX  INTEGER
                  ACCESS  read-write
                  STATUS  mandatory
                  DESCRIPTION
                  "How often to resend mail or Traps. Enter the number of seconds from 10 to 60. Mail for WARNING and ERROR are resent at this interval. Mail for Normal status are sent once"
                  ::=  {  sensorProbeEntry 36  }

               sensorProbeMailMaxResend OBJECT-TYPE
                  SYNTAX  INTEGER
                  ACCESS  read-write
                  STATUS  mandatory
                  DESCRIPTION
                  "The maximum number of times to resend mail. If set to 0 only send once. The maximum value is 5"
                  ::=  {  sensorProbeEntry 37  }

               sensorProbeMailLastStatus OBJECT-TYPE
                  SYNTAX  DisplayString
                  ACCESS  read-only
                  STATUS  mandatory
                  DESCRIPTION
                  "The status of the most recent attempt to send an email"
                  ::=  {  sensorProbeEntry 39  }

               sensorProbeSupportMailRcpt OBJECT-TYPE
                  SYNTAX  DisplayString
                  ACCESS  read-write
                  STATUS  mandatory
                  DESCRIPTION
                  "SP8L only: E-Mail address of support"
                  ::=  {  sensorProbeEntry 40  }

               sensorProbeCameraServerTable OBJECT-TYPE
                  SYNTAX  SEQUENCE OF SensorProbeCameraServerEntry
                  ACCESS  not-accessible
                  STATUS  mandatory
                  DESCRIPTION
                  "CP8 Only: This table contains the Camera Server features, This allows the sensorProbe to connect to a sensorProbe"
                  ::=  {  sensorProbeEntry 42   }

               sensorProbeCameraServerEntry OBJECT-TYPE
                  SYNTAX  SensorProbeCameraServerEntry
                  ACCESS  not-accessible
                  STATUS  mandatory
                  DESCRIPTION
                  "This is an entry in the sensorProbeCameraServerEntry Table"
                  INDEX         { sensorProbeCameraServerIndex }
                  ::=  { sensorProbeCameraServerTable 1 }

                  SensorProbeCameraServerEntry ::= SEQUENCE {
                     sensorProbeCameraServerClientOnline
                        INTEGER,
                     sensorProbeCameraServerClientGoOnline
                        INTEGER,
                     sensorProbeCameraServerClientIP
                        IpAddress,
                     sensorProbeCameraServerClientSetPassword
                        DisplayString,
                     sensorProbeCameraServerIndex
                          INTEGER,
                     sensorProbeJavaTimeOut
                          INTEGER,
                     sensorProbeJpegQualityFactor
                          INTEGER,
                     sensorProbeCameraDescription
                          DisplayString,
                     sensorProbeCameraRotate
                          INTEGER,
                     sensorProbeCameraResolution
                          INTEGER,
                     sensorProbePTZRotateRelative
                          DisplayString,
                     sensorProbePTZRotateAbsolute
                          DisplayString,
                     sensorProbeAudioAttachChannel
                          INTEGER,
                     sensorProbePTZEnable
                          INTEGER,
                     sensorProbePTZBrand
                          INTEGER,
                     sensorProbePTZPanTiltUntilEnd
                          INTEGER
                  }


                  sensorProbeCameraServerClientOnline OBJECT-TYPE
                     SYNTAX  INTEGER {
                        online(1),
                        offline(2)
                     }
                     ACCESS  read-only
                     STATUS  mandatory
                     DESCRIPTION
                     "If this Client is currently online"
                     ::=  {  sensorProbeCameraServerEntry 1  }

                  sensorProbeCameraServerClientGoOnline OBJECT-TYPE
                     SYNTAX  INTEGER {
                        goOnline(1),
                        goOffline(2)
                     }
                     ACCESS  read-write
                     STATUS  mandatory
                     DESCRIPTION
                     "To put this Client online enter a 1, to take offline enter a 2"
                     ::=  {  sensorProbeCameraServerEntry 2  }

                  sensorProbeCameraServerClientIP OBJECT-TYPE
                     SYNTAX  IpAddress
                     ACCESS  read-write
                     STATUS  mandatory
                     DESCRIPTION
                     "The IP address of the sensorProbe, used to send snmp keep alive messages"
                     ::=  {  sensorProbeCameraServerEntry 3  }

                  sensorProbeCameraServerClientSetPassword OBJECT-TYPE
                     SYNTAX  DisplayString
                     ACCESS  read-write
                     STATUS  mandatory
                     DESCRIPTION
                     "SP Only: The Set Password for the snmp keep alive messages sent to the sensorProbes"
                     ::=  {  sensorProbeCameraServerEntry 4  }

                    sensorProbeCameraServerIndex OBJECT-TYPE
                       SYNTAX  INTEGER (0..9)
                       ACCESS  read-only
                       STATUS  mandatory
                       DESCRIPTION
                       "The index into the Camera table"
                       ::=  {  sensorProbeCameraServerEntry 5  }

                  sensorProbeJavaTimeOut OBJECT-TYPE
                     SYNTAX  INTEGER
                     ACCESS  read-write
                     STATUS  mandatory
                     DESCRIPTION
                     "Timeout in minutes for Java client"
                     ::=  {  sensorProbeCameraServerEntry 6  }

                  sensorProbeJpegQualityFactor OBJECT-TYPE
                     SYNTAX  INTEGER (5..95)
                     ACCESS  read-write
                     STATUS  mandatory
                     DESCRIPTION
                     "Quality factor of jpeg image"
                     ::=  {  sensorProbeCameraServerEntry 7  }

                  sensorProbeCameraDescription OBJECT-TYPE
                     SYNTAX  DisplayString
                     ACCESS  read-write
                     STATUS  mandatory
                     DESCRIPTION
                     "A description of camera"
                     ::=  {  sensorProbeCameraServerEntry 8 }

                  sensorProbeCameraRotate OBJECT-TYPE
                     SYNTAX  INTEGER {
                        nonRotate(0),
                        rotate(1)
                     }
                     ACCESS  read-write
                     STATUS  mandatory
                     DESCRIPTION
                     "A Rotate of this camera"
                     ::=  {  sensorProbeCameraServerEntry 9 }

                  sensorProbeCameraResolution OBJECT-TYPE
                     SYNTAX  INTEGER {
                        resolution320x240(0),
                        resolution640x480(1)
                     }
                     ACCESS  read-write
                     STATUS  mandatory
                     DESCRIPTION
                     "Resolution of camera"
                     ::=  {  sensorProbeCameraServerEntry 10 }

                  sensorProbePTZRotateRelative OBJECT-TYPE
                     SYNTAX  DisplayString
                     ACCESS  read-write
                     STATUS  mandatory
                     DESCRIPTION
                     "Control PTZ by put Direction and step 'DIR STEP' when direction 0 or 1 is LEFT or RIGH and 2 or 3 is UP or DOWN "
                     ::=  {  sensorProbeCameraServerEntry 11 }

                  sensorProbePTZRotateAbsolute OBJECT-TYPE
                     SYNTAX  DisplayString
                     ACCESS  read-write
                     STATUS  mandatory
                     DESCRIPTION
                     "Control PTZ by put position of x and y 'POS_X POS_Y' value of position is 0 to 100"
                     ::=  {  sensorProbeCameraServerEntry 12 }

                  sensorProbeAudioAttachChannel OBJECT-TYPE
                     SYNTAX  INTEGER {
                        notAttachAudio(0),
                        attachAudio(1)
                     }
                     ACCESS  read-write
                     STATUS  mandatory
                     DESCRIPTION
                     "Disable/Enable audio attachment"
                     ::=  {  sensorProbeCameraServerEntry 13 }

                  sensorProbePTZEnable OBJECT-TYPE
                     SYNTAX  INTEGER {
                        disable(0),
                        enableInternal(1),
                        enableExternal(2)
                     }
                     ACCESS  read-write
                     STATUS  mandatory
                     DESCRIPTION
                     "Disable/Enable Ptz controller"
                     ::=  {  sensorProbeCameraServerEntry 14 }

                  sensorProbePTZBrand OBJECT-TYPE
                     SYNTAX  INTEGER {
                        generalBrand(0),
                        akcpBrand(1)
                     }
                     ACCESS  read-write
                     STATUS  mandatory
                     DESCRIPTION
                     "PTZ Brand"
                     ::=  {  sensorProbeCameraServerEntry 15 }

                  sensorProbePTZPanTiltUntilEnd OBJECT-TYPE
                     SYNTAX  INTEGER {
                        stop(0),
                        right(1),
                        left(2),
                        up(3),
                        down(4),
                        right-up(5),
                        right-down(6),
                        left-up(7),
                        left-down(8)
                     }
                     ACCESS  read-write
                     STATUS  mandatory
                     DESCRIPTION
                     "Pan or Tilt PTZ until endpoint"
                     ::=  {  sensorProbeCameraServerEntry 16 }


               sensorProbeTrapMailPollInterval OBJECT-TYPE
                  SYNTAX  INTEGER
                  ACCESS  read-write
                  STATUS  mandatory
                  DESCRIPTION
                  "SP Only: How often the sensor thresholds are tested before sending traps or mail. This can vary from 3 to 15 seconds"
                  ::=  {  sensorProbeEntry 50  }

               sensorProbeSendTestMail OBJECT-TYPE
                  SYNTAX  INTEGER
                  ACCESS  read-write
                  STATUS  mandatory
                  DESCRIPTION
                  "Send out an email test message"
                  ::=  {  sensorProbeEntry 51  }

               sensorProbeLastSystemError OBJECT-TYPE
                  SYNTAX  DisplayString
                  ACCESS  read-only
                  STATUS  mandatory
                  DESCRIPTION
                  "A text string containing the description of the last system error"
                  ::=  {  sensorProbeEntry 52  }

               sensorProbeDataCollectionPeriod OBJECT-TYPE
                  SYNTAX  INTEGER
                  ACCESS  read-write
                  STATUS  mandatory
                  DESCRIPTION
                  "The number of minutes between collections of the data logger. This can vary from 1 to 60 minutes"
                  ::=  {  sensorProbeEntry 53  }

               sensorProbeMailTimeout OBJECT-TYPE
                  SYNTAX  INTEGER
                  ACCESS  read-write
                  STATUS  mandatory
                  DESCRIPTION
                  "The number of seconds to wait for a timeout while sending email This can vary from 10 to 30 seconds"
                  ::=  {  sensorProbeEntry 54  }

               sensorProbeAutoSense OBJECT-TYPE
                  SYNTAX  INTEGER {
                     disable(0),
                     enable(1)
                  }                  
                  ACCESS  read-write
                  STATUS  mandatory
                  DESCRIPTION
                  "Enable Auto-sense feature"
                  ::=  {  sensorProbeEntry 55  }

               sensorProbeChecksum OBJECT-TYPE
                  SYNTAX  INTEGER
                  ACCESS  read-only
                  STATUS  mandatory
                  DESCRIPTION
                  "SP Only: The Flash Checksum, computed dynamically whenever this object is read"
                  ::=  {  sensorProbeEntry 56  }

               sensorProbeUsePassword OBJECT-TYPE
                  SYNTAX  INTEGER {
                     usePassword(0),
                     doNotUsePassword(1)
                  }
                  ACCESS  read-write
                  STATUS  mandatory
                  DESCRIPTION
                  "Determines whether or not the set and get community are used to check for access rights"
                  ::=  {  sensorProbeEntry 57  }

               sensorProbeDisplayLogo OBJECT-TYPE
                  SYNTAX  INTEGER {
                     disable(0),
                     enable(1)
                  }                  
                  ACCESS  read-write
                  STATUS  mandatory
                  DESCRIPTION
                  "Enable or Disable the display of the logo"
                  ::=  {  sensorProbeEntry 59  }

               sensorProbeTrapType OBJECT-TYPE
                  SYNTAX  INTEGER {
                     specificTypeTrap(1),
                     generalTypeTrap(2),
                     bothTypeTraps(3),
                     statusTypeTraps(4)
                  }                  
                  ACCESS  read-write
                  STATUS  mandatory
                  DESCRIPTION
                  "Whether to generate a trap that covers all sensors, a specific trap for each sensor, or both types of traps"
                  ::=  {  sensorProbeEntry 60  }

               sensorProbeMailCC OBJECT-TYPE
                  SYNTAX  DisplayString
                  ACCESS  read-write
                  STATUS  mandatory
                  DESCRIPTION
                  "The email address of the CC"
                  ::=  {  sensorProbeEntry 61  }

               sensorProbeAllowIPChange OBJECT-TYPE
                SYNTAX  INTEGER {
                    enable(1),
                    disable(2)
                  }
                  ACCESS  read-write
                  STATUS  mandatory
                  DESCRIPTION
                  "This disables the changing of the IP address. The default is to enable changing the IP address"
                  ::=  {  sensorProbeEntry 62  }

               sensorProbeTimeOfDay OBJECT-TYPE
                  SYNTAX  DisplayString
                  ACCESS  read-write
                  STATUS  mandatory
                  DESCRIPTION
                  "The time of day in the format day/month/year hour(1-24):minutes:seconds for example 23/10/02 12:45:06"
                  ::=  {  sensorProbeEntry 65  }

               sensorProbeEnableSysLog OBJECT-TYPE
                SYNTAX  INTEGER {
                     enableLogToFlash(1),
                     enableLogToNetAndFlash(2),
                     disable(3)
                  }                  
                  ACCESS  read-write
                  STATUS  mandatory
                  DESCRIPTION
                  "This enables sysLog Messages,including logging to the Net. The Destination IP of the net messages is the same as the source IP of the sender of this command"
                  ::=  {  sensorProbeEntry 66  }

               sensorProbeReadSysLog OBJECT-TYPE
                  SYNTAX  INTEGER {
                     lastMessage(1),
                     allMessages(2)
                  }                  
                  ACCESS  read-write
                  STATUS  mandatory
                  DESCRIPTION
                  "Return the sysLog Message in the snmp PDU and if enableLogToNetAndFlash in sensorProbeEnableSysLog, also send in debug message format, A Write of a 2 will return all of the messages in debug format"
                  ::=  {  sensorProbeEntry 67  }

               sensorProbeClearSysLog OBJECT-TYPE
                  SYNTAX  INTEGER {
                     allMessages(2)
                  }                  
                  ACCESS  read-write
                  STATUS  mandatory
                  DESCRIPTION
                  "Delete all entries in the sys log"
                  ::=  {  sensorProbeEntry 68  }

               sensorProbeSyslogDestIP OBJECT-TYPE
                  SYNTAX  IpAddress
                  ACCESS  read-write
                  STATUS  mandatory
                  DESCRIPTION
                  "The IP Address of the Syslog server. Note: This must be in dotted decimal form"
                  ::=  {  sensorProbeEntry 69  }

               sensorProbeSyslogPort OBJECT-TYPE
                  SYNTAX  Gauge 
                  ACCESS  read-write
                  STATUS  mandatory
                  DESCRIPTION
                  "The Port Number of the Syslog server."
                  ::=  {  sensorProbeEntry 70  }

               sensorProbeSetSyslogMsgPrefix OBJECT-TYPE
                  SYNTAX  DisplayString
                  ACCESS  read-write
                  STATUS  mandatory
                  DESCRIPTION
                  "SP Only: The Prefix message of the Syslog message"
                  ::=  {  sensorProbeEntry 71  }

--
-- sensorProbeEntry 72 is reserved for sensorProbeLanFullDuplex ( SP Only )
--

--
-- sensorProbeEntry 73 is reserved for sensorProbeExpectedMicrocodeCRC ( SP Only )
--

--
-- sensorProbeEntry 74 is reserved for sensorProbeExpectedMicrocodeLength ( SP Only )
--

--
-- sensorProbeEntry 75 is reserved for sensorProbeActualMicrocodeCRC ( SP Only )
--

--
-- sensorProbeEntry 76 is reserved for sensorProbeExpectedBootCRC ( SP Only )
--

--
-- sensorProbeEntry 77 is reserved for sensorProbeActualBootCRC ( SP Only )
--

--
-- sensorProbeEntry 78 is reserved for sensorProbeBootVersion ( SP Only )
--

--
-- sensorProbeEntry 80 is reserved for sensorProbeAdcCalibrate
--

               sensorProbeTimeZone OBJECT-TYPE
                  SYNTAX  INTEGER  
                  ACCESS  read-write
                  STATUS  mandatory
                  DESCRIPTION
                  "System time zone" 
                  ::=  {  sensorProbeEntry 81  }

--
-- sensorProbeEntry 82 is reserved for sensorProbeExtraDryContactEnable ( SP Only )
--

               sensorProbeMegaVersion OBJECT-TYPE
                  SYNTAX  INTEGER
                  ACCESS  read-only
                  STATUS  mandatory
                  DESCRIPTION
                  "Version number of mega board"
                  ::=  {  sensorProbeEntry 83  }

               sensorProbeNtpMode OBJECT-TYPE
                  SYNTAX  INTEGER {
                     notUse(0),
                     oneTime(1),
                     onSystemStartUp(2),
                     onceAMounth(3),
                     onceAWeek(4),
                     onceADay(5),
                     onceAnHour(6),
                     continuous(7)
                  }
                  ACCESS  read-write
                  STATUS  mandatory
                  DESCRIPTION
                  "Mode to synchronous with ntp server" 
                  ::=  {  sensorProbeEntry 84  }

               sensorProbeNtpServer OBJECT-TYPE
                  SYNTAX  DisplayString
                  ACCESS  read-write
                  STATUS  mandatory
                  DESCRIPTION
                  "NTP server which this machine synchronous with"
                  ::=  {  sensorProbeEntry 85  }

--
-- sensorProbeEntry 86 is reserved for SensorProbeModel string which is used internaly (AKCP).
--

               sensorProbeSMTPAuth OBJECT-TYPE
                  SYNTAX  INTEGER {
                     enable(1),
                     disable(2)
                  }                  
                  ACCESS  read-write
                  STATUS  mandatory
                  DESCRIPTION
                  "This enables the SMTP authentication"
                  ::=  {  sensorProbeEntry 87  }

               sensorProbeSMTPLogin OBJECT-TYPE
                  SYNTAX  DisplayString
                  ACCESS  read-write
                  STATUS  mandatory
                  DESCRIPTION
                  "The username used to login into SMTP server"
                  ::=  {  sensorProbeEntry 88  }

               sensorProbeSMTPPassword OBJECT-TYPE
                  SYNTAX  DisplayString
                  ACCESS  read-write
                  STATUS  mandatory
                  DESCRIPTION
                  "The password used to login into SMTP server"
                  ::=  {  sensorProbeEntry 89  }

               sensorProbeDNSServer OBJECT-TYPE
                  SYNTAX  IpAddress
                  ACCESS  read-write
                  STATUS  mandatory
                  DESCRIPTION
                  "IP address of the DNS server"
                  ::=  {  sensorProbeEntry 90  }

               sensorProbeAltWebPort OBJECT-TYPE
                  SYNTAX  Gauge
                  ACCESS  read-write
                  STATUS  mandatory
                  DESCRIPTION
                  "The alternative for a port number 80 used to access the web interface"
                  ::=  {  sensorProbeEntry 91  }

               sensorProbeNumberOfSensorPort OBJECT-TYPE
                  SYNTAX  INTEGER
                  ACCESS  read-only
                  STATUS  mandatory
                  DESCRIPTION
                  "The number of sensor ports(regardless of their current state)"
                  ::=  {  sensorProbeEntry 92  }
               
               sensorProbeSendTrapsAlive OBJECT-TYPE
                  SYNTAX  INTEGER {
                     on(1),
                     off(2)
                  }
                  ACCESS  read-write
                  STATUS  mandatory
                  DESCRIPTION
                  "On or off send keep alive traps."
                  ::=  {  sensorProbeEntry 93  }
               
               sensorProbeTrapReIntervalAlive OBJECT-TYPE
                  SYNTAX  INTEGER
                  ACCESS  read-write
                  STATUS  mandatory
                  DESCRIPTION
                  "Time between each keep alive trap."
                  ::=  {  sensorProbeEntry 94  }
               
               sensorProbeUseCamera OBJECT-TYPE
                  SYNTAX  INTEGER {
                     off(0),
                     on(1)
                  }
                  ACCESS  read-write
                  STATUS  mandatory
                  DESCRIPTION
                  "On or off camera."
                  ::=  {  sensorProbeEntry 95  }
                                 
               sensorProbeAdcCalibratePort OBJECT-TYPE
                  SYNTAX  INTEGER
                  ACCESS  read-write
                  STATUS  mandatory
                  DESCRIPTION
                  "Calibrate value for analog sensor."
                  ::=  {  sensorProbeEntry 96  }

--
-- sensorProbeEntry 97 is reseverd for future using with Linux version (AKCP).
--

               sensorProbeMailSubject OBJECT-TYPE
                  SYNTAX  DisplayString
                  ACCESS  read-write
                  STATUS  mandatory
                  DESCRIPTION
                  "Email Subject."
                  ::=  {  sensorProbeEntry 98  }

          sensorProbeSnmpPort OBJECT-TYPE
                  SYNTAX  Gauge 
                  ACCESS  read-write
                  STATUS  mandatory
                  DESCRIPTION
                  "SP Only: Port number used to access snmp"
                  ::=  {  sensorProbeEntry 99  }

          sensorProbeSnmpTrapPort OBJECT-TYPE
                  SYNTAX  Gauge 
                  ACCESS  read-write
                  STATUS  mandatory
                  DESCRIPTION
                  "SP Only: Port number used to access trap snmp"
                  ::=  {  sensorProbeEntry 100  }

          sensorProbeSnmpIndexingMode OBJECT-TYPE
                  SYNTAX  INTEGER {
                     index0(0),
                     index1(1)
                  }
                  ACCESS  read-write
                  STATUS  mandatory
                  DESCRIPTION
                  "CP8 Only: Snmp table index starting from 0 or 1 "
                  ::=  {  sensorProbeEntry 101  }

--
-- sensorProbeEntry 102 is reserved for sensorProbeSensorSummary
--
               sensorProbeNotifyBoot OBJECT-TYPE
                  SYNTAX  INTEGER
                  ACCESS  read-write
                  STATUS  mandatory
                  DESCRIPTION
                  "SP2 Only: Enable Notify on boot up"
                  ::=  {  sensorProbeEntry 103  }

               sensorProbeDelayNotifyBoot OBJECT-TYPE
                  SYNTAX  INTEGER
                  ACCESS  read-write
                  STATUS  mandatory
                  DESCRIPTION
                  "SP2 Only: Delay time for boot up notify"
                  ::=  {  sensorProbeEntry 104  }

               sensorProbeSmtpPort OBJECT-TYPE
                  SYNTAX  INTEGER
                  ACCESS  read-write
                  STATUS  mandatory
                  DESCRIPTION
                  "SMTP Port number used to send email"
                  ::=  {  sensorProbeEntry 105  }

               sensorProbeReboot OBJECT-TYPE
                  SYNTAX  INTEGER
                  ACCESS  read-write
                  STATUS  mandatory
                  DESCRIPTION
                  "Reboot SP2/SP8 set to 1"
                  ::=  {  sensorProbeEntry 106  }

          sensorProbeServerEnable OBJECT-TYPE
                  SYNTAX  INTEGER {
                     disable(0),
                     enable(1)
                  }
                  ACCESS  read-write
                  STATUS  mandatory
                  DESCRIPTION
                  "Enable database changed notify feature"
                  ::=  {  sensorProbeEntry 107  }

          sensorProbeFirmwareVersion OBJECT-TYPE
                  SYNTAX  DisplayString
                  ACCESS  read-only
                  STATUS  mandatory
                  DESCRIPTION
                  "Current firmware version"
                  ::=  {  sensorProbeEntry 108  }

          sensorProbeProductType OBJECT-TYPE
                  SYNTAX  INTEGER {
                     sensorProbe2(1),
                     sensorProbe8(2),
                     cameraProbe(4),
                     securityProbe(5),
                     securityProbe5E(6),
                     securityProbe5ES(11),
                     securityProbe5ESV(12),
                     securityProbeDCU(13),
                     sensorProbePlus(16)
                  }
                  ACCESS  read-only
                  STATUS  mandatory
                  DESCRIPTION
                  "Product type"
                  ::=  {  sensorProbeEntry 109  }

               sensorProbeRequestResendTrap OBJECT-TYPE
                  SYNTAX  INTEGER
                  ACCESS  read-write
                  STATUS  mandatory
                  DESCRIPTION
                  "SP only: Send immediately all traps by set to 1"
                  ::=  {  sensorProbeEntry 110  }

--
-- sensorProbeEntry 111 is reserved for Server Project
--

               sensorProbeSeparateEmail OBJECT-TYPE
                  SYNTAX  INTEGER {
                     notSeparate(0),
                     separate(1)
                  }
                  ACCESS  read-write
                  STATUS  mandatory
                  DESCRIPTION
                  "SP only: Separate Email by set 1 for not Separate Email set 0"
                  ::=  {  sensorProbeEntry 112  }

               sensorProbeMailCustom OBJECT-TYPE
                  SYNTAX  INTEGER {
                     normal(0),
                     custom(1)
                  }
                  ACCESS  read-write
                  STATUS  mandatory
                  DESCRIPTION
                  "SP only: Custom mail is removed 'http://' in the mail footer"
                  ::=  {  sensorProbeEntry 113  }

          sensorProbeUntidePassword OBJECT-TYPE
                  SYNTAX  INTEGER {
                     tidePassword(0),
                     untidePassword(1)
                  }
                  ACCESS  read-only
                  STATUS  mandatory
                  DESCRIPTION
                  "Use web password as SNMP password"
                  ::=  {  sensorProbeEntry 114  }
         
          sensorProbeReloadNetwork OBJECT-TYPE
                  SYNTAX  INTEGER {
                     reload(1)
                  }
                  ACCESS  read-write
                  STATUS  mandatory
                  DESCRIPTION
                  "Set 1 for reload network seting"
                  ::=  {  sensorProbeEntry 116  }

          sensorProbeStatusNumber OBJECT IDENTIFIER ::= { sensorProbeEntry 117  }
              sensorProbeStatusNumberNotNormal OBJECT-TYPE
                  SYNTAX INTEGER
                  ACCESS read-only
                  STATUS mandatory
                  DESCRIPTION
                  "Number of sensor status is Warning, Critical and Sensor Error"
                  ::= {  sensorProbeStatusNumber 1 }

              sensorProbeStatusNumberCriticalAndError OBJECT-TYPE
                  SYNTAX INTEGER
                  ACCESS read-only
                  STATUS mandatory
                  DESCRIPTION
                  "Number of sensor status is Critical and Sensor Error"
                  ::= {  sensorProbeStatusNumber 2 }

              sensorProbeStatusNumberError OBJECT-TYPE
                  SYNTAX INTEGER
                  ACCESS read-only
                  STATUS mandatory
                  DESCRIPTION
                  "Number of sensor status is Sensor Error"
                  ::= {  sensorProbeStatusNumber 3 }

          sensorProbeTypeName OBJECT IDENTIFIER ::= { sensorProbeEntry 118  }
              sensorProbeTypeTemperatureName OBJECT-TYPE
                  SYNTAX DisplayString
                  ACCESS read-write
                  STATUS mandatory
                  DESCRIPTION
                  "A Description of Sensor Type Name on web interface"
                  ::= {  sensorProbeTypeName 1 }

              sensorProbeTypeSHT11HumidityName OBJECT-TYPE
                  SYNTAX DisplayString
                  ACCESS read-write
                  STATUS mandatory
                  DESCRIPTION
                  "A Description of Sensor Type Name on web interface"
                  ::= {  sensorProbeTypeName 2 }
                  
              sensorProbeTypeSHT11TempName OBJECT-TYPE
                  SYNTAX DisplayString
                  ACCESS read-write
                  STATUS mandatory
                  DESCRIPTION
                  "A Description of Sensor Type Name on web interface"
                  ::= {  sensorProbeTypeName 3 }
           
              sensorProbeType4to20MAName OBJECT-TYPE
                  SYNTAX DisplayString
                  ACCESS read-write
                  STATUS mandatory
                  DESCRIPTION
                  "A Description of Sensor Type Name on web interface"
                  ::= {  sensorProbeTypeName 4 }

              sensorProbeTypeDCvoltageName OBJECT-TYPE
                  SYNTAX DisplayString
                  ACCESS read-write
                  STATUS mandatory
                  DESCRIPTION
                  "A Description of Sensor Type Name on web interface"
                  ::= {  sensorProbeTypeName 5 }
                  
              sensorProbeTypeAirflowName OBJECT-TYPE
                  SYNTAX DisplayString
                  ACCESS read-write
                  STATUS mandatory
                  DESCRIPTION
                  "A Description of Sensor Type Name on web interface"
                  ::= {  sensorProbeTypeName 6 }
                  
              sensorProbeTypeDrycontactInoutName OBJECT-TYPE
                  SYNTAX DisplayString
                  ACCESS read-write
                  STATUS mandatory
                  DESCRIPTION
                  "A Description of Sensor Type Name on web interface"
                  ::= {  sensorProbeTypeName 7 }

              sensorProbeTypeDrycontactInputName OBJECT-TYPE
                  SYNTAX DisplayString
                  ACCESS read-write
                  STATUS mandatory
                  DESCRIPTION
                  "A Description of Sensor Type Name on web interface"
                  ::= {  sensorProbeTypeName 8 }
                  
              sensorProbeTypeMotionName OBJECT-TYPE
                  SYNTAX DisplayString
                  ACCESS read-write
                  STATUS mandatory
                  DESCRIPTION
                  "A Description of Sensor Type Name on web interface"
                  ::= {  sensorProbeTypeName 9 }
                  
              sensorProbeTypeWaterName OBJECT-TYPE
                  SYNTAX DisplayString
                  ACCESS read-write
                  STATUS mandatory
                  DESCRIPTION
                  "A Description of Sensor Type Name on web interface"
                  ::= {  sensorProbeTypeName 10 }

              sensorProbeTypeSecurityName OBJECT-TYPE
                  SYNTAX DisplayString
                  ACCESS read-write
                  STATUS mandatory
                  DESCRIPTION
                  "A Description of Sensor Type Name on web interface"
                  ::= {  sensorProbeTypeName 11 }
                  
              sensorProbeTypeSirenName OBJECT-TYPE
                  SYNTAX DisplayString
                  ACCESS read-write
                  STATUS mandatory
                  DESCRIPTION
                  "A Description of Sensor Type Name on web interface"
                  ::= {  sensorProbeTypeName 12 }
                  
              sensorProbeTypeRelayName OBJECT-TYPE
                  SYNTAX DisplayString
                  ACCESS read-write
                  STATUS mandatory
                  DESCRIPTION
                  "A Description of Sensor Type Name on web interface"
                  ::= {  sensorProbeTypeName 13 }

              sensorProbeTypeACvoltageName OBJECT-TYPE
                  SYNTAX DisplayString
                  ACCESS read-write
                  STATUS mandatory
                  DESCRIPTION
                  "A Description of Sensor Type Name on web interface"
                  ::= {  sensorProbeTypeName 14 }
                  
              sensorProbeTypeADE7763VRMSName OBJECT-TYPE
                  SYNTAX DisplayString
                  ACCESS read-write
                  STATUS mandatory
                  DESCRIPTION
                  "A Description of Sensor Type Name on web interface"
                  ::= {  sensorProbeTypeName 15 }

              sensorProbeTypeADE7763IRMSName OBJECT-TYPE
                  SYNTAX DisplayString
                  ACCESS read-write
                  STATUS mandatory
                  DESCRIPTION
                  "A Description of Sensor Type Name on web interface"
                  ::= {  sensorProbeTypeName  16 }
                  
              sensorProbeTypeADE7763WattName OBJECT-TYPE
                  SYNTAX DisplayString
                  ACCESS read-write
                  STATUS mandatory
                  DESCRIPTION
                  "A Description of Sensor Type Name on web interface"
                  ::= {  sensorProbeTypeName  17 }
                  
              sensorProbeTypeADE7763WatthourName OBJECT-TYPE
                  SYNTAX DisplayString
                  ACCESS read-write
                  STATUS mandatory
                  DESCRIPTION
                  "A Description of Sensor Type Name on web interface"
                  ::= {  sensorProbeTypeName  18 }
                  
              sensorProbeTypePCF8574XRelayName OBJECT-TYPE
                  SYNTAX DisplayString
                  ACCESS read-write
                  STATUS mandatory
                  DESCRIPTION
                  "A Description of Sensor Type Name on web interface"
                  ::= {  sensorProbeTypeName  19 }
                  
              sensorProbeTypeThermocoupleName OBJECT-TYPE
                  SYNTAX DisplayString
                  ACCESS read-write
                  STATUS mandatory
                  DESCRIPTION
                  "A Description of Sensor Type Name on web interface"
                  ::= {  sensorProbeTypeName  20 }
                  
              sensorProbeTypeSmokeName OBJECT-TYPE
                  SYNTAX DisplayString
                  ACCESS read-write
                  STATUS mandatory
                  DESCRIPTION
                  "A Description of Sensor Type Name on web interface"
                  ::= {  sensorProbeTypeName  21 }
                  
              sensorProbeTypeXDryName OBJECT-TYPE
                  SYNTAX DisplayString
                  ACCESS read-write
                  STATUS mandatory
                  DESCRIPTION
                  "A Description of Sensor Type Name on web interface"
                  ::= {  sensorProbeTypeName  22 }
                  
              sensorProbeTypeTemperatureArrayName OBJECT-TYPE
                  SYNTAX DisplayString
                  ACCESS read-write
                  STATUS mandatory
                  DESCRIPTION
                  "A Description of Sensor Type Name on web interface"
                  ::= {  sensorProbeTypeName  23 }

              sensorProbeTypeWaterRopeName OBJECT-TYPE
                  SYNTAX DisplayString
                  ACCESS read-write
                  STATUS mandatory
                  DESCRIPTION
                  "A Description of Sensor Type Name on web interface"
                  ::= {  sensorProbeTypeName  24 }

              sensorProbeTypeFuelLevelName OBJECT-TYPE
                  SYNTAX DisplayString
                  ACCESS read-write
                  STATUS mandatory
                  DESCRIPTION
                  "A Description of Sensor Type Name on web interface"
                  ::= {  sensorProbeTypeName  25 }

              sensorProbeTypeTankSenderName OBJECT-TYPE
                  SYNTAX DisplayString
                  ACCESS read-write
                  STATUS mandatory
                  DESCRIPTION
                  "A Description of Sensor Type Name on web interface"
                  ::= {  sensorProbeTypeName  26 }

              sensorProbeTypeThermostatName OBJECT-TYPE
                  SYNTAX DisplayString
                  ACCESS read-write
                  STATUS mandatory
                  DESCRIPTION
                  "A Description of Sensor Type Name on web interface"
                  ::= {  sensorProbeTypeName  128 }

              sensorProbeTypeVirtualName OBJECT-TYPE
                  SYNTAX DisplayString
                  ACCESS read-write
                  STATUS mandatory
                  DESCRIPTION
                  "A Description of Sensor Type Name on web interface"
                  ::= {  sensorProbeTypeName  129 }

              sensorProbeTypeSoundName OBJECT-TYPE
                  SYNTAX DisplayString
                  ACCESS read-write
                  STATUS mandatory
                  DESCRIPTION
                  "A Description of Sensor Type Name on web interface"
                  ::= {  sensorProbeTypeName  130 }

              sensorProbeTypeSoftMotionName OBJECT-TYPE
                  SYNTAX DisplayString
                  ACCESS read-write
                  STATUS mandatory
                  DESCRIPTION
                  "A Description of Sensor Type Name on web interface"
                  ::= {  sensorProbeTypeName  131 }

              sensorProbeTypeNoSignalName OBJECT-TYPE
                  SYNTAX DisplayString
                  ACCESS read-write
                  STATUS mandatory
                  DESCRIPTION
                  "A Description of Sensor Type Name on web interface"
                  ::= {  sensorProbeTypeName  132 }

              sensorProbeTypePowerMeterName OBJECT-TYPE
                  SYNTAX DisplayString
                  ACCESS read-write
                  STATUS mandatory
                  DESCRIPTION
                  "A Description of Sensor Type Name on web interface"
                  ::= {  sensorProbeTypeName  134 }

              sensorProbeTypeSHT11Name OBJECT-TYPE
                  SYNTAX DisplayString
                  ACCESS read-write
                  STATUS mandatory
                  DESCRIPTION
                  "A Description of Sensor Type Name on web interface"
                  ::= {  sensorProbeTypeName 135 }

              sensorProbeTypeADE7763Name OBJECT-TYPE
                  SYNTAX DisplayString
                  ACCESS read-write
                  STATUS mandatory
                  DESCRIPTION
                  "A Description of Sensor Type Name on web interface"
                  ::= {  sensorProbeTypeName 136 }

          sensorProbeProductRevision OBJECT-TYPE
                  SYNTAX  INTEGER
                  ACCESS  read-only
                  STATUS  mandatory
                  DESCRIPTION
                  "SP only: Revision number"
                  ::=  {  sensorProbeEntry 119  }

          sensorProbePowerMeter OBJECT IDENTIFIER ::= { sensorProbeEntry 125  }
              sensorProbePowerMeter1phDelayBetweenCommand OBJECT-TYPE
                  SYNTAX INTEGER
                  ACCESS read-write
                  STATUS mandatory
                  DESCRIPTION
                  "A delay time between command for 1ph power meter(in milliseconds)"
                  ::= {  sensorProbePowerMeter 1 }

              sensorProbePowerMeter3phDelayBetweenCommand OBJECT-TYPE
                  SYNTAX INTEGER
                  ACCESS read-write
                  STATUS mandatory
                  DESCRIPTION
                  "A delay time between command for 3ph power meter(in milliseconds)"
                  ::= {  sensorProbePowerMeter 2 }

              sensorProbePowerMeter1phDelayBetweenMeter OBJECT-TYPE
                  SYNTAX INTEGER
                  ACCESS read-write
                  STATUS mandatory
                  DESCRIPTION
                  "A delay time of command between power meter(in milliseconds)"
                  ::= {  sensorProbePowerMeter 3 }

              sensorProbePowerMeter3phDelayBetweenMeter OBJECT-TYPE
                  SYNTAX INTEGER
                  ACCESS read-write
                  STATUS mandatory
                  DESCRIPTION
                  "A delay time of command between power meter(in milliseconds)"
                  ::= {  sensorProbePowerMeter 4 }

              sensorProbePowerMeterWaitTimeout OBJECT-TYPE
                  SYNTAX INTEGER
                  ACCESS read-write
                  STATUS mandatory
                  DESCRIPTION
                  "A waiting timeout for receiving a command(in milliseconds)"
                  ::= {  sensorProbePowerMeter 5 }

              sensorProbePowerMeterCountSentPacket OBJECT-TYPE
                  SYNTAX  INTEGER
                  ACCESS  read-only
                  STATUS  mandatory
                  DESCRIPTION
                  "Count send packets of this sensorProbe"
                  ::= {  sensorProbePowerMeter 6  }

              sensorProbePowerMeterCountRecievedPacket OBJECT-TYPE
                  SYNTAX  INTEGER
                  ACCESS  read-only
                  STATUS  mandatory
                  DESCRIPTION
                  "Count received packets of this sensorProbe"
                  ::= {  sensorProbePowerMeter 7  }

              sensorProbePowerMeterCountTimeoutPacket OBJECT-TYPE
                  SYNTAX  INTEGER
                  ACCESS  read-only
                  STATUS  mandatory
                  DESCRIPTION
                  "Count timeout packets of this sensorProbe"
                  ::= {  sensorProbePowerMeter 8  }

              sensorProbePowerMeterCountCRCErrorPacket OBJECT-TYPE
                  SYNTAX  INTEGER
                  ACCESS  read-only
                  STATUS  mandatory
                  DESCRIPTION
                  "Count error crc packets of this sensorProbe"
                  ::= {  sensorProbePowerMeter 9  }

   securityProbe OBJECT IDENTIFIER ::= { akcp 2 }

      secSummary OBJECT IDENTIFIER  ::=  {  securityProbe 1 }

      secDevice OBJECT IDENTIFIER  ::=  {  securityProbe 2 }

         deviceTable OBJECT-TYPE
            SYNTAX  SEQUENCE OF DeviceEntry
            ACCESS  not-accessible
            STATUS  mandatory
            DESCRIPTION
            "This table contains the property for every plugged-in device."
            ::=  {  secDevice 1   }

         deviceEntry OBJECT-TYPE
            SYNTAX  DeviceEntry
            ACCESS  not-accessible
            STATUS  mandatory
            DESCRIPTION
            "This is an entry in the deviceEntry Table"
            INDEX         { deviceIndex }
            ::=  {  deviceTable 1 }

         DeviceEntry ::= SEQUENCE {
               deviceIndex
                  INTEGER,
               deviceDescription
                  DisplayString,
               deviceType
                  INTEGER,
               deviceInfo
                  DisplayString,
               deviceStatus
                  INTEGER,
               deviceWorstSensotStatus
                  INTEGER
         }

            deviceIndex OBJECT-TYPE
               SYNTAX  INTEGER (1..184549375)
               ACCESS  read-only
               STATUS  mandatory
               DESCRIPTION
               "The index into the device table"
               ::=  {  deviceEntry 1   }

            deviceDescription OBJECT-TYPE
               SYNTAX  DisplayString
               ACCESS  read-write
               STATUS  mandatory
               DESCRIPTION
               "A Description of this device"
               ::=  {  deviceEntry 2   }

            deviceType OBJECT-TYPE
               SYNTAX  INTEGER {
                  internal(0),
                  eSensor8(1),
                  dryContact(2),
                  optoDryContact(3),
                  sensor(4),
                  x20DryContact(5),
                  x60DryContact(6)
               }
               ACCESS  read-only
               STATUS  mandatory
               DESCRIPTION
               "..."
               ::=  {  deviceEntry 3   }

            deviceInfo OBJECT-TYPE
               SYNTAX  DisplayString
               ACCESS  read-only
               STATUS  mandatory
               DESCRIPTION
               "A information of this device"
               ::=  {  deviceEntry 4   }

            deviceStatus OBJECT-TYPE
               SYNTAX  INTEGER {
                  offline(0),
                  starting(1),
                  normal(2)
               }
               ACCESS  read-only
               STATUS  mandatory
               DESCRIPTION
               "..."
               ::=  {  deviceEntry 5   }

            deviceWorstSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "..."
               ::=  {  deviceEntry 6   }

         deviceIntelligentTable OBJECT-TYPE
            SYNTAX  SEQUENCE OF DeviceIntelligentEntry
            ACCESS  not-accessible
            STATUS  mandatory
            DESCRIPTION
            "This table contains the property for every plugged-in device."
            ::=  {  secDevice 2  }

         deviceIntelligentEntry OBJECT-TYPE
            SYNTAX  DeviceIntelligentEntry
            ACCESS  not-accessible
            STATUS  mandatory
            DESCRIPTION
            "This is an entry in the deviceEntry Table"
            INDEX         { deviceIntelligentIndex }
            ::=  {  deviceIntelligentTable 1 }

         DeviceIntelligentEntry ::= SEQUENCE {
               deviceIntelligentIndex
                  INTEGER,
               deviceIntelligentDescription
                  DisplayString,
               deviceIntelligentInfo
                  DisplayString,
               deviceIntelligentStatus
                  INTEGER,
               sensorIntelligentTypeSelected
                  INTEGER,
               deviceIntelligentWorstSensotStatus
                  INTEGER,
               sensorIntelligentPort1GoOnline
                  INTEGER,
               sensorIntelligentPort2GoOnline
                  INTEGER,
               sensorIntelligentPort3GoOnline
                  INTEGER,
               sensorIntelligentPort4GoOnline
                  INTEGER,
               sensorIntelligentPort5GoOnline
                  INTEGER,
               sensorIntelligentPort6GoOnline
                  INTEGER,
               sensorIntelligentPort7GoOnline
                  INTEGER,
               sensorIntelligentPort8GoOnline
                  INTEGER
         }
            deviceIntelligentIndex OBJECT-TYPE
               SYNTAX  INTEGER (1..65535)
               ACCESS  read-only
               STATUS  mandatory
               DESCRIPTION
               "The index into the deviceIntelligent table"
               ::=  {  deviceIntelligentEntry 1   }

            deviceIntelligentDescription OBJECT-TYPE
               SYNTAX  DisplayString
               ACCESS  read-write
               STATUS  mandatory
               DESCRIPTION
               "A Description of this device"
               ::=  {  deviceIntelligentEntry 2   }

            deviceIntelligentInfo OBJECT-TYPE
               SYNTAX  DisplayString
               ACCESS  read-only
               STATUS  mandatory
               DESCRIPTION
               "A information of this device"
               ::=  {  deviceIntelligentEntry 4   }

            deviceIntelligentStatus OBJECT-TYPE
               SYNTAX  INTEGER
               ACCESS  read-only
               STATUS  mandatory
               DESCRIPTION
               "..."
               ::=  {  deviceIntelligentEntry 5   }

            sensorIntelligentTypeSelected OBJECT-TYPE
               SYNTAX  INTEGER
               ACCESS  read-write
               STATUS  mandatory
               DESCRIPTION
               "..."
               ::=  {  deviceIntelligentEntry 6   }

            deviceIntelligentWorstSensotStatus OBJECT-TYPE
               SYNTAX  INTEGER
               ACCESS  read-only
               STATUS  mandatory
               DESCRIPTION
               "..."
               ::=  {  deviceIntelligentEntry 7   }

            sensorIntelligentPort1GoOnline OBJECT-TYPE
               SYNTAX  INTEGER {
               goOnline(1),
               goOffline(2)
               }
               ACCESS  read-write
               STATUS  mandatory
               DESCRIPTION
               "..."
               ::=  {  deviceIntelligentEntry 100   }

            sensorIntelligentPort2GoOnline OBJECT-TYPE
               SYNTAX  INTEGER {
               goOnline(1),
               goOffline(2)
               }
               ACCESS  read-write
               STATUS  mandatory
               DESCRIPTION
               "..."
               ::=  {  deviceIntelligentEntry 101   }

            sensorIntelligentPort3GoOnline OBJECT-TYPE
               SYNTAX  INTEGER {
               goOnline(1),
               goOffline(2)
               }
               ACCESS  read-write
               STATUS  mandatory
               DESCRIPTION
               "..."
               ::=  {  deviceIntelligentEntry 102   }

            sensorIntelligentPort4GoOnline OBJECT-TYPE
               SYNTAX  INTEGER {
               goOnline(1),
               goOffline(2)
               }
               ACCESS  read-write
               STATUS  mandatory
               DESCRIPTION
               "..."
               ::=  {  deviceIntelligentEntry 103   }

            sensorIntelligentPort5GoOnline OBJECT-TYPE
               SYNTAX  INTEGER {
               goOnline(1),
               goOffline(2)
               }
               ACCESS  read-write
               STATUS  mandatory
               DESCRIPTION
               "..."
               ::=  {  deviceIntelligentEntry 104   }

            sensorIntelligentPort6GoOnline OBJECT-TYPE
               SYNTAX  INTEGER {
               goOnline(1),
               goOffline(2)
               }
               ACCESS  read-write
               STATUS  mandatory
               DESCRIPTION
               "..."
               ::=  {  deviceIntelligentEntry 105   }

            sensorIntelligentPort7GoOnline OBJECT-TYPE
               SYNTAX  INTEGER {
               goOnline(1),
               goOffline(2)
               }
               ACCESS  read-write
               STATUS  mandatory
               DESCRIPTION
               "..."
               ::=  {  deviceIntelligentEntry 106   }

            sensorIntelligentPort8GoOnline OBJECT-TYPE
               SYNTAX  INTEGER {
               goOnline(1),
               goOffline(2)
               }
               ACCESS  read-write
               STATUS  mandatory
               DESCRIPTION
               "..."
               ::=  {  deviceIntelligentEntry 107   }

         deviceDryContactTable OBJECT-TYPE
            SYNTAX  SEQUENCE OF DeviceDryContactEntry
            ACCESS  not-accessible
            STATUS  mandatory
            DESCRIPTION
            "This table contains the property for every plugged-in device."
            ::=  {  secDevice 3  }

         deviceDryContactEntry OBJECT-TYPE
            SYNTAX  DeviceDryContactEntry
            ACCESS  not-accessible
            STATUS  mandatory
            DESCRIPTION
            "This is an entry in the deviceEntry Table"
            INDEX         { deviceDryContactIndex }
            ::=  {  deviceDryContactTable 1 }

         DeviceDryContactEntry ::= SEQUENCE {
               deviceDryContactIndex
                  INTEGER,
               deviceDryContactDescription
                  DisplayString,
               deviceDryContactInfo
                  DisplayString,
               deviceDryContactStatus
                  INTEGER,
               deviceDryContactWorstSensotStatus
                  INTEGER,
               sensorDryContactPort1GoOnline
                  INTEGER,
               sensorDryContactPort2GoOnline
                  INTEGER,
               sensorDryContactPort3GoOnline
                  INTEGER,
               sensorDryContactPort4GoOnline
                  INTEGER,
               sensorDryContactPort5GoOnline
                  INTEGER,
               sensorDryContactPort6GoOnline
                  INTEGER,
               sensorDryContactPort7GoOnline
                  INTEGER,
               sensorDryContactPort8GoOnline
                  INTEGER,
               sensorDryContactPort9GoOnline
                  INTEGER,
               sensorDryContactPort10GoOnline
                  INTEGER,
               sensorDryContactPort11GoOnline
                  INTEGER,
               sensorDryContactPort12GoOnline
                  INTEGER,
               sensorDryContactPort13GoOnline
                  INTEGER,
               sensorDryContactPort14GoOnline
                  INTEGER,
               sensorDryContactPort15GoOnline
                  INTEGER,
               sensorDryContactPort16GoOnline
                  INTEGER
         }

            deviceDryContactIndex OBJECT-TYPE
               SYNTAX  INTEGER (1..65535)
               ACCESS  read-only
               STATUS  mandatory
               DESCRIPTION
               "The index into the deviceDryContact table"
               ::=  {  deviceDryContactEntry 1   }

            deviceDryContactDescription OBJECT-TYPE
               SYNTAX  DisplayString
               ACCESS  read-write
               STATUS  mandatory
               DESCRIPTION
               "A Description of this device"
               ::=  {  deviceDryContactEntry 2   }

            deviceDryContactInfo OBJECT-TYPE
               SYNTAX  DisplayString
               ACCESS  read-only
               STATUS  mandatory
               DESCRIPTION
               "A information of this device"
               ::=  {  deviceDryContactEntry 4   }

            deviceDryContactStatus OBJECT-TYPE
               SYNTAX  INTEGER
               ACCESS  read-only
               STATUS  mandatory
               DESCRIPTION
               "..."
               ::=  {  deviceDryContactEntry 5   }

            deviceDryContactWorstSensotStatus OBJECT-TYPE
               SYNTAX  INTEGER
               ACCESS  read-only
               STATUS  mandatory
               DESCRIPTION
               "..."
               ::=  {  deviceDryContactEntry 6   }

            sensorDryContactPort1GoOnline OBJECT-TYPE
               SYNTAX  INTEGER {
               goOnline(1),
               goOffline(2)
               }
               ACCESS  read-write
               STATUS  mandatory
               DESCRIPTION
               "..."
               ::=  {  deviceDryContactEntry 100   }

            sensorDryContactPort2GoOnline OBJECT-TYPE
               SYNTAX  INTEGER {
               goOnline(1),
               goOffline(2)
               }
               ACCESS  read-write
               STATUS  mandatory
               DESCRIPTION
               "..."
               ::=  {  deviceDryContactEntry 101   }

            sensorDryContactPort3GoOnline OBJECT-TYPE
               SYNTAX  INTEGER {
               goOnline(1),
               goOffline(2)
               }
               ACCESS  read-write
               STATUS  mandatory
               DESCRIPTION
               "..."
               ::=  {  deviceDryContactEntry 102   }

            sensorDryContactPort4GoOnline OBJECT-TYPE
               SYNTAX  INTEGER {
               goOnline(1),
               goOffline(2)
               }
               ACCESS  read-write
               STATUS  mandatory
               DESCRIPTION
               "..."
               ::=  {  deviceDryContactEntry 103   }

            sensorDryContactPort5GoOnline OBJECT-TYPE
               SYNTAX  INTEGER {
               goOnline(1),
               goOffline(2)
               }
               ACCESS  read-write
               STATUS  mandatory
               DESCRIPTION
               "..."
               ::=  {  deviceDryContactEntry 104   }

            sensorDryContactPort6GoOnline OBJECT-TYPE
               SYNTAX  INTEGER {
               goOnline(1),
               goOffline(2)
               }
               ACCESS  read-write
               STATUS  mandatory
               DESCRIPTION
               "..."
               ::=  {  deviceDryContactEntry 105   }

            sensorDryContactPort7GoOnline OBJECT-TYPE
               SYNTAX  INTEGER {
               goOnline(1),
               goOffline(2)
               }
               ACCESS  read-write
               STATUS  mandatory
               DESCRIPTION
               "..."
               ::=  {  deviceDryContactEntry 106   }

            sensorDryContactPort8GoOnline OBJECT-TYPE
               SYNTAX  INTEGER {
               goOnline(1),
               goOffline(2)
               }
               ACCESS  read-write
               STATUS  mandatory
               DESCRIPTION
               "..."
               ::=  {  deviceDryContactEntry 107   }

            sensorDryContactPort9GoOnline OBJECT-TYPE
               SYNTAX  INTEGER {
               goOnline(1),
               goOffline(2)
               }
               ACCESS  read-write
               STATUS  mandatory
               DESCRIPTION
               "..."
               ::=  {  deviceDryContactEntry 108   }

            sensorDryContactPort10GoOnline OBJECT-TYPE
               SYNTAX  INTEGER {
               goOnline(1),
               goOffline(2)
               }
               ACCESS  read-write
               STATUS  mandatory
               DESCRIPTION
               "..."
               ::=  {  deviceDryContactEntry 109   }

            sensorDryContactPort11GoOnline OBJECT-TYPE
               SYNTAX  INTEGER {
               goOnline(1),
               goOffline(2)
               }
               ACCESS  read-write
               STATUS  mandatory
               DESCRIPTION
               "..."
               ::=  {  deviceDryContactEntry 110   }

            sensorDryContactPort12GoOnline OBJECT-TYPE
               SYNTAX  INTEGER {
               goOnline(1),
               goOffline(2)
               }
               ACCESS  read-write
               STATUS  mandatory
               DESCRIPTION
               "..."
               ::=  {  deviceDryContactEntry 111   }

            sensorDryContactPort13GoOnline OBJECT-TYPE
               SYNTAX  INTEGER {
               goOnline(1),
               goOffline(2)
               }
               ACCESS  read-write
               STATUS  mandatory
               DESCRIPTION
               "..."
               ::=  {  deviceDryContactEntry 112   }

            sensorDryContactPort14GoOnline OBJECT-TYPE
               SYNTAX  INTEGER {
               goOnline(1),
               goOffline(2)
               }
               ACCESS  read-write
               STATUS  mandatory
               DESCRIPTION
               "..."
               ::=  {  deviceDryContactEntry 113   }

            sensorDryContactPort15GoOnline OBJECT-TYPE
               SYNTAX  INTEGER {
               goOnline(1),
               goOffline(2)
               }
               ACCESS  read-write
               STATUS  mandatory
               DESCRIPTION
               "..."
               ::=  {  deviceDryContactEntry 114   }

            sensorDryContactPort16GoOnline OBJECT-TYPE
               SYNTAX  INTEGER {
               goOnline(1),
               goOffline(2)
               }
               ACCESS  read-write
               STATUS  mandatory
               DESCRIPTION
               "..."
               ::=  {  deviceDryContactEntry 115   }

         deviceAccessTable OBJECT-TYPE
            SYNTAX  SEQUENCE OF DeviceAccessEntry
            ACCESS  not-accessible
            STATUS  mandatory
            DESCRIPTION
            "This table contains the property for every plugged-in device."
            ::=  {  secDevice 4  }

         deviceAccessEntry OBJECT-TYPE
            SYNTAX  DeviceAccessEntry
            ACCESS  not-accessible
            STATUS  mandatory
            DESCRIPTION
            "This is an entry in the deviceEntry Table"
            INDEX         { deviceAccessIndex }
            ::=  {  deviceAccessTable 1 }

         DeviceAccessEntry ::= SEQUENCE {
               deviceAccessIndex
                  INTEGER,
               deviceAccessDescription
                  DisplayString,
               deviceAccessInfo
                  DisplayString,
               deviceAccessStatus
                  INTEGER,
               deviceAccessWorstSensorStatus
                  INTEGER
         }
            deviceAccessIndex OBJECT-TYPE
               SYNTAX  INTEGER (1..65535)
               ACCESS  read-only
               STATUS  mandatory
               DESCRIPTION
               "The index into the deviceAccess table"
               ::=  {  deviceAccessEntry 1   }

            deviceAccessDescription OBJECT-TYPE
               SYNTAX  DisplayString
               ACCESS  read-write
               STATUS  mandatory
               DESCRIPTION
               "A Description of this device"
               ::=  {  deviceAccessEntry 2   }

            deviceAccessInfo OBJECT-TYPE
               SYNTAX  DisplayString
               ACCESS  read-only
               STATUS  mandatory
               DESCRIPTION
               "A information of this device"
               ::=  {  deviceAccessEntry 4   }

            deviceAccessStatus OBJECT-TYPE
               SYNTAX  INTEGER
               ACCESS  read-only
               STATUS  mandatory
               DESCRIPTION
               "..."
               ::=  {  deviceAccessEntry 5   }

            deviceAccessWorstSensorStatus OBJECT-TYPE
               SYNTAX  INTEGER
               ACCESS  read-only
               STATUS  mandatory
               DESCRIPTION
               "..."
               ::=  {  deviceAccessEntry 7   }

         devicePowerMeterTable OBJECT-TYPE
            SYNTAX  SEQUENCE OF DevicePowerMeterEntry
            ACCESS  not-accessible
            STATUS  mandatory
            DESCRIPTION
            "This table contains the property for every power meter plugged-in."
            ::=  {  secDevice 5   }

         devicePowerMeterEntry OBJECT-TYPE
            SYNTAX  DevicePowerMeterEntry
            ACCESS  not-accessible
            STATUS  mandatory
            DESCRIPTION
            "This is an entry in the devicePowerMeterEntry Table"
            INDEX         { devicePowerMeterIndex }
            ::=  {  devicePowerMeterTable 1 }

         DevicePowerMeterEntry ::= SEQUENCE {
               devicePowerMeterIndex
                  INTEGER,
               devicePowerMeterDescription
                  DisplayString,
               devicePowerMeterInfo
                  DisplayString,
               devicePowerMeterStatus
                  INTEGER,
               devicePowerMeterWorstSensotStatus
                  INTEGER,
               devicePowerMeterType
                  INTEGER,
               devicePowerMeterDelayBetweenCommand
                  INTEGER,
               devicePowerMeterCountSentPacket 
                  INTEGER,
               devicePowerMeterCountRecievedPacket 
                  INTEGER,
               devicePowerMeterCountTimeoutPacket 
                  INTEGER,
               devicePowerMeterCountCRCerrorPacket 
                  INTEGER
         }

            devicePowerMeterIndex OBJECT-TYPE
               SYNTAX  INTEGER (1..184549375)
               ACCESS  read-only
               STATUS  mandatory
               DESCRIPTION
               "The index into the power meter table"
               ::=  {  devicePowerMeterEntry 1   }

            devicePowerMeterDescription OBJECT-TYPE
               SYNTAX  DisplayString
               ACCESS  read-write
               STATUS  mandatory
               DESCRIPTION
               "A Description of this power meter"
               ::=  {  devicePowerMeterEntry 2   }

            devicePowerMeterInfo OBJECT-TYPE
               SYNTAX  DisplayString
               ACCESS  read-only
               STATUS  mandatory
               DESCRIPTION
               "A information of this power meter"
               ::=  {  devicePowerMeterEntry 4   }

            devicePowerMeterStatus OBJECT-TYPE
               SYNTAX  INTEGER
               ACCESS  read-only
               STATUS  mandatory
               DESCRIPTION
               "A status of this power meter"
               ::=  {  devicePowerMeterEntry 5   }

            devicePowerMeterWorstSensotStatus OBJECT-TYPE
               SYNTAX  INTEGER
               ACCESS  read-only
               STATUS  mandatory
               DESCRIPTION
               "..."
               ::=  {  devicePowerMeterEntry 7   }

            devicePowerMeterType OBJECT-TYPE
               SYNTAX  INTEGER
               ACCESS  read-only
               STATUS  mandatory
               DESCRIPTION
               "A type of this power meter"
               ::=  {  devicePowerMeterEntry 9   }

            devicePowerMeterDelayBetweenCommand OBJECT-TYPE
               SYNTAX  INTEGER
               ACCESS  read-write
               STATUS  mandatory
               DESCRIPTION
               "A delay time between communication packet of this power meter(in milliseconds)"
               ::=  {  devicePowerMeterEntry 10   }

            devicePowerMeterCountSentPacket OBJECT-TYPE
               SYNTAX  INTEGER
               ACCESS  read-only
               STATUS  mandatory
               DESCRIPTION
               "Count send packets of this sensor"
               ::=  {  devicePowerMeterEntry  11  }

            devicePowerMeterCountRecievedPacket OBJECT-TYPE
               SYNTAX  INTEGER
               ACCESS  read-only
               STATUS  mandatory
               DESCRIPTION
               "Count received packets of this sensor"
               ::=  {  devicePowerMeterEntry  12  }

            devicePowerMeterCountTimeoutPacket OBJECT-TYPE
               SYNTAX  INTEGER
               ACCESS  read-only
               STATUS  mandatory
               DESCRIPTION
               "Count timeout packets of this sensor"
               ::=  {  devicePowerMeterEntry  13  }

            devicePowerMeterCountCRCerrorPacket OBJECT-TYPE
               SYNTAX  INTEGER
               ACCESS  read-only
               STATUS  mandatory
               DESCRIPTION
               "Count error crc packets of this sensor"
               ::=  {  devicePowerMeterEntry  14  }

         deviceLicense OBJECT IDENTIFIER  ::=  {  secDevice 6  }

               deviceLicenseExpTotal OBJECT-TYPE
                  SYNTAX  INTEGER
                  ACCESS  read-only
                  STATUS  mandatory
                  DESCRIPTION
                  "Expansion License Total"
                  ::=  {  deviceLicense 1  }

               deviceLicenseExpUsed OBJECT-TYPE
                  SYNTAX  INTEGER
                  ACCESS  read-only
                  STATUS  mandatory
                  DESCRIPTION
                  "Expansion License Used"
                  ::=  {  deviceLicense 2  }

               deviceLicenseExpAvailable OBJECT-TYPE
                  SYNTAX  INTEGER
                  ACCESS  read-only
                  STATUS  mandatory
                  DESCRIPTION
                  "Expansion License Available"
                  ::=  {  deviceLicense 3  }

               deviceLicensePmsTotal OBJECT-TYPE
                  SYNTAX  INTEGER
                  ACCESS  read-only
                  STATUS  mandatory
                  DESCRIPTION
                  "PMS License Total"
                  ::=  {  deviceLicense 4  }

               deviceLicensePmsUsed OBJECT-TYPE
                  SYNTAX  INTEGER
                  ACCESS  read-only
                  STATUS  mandatory
                  DESCRIPTION
                  "PMS License Used"
                  ::=  {  deviceLicense 5  }

               deviceLicensePmsAvailable OBJECT-TYPE
                  SYNTAX  INTEGER
                  ACCESS  read-only
                  STATUS  mandatory
                  DESCRIPTION
                  "PMS License Available"
                  ::=  {  deviceLicense 6  }

               deviceLicenseVrtTotal OBJECT-TYPE
                  SYNTAX  INTEGER
                  ACCESS  read-only
                  STATUS  mandatory
                  DESCRIPTION
                  "Virtual License Total"
                  ::=  {  deviceLicense 7  }

               deviceLicenseVrtUsed OBJECT-TYPE
                  SYNTAX  INTEGER
                  ACCESS  read-only
                  STATUS  mandatory
                  DESCRIPTION
                  "Virtual License Used"
                  ::=  {  deviceLicense 8  }

               deviceLicenseVrtAvailable OBJECT-TYPE
                  SYNTAX  INTEGER
                  ACCESS  read-only
                  STATUS  mandatory
                  DESCRIPTION
                  "Virtual License Available"
                  ::=  {  deviceLicense 9  }

               deviceLicenseIPv6Enable OBJECT-TYPE
                  SYNTAX  INTEGER
                  ACCESS  read-only
                  STATUS  mandatory
                  DESCRIPTION
                  "IPv6 License Enable (0 : Disable, 1 : Enable)"
                  ::=  {  deviceLicense 10  }

               deviceLicenseTable OBJECT-TYPE
                  SYNTAX  SEQUENCE OF DeviceLicenseEntry
                  ACCESS  not-accessible
                  STATUS  mandatory
                  DESCRIPTION
                  "This table contains the license of Expansion board, PMS and Virtual sensor."
                  ::=  {  deviceLicense 11  }

               deviceLicenseEntry OBJECT-TYPE
                  SYNTAX  DeviceLicenseEntry
                  ACCESS  not-accessible
                  STATUS  mandatory
                  DESCRIPTION
                  "This is an entry in the deviceLicenseEntry Table"
                  INDEX  { deviceLicenseIndex }
                  ::=  {  deviceLicenseTable 1  }

               DeviceLicenseEntry ::= SEQUENCE {
                     deviceLicenseIndex
                        DisplayString,
                     deviceLicenseExpCount
                        INTEGER,
                     deviceLicensePmsCount
                        INTEGER,
                     deviceLicenseVrtCount
                        INTEGER,
                     deviceLicenseIpv6
                        INTEGER,
                     deviceLicenseStatus
                        INTEGER
               }

                  deviceLicenseIndex OBJECT-TYPE
                     SYNTAX  DisplayString
                     ACCESS  read-only
                     STATUS  mandatory
                     DESCRIPTION
                     "The index into the device table (License Key)"
                     ::=  {  deviceLicenseEntry 1   }

                  deviceLicenseExpCount OBJECT-TYPE
                     SYNTAX  INTEGER
                     ACCESS  read-only
                     STATUS  mandatory
                     DESCRIPTION
                     "Expansion Connection"
                     ::=  {  deviceLicenseEntry 2   }

                  deviceLicensePmsCount OBJECT-TYPE
                     SYNTAX  INTEGER
                     ACCESS  read-only
                     STATUS  mandatory
                     DESCRIPTION
                     "PMS Unit number"
                     ::=  {  deviceLicenseEntry 3   }

                  deviceLicenseVrtCount OBJECT-TYPE
                     SYNTAX  INTEGER
                     ACCESS  read-only
                     STATUS  mandatory
                     DESCRIPTION
                     "Virtual Sensor"
                     ::=  {  deviceLicenseEntry 4   }

                  deviceLicenseIpv6 OBJECT-TYPE
                     SYNTAX  INTEGER
                     ACCESS  read-only
                     STATUS  mandatory
                     DESCRIPTION
                     "IPv6 license enable (0 : Disable, 1 : Enable)"
                     ::=  {  deviceLicenseEntry 5   }

                  deviceLicenseStatus OBJECT-TYPE
                     SYNTAX  INTEGER {
                        activated(1),
                        deactivated(2)
                     }
                     ACCESS  read-only
                     STATUS  mandatory
                     DESCRIPTION
                     "License status"
                     ::=  {  deviceLicenseEntry 6   }

      secSensor OBJECT IDENTIFIER  ::=  {  securityProbe 3 }

         sensorTable OBJECT-TYPE
            SYNTAX  SEQUENCE OF SensorEntry
            ACCESS  not-accessible
            STATUS  mandatory
            DESCRIPTION
            "This table contains the property and reading value for every sensor."
            ::=  {  secSensor 1   }

--/* Begin of sensorEntry */

         sensorEntry OBJECT-TYPE
            SYNTAX  SensorEntry
            ACCESS  not-accessible
            STATUS  mandatory
            DESCRIPTION
            "This is an entry in the sensorTable Table"
            INDEX         { sensorIndex }
            ::=  {  sensorTable 1 }

         SensorEntry ::= SEQUENCE {
               sensorIndex
                  INTEGER,
               sensorDescription
                  DisplayString,
               sensorType
                  INTEGER,
               sensorValue
                  INTEGER,
               sensorUnit
                  DisplayString,
               sensorStatus
                  INTEGER,
               sensorGoOffline
                  INTEGER,
               sensorPort
                  INTEGER,
               sensorSubPort
                  INTEGER,
               sensorDeviceIndex
                  INTEGER,
               sensorDisplayStyle
                  INTEGER,
               sensorHighCriticalDescription
                  DisplayString,
               sensorLowCriticalDescription
                  DisplayString,
               sensorNormalDescription
                  DisplayString,
               sensorLowWarningDescription
                  DisplayString,
               sensorHighWarningDescription
                  DisplayString,
               sensorErrorDescription
                  DisplayString,
               sensorOnDescription
                  DisplayString,
               sensorOffDescription
                  DisplayString,
               sensorHighCriticalColor
                  INTEGER,
               sensorLowCriticalColor
                  INTEGER,
               sensorNormalColor
                  INTEGER,
               sensorLowWarningColor
                  INTEGER,
               sensorHighWarningColor
                  INTEGER,
               sensorErrorColor
                  INTEGER,
               sensorOnColor
                  INTEGER,
               sensorOffColor
                  INTEGER,
               sensorAcknowledge
                  INTEGER,
               sensorValueFormatFloat
                  Opaque,
               sensorId
                  INTEGER
         }

            sensorIndex OBJECT-TYPE
               SYNTAX  INTEGER (1..65535)
               ACCESS  read-only
               STATUS  mandatory
               DESCRIPTION
               "The index into the sensor table"
               ::=  {  sensorEntry 1   }

            sensorDescription OBJECT-TYPE
               SYNTAX  DisplayString
               ACCESS  read-write
               STATUS  mandatory
               DESCRIPTION
               "A Description of this sensor"
               ::=  {  sensorEntry 2   }

            sensorType OBJECT-TYPE
               SYNTAX  INTEGER {
                  temperature(1),
                  humidity(2),
                  temperature-dual(3),
                  four-20mA(4),
                  dcvoltage(5),
                  airflow(6),
                  io(7),
                  drycontact(8),
                  motion(9),
                  water(10),
                  security(11),
                  siren(12),
                  relay(13),
                  acvoltage(14),
                  vrms(15),
                  irms(16),
                  watt(17),
                  watthour(18),
                  xrelay(19),
                  thermocouple(20),
                  smoke(21),
                  drycontact-array(22),
                  temperature-array(23),
                  thermostat(128),
                  virtual(129),
                  sound(130),
                  softmotion(131),
                  camera-dummy(132),
                  board-state(133),
                  nosignal(224),
                  test(255)
               }
               ACCESS  read-only
               STATUS  mandatory
               DESCRIPTION
               "Enter the type of this Sensor"
               ::=  {  sensorEntry 3  }

            sensorValue OBJECT-TYPE
               SYNTAX  INTEGER
               ACCESS  read-only
               STATUS  mandatory
               DESCRIPTION
               "The value in this sensor"
               ::=  {  sensorEntry 4   }

            sensorUnit OBJECT-TYPE
               SYNTAX  DisplayString
               ACCESS  read-only
               STATUS  mandatory
               DESCRIPTION
               "The unit string"
               ::=  {  sensorEntry 5  }

            sensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this sensor"
               ::=  {  sensorEntry 6   }

            sensorGoOffline OBJECT-TYPE
               SYNTAX  INTEGER {
                  online(1),
                  goOffline(2)
               }
               ACCESS  read-write
               STATUS  mandatory
               DESCRIPTION
               "To take offline enter a 2"
               ::=  {  sensorEntry 8   }

            sensorPort OBJECT-TYPE
               SYNTAX  INTEGER (0..65534)
               ACCESS  read-only
               STATUS  mandatory
               DESCRIPTION
               "Sensor port"
               ::=  {  sensorEntry 35 }

            sensorSubPort OBJECT-TYPE
               SYNTAX  INTEGER (0..65534)
               ACCESS  read-only
               STATUS  mandatory
               DESCRIPTION
               "Sensor sub port"
               ::=  {  sensorEntry 36 }

            sensorDeviceIndex OBJECT-TYPE
               SYNTAX  INTEGER (0..65534)
               ACCESS  read-only
               STATUS  mandatory
               DESCRIPTION
               "Device Index of sensor"
               ::=  {  sensorEntry 37 }

            sensorDisplayStyle OBJECT-TYPE
               SYNTAX  INTEGER {
                  basic(0),
                  gauge(1)
               }
               ACCESS  read-write
               STATUS  mandatory
               DESCRIPTION
               "Temperature display style"
               ::=  {  sensorEntry 45 }   

            sensorHighCriticalDescription OBJECT-TYPE
               SYNTAX  DisplayString
               ACCESS  read-write
               STATUS  mandatory
               DESCRIPTION
               "A HighCritical Description of this sensor"
               ::=  {  sensorEntry  46  }

            sensorLowCriticalDescription OBJECT-TYPE
               SYNTAX  DisplayString
               ACCESS  read-write
               STATUS  mandatory
               DESCRIPTION
               "A LowCritical Description of this sensor"
               ::=  {  sensorEntry  47  }

            sensorNormalDescription OBJECT-TYPE
               SYNTAX  DisplayString
               ACCESS  read-write
               STATUS  mandatory
               DESCRIPTION
               "A Normal Description of this sensor"
               ::=  {  sensorEntry  48  }
               
            sensorLowWarningDescription OBJECT-TYPE
               SYNTAX  DisplayString
               ACCESS  read-write
               STATUS  mandatory
               DESCRIPTION
               "A LowWarning Description of this sensor"
               ::=  {  sensorEntry  49  }
               
            sensorHighWarningDescription OBJECT-TYPE
               SYNTAX  DisplayString
               ACCESS  read-write
               STATUS  mandatory
               DESCRIPTION
               "A HighWarning Description of this sensor"
               ::=  {  sensorEntry  50  }
               
            sensorErrorDescription OBJECT-TYPE
               SYNTAX  DisplayString
               ACCESS  read-write
               STATUS  mandatory
               DESCRIPTION
               "A SensorError Description of this sensor"
               ::=  {  sensorEntry  51  }
               
            sensorOnDescription OBJECT-TYPE
               SYNTAX  DisplayString
               ACCESS  read-write
               STATUS  mandatory
               DESCRIPTION
               "A On Description of this sensor"
               ::=  {  sensorEntry  52  }     

            sensorOffDescription OBJECT-TYPE
               SYNTAX  DisplayString
               ACCESS  read-write
               STATUS  mandatory
               DESCRIPTION
               "A Off Description of this sensor"
               ::=  {  sensorEntry  53  }

            sensorHighCriticalColor OBJECT-TYPE
               SYNTAX  INTEGER
               ACCESS  read-write
               STATUS  mandatory
               DESCRIPTION
               "A HighCritical Color of this sensor"
               ::=  {  sensorEntry  54  }

            sensorLowCriticalColor OBJECT-TYPE
               SYNTAX  INTEGER
               ACCESS  read-write
               STATUS  mandatory
               DESCRIPTION
               "A LowCritical Color of this sensor"
               ::=  {  sensorEntry  55  }

            sensorNormalColor OBJECT-TYPE
               SYNTAX  INTEGER
               ACCESS  read-write
               STATUS  mandatory
               DESCRIPTION
               "A Normal Color of this sensor"
               ::=  {  sensorEntry  56  }
               
            sensorLowWarningColor OBJECT-TYPE
               SYNTAX  INTEGER
               ACCESS  read-write
               STATUS  mandatory
               DESCRIPTION
               "A LowWarning Color of this sensor"
               ::=  {  sensorEntry  57  }
               
            sensorHighWarningColor OBJECT-TYPE
               SYNTAX  INTEGER
               ACCESS  read-write
               STATUS  mandatory
               DESCRIPTION
               "A HighWarning Color of this sensor"
               ::=  {  sensorEntry  58  }
               
            sensorErrorColor OBJECT-TYPE
               SYNTAX  INTEGER
               ACCESS  read-write
               STATUS  mandatory
               DESCRIPTION
               "A SensorError Color of this sensor"
               ::=  {  sensorEntry  59  }
               
            sensorOnColor OBJECT-TYPE
               SYNTAX  INTEGER
               ACCESS  read-write
               STATUS  mandatory
               DESCRIPTION
               "A On Color of this sensor"
               ::=  {  sensorEntry  60  }

            sensorOffColor OBJECT-TYPE
               SYNTAX  INTEGER
               ACCESS  read-write
               STATUS  mandatory
               DESCRIPTION
               "A Off Color of this sensor"
               ::=  {  sensorEntry  61  }

            sensorAcknowledge OBJECT-TYPE
               SYNTAX  INTEGER {
                  acked(2)
               }
               ACCESS  read-write
               STATUS  mandatory
               DESCRIPTION
               "Sensor acknowledge"
               ::=  {  sensorEntry  70  }

            sensorValueFormatFloat OBJECT-TYPE
               SYNTAX  Opaque (SIZE(4))
               ACCESS  read-only
               STATUS  mandatory
               DESCRIPTION
               "The floating-point IEEE Standard 754 reading value in this sensor"
               ::=  {  sensorEntry  99  }

            sensorId OBJECT-TYPE
               SYNTAX  INTEGER
               ACCESS  read-only
               STATUS  mandatory
               DESCRIPTION
               "The Sensor ID of this sensor, used to identify which sensor it is in the system configuration."
               ::= { sensorEntry 1000 }

--/* End of sensorEntry */

--/* Begin of sensorTemperatureEntry */
         sensorTemperatureTable OBJECT-TYPE
            SYNTAX  SEQUENCE OF SensorTemperatureEntry
            ACCESS  not-accessible
            STATUS  mandatory
            DESCRIPTION
            "This table contains the property and reading value for every Temperature sensor."
            ::=  {  secSensor 2   }

         sensorTemperatureEntry OBJECT-TYPE
            SYNTAX  SensorTemperatureEntry
            ACCESS  not-accessible
            STATUS  mandatory
            DESCRIPTION
            "This is an entry in the sensorTemperatureEntry Table"
            INDEX         { sensorTemperatureIndex }
            ::=  {  sensorTemperatureTable 1 }

         SensorTemperatureEntry ::= SEQUENCE {
               sensorTemperatureIndex
                  INTEGER,
               sensorTemperatureDescription
                  DisplayString,
               sensorTemperatureType
                  INTEGER,
               sensorTemperatureDegree
                  INTEGER,
               sensorTemperatureUnit
                  DisplayString,               
               sensorTemperatureStatus
                  INTEGER,
               sensorTemperatureGoOffline
                  INTEGER,
               sensorTemperatureLowCritical
                  INTEGER,
               sensorTemperatureLowWarning
                  INTEGER,
               sensorTemperatureHighWarning
                  INTEGER,
               sensorTemperatureHighCritical
                  INTEGER,
               sensorTemperatureRearm
                  INTEGER,
               sensorTemperatureDelayError
                  INTEGER,
               sensorTemperatureDelayNormal
                  INTEGER,
               sensorTemperatureDelayLowCritical
                  INTEGER,
               sensorTemperatureDelayLowWarning
                  INTEGER,
               sensorTemperatureDelayHighWarning
                  INTEGER,
               sensorTemperatureDelayHighCritical
                  INTEGER,
               sensorTemperatureRaw
                  INTEGER,
               sensorTemperatureOffset
                  INTEGER,
               sensorTemperaturePort
                  INTEGER,
               sensorTemperatureSubPort
                  INTEGER,
               sensorTemperatureDeviceIndex
                  INTEGER,
               sensorTemperatureDisplayStyle
                  INTEGER,
               sensorTemperatureHighCriticalDesc 
                  DisplayString,
               sensorTemperatureLowCriticalDesc 
                  DisplayString,
               sensorTemperatureNormalDesc 
                  DisplayString,
               sensorTemperatureLowWarningDesc 
                  DisplayString,   
               sensorTemperatureHighWarningDesc 
                  DisplayString,
               sensorTemperatureSensorErrorDesc 
                  DisplayString,
               sensorTemperatureHighCriticalColor 
                  INTEGER,
               sensorTemperatureLowCriticalColor 
                  INTEGER,
               sensorTemperatureNormalColor 
                  INTEGER,
               sensorTemperatureLowWarningColor 
                  INTEGER,   
               sensorTemperatureHighWarningColor 
                  INTEGER,
               sensorTemperatureSensorErrorColor 
                  INTEGER,                 
               sensorTemperatureAcknowledge
                  INTEGER,
               sensorTemperatureSerialNumber
                  DisplayString,
               sensorTemperatureId
                  INTEGER
            }

            sensorTemperatureIndex OBJECT-TYPE
               SYNTAX  INTEGER (1..65535)
               ACCESS  read-only
               STATUS  mandatory
               DESCRIPTION
               "The index into the sensor table"
               ::=  {  sensorTemperatureEntry 1   }

            sensorTemperatureDescription OBJECT-TYPE
               SYNTAX  DisplayString
               ACCESS  read-write
               STATUS  mandatory
               DESCRIPTION
               "A Description of this sensor"
               ::=  {  sensorTemperatureEntry 2   }

            sensorTemperatureType OBJECT-TYPE
               SYNTAX  INTEGER {
                  temperature(1),
                  dualsensor(3),
                  thermocouple(20),
                  arraytemp(23)
               }
               ACCESS  read-only
               STATUS  mandatory
               DESCRIPTION
               "Enter the type of this Sensor"
               ::=  {  sensorTemperatureEntry 3  }

            sensorTemperatureDegree OBJECT-TYPE
               SYNTAX  INTEGER
               ACCESS  read-only
               STATUS  mandatory
               DESCRIPTION
               "The degrees in this sensor"
               ::=  {  sensorTemperatureEntry 4   }

            sensorTemperatureUnit OBJECT-TYPE
               SYNTAX  DisplayString
               ACCESS  read-only
               STATUS  mandatory
               DESCRIPTION
               "The unit string"
               ::=  {  sensorTemperatureEntry 5  }

            sensorTemperatureStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorTemperatureEntry 6   }
   
            sensorTemperatureGoOffline OBJECT-TYPE
               SYNTAX  INTEGER {
                  online(1),
                  goOffline(2)
               }
               ACCESS  read-write
               STATUS  mandatory
               DESCRIPTION
               "To take offline enter a 2"
               ::=  {  sensorTemperatureEntry 8   }

            sensorTemperatureLowCritical OBJECT-TYPE
               SYNTAX  INTEGER
               ACCESS  read-write
               STATUS  mandatory
               DESCRIPTION
               "How cold this sensor gets before it sends a critical event"
               ::=  {  sensorTemperatureEntry 9   }

            sensorTemperatureLowWarning OBJECT-TYPE
               SYNTAX  INTEGER
               ACCESS  read-write
               STATUS  mandatory
               DESCRIPTION
               "How cold this sensor gets before it sends a warning"
               ::=  {  sensorTemperatureEntry 10   }
   
            sensorTemperatureHighWarning OBJECT-TYPE
               SYNTAX  INTEGER
               ACCESS  read-write
               STATUS  mandatory
               DESCRIPTION
               "How hot this sensor gets before it sends a warning"
               ::=  {  sensorTemperatureEntry 11   }  

            sensorTemperatureHighCritical OBJECT-TYPE
               SYNTAX  INTEGER
               ACCESS  read-write
               STATUS  mandatory
               DESCRIPTION
               "How hot this sensor gets before it sends a critical event"
               ::=  {  sensorTemperatureEntry 12   }   

            sensorTemperatureRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorTemperatureEntry 13   }

            sensorTemperatureDelayError OBJECT-TYPE
               SYNTAX  INTEGER (0..65534)
               ACCESS  read-write
               STATUS  mandatory
               DESCRIPTION
               "Time in seconds after the sensor has been in error status before report as an error"
               ::=  {  sensorTemperatureEntry 14   }

            sensorTemperatureDelayNormal OBJECT-TYPE
               SYNTAX  INTEGER (0..65534)
               ACCESS  read-write
               STATUS  mandatory
               DESCRIPTION
               "Time in seconds after the sensor change from error to normal before report as normal"
               ::=  {  sensorTemperatureEntry 15   }

            sensorTemperatureDelayLowCritical OBJECT-TYPE
               SYNTAX INTEGER (0..65535)
               ACCESS read-write
               STATUS mandatory
               DESCRIPTION
               "Continuous time for this sensor to be in Low Critical before accepting new Status."
               ::= {  sensorTemperatureEntry 16 }
               
            sensorTemperatureDelayLowWarning OBJECT-TYPE
               SYNTAX INTEGER (0..65535)
               ACCESS read-write
               STATUS mandatory
               DESCRIPTION
               "Continuous time for this sensor to be in Low Warning before accepting new Status."
               ::= {  sensorTemperatureEntry 17 }

            sensorTemperatureDelayHighWarning OBJECT-TYPE
               SYNTAX INTEGER (0..65535)
               ACCESS read-write
               STATUS mandatory
               DESCRIPTION
               "Continuous time for this sensor to be in High Warning before accepting new Status."
               ::= {  sensorTemperatureEntry 18 }

            sensorTemperatureDelayHighCritical OBJECT-TYPE
               SYNTAX INTEGER (0..65535)
               ACCESS read-write
               STATUS mandatory
               DESCRIPTION
               "Continuous time for this sensor to be in High Critical before accepting new Status."
               ::= {  sensorTemperatureEntry 19 }

            sensorTemperatureRaw OBJECT-TYPE
               SYNTAX  INTEGER 
               ACCESS  read-only
               STATUS  mandatory
               DESCRIPTION
               "The raw degree data from the temperature sensor, slightly higher resolution"
               ::=  {  sensorTemperatureEntry 20 }

            sensorTemperatureOffset OBJECT-TYPE
               SYNTAX  INTEGER
               ACCESS  read-write
               STATUS  mandatory
               DESCRIPTION
               "Temperature Offset reading"
               ::=  {  sensorTemperatureEntry 21 }

            sensorTemperaturePort OBJECT-TYPE
               SYNTAX  INTEGER (0..65534)
               ACCESS  read-only
               STATUS  mandatory
               DESCRIPTION
               "Sensor port"
               ::=  {  sensorTemperatureEntry 35 }

            sensorTemperatureSubPort OBJECT-TYPE
               SYNTAX  INTEGER (0..65534)
               ACCESS  read-only
               STATUS  mandatory
               DESCRIPTION
               "Sensor sub port"
               ::=  {  sensorTemperatureEntry 36 }

            sensorTemperatureDeviceIndex OBJECT-TYPE
               SYNTAX  INTEGER (0..65534)
               ACCESS  read-only
               STATUS  mandatory
               DESCRIPTION
               "Device Index of sensor"
               ::=  {  sensorTemperatureEntry 37 }
               
            sensorTemperatureDisplayStyle OBJECT-TYPE
               SYNTAX  INTEGER {
                  basic(0),
                  gauge(1)
               }
               ACCESS  read-write
               STATUS  mandatory
               DESCRIPTION
               "Temperature display style"
               ::=  {  sensorTemperatureEntry 45 }   

            sensorTemperatureHighCriticalDesc OBJECT-TYPE
               SYNTAX  DisplayString
               ACCESS  read-write
               STATUS  mandatory
               DESCRIPTION
               "A HighCritical Description of this sensor"
               ::=  {  sensorTemperatureEntry  46  }               

            sensorTemperatureLowCriticalDesc OBJECT-TYPE
               SYNTAX  DisplayString
               ACCESS  read-write
               STATUS  mandatory
               DESCRIPTION
               "A LowCritical Description of this sensor"
               ::=  {  sensorTemperatureEntry  47  }

            sensorTemperatureNormalDesc OBJECT-TYPE
               SYNTAX  DisplayString
               ACCESS  read-write
               STATUS  mandatory
               DESCRIPTION
               "A Normal Description of this sensor"
               ::=  {  sensorTemperatureEntry  48  }
               
            sensorTemperatureLowWarningDesc OBJECT-TYPE
               SYNTAX  DisplayString
               ACCESS  read-write
               STATUS  mandatory
               DESCRIPTION
               "A LowWarning Description of this sensor"
               ::=  {  sensorTemperatureEntry  49  }
               
            sensorTemperatureHighWarningDesc OBJECT-TYPE
               SYNTAX  DisplayString
               ACCESS  read-write
               STATUS  mandatory
               DESCRIPTION
               "A HighWarning Description of this sensor"
               ::=  {  sensorTemperatureEntry  50  }
               
            sensorTemperatureSensorErrorDesc OBJECT-TYPE
               SYNTAX  DisplayString
               ACCESS  read-write
               STATUS  mandatory
               DESCRIPTION
               "A SensorError Description of this sensor"
               ::=  {  sensorTemperatureEntry  51  }

            sensorTemperatureHighCriticalColor OBJECT-TYPE
               SYNTAX  INTEGER
               ACCESS  read-write
               STATUS  mandatory
               DESCRIPTION
               "A HighCritical Color of this sensor"
               ::=  {  sensorTemperatureEntry  54  }               

            sensorTemperatureLowCriticalColor OBJECT-TYPE
               SYNTAX  INTEGER
               ACCESS  read-write
               STATUS  mandatory
               DESCRIPTION
               "A LowCritical Color of this sensor"
               ::=  {  sensorTemperatureEntry  55  }

            sensorTemperatureNormalColor OBJECT-TYPE
               SYNTAX  INTEGER
               ACCESS  read-write
               STATUS  mandatory
               DESCRIPTION
               "A Normal Color of this sensor"
               ::=  {  sensorTemperatureEntry  56  }
               
            sensorTemperatureLowWarningColor OBJECT-TYPE
               SYNTAX  INTEGER
               ACCESS  read-write
               STATUS  mandatory
               DESCRIPTION
               "A LowWarning Color of this sensor"
               ::=  {  sensorTemperatureEntry  57  }
               
            sensorTemperatureHighWarningColor OBJECT-TYPE
               SYNTAX  INTEGER
               ACCESS  read-write
               STATUS  mandatory
               DESCRIPTION
               "A HighWarning Color of this sensor"
               ::=  {  sensorTemperatureEntry  58  }
               
            sensorTemperatureSensorErrorColor OBJECT-TYPE
               SYNTAX  INTEGER
               ACCESS  read-write
               STATUS  mandatory
               DESCRIPTION
               "A SensorError Color of this sensor"
               ::=  {  sensorTemperatureEntry  59  }    
               
            sensorTemperatureAcknowledge OBJECT-TYPE
               SYNTAX  INTEGER {
                  acked(2)
               }
               ACCESS  read-write
               STATUS  mandatory
               DESCRIPTION
               "Temperature sensor acknowledge"
               ::=  {  sensorTemperatureEntry 70 } 
               
            sensorTemperatureSerialNumber OBJECT-TYPE
               SYNTAX  DisplayString
               ACCESS  read-write
               STATUS  mandatory
               DESCRIPTION
               "Serial Number of Temperature Sensor in the following format
               x is Hex Digit xx-xx-xx-xx-xx-xx-xx-xx"
               ::=  {  sensorTemperatureEntry 71 }                            
               
            sensorTemperatureId OBJECT-TYPE
               SYNTAX  INTEGER
               ACCESS  read-only
               STATUS  mandatory
               DESCRIPTION
               "The Sensor ID of this sensor, used to identify which sensor it is in the system configuration."
               ::= { sensorTemperatureEntry 1000 }

--/* End of sensorTemperatureEntry */

--/* Begin of sensorHumidityEntry */
         sensorHumidityTable OBJECT-TYPE
            SYNTAX  SEQUENCE OF SensorHumidityEntry
            ACCESS  not-accessible
            STATUS  mandatory
            DESCRIPTION
            "This table contains the property and reading value for every sensor."
            ::=  {  secSensor 3   }

         sensorHumidityEntry OBJECT-TYPE
            SYNTAX  SensorHumidityEntry
            ACCESS  not-accessible
            STATUS  mandatory
            DESCRIPTION
            "This is an entry in the sensorTemperatureEntry Table"
            INDEX         { sensorHumidityIndex }
            ::=  {  sensorHumidityTable 1 }

         SensorHumidityEntry ::= SEQUENCE {
               sensorHumidityIndex
                  INTEGER,
               sensorHumidityDescription
                  DisplayString,
               sensorHumidityPercent
                  INTEGER,
               sensorHumidityUnit
                  DisplayString,
               sensorHumidityStatus
                  INTEGER,
               sensorHumidityGoOffline
                  INTEGER,
               sensorHumidityLowCritical
                  INTEGER,
               sensorHumidityLowWarning
                  INTEGER,
               sensorHumidityHighWarning
                  INTEGER,
               sensorHumidityHighCritical
                  INTEGER,
               sensorHumidityRearm
                  INTEGER,
               sensorHumidityDelayError
                  INTEGER,
               sensorHumidityDelayNormal
                  INTEGER,
               sensorHumidityDelayLowCritical
                  INTEGER,
               sensorHumidityDelayLowWarning
                  INTEGER,
               sensorHumidityDelayHighWarning
                  INTEGER,
               sensorHumidityDelayHighCritical
                  INTEGER,
               sensorHumidityRaw
                  INTEGER,
               sensorHumidityOffset
                  INTEGER,
               sensorHumidityPort
                  INTEGER,
               sensorHumiditySubPort
                  INTEGER,
               sensorHumidityDeviceIndex
                  INTEGER,
               sensorHumidityDisplayStyle
                  INTEGER,
               sensorHumidityHighCriticalDesc 
                  DisplayString,
               sensorHumidityLowCriticalDesc 
                  DisplayString,
               sensorHumidityNormalDesc 
                  DisplayString,
               sensorHumidityLowWarningDesc 
                  DisplayString,   
               sensorHumidityHighWarningDesc 
                  DisplayString,
               sensorHumiditySensorErrorDesc 
                  DisplayString,
               sensorHumidityHighCriticalColor 
                  INTEGER,
               sensorHumidityLowCriticalColor 
                  INTEGER,
               sensorHumidityNormalColor 
                  INTEGER,
               sensorHumidityLowWarningColor 
                  INTEGER,   
               sensorHumidityHighWarningColor 
                  INTEGER,
               sensorHumiditySensorErrorColor 
                  INTEGER,
               sensorHumidityAcknowledge
                  INTEGER,
               sensorHumidityId
                  INTEGER
            }

            sensorHumidityIndex OBJECT-TYPE
               SYNTAX  INTEGER (1..65535)
               ACCESS  read-only
               STATUS  mandatory
               DESCRIPTION
               "The index into the sensor table"
               ::=  {  sensorHumidityEntry 1   }

            sensorHumidityDescription OBJECT-TYPE
               SYNTAX  DisplayString
               ACCESS  read-write
               STATUS  mandatory
               DESCRIPTION
               "A Description of this sensor"
               ::=  {  sensorHumidityEntry 2   }

            sensorHumidityPercent OBJECT-TYPE
               SYNTAX  INTEGER
               ACCESS  read-only
               STATUS  mandatory
               DESCRIPTION
               "The relative humidity percentage measured by this sensor"
               ::=  {  sensorHumidityEntry 4   }

            sensorHumidityUnit OBJECT-TYPE
               SYNTAX  DisplayString
               ACCESS  read-write
               STATUS  mandatory
               DESCRIPTION
               "The unit string"
               ::=  {  sensorHumidityEntry 5  }

            sensorHumidityStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorHumidityEntry 6   }

            sensorHumidityGoOffline OBJECT-TYPE
               SYNTAX  INTEGER {
                  online(1),
                  goOffline(2)
               }
               ACCESS  read-write
               STATUS  mandatory
               DESCRIPTION
               "To take offline enter a 2"
               ::=  {  sensorHumidityEntry 8   }

            sensorHumidityLowCritical OBJECT-TYPE
               SYNTAX  INTEGER
               ACCESS  read-write
               STATUS  mandatory
               DESCRIPTION
               "How cold this sensor gets before it sends a critical event"
               ::=  {  sensorHumidityEntry 9   }

            sensorHumidityLowWarning OBJECT-TYPE
               SYNTAX  INTEGER
               ACCESS  read-write
               STATUS  mandatory
               DESCRIPTION
               "How cold this sensor gets before it sends a warning"
               ::=  {  sensorHumidityEntry 10   }
   
            sensorHumidityHighWarning OBJECT-TYPE
               SYNTAX  INTEGER
               ACCESS  read-write
               STATUS  mandatory
               DESCRIPTION
               "How hot this sensor gets before it sends a warning"
               ::=  {  sensorHumidityEntry 11   }  

            sensorHumidityHighCritical OBJECT-TYPE
               SYNTAX  INTEGER
               ACCESS  read-write
               STATUS  mandatory
               DESCRIPTION
               "How hot this sensor gets before it sends a critical event"
               ::=  {  sensorHumidityEntry 12   }   

            sensorHumidityRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorHumidityEntry 13   }

            sensorHumidityDelayError OBJECT-TYPE
               SYNTAX  INTEGER (0..65534)
               ACCESS  read-write
               STATUS  mandatory
               DESCRIPTION
               "Time in seconds after the sensor has been in error status before report as an error"
               ::=  {  sensorHumidityEntry 14   }

            sensorHumidityDelayNormal OBJECT-TYPE
               SYNTAX  INTEGER (0..65534)
               ACCESS  read-write
               STATUS  mandatory
               DESCRIPTION
               "Time in seconds after the sensor change from error to normal before report as normal"
               ::=  {  sensorHumidityEntry 15   }

            sensorHumidityDelayLowCritical OBJECT-TYPE
               SYNTAX INTEGER (0..65535)
               ACCESS read-write
               STATUS mandatory
               DESCRIPTION
               "Continuous time for this sensor to be in Low Critical before accepting new Status."
               ::= {  sensorHumidityEntry 16 }
               
            sensorHumidityDelayLowWarning OBJECT-TYPE
               SYNTAX INTEGER (0..65535)
               ACCESS read-write
               STATUS mandatory
               DESCRIPTION
               "Continuous time for this sensor to be in Low Warning before accepting new Status."
               ::= {  sensorHumidityEntry 17 }

            sensorHumidityDelayHighWarning OBJECT-TYPE
               SYNTAX INTEGER (0..65535)
               ACCESS read-write
               STATUS mandatory
               DESCRIPTION
               "Continuous time for this sensor to be in High Warning before accepting new Status."
               ::= {  sensorHumidityEntry 18 }

            sensorHumidityDelayHighCritical OBJECT-TYPE
               SYNTAX INTEGER (0..65535)
               ACCESS read-write
               STATUS mandatory
               DESCRIPTION
               "Continuous time for this sensor to be in High Critical before accepting new Status."
               ::= {  sensorHumidityEntry 19 }

            sensorHumidityRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorHumidityEntry 20   }

            sensorHumidityOffset OBJECT-TYPE
               SYNTAX  INTEGER
               ACCESS  read-write
               STATUS  mandatory
               DESCRIPTION
               "Humidity Offset reading"
               ::=  {  sensorHumidityEntry 21   }

            sensorHumidityPort OBJECT-TYPE
               SYNTAX  INTEGER (0..65534)
               ACCESS  read-only
               STATUS  mandatory
               DESCRIPTION
               "Sensor port"
               ::=  {  sensorHumidityEntry 35 }

            sensorHumiditySubPort OBJECT-TYPE
               SYNTAX  INTEGER (0..65534)
               ACCESS  read-only
               STATUS  mandatory
               DESCRIPTION
               "Sensor sub port"
               ::=  {  sensorHumidityEntry 36 }

            sensorHumidityDeviceIndex OBJECT-TYPE
               SYNTAX  INTEGER (0..65534)
               ACCESS  read-only
               STATUS  mandatory
               DESCRIPTION
               "Device Index of sensor"
               ::=  {  sensorHumidityEntry 37 }
               
            sensorHumidityDisplayStyle OBJECT-TYPE
               SYNTAX  INTEGER {
                  basic(0),
                  gauge(1)
               }
               ACCESS  read-write
               STATUS  mandatory
               DESCRIPTION
               "Humidity display style"
               ::=  {  sensorHumidityEntry 45 }           
               
            sensorHumidityHighCriticalDesc OBJECT-TYPE
               SYNTAX  DisplayString
               ACCESS  read-write
               STATUS  mandatory
               DESCRIPTION
               "A HighCritical Description of this sensor"
               ::=  {  sensorHumidityEntry  46  }               

            sensorHumidityLowCriticalDesc OBJECT-TYPE
               SYNTAX  DisplayString
               ACCESS  read-write
               STATUS  mandatory
               DESCRIPTION
               "A LowCritical Description of this sensor"
               ::=  {  sensorHumidityEntry  47  }

            sensorHumidityNormalDesc OBJECT-TYPE
               SYNTAX  DisplayString
               ACCESS  read-write
               STATUS  mandatory
               DESCRIPTION
               "A Normal Description of this sensor"
               ::=  {  sensorHumidityEntry  48  }
               
            sensorHumidityLowWarningDesc OBJECT-TYPE
               SYNTAX  DisplayString
               ACCESS  read-write
               STATUS  mandatory
               DESCRIPTION
               "A LowWarning Description of this sensor"
               ::=  {  sensorHumidityEntry  49  }
               
            sensorHumidityHighWarningDesc OBJECT-TYPE
               SYNTAX  DisplayString
               ACCESS  read-write
               STATUS  mandatory
               DESCRIPTION
               "A HighWarning Description of this sensor"
               ::=  {  sensorHumidityEntry  50  }
               
            sensorHumiditySensorErrorDesc OBJECT-TYPE
               SYNTAX  DisplayString
               ACCESS  read-write
               STATUS  mandatory
               DESCRIPTION
               "A SensorError Description of this sensor"
               ::=  {  sensorHumidityEntry  51  }  

            sensorHumidityHighCriticalColor OBJECT-TYPE
               SYNTAX  INTEGER
               ACCESS  read-write
               STATUS  mandatory
               DESCRIPTION
               "A HighCritical Color of this sensor"
               ::=  {  sensorHumidityEntry  54  }               

            sensorHumidityLowCriticalColor OBJECT-TYPE
               SYNTAX  INTEGER
               ACCESS  read-write
               STATUS  mandatory
               DESCRIPTION
               "A LowCritical Color of this sensor"
               ::=  {  sensorHumidityEntry  55  }

            sensorHumidityNormalColor OBJECT-TYPE
               SYNTAX  INTEGER
               ACCESS  read-write
               STATUS  mandatory
               DESCRIPTION
               "A Normal Color of this sensor"
               ::=  {  sensorHumidityEntry  56  }
               
            sensorHumidityLowWarningColor OBJECT-TYPE
               SYNTAX  INTEGER
               ACCESS  read-write
               STATUS  mandatory
               DESCRIPTION
               "A LowWarning Color of this sensor"
               ::=  {  sensorHumidityEntry  57  }
               
            sensorHumidityHighWarningColor OBJECT-TYPE
               SYNTAX  INTEGER
               ACCESS  read-write
               STATUS  mandatory
               DESCRIPTION
               "A HighWarning Color of this sensor"
               ::=  {  sensorHumidityEntry  58  }
               
            sensorHumiditySensorErrorColor OBJECT-TYPE
               SYNTAX  INTEGER
               ACCESS  read-write
               STATUS  mandatory
               DESCRIPTION
               "A SensorError Color of this sensor"
               ::=  {  sensorHumidityEntry  59  }     

            sensorHumidityAcknowledge OBJECT-TYPE
               SYNTAX  INTEGER {
                  acked(2)
               }
               ACCESS  read-write
               STATUS  mandatory
               DESCRIPTION
               "Humidity sensor acknowledge"
               ::=  {  sensorHumidityEntry 70 }  

            sensorHumidityId OBJECT-TYPE
               SYNTAX  INTEGER
               ACCESS  read-only
               STATUS  mandatory
               DESCRIPTION
               "The Sensor ID of this sensor, used to identify which sensor it is in the system configuration."
               ::= { sensorHumidityEntry 1000 }

--/* End of sensorHumidityEntry */

--/* Begin of sensorDryContactEntry */
         sensorDryContactTable OBJECT-TYPE
            SYNTAX  SEQUENCE OF SensorDryContactEntry
            ACCESS  not-accessible
            STATUS  mandatory
            DESCRIPTION
            "This table contains the property and reading value for every sensor."
            ::=  {  secSensor 4   }

         sensorDryContactEntry OBJECT-TYPE
            SYNTAX  SensorDryContactEntry
            ACCESS  not-accessible
            STATUS  mandatory
            DESCRIPTION
            "This is an entry in the sensorTemperatureEntry Table"
            INDEX         { sensorDryContactIndex }
            ::=  {  sensorDryContactTable 1 }

         SensorDryContactEntry ::= SEQUENCE {
               sensorDryContactIndex
                  INTEGER,
               sensorDryContactDescription
                  DisplayString,
               sensorDryContactType
                  INTEGER,
               sensorDryContactStatus
                  INTEGER,
               sensorDryContactGoOffline
                  INTEGER,
               sensorDryContactDirection
                  INTEGER,
               sensorDryContactNormalState
                  INTEGER,
               sensorDryContactControlMode
                  INTEGER,
               sensorDryContactOutputManualCycleTime
                  INTEGER,
               sensorDryContactOutputManualAction
                  INTEGER,
               sensorDryContactPort
                  INTEGER,
               sensorDryContactSubPort
                  INTEGER,
               sensorDryContactDeviceIndex
                  INTEGER,
               sensorDryContactCriticalDesc 
                  DisplayString,
               sensorDryContactNormalDesc 
                  DisplayString,
               sensorDryContactOnDesc
                  DisplayString,
               sensorDryContactOffDesc
                  DisplayString,
               sensorDryContactCriticalColor 
                  INTEGER,
               sensorDryContactNormalColor 
                  INTEGER,
               sensorDryContactOnColor
                  INTEGER,
               sensorDryContactOffColor
                  INTEGER,         
               sensorDryContactAcknowledge
                  INTEGER,
               sensorDryContactId
                  INTEGER
            }

            sensorDryContactIndex OBJECT-TYPE
               SYNTAX  INTEGER (1..65535)
               ACCESS  read-only
               STATUS  mandatory
               DESCRIPTION
               "The index into the Switch sensor table"
               ::=  {  sensorDryContactEntry 1   }

            sensorDryContactDescription OBJECT-TYPE
               SYNTAX  DisplayString
               ACCESS  read-write
               STATUS  mandatory
               DESCRIPTION
               "A Description of this sensor Switch"
               ::=  {  sensorDryContactEntry 2   }

            sensorDryContactType OBJECT-TYPE
               SYNTAX  INTEGER {
                  drycontact-inout(7),
                  drycontact-input(8),
                  drycontact-array(22)
               }
               ACCESS  read-only
               STATUS  mandatory
               DESCRIPTION
               "Enter the type of this Sensor"
               ::=  {  sensorDryContactEntry 3  }

            sensorDryContactStatus OBJECT-TYPE
               SYNTAX  INTEGER {
                  noStatus(1),
                  normal(2),
                  highCritical(4),
                  lowCritical(6),
                  sensorError(7),
                  outputLow(8),
                  outputHigh(9)
               }
               ACCESS  read-only
               STATUS  mandatory
               DESCRIPTION
               "The current status of this Sensor, only input switches have a status"
               ::=  {  sensorDryContactEntry 6  }

            sensorDryContactGoOffline OBJECT-TYPE
               SYNTAX  INTEGER {
                  online(1),
                  goOffline(2)
               }
               ACCESS  read-write
               STATUS  mandatory
               DESCRIPTION
               "To take offline enter a 2"
               ::=  {  sensorDryContactEntry 8  }

            sensorDryContactDirection OBJECT-TYPE
               SYNTAX  INTEGER {
                  input(0),
                  output(1)
               }
               ACCESS  read-write
               STATUS  mandatory
               DESCRIPTION
               "To set a switch to input enter 0. To set a switch to output enter 1"
               ::=  {  sensorDryContactEntry 22  }

            sensorDryContactNormalState OBJECT-TYPE
               SYNTAX  INTEGER {
                  closed(0),
                  open(1)
               }
               ACCESS  read-write
               STATUS  mandatory
               DESCRIPTION
               "The normal state of an input switch. If an input switch is in this state it is normal, else it is critical. An open switch senses +5 volts. A closed switch senses 0 volts."
               ::=  {  sensorDryContactEntry 23  }
               
            sensorDryContactControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a sensor output."
               ::=  {  sensorDryContactEntry 24  }
               
            sensorDryContactOutputManualCycleTime OBJECT-TYPE
               SYNTAX  INTEGER (1..255)
               ACCESS  read-write
               STATUS  mandatory
               DESCRIPTION
               "Toggle period in seconds for Manual Cycle action."
               ::=  {  sensorDryContactEntry 25  }
               
            sensorDryContactOutputManualAction OBJECT-TYPE
               SYNTAX  INTEGER {
                  low(0),
                  high(1),
                  cycle-Low-High-Low(2),
                  cycle-High-Low-High(3)
               }
               ACCESS  read-write
               STATUS  mandatory
               DESCRIPTION
               "Control the sensor output manualy"
               ::=  {  sensorDryContactEntry 26  }

            sensorDryContactPort OBJECT-TYPE
               SYNTAX  INTEGER (0..65534)
               ACCESS  read-only
               STATUS  mandatory
               DESCRIPTION
               "Sensor port"
               ::=  {  sensorDryContactEntry 35 }

            sensorDryContactSubPort OBJECT-TYPE
               SYNTAX  INTEGER (0..65534)
               ACCESS  read-only
               STATUS  mandatory
               DESCRIPTION
               "Sensor sub port"
               ::=  {  sensorDryContactEntry 36 }

            sensorDryContactDeviceIndex OBJECT-TYPE
               SYNTAX  INTEGER (0..65534)
               ACCESS  read-only
               STATUS  mandatory
               DESCRIPTION
               "Device Index of sensor"
               ::=  {  sensorDryContactEntry 37 }
               
            sensorDryContactCriticalDesc OBJECT-TYPE
               SYNTAX  DisplayString
               ACCESS  read-write
               STATUS  mandatory
               DESCRIPTION
               "A Critical Description of this sensor"
               ::=  {  sensorDryContactEntry  46 } 

            sensorDryContactNormalDesc OBJECT-TYPE
               SYNTAX  DisplayString
               ACCESS  read-write
               STATUS  mandatory
               DESCRIPTION
               "A Normal Description of this sensor"
               ::=  {  sensorDryContactEntry  48  }

            sensorDryContactOnDesc OBJECT-TYPE
               SYNTAX  DisplayString
               ACCESS  read-write
               STATUS  mandatory
               DESCRIPTION
               "A On Description of this sensor"
               ::=  {  sensorDryContactEntry  52  }     

            sensorDryContactOffDesc OBJECT-TYPE
               SYNTAX  DisplayString
               ACCESS  read-write
               STATUS  mandatory
               DESCRIPTION
               "A Off Description of this sensor"
               ::=  {  sensorDryContactEntry  53  }                   

            sensorDryContactCriticalColor OBJECT-TYPE
               SYNTAX  INTEGER
               ACCESS  read-write
               STATUS  mandatory
               DESCRIPTION
               "A Critical Color of this sensor"
               ::=  {  sensorDryContactEntry  54  }               

            sensorDryContactNormalColor OBJECT-TYPE
               SYNTAX  INTEGER
               ACCESS  read-write
               STATUS  mandatory
               DESCRIPTION
               "A Normal Color of this sensor"
               ::=  {  sensorDryContactEntry  56  }

            sensorDryContactOnColor OBJECT-TYPE
               SYNTAX  INTEGER
               ACCESS  read-write
               STATUS  mandatory
               DESCRIPTION
               "A On Color of this sensor"
               ::=  {  sensorDryContactEntry  60  }

            sensorDryContactOffColor OBJECT-TYPE
               SYNTAX  INTEGER
               ACCESS  read-write
               STATUS  mandatory
               DESCRIPTION
               "A Off Color of this sensor"
               ::=  {  sensorDryContactEntry  61  }
        
            sensorDryContactAcknowledge OBJECT-TYPE
               SYNTAX  INTEGER {
                  acked(2)
               }
               ACCESS  read-write
               STATUS  mandatory
               DESCRIPTION
               "Dry Contact sensor acknowledge"
               ::=  {  sensorDryContactEntry 70 }
               
            sensorDryContactId OBJECT-TYPE
               SYNTAX  INTEGER
               ACCESS  read-only
               STATUS  mandatory
               DESCRIPTION
               "The Sensor ID of this sensor, used to identify which sensor it is in the system configuration."
               ::= { sensorDryContactEntry 1000 }

--/* End of sensorDryContactEntry */

--/* Begin of sensor4to20mAEntry */
         sensor4to20mATable OBJECT-TYPE
            SYNTAX  SEQUENCE OF Sensor4to20mAEntry
            ACCESS  not-accessible
            STATUS  mandatory
            DESCRIPTION
            "This table contains the property and reading value for every sensor."
            ::=  {  secSensor 5   }

         sensor4to20mAEntry OBJECT-TYPE
            SYNTAX  Sensor4to20mAEntry
            ACCESS  not-accessible
            STATUS  mandatory
            DESCRIPTION
            "This is an entry in the sensorTemperatureEntry Table"
            INDEX         { sensor4to20mAIndex }
            ::=  {  sensor4to20mATable 1 }

         Sensor4to20mAEntry ::= SEQUENCE {
               sensor4to20mAIndex
                  INTEGER,
               sensor4to20mADescription
                  DisplayString,
               sensor4to20mAValue
                  INTEGER,
               sensor4to20mAUnit
                  DisplayString,
               sensor4to20mAStatus
                  INTEGER,
               sensor4to20mAGoOffline
                  INTEGER,
               sensor4to20mALowCritical
                  INTEGER,
               sensor4to20mALowWarning
                  INTEGER,
               sensor4to20mAHighWarning
                  INTEGER,
               sensor4to20mAHighCritical
                  INTEGER,
               sensor4to20mARearm
                  INTEGER,
               sensor4to20mADelayError
                  INTEGER,
               sensor4to20mADelayNormal
                  INTEGER,
               sensor4to20mADelayLowCritical
                  INTEGER,
               sensor4to20mADelayLowWarning
                  INTEGER,
               sensor4to20mADelayHighWarning
                  INTEGER,
               sensor4to20mADelayHighCritical
                  INTEGER,
               sensor4to20mARaw
                  INTEGER,
               sensor4to20mAOffset
                  INTEGER,
               sensor4to20mAAmountMaxVoltage
                  INTEGER,
               sensor4to20mAAmountBaseVoltage
                  INTEGER,
               sensor4to20mAPort
                  INTEGER,
               sensor4to20mASubPort
                  INTEGER,
               sensor4to20mADeviceIndex
                  INTEGER,
               sensor4to20mAMaxVoltage
                  INTEGER,
               sensor4to20mABaseVoltage
                  INTEGER,
               sensor4to20mADisplayStyle
                  INTEGER,
               sensor4to20mAHighCriticalDesc 
                  DisplayString,
               sensor4to20mALowCriticalDesc 
                  DisplayString,
               sensor4to20mANormalDesc 
                  DisplayString,
               sensor4to20mALowWarningDesc 
                  DisplayString,   
               sensor4to20mAHighWarningDesc 
                  DisplayString,
               sensor4to20mASensorErrorDesc 
                  DisplayString,
               sensor4to20mAHighCriticalColor 
                  INTEGER,
               sensor4to20mALowCriticalColor 
                  INTEGER,
               sensor4to20mANormalColor 
                  INTEGER,
               sensor4to20mALowWarningColor 
                  INTEGER,   
               sensor4to20mAHighWarningColor 
                  INTEGER,
               sensor4to20mASensorErrorColor 
                  INTEGER,
               sensor4to20mASensorAcknowledge
                  INTEGER,
               sensor4to20mAId
                  INTEGER
            }

            sensor4to20mAIndex OBJECT-TYPE
               SYNTAX  INTEGER (1..65535)
               ACCESS  read-only
               STATUS  mandatory
               DESCRIPTION
               "The index into the sensor table"
               ::=  {  sensor4to20mAEntry 1   }

            sensor4to20mADescription OBJECT-TYPE
               SYNTAX  DisplayString
               ACCESS  read-write
               STATUS  mandatory
               DESCRIPTION
               "A Description of this sensor"
               ::=  {  sensor4to20mAEntry 2   }

            sensor4to20mAValue OBJECT-TYPE
               SYNTAX  INTEGER
               ACCESS  read-only
               STATUS  mandatory
               DESCRIPTION
               "The reading value in this sensor"
               ::=  {  sensor4to20mAEntry 4   }

            sensor4to20mAUnit OBJECT-TYPE
               SYNTAX  DisplayString
               ACCESS  read-write
               STATUS  mandatory
               DESCRIPTION
               "The unit string"
               ::=  {  sensor4to20mAEntry 5  }

            sensor4to20mAStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensor4to20mAEntry 6   }

            sensor4to20mAGoOffline OBJECT-TYPE
               SYNTAX  INTEGER {
                  online(1),
                  goOffline(2)
               }
               ACCESS  read-write
               STATUS  mandatory
               DESCRIPTION
               "To take offline enter a 2"
               ::=  {  sensor4to20mAEntry 8   }

            sensor4to20mALowCritical OBJECT-TYPE
               SYNTAX  INTEGER
               ACCESS  read-write
               STATUS  mandatory
               DESCRIPTION
               "How cold this sensor gets before it sends a critical event"
               ::=  {  sensor4to20mAEntry 9   }

            sensor4to20mALowWarning OBJECT-TYPE
               SYNTAX  INTEGER
               ACCESS  read-write
               STATUS  mandatory
               DESCRIPTION
               "How cold this sensor gets before it sends a warning"
               ::=  {  sensor4to20mAEntry 10   }
   
            sensor4to20mAHighWarning OBJECT-TYPE
               SYNTAX  INTEGER
               ACCESS  read-write
               STATUS  mandatory
               DESCRIPTION
               "How hot this sensor gets before it sends a warning"
               ::=  {  sensor4to20mAEntry 11   }  

            sensor4to20mAHighCritical OBJECT-TYPE
               SYNTAX  INTEGER
               ACCESS  read-write
               STATUS  mandatory
               DESCRIPTION
               "How hot this sensor gets before it sends a critical event"
               ::=  {  sensor4to20mAEntry 12   }   

            sensor4to20mARearm OBJECT-TYPE
               SYNTAX  INTEGER
               ACCESS  read-write
               STATUS  mandatory
               DESCRIPTION
               "The number of degrees to rearm the status. For example if status goes from normal to warning, the temp must go down spTempRearm degrees below warning before the status goes to normal"
               ::=  {  sensor4to20mAEntry 13   }

            sensor4to20mADelayError OBJECT-TYPE
               SYNTAX  INTEGER (0..65534)
               ACCESS  read-write
               STATUS  mandatory
               DESCRIPTION
               "Time in seconds after the sensor has been in error status before report as an error"
               ::=  {  sensor4to20mAEntry 14   }

            sensor4to20mADelayNormal OBJECT-TYPE
               SYNTAX  INTEGER (0..65534)
               ACCESS  read-write
               STATUS  mandatory
               DESCRIPTION
               "Time in seconds after the sensor change from error to normal before report as normal"
               ::=  {  sensor4to20mAEntry 15   }

            sensor4to20mADelayLowCritical OBJECT-TYPE
               SYNTAX INTEGER (0..65535)
               ACCESS read-write
               STATUS mandatory
               DESCRIPTION
               "Continuous time for this sensor to be in Low Critical before accepting new Status."
               ::= {  sensor4to20mAEntry 16 }
               
            sensor4to20mADelayLowWarning OBJECT-TYPE
               SYNTAX INTEGER (0..65535)
               ACCESS read-write
               STATUS mandatory
               DESCRIPTION
               "Continuous time for this sensor to be in Low Warning before accepting new Status."
               ::= {  sensor4to20mAEntry 17 }

            sensor4to20mADelayHighWarning OBJECT-TYPE
               SYNTAX INTEGER (0..65535)
               ACCESS read-write
               STATUS mandatory
               DESCRIPTION
               "Continuous time for this sensor to be in High Warning before accepting new Status."
               ::= {  sensor4to20mAEntry 18 }

            sensor4to20mADelayHighCritical OBJECT-TYPE
               SYNTAX INTEGER (0..65535)
               ACCESS read-write
               STATUS mandatory
               DESCRIPTION
               "Continuous time for this sensor to be in High Critical before accepting new Status."
               ::= {  sensor4to20mAEntry 19 }

            sensor4to20mARaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensor4to20mAEntry 20   }

            sensor4to20mAOffset OBJECT-TYPE
               SYNTAX  INTEGER
               ACCESS  read-write
               STATUS  mandatory
               DESCRIPTION
               "4to20mA Offset reading"
               ::=  {  sensor4to20mAEntry 21   }

            sensor4to20mAAmountMaxVoltage OBJECT-TYPE
               SYNTAX  INTEGER
               ACCESS  read-write
               STATUS  mandatory
               DESCRIPTION
               "The maximum scale of 4to20mA conversion."
               ::=  {  sensor4to20mAEntry 33   }

            sensor4to20mAAmountBaseVoltage OBJECT-TYPE
               SYNTAX  INTEGER
               ACCESS  read-write
               STATUS  mandatory
               DESCRIPTION
               "The base scale of 4to20mA conversion."
               ::=  {  sensor4to20mAEntry 34   }

            sensor4to20mAPort OBJECT-TYPE
               SYNTAX  INTEGER (0..65534)
               ACCESS  read-only
               STATUS  mandatory
               DESCRIPTION
               "Sensor port"
               ::=  {  sensor4to20mAEntry 35 }

            sensor4to20mASubPort OBJECT-TYPE
               SYNTAX  INTEGER (0..65534)
               ACCESS  read-only
               STATUS  mandatory
               DESCRIPTION
               "Sensor sub port"
               ::=  {  sensor4to20mAEntry 36 }

            sensor4to20mADeviceIndex OBJECT-TYPE
               SYNTAX  INTEGER (0..65534)
               ACCESS  read-only
               STATUS  mandatory
               DESCRIPTION
               "Device Index of sensor"
               ::=  {  sensor4to20mAEntry 37 }
               
            sensor4to20mAMaxVoltage OBJECT-TYPE
               SYNTAX  INTEGER
               ACCESS  read-write
               STATUS  mandatory
               DESCRIPTION
               "The max range for use in conversion."
               ::=  {  sensor4to20mAEntry 43   }

            sensor4to20mABaseVoltage OBJECT-TYPE
               SYNTAX  INTEGER
               ACCESS  read-write
               STATUS  mandatory
               DESCRIPTION
               "The base range for use in conversion."
               ::=  {  sensor4to20mAEntry 44   }
               
            sensor4to20mADisplayStyle OBJECT-TYPE
               SYNTAX  INTEGER {
                  basic(0),
                  gauge(1)
               }
               ACCESS  read-write
               STATUS  mandatory
               DESCRIPTION
               "4to20mA display style"
               ::=  {  sensor4to20mAEntry 45 }  
               
            sensor4to20mAHighCriticalDesc OBJECT-TYPE
               SYNTAX  DisplayString
               ACCESS  read-write
               STATUS  mandatory
               DESCRIPTION
               "A HighCritical Description of this sensor"
               ::=  {  sensor4to20mAEntry  46  }               

            sensor4to20mALowCriticalDesc OBJECT-TYPE
               SYNTAX  DisplayString
               ACCESS  read-write
               STATUS  mandatory
               DESCRIPTION
               "A LowCritical Description of this sensor"
               ::=  {  sensor4to20mAEntry  47  }

            sensor4to20mANormalDesc OBJECT-TYPE
               SYNTAX  DisplayString
               ACCESS  read-write
               STATUS  mandatory
               DESCRIPTION
               "A Normal Description of this sensor"
               ::=  {  sensor4to20mAEntry  48  }
               
            sensor4to20mALowWarningDesc OBJECT-TYPE
               SYNTAX  DisplayString
               ACCESS  read-write
               STATUS  mandatory
               DESCRIPTION
               "A LowWarning Description of this sensor"
               ::=  {  sensor4to20mAEntry  49  }
               
            sensor4to20mAHighWarningDesc OBJECT-TYPE
               SYNTAX  DisplayString
               ACCESS  read-write
               STATUS  mandatory
               DESCRIPTION
               "A HighWarning Description of this sensor"
               ::=  {  sensor4to20mAEntry  50  }
               
            sensor4to20mASensorErrorDesc OBJECT-TYPE
               SYNTAX  DisplayString
               ACCESS  read-write
               STATUS  mandatory
               DESCRIPTION
               "A SensorError Description of this sensor"
               ::=  {  sensor4to20mAEntry  51  }    

            sensor4to20mAHighCriticalColor OBJECT-TYPE
               SYNTAX  INTEGER
               ACCESS  read-write
               STATUS  mandatory
               DESCRIPTION
               "A HighCritical Color of this sensor"
               ::=  {  sensor4to20mAEntry  54  }               

            sensor4to20mALowCriticalColor OBJECT-TYPE
               SYNTAX  INTEGER
               ACCESS  read-write
               STATUS  mandatory
               DESCRIPTION
               "A LowCritical Color of this sensor"
               ::=  {  sensor4to20mAEntry  55  }

            sensor4to20mANormalColor OBJECT-TYPE
               SYNTAX  INTEGER
               ACCESS  read-write
               STATUS  mandatory
               DESCRIPTION
               "A Normal Color of this sensor"
               ::=  {  sensor4to20mAEntry  56  }
               
            sensor4to20mALowWarningColor OBJECT-TYPE
               SYNTAX  INTEGER
               ACCESS  read-write
               STATUS  mandatory
               DESCRIPTION
               "A LowWarning Color of this sensor"
               ::=  {  sensor4to20mAEntry  57  }
               
            sensor4to20mAHighWarningColor OBJECT-TYPE
               SYNTAX  INTEGER
               ACCESS  read-write
               STATUS  mandatory
               DESCRIPTION
               "A HighWarning Color of this sensor"
               ::=  {  sensor4to20mAEntry  58  }
               
            sensor4to20mASensorErrorColor OBJECT-TYPE
               SYNTAX  INTEGER
               ACCESS  read-write
               STATUS  mandatory
               DESCRIPTION
               "A SensorError Color of this sensor"
               ::=  {  sensor4to20mAEntry  59  }  

            sensor4to20mASensorAcknowledge OBJECT-TYPE
               SYNTAX  INTEGER {
                  acked(2)
               }
               ACCESS  read-write
               STATUS  mandatory
               DESCRIPTION
               "4to20mA sensor acknowledge"
               ::=  {  sensor4to20mAEntry 70 }  

            sensor4to20mAId OBJECT-TYPE
               SYNTAX  INTEGER
               ACCESS  read-only
               STATUS  mandatory
               DESCRIPTION
               "The Sensor ID of this sensor, used to identify which sensor it is in the system configuration."
               ::= { sensor4to20mAEntry 1000 }

--/* End of sensor4to20mAEntry */

--/* Begin of sensorDCvoltageEntry */
         sensorDCvoltageTable OBJECT-TYPE
            SYNTAX  SEQUENCE OF SensorDCvoltageEntry
            ACCESS  not-accessible
            STATUS  mandatory
            DESCRIPTION
            "This table contains the property and reading value for every sensor."
            ::=  {  secSensor 6   }

         sensorDCvoltageEntry OBJECT-TYPE
            SYNTAX  SensorDCvoltageEntry
            ACCESS  not-accessible
            STATUS  mandatory
            DESCRIPTION
            "This is an entry in the sensorTemperatureEntry Table"
            INDEX         { sensorDCvoltageIndex }
            ::=  {  sensorDCvoltageTable 1 }

         SensorDCvoltageEntry ::= SEQUENCE {
               sensorDCvoltageIndex
                  INTEGER,
               sensorDCvoltageDescription
                  DisplayString,
               sensorDCvoltageValue
                  INTEGER,
               sensorDCvoltageUnit
                  DisplayString,
               sensorDCvoltageStatus
                  INTEGER,
               sensorDCvoltageGoOffline
                  INTEGER,
               sensorDCvoltageLowCritical
                  INTEGER,
               sensorDCvoltageLowWarning
                  INTEGER,
               sensorDCvoltageHighWarning
                  INTEGER,
               sensorDCvoltageHighCritical
                  INTEGER,
               sensorDCvoltageRearm
                  INTEGER,
               sensorDCvoltageDelayError
                  INTEGER,
               sensorDCvoltageDelayNormal
                  INTEGER,
               sensorDCvoltageDelayLowCritical
                  INTEGER,
               sensorDCvoltageDelayLowWarning
                  INTEGER,
               sensorDCvoltageDelayHighWarning
                  INTEGER,
               sensorDCvoltageDelayHighCritical
                  INTEGER,
               sensorDCvoltageRaw
                  INTEGER,
               sensorDCvoltageOffset
                  INTEGER,
               sensorDCvoltageJumper
                  INTEGER,
               sensorDCvoltageAmountMaxVoltage
                  INTEGER,
               sensorDCvoltageAmountBaseVoltage
                  INTEGER,
               sensorDCvoltagePort
                  INTEGER,
               sensorDCvoltageSubPort
                  INTEGER,
               sensorDCvoltageDeviceIndex
                  INTEGER,
               sensorDCvoltageMaxVoltage
                  INTEGER,
               sensorDCvoltageBaseVoltage                  
                  INTEGER,
               sensorDCvoltageDisplayStyle
                  INTEGER,
               sensorDCvoltageHighCriticalDesc 
                  DisplayString,
               sensorDCvoltageLowCriticalDesc 
                  DisplayString,
               sensorDCvoltageNormalDesc 
                  DisplayString,
               sensorDCvoltageLowWarningDesc 
                  DisplayString,   
               sensorDCvoltageHighWarningDesc 
                  DisplayString,
               sensorDCvoltageSensorErrorDesc 
                  DisplayString,
               sensorDCvoltageHighCriticalColor 
                  INTEGER,
               sensorDCvoltageLowCriticalColor 
                  INTEGER,
               sensorDCvoltageNormalColor 
                  INTEGER,
               sensorDCvoltageLowWarningColor 
                  INTEGER,   
               sensorDCvoltageHighWarningColor 
                  INTEGER,
               sensorDCvoltageSensorErrorColor 
                  INTEGER,
               sensorDCvoltageAcknowledge
                  INTEGER,
               sensorDCvoltageId
                  INTEGER
            }

            sensorDCvoltageIndex OBJECT-TYPE
               SYNTAX  INTEGER (1..65535)
               ACCESS  read-only
               STATUS  mandatory
               DESCRIPTION
               "The index into the sensor table"
               ::=  {  sensorDCvoltageEntry 1   }

            sensorDCvoltageDescription OBJECT-TYPE
               SYNTAX  DisplayString
               ACCESS  read-write
               STATUS  mandatory
               DESCRIPTION
               "A Description of this sensor"
               ::=  {  sensorDCvoltageEntry 2   }

            sensorDCvoltageValue OBJECT-TYPE
               SYNTAX  INTEGER
               ACCESS  read-only
               STATUS  mandatory
               DESCRIPTION
               "The reading value in this sensor"
               ::=  {  sensorDCvoltageEntry 4   }

            sensorDCvoltageUnit OBJECT-TYPE
               SYNTAX  DisplayString
               ACCESS  read-write
               STATUS  mandatory
               DESCRIPTION
               "The unit string"
               ::=  {  sensorDCvoltageEntry 5  }

            sensorDCvoltageStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorDCvoltageEntry 6   }

            sensorDCvoltageGoOffline OBJECT-TYPE
               SYNTAX  INTEGER {
                  online(1),
                  goOffline(2)
               }
               ACCESS  read-write
               STATUS  mandatory
               DESCRIPTION
               "To take offline enter a 2"
               ::=  {  sensorDCvoltageEntry 8   }

            sensorDCvoltageLowCritical OBJECT-TYPE
               SYNTAX  INTEGER
               ACCESS  read-write
               STATUS  mandatory
               DESCRIPTION
               "How cold this sensor gets before it sends a critical event"
               ::=  {  sensorDCvoltageEntry 9   }

            sensorDCvoltageLowWarning OBJECT-TYPE
               SYNTAX  INTEGER
               ACCESS  read-write
               STATUS  mandatory
               DESCRIPTION
               "How cold this sensor gets before it sends a warning"
               ::=  {  sensorDCvoltageEntry 10   }
   
            sensorDCvoltageHighWarning OBJECT-TYPE
               SYNTAX  INTEGER
               ACCESS  read-write
               STATUS  mandatory
               DESCRIPTION
               "How hot this sensor gets before it sends a warning"
               ::=  {  sensorDCvoltageEntry 11   }  

            sensorDCvoltageHighCritical OBJECT-TYPE
               SYNTAX  INTEGER
               ACCESS  read-write
               STATUS  mandatory
               DESCRIPTION
               "How hot this sensor gets before it sends a critical event"
               ::=  {  sensorDCvoltageEntry 12   }   

            sensorDCvoltageRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorDCvoltageEntry 13   }

            sensorDCvoltageDelayError OBJECT-TYPE
               SYNTAX  INTEGER (0..65534)
               ACCESS  read-write
               STATUS  mandatory
               DESCRIPTION
               "Time in seconds after the sensor has been in error status before report as an error"
               ::=  {  sensorDCvoltageEntry 14   }

            sensorDCvoltageDelayNormal OBJECT-TYPE
               SYNTAX  INTEGER (0..65534)
               ACCESS  read-write
               STATUS  mandatory
               DESCRIPTION
               "Time in seconds after the sensor change from error to normal before report as normal"
               ::=  {  sensorDCvoltageEntry 15   }

            sensorDCvoltageDelayLowCritical OBJECT-TYPE
               SYNTAX INTEGER (0..65535)
               ACCESS read-write
               STATUS mandatory
               DESCRIPTION
               "Continuous time for this sensor to be in Low Critical before accepting new Status."
               ::= {  sensorDCvoltageEntry 16 }
               
            sensorDCvoltageDelayLowWarning OBJECT-TYPE
               SYNTAX INTEGER (0..65535)
               ACCESS read-write
               STATUS mandatory
               DESCRIPTION
               "Continuous time for this sensor to be in Low Warning before accepting new Status."
               ::= {  sensorDCvoltageEntry 17 }

            sensorDCvoltageDelayHighWarning OBJECT-TYPE
               SYNTAX INTEGER (0..65535)
               ACCESS read-write
               STATUS mandatory
               DESCRIPTION
               "Continuous time for this sensor to be in High Warning before accepting new Status."
               ::= {  sensorDCvoltageEntry 18 }

            sensorDCvoltageDelayHighCritical OBJECT-TYPE
               SYNTAX INTEGER (0..65535)
               ACCESS read-write
               STATUS mandatory
               DESCRIPTION
               "Continuous time for this sensor to be in High Critical before accepting new Status."
               ::= {  sensorDCvoltageEntry 19 }

            sensorDCvoltageRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorDCvoltageEntry 20   }

            sensorDCvoltageOffset OBJECT-TYPE
               SYNTAX  INTEGER
               ACCESS  read-write
               STATUS  mandatory
               DESCRIPTION
               "DC voltage Offset reading"
               ::=  {  sensorDCvoltageEntry 21   }

            sensorDCvoltageJumper OBJECT-TYPE
               SYNTAX  INTEGER {
                  jumperAt-60(-600),
                  jumperAt-40(-400),
                  jumperAt-30(-300),
                  jumperAt-20(-200),
                  jumperAt-10(-100),                  
                  jumperAt10(100),
                  jumperAt20(200),
                  jumperAt30(300),
                  jumperAt40(400),
                  jumperAt60(600)                  
               }
               ACCESS  read-write
               STATUS  mandatory
               DESCRIPTION
               "Selected voltage scale (jumper 0) in DC voltage conversion."
               ::=  {  sensorDCvoltageEntry 32   }

            sensorDCvoltageAmountMaxVoltage OBJECT-TYPE
               SYNTAX  INTEGER
               ACCESS  read-write
               STATUS  mandatory
               DESCRIPTION
               "The maximum scale of DC voltage conversion."
               ::=  {  sensorDCvoltageEntry 33   }

            sensorDCvoltageAmountBaseVoltage OBJECT-TYPE
               SYNTAX  INTEGER
               ACCESS  read-write
               STATUS  mandatory
               DESCRIPTION
               "The base scale of DC voltage conversion."
               ::=  {  sensorDCvoltageEntry 34   }

            sensorDCvoltagePort OBJECT-TYPE
               SYNTAX  INTEGER (0..65534)
               ACCESS  read-only
               STATUS  mandatory
               DESCRIPTION
               "Sensor port"
               ::=  {  sensorDCvoltageEntry 35 }

            sensorDCvoltageSubPort OBJECT-TYPE
               SYNTAX  INTEGER (0..65534)
               ACCESS  read-only
               STATUS  mandatory
               DESCRIPTION
               "Sensor sub port"
               ::=  {  sensorDCvoltageEntry 36 }

            sensorDCvoltageDeviceIndex OBJECT-TYPE
               SYNTAX  INTEGER (0..65534)
               ACCESS  read-only
               STATUS  mandatory
               DESCRIPTION
               "Device Index of sensor"
               ::=  {  sensorDCvoltageEntry 37 }

            sensorDCvoltageMaxVoltage OBJECT-TYPE
               SYNTAX  INTEGER
               ACCESS  read-write
               STATUS  mandatory
               DESCRIPTION
               "The max voltage range for use in conversion."
               ::=  {  sensorDCvoltageEntry 43   }

            sensorDCvoltageBaseVoltage OBJECT-TYPE
               SYNTAX  INTEGER
               ACCESS  read-write
               STATUS  mandatory
               DESCRIPTION
               "The base voltage range for use in conversion."
               ::=  {  sensorDCvoltageEntry 44   }
               
            sensorDCvoltageDisplayStyle OBJECT-TYPE
               SYNTAX  INTEGER {
                  basic(0),
                  gauge(1)
               }
               ACCESS  read-write
               STATUS  mandatory
               DESCRIPTION
               "DCVoltage display style"
               ::=  {  sensorDCvoltageEntry 45 }
               
            sensorDCvoltageHighCriticalDesc OBJECT-TYPE
               SYNTAX  DisplayString
               ACCESS  read-write
               STATUS  mandatory
               DESCRIPTION
               "A HighCritical Description of this sensor"
               ::=  {  sensorDCvoltageEntry  46  }               

            sensorDCvoltageLowCriticalDesc OBJECT-TYPE
               SYNTAX  DisplayString
               ACCESS  read-write
               STATUS  mandatory
               DESCRIPTION
               "A LowCritical Description of this sensor"
               ::=  {  sensorDCvoltageEntry  47  }

            sensorDCvoltageNormalDesc OBJECT-TYPE
               SYNTAX  DisplayString
               ACCESS  read-write
               STATUS  mandatory
               DESCRIPTION
               "A Normal Description of this sensor"
               ::=  {  sensorDCvoltageEntry  48  }
               
            sensorDCvoltageLowWarningDesc OBJECT-TYPE
               SYNTAX  DisplayString
               ACCESS  read-write
               STATUS  mandatory
               DESCRIPTION
               "A LowWarning Description of this sensor"
               ::=  {  sensorDCvoltageEntry  49  }
               
            sensorDCvoltageHighWarningDesc OBJECT-TYPE
               SYNTAX  DisplayString
               ACCESS  read-write
               STATUS  mandatory
               DESCRIPTION
               "A HighWarning Description of this sensor"
               ::=  {  sensorDCvoltageEntry  50  }
               
            sensorDCvoltageSensorErrorDesc OBJECT-TYPE
               SYNTAX  DisplayString
               ACCESS  read-write
               STATUS  mandatory
               DESCRIPTION
               "A SensorError Description of this sensor"
               ::=  {  sensorDCvoltageEntry  51  }  

            sensorDCvoltageHighCriticalColor OBJECT-TYPE
               SYNTAX  INTEGER
               ACCESS  read-write
               STATUS  mandatory
               DESCRIPTION
               "A HighCritical Color of this sensor"
               ::=  {  sensorDCvoltageEntry  54  }               

            sensorDCvoltageLowCriticalColor OBJECT-TYPE
               SYNTAX  INTEGER
               ACCESS  read-write
               STATUS  mandatory
               DESCRIPTION
               "A LowCritical Color of this sensor"
               ::=  {  sensorDCvoltageEntry  55  }

            sensorDCvoltageNormalColor OBJECT-TYPE
               SYNTAX  INTEGER
               ACCESS  read-write
               STATUS  mandatory
               DESCRIPTION
               "A Normal Color of this sensor"
               ::=  {  sensorDCvoltageEntry  56  }
               
            sensorDCvoltageLowWarningColor OBJECT-TYPE
               SYNTAX  INTEGER
               ACCESS  read-write
               STATUS  mandatory
               DESCRIPTION
               "A LowWarning Color of this sensor"
               ::=  {  sensorDCvoltageEntry  57  }
               
            sensorDCvoltageHighWarningColor OBJECT-TYPE
               SYNTAX  INTEGER
               ACCESS  read-write
               STATUS  mandatory
               DESCRIPTION
               "A HighWarning Color of this sensor"
               ::=  {  sensorDCvoltageEntry  58  }
               
            sensorDCvoltageSensorErrorColor OBJECT-TYPE
               SYNTAX  INTEGER
               ACCESS  read-write
               STATUS  mandatory
               DESCRIPTION
               "A SensorError Color of this sensor"
               ::=  {  sensorDCvoltageEntry  59  }  

            sensorDCvoltageAcknowledge OBJECT-TYPE
               SYNTAX  INTEGER {
                  acked(2)
               }
               ACCESS  read-write
               STATUS  mandatory
               DESCRIPTION
               "DCvoltage sensor acknowledge"
               ::=  {  sensorDCvoltageEntry 70 }  

            sensorDCvoltageId OBJECT-TYPE
               SYNTAX  INTEGER
               ACCESS  read-only
               STATUS  mandatory
               DESCRIPTION
               "The Sensor ID of this sensor, used to identify which sensor it is in the system configuration."
               ::= { sensorDCvoltageEntry 1000 }

--/* End of sensorDCvoltageEntry */

--/* Begin of sensorAirflowEntry */
         sensorAirflowTable OBJECT-TYPE
            SYNTAX  SEQUENCE OF SensorAirflowEntry
            ACCESS  not-accessible
            STATUS  mandatory
            DESCRIPTION
            "This table contains the property and reading value for every sensor."
            ::=  {  secSensor 7   }

         sensorAirflowEntry OBJECT-TYPE
            SYNTAX  SensorAirflowEntry
            ACCESS  not-accessible
            STATUS  mandatory
            DESCRIPTION
            "This is an entry in the sensorTemperatureEntry Table"
            INDEX         { sensorAirflowIndex }
            ::=  {  sensorAirflowTable 1 }

         SensorAirflowEntry ::= SEQUENCE {
               sensorAirflowIndex
                  INTEGER,
               sensorAirflowDescription
                  DisplayString,
               sensorAirflowValue
                  INTEGER,
               sensorAirflowStatus
                  INTEGER,
               sensorAirflowGoOffline
                  INTEGER,
               sensorAirflowLowCritical
                  INTEGER,
               sensorAirflowLowWarning
                  INTEGER,
               sensorAirflowHighWarning
                  INTEGER,
               sensorAirflowHighCritical
                  INTEGER,
               sensorAirflowRearm
                  INTEGER,
               sensorAirflowDelayError
                  INTEGER,
               sensorAirflowDelayNormal
                  INTEGER,
               sensorAirflowDelayLowCritical
                  INTEGER,
               sensorAirflowDelayLowWarning
                  INTEGER,
               sensorAirflowDelayHighWarning
                  INTEGER,
               sensorAirflowDelayHighCritical
                  INTEGER,
               sensorAirflowRaw
                  INTEGER,
               sensorAirflowPort
                  INTEGER,
               sensorAirflowSubPort
                  INTEGER,
               sensorAirflowDeviceIndex
                  INTEGER,
               sensorAirflowDisplayStyle
                  INTEGER,
               sensorAirflowHighCriticalDesc 
                  DisplayString,
               sensorAirflowLowCriticalDesc 
                  DisplayString,
               sensorAirflowNormalDesc 
                  DisplayString,
               sensorAirflowLowWarningDesc 
                  DisplayString,   
               sensorAirflowHighWarningDesc 
                  DisplayString,
               sensorAirflowSensorErrorDesc 
                  DisplayString,
               sensorAirflowHighCriticalColor 
                  INTEGER,
               sensorAirflowLowCriticalColor 
                  INTEGER,
               sensorAirflowNormalColor 
                  INTEGER,
               sensorAirflowLowWarningColor 
                  INTEGER,   
               sensorAirflowHighWarningColor 
                  INTEGER,
               sensorAirflowSensorErrorColor 
                  INTEGER,
               sensorAirflowAcknowledge
                  INTEGER,
               sensorAirflowId
                  INTEGER
            }

            sensorAirflowIndex OBJECT-TYPE
               SYNTAX  INTEGER (1..65535)
               ACCESS  read-only
               STATUS  mandatory
               DESCRIPTION
               "The index into the Switch sensor table"
               ::=  {  sensorAirflowEntry 1   }

            sensorAirflowDescription OBJECT-TYPE
               SYNTAX  DisplayString
               ACCESS  read-write
               STATUS  mandatory
               DESCRIPTION
               "A Description of this sensor Switch"
               ::=  {  sensorAirflowEntry 2   }

            sensorAirflowValue OBJECT-TYPE
               SYNTAX  INTEGER
               ACCESS  read-only
               STATUS  mandatory
               DESCRIPTION
               "The reading value in this sensor"
               ::=  {  sensorAirflowEntry 4   }

            sensorAirflowStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorAirflowEntry 6  }

            sensorAirflowGoOffline OBJECT-TYPE
               SYNTAX  INTEGER {
                  online(1),
                  goOffline(2)
               }
               ACCESS  read-write
               STATUS  mandatory
               DESCRIPTION
               "To take offline enter a 2"
               ::=  {  sensorAirflowEntry 8  }

            sensorAirflowLowCritical OBJECT-TYPE
               SYNTAX  INTEGER
               ACCESS  read-write
               STATUS  mandatory
               DESCRIPTION
               "How cold this sensor gets before it sends a critical event"
               ::=  {  sensorAirflowEntry 9   }

            sensorAirflowLowWarning OBJECT-TYPE
               SYNTAX  INTEGER
               ACCESS  read-write
               STATUS  mandatory
               DESCRIPTION
               "How cold this sensor gets before it sends a warning"
               ::=  {  sensorAirflowEntry 10   }
   
            sensorAirflowHighWarning OBJECT-TYPE
               SYNTAX  INTEGER
               ACCESS  read-write
               STATUS  mandatory
               DESCRIPTION
               "How hot this sensor gets before it sends a warning"
               ::=  {  sensorAirflowEntry 11   }  

            sensorAirflowHighCritical OBJECT-TYPE
               SYNTAX  INTEGER
               ACCESS  read-write
               STATUS  mandatory
               DESCRIPTION
               "How hot this sensor gets before it sends a critical event"
               ::=  {  sensorAirflowEntry 12   }   

            sensorAirflowRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorAirflowEntry 13   }

            sensorAirflowDelayError OBJECT-TYPE
               SYNTAX  INTEGER (0..65534)
               ACCESS  read-write
               STATUS  mandatory
               DESCRIPTION
               "Time in seconds after the sensor has been in error status before report as an error"
               ::=  {  sensorAirflowEntry 14   }

            sensorAirflowDelayNormal OBJECT-TYPE
               SYNTAX  INTEGER (0..65534)
               ACCESS  read-write
               STATUS  mandatory
               DESCRIPTION
               "Time in seconds after the sensor change from error to normal before report as normal"
               ::=  {  sensorAirflowEntry 15   }

            sensorAirflowDelayLowCritical OBJECT-TYPE
               SYNTAX INTEGER (0..65535)
               ACCESS read-write
               STATUS mandatory
               DESCRIPTION
               "Continuous time for this sensor to be in Low Critical before accepting new Status."
               ::= {  sensorAirflowEntry 16 }
               
            sensorAirflowDelayLowWarning OBJECT-TYPE
               SYNTAX INTEGER (0..65535)
               ACCESS read-write
               STATUS mandatory
               DESCRIPTION
               "Continuous time for this sensor to be in Low Warning before accepting new Status."
               ::= {  sensorAirflowEntry 17 }

            sensorAirflowDelayHighWarning OBJECT-TYPE
               SYNTAX INTEGER (0..65535)
               ACCESS read-write
               STATUS mandatory
               DESCRIPTION
               "Continuous time for this sensor to be in High Warning before accepting new Status."
               ::= {  sensorAirflowEntry 18 }

            sensorAirflowDelayHighCritical OBJECT-TYPE
               SYNTAX INTEGER (0..65535)
               ACCESS read-write
               STATUS mandatory
               DESCRIPTION
               "Continuous time for this sensor to be in High Critical before accepting new Status."
               ::= {  sensorAirflowEntry 19 }

            sensorAirflowRaw OBJECT-TYPE
               SYNTAX  INTEGER
               ACCESS  read-only
               STATUS  mandatory
               DESCRIPTION
               "The unformatted, raw, A/D value in this sensor. Contains more resolution than the formated percentage. This number can go from 0 to 1023 depending on the input voltage"
               ::=  {  sensorAirflowEntry 20   }

            sensorAirflowPort OBJECT-TYPE
               SYNTAX  INTEGER (0..65534)
               ACCESS  read-only
               STATUS  mandatory
               DESCRIPTION
               "Sensor port"
               ::=  {  sensorAirflowEntry 35 }

            sensorAirflowSubPort OBJECT-TYPE
               SYNTAX  INTEGER (0..65534)
               ACCESS  read-only
               STATUS  mandatory
               DESCRIPTION
               "Sensor sub port"
               ::=  {  sensorAirflowEntry 36 }

            sensorAirflowDeviceIndex OBJECT-TYPE
               SYNTAX  INTEGER (0..65534)
               ACCESS  read-only
               STATUS  mandatory
               DESCRIPTION
               "Device Index of sensor"
               ::=  {  sensorAirflowEntry 37 }

            sensorAirflowDisplayStyle OBJECT-TYPE
               SYNTAX  INTEGER {
                  basic(0),
                  gauge(1)
               }
               ACCESS  read-write
               STATUS  mandatory
               DESCRIPTION
               "Airflow display style"
               ::=  {  sensorAirflowEntry 45 }
               
            sensorAirflowHighCriticalDesc OBJECT-TYPE
               SYNTAX  DisplayString
               ACCESS  read-write
               STATUS  mandatory
               DESCRIPTION
               "A HighCritical Description of this sensor"
               ::=  {  sensorAirflowEntry  46  }               

            sensorAirflowLowCriticalDesc OBJECT-TYPE
               SYNTAX  DisplayString
               ACCESS  read-write
               STATUS  mandatory
               DESCRIPTION
               "A LowCritical Description of this sensor"
               ::=  {  sensorAirflowEntry  47  }

            sensorAirflowNormalDesc OBJECT-TYPE
               SYNTAX  DisplayString
               ACCESS  read-write
               STATUS  mandatory
               DESCRIPTION
               "A Normal Description of this sensor"
               ::=  {  sensorAirflowEntry  48  }
               
            sensorAirflowLowWarningDesc OBJECT-TYPE
               SYNTAX  DisplayString
               ACCESS  read-write
               STATUS  mandatory
               DESCRIPTION
               "A LowWarning Description of this sensor"
               ::=  {  sensorAirflowEntry  49  }
               
            sensorAirflowHighWarningDesc OBJECT-TYPE
               SYNTAX  DisplayString
               ACCESS  read-write
               STATUS  mandatory
               DESCRIPTION
               "A HighWarning Description of this sensor"
               ::=  {  sensorAirflowEntry  50  }
               
            sensorAirflowSensorErrorDesc OBJECT-TYPE
               SYNTAX  DisplayString
               ACCESS  read-write
               STATUS  mandatory
               DESCRIPTION
               "A SensorError Description of this sensor"
               ::=  {  sensorAirflowEntry  51  }  

            sensorAirflowHighCriticalColor OBJECT-TYPE
               SYNTAX  INTEGER
               ACCESS  read-write
               STATUS  mandatory
               DESCRIPTION
               "A HighCritical Color of this sensor"
               ::=  {  sensorAirflowEntry  54  }               

            sensorAirflowLowCriticalColor OBJECT-TYPE
               SYNTAX  INTEGER
               ACCESS  read-write
               STATUS  mandatory
               DESCRIPTION
               "A LowCritical Color of this sensor"
               ::=  {  sensorAirflowEntry  55  }

            sensorAirflowNormalColor OBJECT-TYPE
               SYNTAX  INTEGER
               ACCESS  read-write
               STATUS  mandatory
               DESCRIPTION
               "A Normal Color of this sensor"
               ::=  {  sensorAirflowEntry  56  }
               
            sensorAirflowLowWarningColor OBJECT-TYPE
               SYNTAX  INTEGER
               ACCESS  read-write
               STATUS  mandatory
               DESCRIPTION
               "A LowWarning Color of this sensor"
               ::=  {  sensorAirflowEntry  57  }
               
            sensorAirflowHighWarningColor OBJECT-TYPE
               SYNTAX  INTEGER
               ACCESS  read-write
               STATUS  mandatory
               DESCRIPTION
               "A HighWarning Color of this sensor"
               ::=  {  sensorAirflowEntry  58  }
               
            sensorAirflowSensorErrorColor OBJECT-TYPE
               SYNTAX  INTEGER
               ACCESS  read-write
               STATUS  mandatory
               DESCRIPTION
               "A SensorError Color of this sensor"
               ::=  {  sensorAirflowEntry  59  }   

            sensorAirflowAcknowledge OBJECT-TYPE
               SYNTAX  INTEGER {
                  acked(2)
               }
               ACCESS  read-write
               STATUS  mandatory
               DESCRIPTION
               "Airflow sensor acknowledge"
               ::=  {  sensorAirflowEntry 70 }
               
            sensorAirflowId OBJECT-TYPE
               SYNTAX  INTEGER
               ACCESS  read-only
               STATUS  mandatory
               DESCRIPTION
               "The Sensor ID of this sensor, used to identify which sensor it is in the system configuration."
               ::= { sensorAirflowEntry 1000 }

--/* End of sensorAirflowEntry */

--/* Begin of sensorMotionEntry */
         sensorMotionTable OBJECT-TYPE
            SYNTAX  SEQUENCE OF SensorMotionEntry
            ACCESS  not-accessible
            STATUS  mandatory
            DESCRIPTION
            "This table contains the property and reading value for every sensor."
            ::=  {  secSensor 8   }

         sensorMotionEntry OBJECT-TYPE
            SYNTAX  SensorMotionEntry
            ACCESS  not-accessible
            STATUS  mandatory
            DESCRIPTION
            "This is an entry in the sensorTemperatureEntry Table"
            INDEX         { sensorMotionIndex }
            ::=  {  sensorMotionTable 1 }

         SensorMotionEntry ::= SEQUENCE {
               sensorMotionIndex
                  INTEGER,
               sensorMotionDescription
                  DisplayString,
               sensorMotionStatus
                  INTEGER,
               sensorMotionGoOffline
                  INTEGER,
               sensorMotionPort
                  INTEGER,
               sensorMotionSubPort
                  INTEGER,
               sensorMotionDeviceIndex
                  INTEGER,
               sensorMotionCriticalDesc 
                  DisplayString,
               sensorMotionNormalDesc 
                  DisplayString,
               sensorMotionCriticalColor 
                  INTEGER,
               sensorMotionNormalColor 
                  INTEGER,
               sensorMotionAcknowledge
                  INTEGER,
               sensorMotionId
                  INTEGER
            }

            sensorMotionIndex OBJECT-TYPE
               SYNTAX  INTEGER (1..65535)
               ACCESS  read-only
               STATUS  mandatory
               DESCRIPTION
               "The index into the Switch sensor table"
               ::=  {  sensorMotionEntry 1   }

            sensorMotionDescription OBJECT-TYPE
               SYNTAX  DisplayString
               ACCESS  read-write
               STATUS  mandatory
               DESCRIPTION
               "A Description of this sensor Switch"
               ::=  {  sensorMotionEntry 2   }

            sensorMotionStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorMotionEntry 6  }

            sensorMotionGoOffline OBJECT-TYPE
               SYNTAX  INTEGER {
                  online(1),
                  goOffline(2)
               }
               ACCESS  read-write
               STATUS  mandatory
               DESCRIPTION
               "To take offline enter a 2"
               ::=  {  sensorMotionEntry 8  }

            sensorMotionPort OBJECT-TYPE
               SYNTAX  INTEGER (0..65534)
               ACCESS  read-only
               STATUS  mandatory
               DESCRIPTION
               "Sensor port"
               ::=  {  sensorMotionEntry 35 }

            sensorMotionSubPort OBJECT-TYPE
               SYNTAX  INTEGER (0..65534)
               ACCESS  read-only
               STATUS  mandatory
               DESCRIPTION
               "Sensor sub port"
               ::=  {  sensorMotionEntry 36 }

            sensorMotionDeviceIndex OBJECT-TYPE
               SYNTAX  INTEGER (0..65534)
               ACCESS  read-only
               STATUS  mandatory
               DESCRIPTION
               "Device Index of sensor"
               ::=  {  sensorMotionEntry 37 }

            sensorMotionCriticalDesc OBJECT-TYPE
               SYNTAX  DisplayString
               ACCESS  read-write
               STATUS  mandatory
               DESCRIPTION
               "A Critical Description of this sensor"
               ::=  {  sensorMotionEntry  46  }           

            sensorMotionNormalDesc OBJECT-TYPE
               SYNTAX  DisplayString
               ACCESS  read-write
               STATUS  mandatory
               DESCRIPTION
               "A Normal Description of this sensor"
               ::=  {  sensorMotionEntry  48  }
               
            sensorMotionCriticalColor OBJECT-TYPE
               SYNTAX  INTEGER
               ACCESS  read-write
               STATUS  mandatory
               DESCRIPTION
               "A Critical Color of this sensor"
               ::=  {  sensorMotionEntry  54  }               
               
            sensorMotionNormalColor OBJECT-TYPE
               SYNTAX  INTEGER
               ACCESS  read-write
               STATUS  mandatory
               DESCRIPTION
               "A Normal Color of this sensor"
               ::=  {  sensorMotionEntry  56  }    

            sensorMotionAcknowledge OBJECT-TYPE
               SYNTAX  INTEGER {
                  acked(2)
               }
               ACCESS  read-write
               STATUS  mandatory
               DESCRIPTION
               "Motion sensor acknowledge"
               ::=  {  sensorMotionEntry 70 }  
               
            sensorMotionId OBJECT-TYPE
               SYNTAX  INTEGER
               ACCESS  read-only
               STATUS  mandatory
               DESCRIPTION
               "The Sensor ID of this sensor, used to identify which sensor it is in the system configuration."
               ::= { sensorMotionEntry 1000 }

--/* End of sensorMotionEntry */

--/* Begin of sensorWaterEntry */
         sensorWaterTable OBJECT-TYPE
            SYNTAX  SEQUENCE OF SensorWaterEntry
            ACCESS  not-accessible
            STATUS  mandatory
            DESCRIPTION
            "This table contains the property and reading value for every sensor."
            ::=  {  secSensor 9   }

         sensorWaterEntry OBJECT-TYPE
            SYNTAX  SensorWaterEntry
            ACCESS  not-accessible
            STATUS  mandatory
            DESCRIPTION
            "This is an entry in the sensorTemperatureEntry Table"
            INDEX         { sensorWaterIndex }
            ::=  {  sensorWaterTable 1 }

         SensorWaterEntry ::= SEQUENCE {
               sensorWaterIndex
                  INTEGER,
               sensorWaterDescription
                  DisplayString,
               sensorWaterStatus
                  INTEGER,
               sensorWaterGoOffline
                  INTEGER,
               sensorWaterPort
                  INTEGER,
               sensorWaterSubPort
                  INTEGER,
               sensorWaterDeviceIndex
                  INTEGER,
               sensorWaterCriticalDesc 
                  DisplayString,
               sensorWaterNormalDesc 
                  DisplayString,
               sensorWaterCriticalColor 
                  INTEGER,
               sensorWaterNormalColor 
                  INTEGER,   
               sensorWaterAcknowledge
                  INTEGER,
               sensorWaterId
                  INTEGER
            }

            sensorWaterIndex OBJECT-TYPE
               SYNTAX  INTEGER (1..65535)
               ACCESS  read-only
               STATUS  mandatory
               DESCRIPTION
               "The index into the Switch sensor table"
               ::=  {  sensorWaterEntry 1   }

            sensorWaterDescription OBJECT-TYPE
               SYNTAX  DisplayString
               ACCESS  read-write
               STATUS  mandatory
               DESCRIPTION
               "A Description of this sensor Switch"
               ::=  {  sensorWaterEntry 2   }

            sensorWaterStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorWaterEntry 6  }

            sensorWaterGoOffline OBJECT-TYPE
               SYNTAX  INTEGER {
                  online(1),
                  goOffline(2)
               }
               ACCESS  read-write
               STATUS  mandatory
               DESCRIPTION
               "To take offline enter a 2"
               ::=  {  sensorWaterEntry 8  }

            sensorWaterPort OBJECT-TYPE
               SYNTAX  INTEGER (0..65534)
               ACCESS  read-only
               STATUS  mandatory
               DESCRIPTION
               "Sensor port"
               ::=  {  sensorWaterEntry 35 }

            sensorWaterSubPort OBJECT-TYPE
               SYNTAX  INTEGER (0..65534)
               ACCESS  read-only
               STATUS  mandatory
               DESCRIPTION
               "Sensor sub port"
               ::=  {  sensorWaterEntry 36 }

            sensorWaterDeviceIndex OBJECT-TYPE
               SYNTAX  INTEGER (0..65534)
               ACCESS  read-only
               STATUS  mandatory
               DESCRIPTION
               "Device Index of sensor"
               ::=  {  sensorWaterEntry 37 }
           
            sensorWaterCriticalDesc OBJECT-TYPE
               SYNTAX  DisplayString
               ACCESS  read-write
               STATUS  mandatory
               DESCRIPTION
               "A Critical Description of this sensor"
               ::=  {  sensorWaterEntry  46  }               

            sensorWaterNormalDesc OBJECT-TYPE
               SYNTAX  DisplayString
               ACCESS  read-write
               STATUS  mandatory
               DESCRIPTION
               "A Normal Description of this sensor"
               ::=  {  sensorWaterEntry  48  }

            sensorWaterCriticalColor OBJECT-TYPE
               SYNTAX  INTEGER
               ACCESS  read-write
               STATUS  mandatory
               DESCRIPTION
               "A Critical Color of this sensor"
               ::=  {  sensorWaterEntry  54  }               

            sensorWaterNormalColor OBJECT-TYPE
               SYNTAX  INTEGER
               ACCESS  read-write
               STATUS  mandatory
               DESCRIPTION
               "A Normal Color of this sensor"
               ::=  {  sensorWaterEntry  56  }    

            sensorWaterAcknowledge OBJECT-TYPE
               SYNTAX  INTEGER {
                  acked(2)
               }
               ACCESS  read-write
               STATUS  mandatory
               DESCRIPTION
               "Water sensor acknowledge"
               ::=  {  sensorWaterEntry 70 }
               
            sensorWaterId OBJECT-TYPE
               SYNTAX  INTEGER
               ACCESS  read-only
               STATUS  mandatory
               DESCRIPTION
               "The Sensor ID of this sensor, used to identify which sensor it is in the system configuration."
               ::= { sensorWaterEntry 1000 }

--/* End of sensorWaterEntry */

--/* Begin of sensorSecurityEntry */
         sensorSecurityTable OBJECT-TYPE
            SYNTAX  SEQUENCE OF SensorSecurityEntry
            ACCESS  not-accessible
            STATUS  mandatory
            DESCRIPTION
            "This table contains the property and reading value for every sensor."
            ::=  {  secSensor 10   }

         sensorSecurityEntry OBJECT-TYPE
            SYNTAX  SensorSecurityEntry
            ACCESS  not-accessible
            STATUS  mandatory
            DESCRIPTION
            "This is an entry in the sensorTemperatureEntry Table"
            INDEX         { sensorSecurityIndex }
            ::=  {  sensorSecurityTable 1 }

         SensorSecurityEntry ::= SEQUENCE {
               sensorSecurityIndex
                  INTEGER,
               sensorSecurityDescription
                  DisplayString,
               sensorSecurityStatus
                  INTEGER,
               sensorSecurityGoOffline
                  INTEGER,
               sensorSecurityPort
                  INTEGER,
               sensorSecuritySubPort
                  INTEGER,
               sensorSecurityDeviceIndex
                  INTEGER,
               sensorSecurityCriticalDesc 
                  DisplayString,
               sensorSecurityNormalDesc 
                  DisplayString,
               sensorSecurityCriticalColor 
                  INTEGER,
               sensorSecurityNormalColor 
                  INTEGER,                
               sensorSecurityAcknowledge
                  INTEGER,
               sensorSecurityId
                  INTEGER
            }

            sensorSecurityIndex OBJECT-TYPE
               SYNTAX  INTEGER (1..65535)
               ACCESS  read-only
               STATUS  mandatory
               DESCRIPTION
               "The index into the Switch sensor table"
               ::=  {  sensorSecurityEntry 1   }

            sensorSecurityDescription OBJECT-TYPE
               SYNTAX  DisplayString
               ACCESS  read-write
               STATUS  mandatory
               DESCRIPTION
               "A Description of this sensor Switch"
               ::=  {  sensorSecurityEntry 2   }

            sensorSecurityStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSecurityEntry 6  }

            sensorSecurityGoOffline OBJECT-TYPE
               SYNTAX  INTEGER {
                  online(1),
                  goOffline(2)
               }
               ACCESS  read-write
               STATUS  mandatory
               DESCRIPTION
               "To take offline enter a 2"
               ::=  {  sensorSecurityEntry 8  }

            sensorSecurityPort OBJECT-TYPE
               SYNTAX  INTEGER (0..65534)
               ACCESS  read-only
               STATUS  mandatory
               DESCRIPTION
               "Sensor port"
               ::=  {  sensorSecurityEntry 35 }

            sensorSecuritySubPort OBJECT-TYPE
               SYNTAX  INTEGER (0..65534)
               ACCESS  read-only
               STATUS  mandatory
               DESCRIPTION
               "Sensor sub port"
               ::=  {  sensorSecurityEntry 36 }

            sensorSecurityDeviceIndex OBJECT-TYPE
               SYNTAX  INTEGER (0..65534)
               ACCESS  read-only
               STATUS  mandatory
               DESCRIPTION
               "Device Index of sensor"
               ::=  {  sensorSecurityEntry 37 }

            sensorSecurityCriticalDesc OBJECT-TYPE
               SYNTAX  DisplayString
               ACCESS  read-write
               STATUS  mandatory
               DESCRIPTION
               "A Critical Description of this sensor"
               ::=  {  sensorSecurityEntry  46  }               

            sensorSecurityNormalDesc OBJECT-TYPE
               SYNTAX  DisplayString
               ACCESS  read-write
               STATUS  mandatory
               DESCRIPTION
               "A Normal Description of this sensor"
               ::=  {  sensorSecurityEntry  48  }

            sensorSecurityCriticalColor OBJECT-TYPE
               SYNTAX  INTEGER
               ACCESS  read-write
               STATUS  mandatory
               DESCRIPTION
               "A Critical Color of this sensor"
               ::=  {  sensorSecurityEntry  54  }               

            sensorSecurityNormalColor OBJECT-TYPE
               SYNTAX  INTEGER
               ACCESS  read-write
               STATUS  mandatory
               DESCRIPTION
               "A Normal Color of this sensor"
               ::=  {  sensorSecurityEntry  56  } 

            sensorSecurityAcknowledge OBJECT-TYPE
               SYNTAX  INTEGER {
                  acked(2)
               }
               ACCESS  read-write
               STATUS  mandatory
               DESCRIPTION
               "Security sensor acknowledge"
               ::=  {  sensorSecurityEntry 70 }
               
            sensorSecurityId OBJECT-TYPE
               SYNTAX  INTEGER
               ACCESS  read-only
               STATUS  mandatory
               DESCRIPTION
               "The Sensor ID of this sensor, used to identify which sensor it is in the system configuration."
               ::= { sensorSecurityEntry 1000 }

--/* End of sensorSecurityEntry */

--/* Begin of sensorSirenEntry */
         sensorSirenTable OBJECT-TYPE
            SYNTAX  SEQUENCE OF SensorSirenEntry
            ACCESS  not-accessible
            STATUS  mandatory
            DESCRIPTION
            "This table contains the property and reading value for every sensor."
            ::=  {  secSensor 11   }

         sensorSirenEntry OBJECT-TYPE
            SYNTAX  SensorSirenEntry
            ACCESS  not-accessible
            STATUS  mandatory
            DESCRIPTION
            "This is an entry in the sensorTemperatureEntry Table"
            INDEX         { sensorSirenIndex }
            ::=  {  sensorSirenTable 1 }

         SensorSirenEntry ::= SEQUENCE {
               sensorSirenIndex
                  INTEGER,
               sensorSirenDescription
                  DisplayString,
               sensorSirenStatus
                  INTEGER,
               sensorSirenGoOffline
                  INTEGER,
               sensorSirenControlMode
                  INTEGER,
               sensorSirenManualCycleTime
                  INTEGER,
               sensorSirenManualAction
                  INTEGER,
               sensorSirenPort
                  INTEGER,
               sensorSirenSubPort
                  INTEGER,
               sensorSirenDeviceIndex
                  INTEGER,
               sensorSirenOnDesc 
                  DisplayString,
               sensorSirenOffDesc 
                  DisplayString,
               sensorSirenOnColor 
                  INTEGER,
               sensorSirenOffColor 
                  INTEGER,               
               sensorSirenAcknowledge
                  INTEGER,
               sensorSirenId
                  INTEGER
            }

            sensorSirenIndex OBJECT-TYPE
               SYNTAX  INTEGER (1..65535)
               ACCESS  read-only
               STATUS  mandatory
               DESCRIPTION
               "The index into the Switch sensor table"
               ::=  {  sensorSirenEntry 1   }

            sensorSirenDescription OBJECT-TYPE
               SYNTAX  DisplayString
               ACCESS  read-write
               STATUS  mandatory
               DESCRIPTION
               "A Description of this sensor Switch"
               ::=  {  sensorSirenEntry 2   }

            sensorSirenStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSirenEntry 6  }

            sensorSirenGoOffline OBJECT-TYPE
               SYNTAX  INTEGER {
                  online(1),
                  goOffline(2)
               }
               ACCESS  read-write
               STATUS  mandatory
               DESCRIPTION
               "To take offline enter a 2"
               ::=  {  sensorSirenEntry 8  }

            sensorSirenControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a siren."
               ::=  {  sensorSirenEntry 24  }
               
            sensorSirenManualCycleTime OBJECT-TYPE
               SYNTAX  INTEGER (1..255)
               ACCESS  read-write
               STATUS  mandatory
               DESCRIPTION
               "Toggle period in seconds for Manual Cycle action."
               ::=  {  sensorSirenEntry 25  }
               
            sensorSirenManualAction OBJECT-TYPE
               SYNTAX  INTEGER {
                  turn-On(0),
                  turn-Off(1),
                  cycle-On-Off-On(2),
                  cycle-Off-On-Off(3)
               }
               ACCESS  read-write
               STATUS  mandatory
               DESCRIPTION
               "Control the siren manualy"
               ::=  {  sensorSirenEntry 26  }

            sensorSirenPort OBJECT-TYPE
               SYNTAX  INTEGER (0..65534)
               ACCESS  read-only
               STATUS  mandatory
               DESCRIPTION
               "Sensor port"
               ::=  {  sensorSirenEntry 35 }

            sensorSirenSubPort OBJECT-TYPE
               SYNTAX  INTEGER (0..65534)
               ACCESS  read-only
               STATUS  mandatory
               DESCRIPTION
               "Sensor sub port"
               ::=  {  sensorSirenEntry 36 }

            sensorSirenDeviceIndex OBJECT-TYPE
               SYNTAX  INTEGER (0..65534)
               ACCESS  read-only
               STATUS  mandatory
               DESCRIPTION
               "Device Index of sensor"
               ::=  {  sensorSirenEntry 37 }
              
            sensorSirenOnDesc OBJECT-TYPE
               SYNTAX  DisplayString
               ACCESS  read-write
               STATUS  mandatory
               DESCRIPTION
               "A On Description of this sensor"
               ::=  {  sensorSirenEntry  52  }

            sensorSirenOffDesc OBJECT-TYPE
               SYNTAX  DisplayString
               ACCESS  read-write
               STATUS  mandatory
               DESCRIPTION
               "A Off Description of this sensor"
               ::=  {  sensorSirenEntry  53  }

            sensorSirenOnColor OBJECT-TYPE
               SYNTAX  INTEGER
               ACCESS  read-write
               STATUS  mandatory
               DESCRIPTION
               "A On Color of this sensor"
               ::=  {  sensorSirenEntry  60  }               

            sensorSirenOffColor OBJECT-TYPE
               SYNTAX  INTEGER
               ACCESS  read-write
               STATUS  mandatory
               DESCRIPTION
               "A Off Color of this sensor"
               ::=  {  sensorSirenEntry  61  }      

            sensorSirenAcknowledge OBJECT-TYPE
               SYNTAX  INTEGER {
                  acked(2)
               }
               ACCESS  read-write
               STATUS  mandatory
               DESCRIPTION
               "Siren sensor acknowledge"
               ::=  {  sensorSirenEntry 70 }
               
            sensorSirenId OBJECT-TYPE
               SYNTAX  INTEGER
               ACCESS  read-only
               STATUS  mandatory
               DESCRIPTION
               "The Sensor ID of this sensor, used to identify which sensor it is in the system configuration."
               ::= { sensorSirenEntry 1000 }

--/* End of sensorSirenEntry */

--/* Begin of sensorRelayEntry */
         sensorRelayTable OBJECT-TYPE
            SYNTAX  SEQUENCE OF SensorRelayEntry
            ACCESS  not-accessible
            STATUS  mandatory
            DESCRIPTION
            "This table contains the property and reading value for every sensor."
            ::=  {  secSensor 12   }

         sensorRelayEntry OBJECT-TYPE
            SYNTAX  SensorRelayEntry
            ACCESS  not-accessible
            STATUS  mandatory
            DESCRIPTION
            "This is an entry in the sensorTemperatureEntry Table"
            INDEX         { sensorRelayIndex }
            ::=  {  sensorRelayTable 1 }

         SensorRelayEntry ::= SEQUENCE {
               sensorRelayIndex
                  INTEGER,
               sensorRelayDescription
                  DisplayString,
               sensorRelayType
                  INTEGER,
               sensorRelayStatus
                  INTEGER,
               sensorRelayGoOffline
                  INTEGER,
               sensorRelayControlMode
                  INTEGER,
               sensorRelayManualCycleTime
                  INTEGER,
               sensorRelayManualAction
                  INTEGER,
               sensorRelayPort
                  INTEGER,
               sensorRelaySubPort
                  INTEGER,
               sensorRelayDeviceIndex
                  INTEGER,
               sensorRelayOnDesc 
                  DisplayString,
               sensorRelayOffDesc 
                  DisplayString,
               sensorRelayOnColor 
                  INTEGER,
               sensorRelayOffColor 
                  INTEGER,        
               sensorRelayAcknowledge
                  INTEGER,
               sensorRelayId
                  INTEGER
            }

            sensorRelayIndex OBJECT-TYPE
               SYNTAX  INTEGER (1..65535)
               ACCESS  read-only
               STATUS  mandatory
               DESCRIPTION
               "The index into the Switch sensor table"
               ::=  {  sensorRelayEntry 1   }

            sensorRelayDescription OBJECT-TYPE
               SYNTAX  DisplayString
               ACCESS  read-write
               STATUS  mandatory
               DESCRIPTION
               "A Description of this sensor Switch"
               ::=  {  sensorRelayEntry 2   }

            sensorRelayType OBJECT-TYPE
               SYNTAX  INTEGER {
                  relay(13),
                  xrelay(19)
               }
               ACCESS  read-only
               STATUS  mandatory
               DESCRIPTION
               "Enter the type of this Sensor"
               ::=  {  sensorRelayEntry 3  }

            sensorRelayStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorRelayEntry 6  }

            sensorRelayGoOffline OBJECT-TYPE
               SYNTAX  INTEGER {
                  online(1),
                  goOffline(2)
               }
               ACCESS  read-write
               STATUS  mandatory
               DESCRIPTION
               "To take offline enter a 2"
               ::=  {  sensorRelayEntry 8  }

            sensorRelayControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a relay."
               ::=  {  sensorRelayEntry 24  }
               
            sensorRelayManualCycleTime OBJECT-TYPE
               SYNTAX  INTEGER (1..255)
               ACCESS  read-write
               STATUS  mandatory
               DESCRIPTION
               "Toggle period in seconds for Manual Cycle action."
               ::=  {  sensorRelayEntry 25  }
               
            sensorRelayManualAction OBJECT-TYPE
               SYNTAX  INTEGER {
                  turn-On(0),
                  turn-Off(1),
                  cycle-On-Off-On(2),
                  cycle-Off-On-Off(3)
               }
               ACCESS  read-write
               STATUS  mandatory
               DESCRIPTION
               "Control the relay manualy"
               ::=  {  sensorRelayEntry 26  }

            sensorRelayPort OBJECT-TYPE
               SYNTAX  INTEGER (0..65534)
               ACCESS  read-only
               STATUS  mandatory
               DESCRIPTION
               "Sensor port"
               ::=  {  sensorRelayEntry 35 }

            sensorRelaySubPort OBJECT-TYPE
               SYNTAX  INTEGER (0..65534)
               ACCESS  read-only
               STATUS  mandatory
               DESCRIPTION
               "Sensor sub port"
               ::=  {  sensorRelayEntry 36 }

            sensorRelayDeviceIndex OBJECT-TYPE
               SYNTAX  INTEGER (0..65534)
               ACCESS  read-only
               STATUS  mandatory
               DESCRIPTION
               "Device Index of sensor"
               ::=  {  sensorRelayEntry 37 }
               
            sensorRelayOnDesc OBJECT-TYPE
               SYNTAX  DisplayString
               ACCESS  read-write
               STATUS  mandatory
               DESCRIPTION
               "A On Description of this sensor"
               ::=  {  sensorRelayEntry  52  }               

            sensorRelayOffDesc OBJECT-TYPE
               SYNTAX  DisplayString
               ACCESS  read-write
               STATUS  mandatory
               DESCRIPTION
               "A Off Description of this sensor"
               ::=  {  sensorRelayEntry  53  }

            sensorRelayOnColor OBJECT-TYPE
               SYNTAX  INTEGER
               ACCESS  read-write
               STATUS  mandatory
               DESCRIPTION
               "A On Color of this sensor"
               ::=  {  sensorRelayEntry  60  }               

            sensorRelayOffColor OBJECT-TYPE
               SYNTAX  INTEGER
               ACCESS  read-write
               STATUS  mandatory
               DESCRIPTION
               "A Off Color of this sensor"
               ::=  {  sensorRelayEntry  61  }     

            sensorRelayAcknowledge OBJECT-TYPE
               SYNTAX  INTEGER {
                  acked(2)
               }
               ACCESS  read-write
               STATUS  mandatory
               DESCRIPTION
               "Relay sensor acknowledge"
               ::=  {  sensorRelayEntry 70 }  

            sensorRelayId OBJECT-TYPE
               SYNTAX  INTEGER
               ACCESS  read-only
               STATUS  mandatory
               DESCRIPTION
               "The Sensor ID of this sensor, used to identify which sensor it is in the system configuration."
               ::= { sensorRelayEntry 1000 }

--/* End of sensorRelayEntry */

--/* Begin of sensorACvoltageEntry */
         sensorACvoltageTable OBJECT-TYPE
            SYNTAX  SEQUENCE OF SensorACvoltageEntry
            ACCESS  not-accessible
            STATUS  mandatory
            DESCRIPTION
            "This table contains the property and reading value for every sensor."
            ::=  {  secSensor 13   }

         sensorACvoltageEntry OBJECT-TYPE
            SYNTAX  SensorACvoltageEntry
            ACCESS  not-accessible
            STATUS  mandatory
            DESCRIPTION
            "This is an entry in the sensorTemperatureEntry Table"
            INDEX         { sensorACvoltageIndex }
            ::=  {  sensorACvoltageTable 1 }

         SensorACvoltageEntry ::= SEQUENCE {
               sensorACvoltageIndex
                  INTEGER,
               sensorACvoltageDescription
                  DisplayString,
               sensorACvoltageStatus
                  INTEGER,
               sensorACvoltageGoOffline
                  INTEGER,
               sensorACvoltagePort
                  INTEGER,
               sensorACvoltageSubPort
                  INTEGER,
               sensorACvoltageDeviceIndex
                  INTEGER,
               sensorACvoltageCriticalDesc 
                  DisplayString,
               sensorACvoltageNormalDesc 
                  DisplayString,
               sensorACvoltageCriticalColor 
                  INTEGER,
               sensorACvoltageNormalColor 
                  INTEGER,
               sensorACvoltageAcknowledge
                  INTEGER,
               sensorACvoltageId
                  INTEGER
            }

            sensorACvoltageIndex OBJECT-TYPE
               SYNTAX  INTEGER (1..65535)
               ACCESS  read-only
               STATUS  mandatory
               DESCRIPTION
               "The index into the Switch sensor table"
               ::=  {  sensorACvoltageEntry 1   }

            sensorACvoltageDescription OBJECT-TYPE
               SYNTAX  DisplayString
               ACCESS  read-write
               STATUS  mandatory
               DESCRIPTION
               "A Description of this sensor Switch"
               ::=  {  sensorACvoltageEntry 2   }

            sensorACvoltageStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorACvoltageEntry 6  }

            sensorACvoltageGoOffline OBJECT-TYPE
               SYNTAX  INTEGER {
                  online(1),
                  goOffline(2)
               }
               ACCESS  read-write
               STATUS  mandatory
               DESCRIPTION
               "To put online enter a 1, to take offline enter a 2"
               ::=  {  sensorACvoltageEntry 8  }

            sensorACvoltagePort OBJECT-TYPE
               SYNTAX  INTEGER (0..65534)
               ACCESS  read-only
               STATUS  mandatory
               DESCRIPTION
               "Sensor port"
               ::=  {  sensorACvoltageEntry 35 }

            sensorACvoltageSubPort OBJECT-TYPE
               SYNTAX  INTEGER (0..65534)
               ACCESS  read-only
               STATUS  mandatory
               DESCRIPTION
               "Sensor sub port"
               ::=  {  sensorACvoltageEntry 36 }

            sensorACvoltageDeviceIndex OBJECT-TYPE
               SYNTAX  INTEGER (0..65534)
               ACCESS  read-only
               STATUS  mandatory
               DESCRIPTION
               "Device Index of sensor"
               ::=  {  sensorACvoltageEntry 37 }
               
            sensorACvoltageCriticalDesc OBJECT-TYPE
               SYNTAX  DisplayString
               ACCESS  read-write
               STATUS  mandatory
               DESCRIPTION
               "A Critical Description of this sensor"
               ::=  {  sensorACvoltageEntry  46  }               

            sensorACvoltageNormalDesc OBJECT-TYPE
               SYNTAX  DisplayString
               ACCESS  read-write
               STATUS  mandatory
               DESCRIPTION
               "A Normal Description of this sensor"
               ::=  {  sensorACvoltageEntry  48  }
               
            sensorACvoltageCriticalColor OBJECT-TYPE
               SYNTAX  INTEGER
               ACCESS  read-write
               STATUS  mandatory
               DESCRIPTION
               "A Critical Color of this sensor"
               ::=  {  sensorACvoltageEntry  54  }               

            sensorACvoltageNormalColor OBJECT-TYPE
               SYNTAX  INTEGER
               ACCESS  read-write
               STATUS  mandatory
               DESCRIPTION
               "A Normal Color of this sensor"
               ::=  {  sensorACvoltageEntry  56  }      

            sensorACvoltageAcknowledge OBJECT-TYPE
               SYNTAX  INTEGER {
                  acked(2)
               }
               ACCESS  read-write
               STATUS  mandatory
               DESCRIPTION
               "ACvoltage sensor acknowledge"
               ::=  {  sensorACvoltageEntry 70 }

            sensorACvoltageId OBJECT-TYPE
               SYNTAX  INTEGER
               ACCESS  read-only
               STATUS  mandatory
               DESCRIPTION
               "The Sensor ID of this sensor, used to identify which sensor it is in the system configuration."
               ::= { sensorACvoltageEntry 1000 }

--/* End of sensorACvoltageEntry */

--/* Begin of sensorSmokeEntry */
         sensorSmokeTable OBJECT-TYPE
            SYNTAX  SEQUENCE OF SensorSmokeEntry
            ACCESS  not-accessible
            STATUS  mandatory
            DESCRIPTION
            "This table contains the property and reading value for every sensor."
            ::=  {  secSensor 14   }

         sensorSmokeEntry OBJECT-TYPE
            SYNTAX  SensorSmokeEntry
            ACCESS  not-accessible
            STATUS  mandatory
            DESCRIPTION
            "This is an entry in the sensorTemperatureEntry Table"
            INDEX         { sensorSmokeIndex }
            ::=  {  sensorSmokeTable 1 }

         SensorSmokeEntry ::= SEQUENCE {
               sensorSmokeIndex
                  INTEGER,
               sensorSmokeDescription
                  DisplayString,
               sensorSmokeStatus
                  INTEGER,
               sensorSmokeGoOffline
                  INTEGER,
               sensorSmokePort
                  INTEGER,
               sensorSmokeSubPort
                  INTEGER,
               sensorSmokeDeviceIndex
                  INTEGER,
               sensorSmokeCriticalDesc 
                  DisplayString,
               sensorSmokeNormalDesc 
                  DisplayString,
               sensorSmokeCriticalColor 
                  INTEGER,
               sensorSmokeNormalColor 
                  INTEGER,      
               sensorSmokeAcknowledge
                  INTEGER,
               sensorSmokeId
                  INTEGER
            }

            sensorSmokeIndex OBJECT-TYPE
               SYNTAX  INTEGER (1..65535)
               ACCESS  read-only
               STATUS  mandatory
               DESCRIPTION
               "The index into the Switch sensor table"
               ::=  {  sensorSmokeEntry 1   }

            sensorSmokeDescription OBJECT-TYPE
               SYNTAX  DisplayString
               ACCESS  read-write
               STATUS  mandatory
               DESCRIPTION
               "A Description of this sensor Switch"
               ::=  {  sensorSmokeEntry 2   }

            sensorSmokeStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSmokeEntry 6  }

            sensorSmokeGoOffline OBJECT-TYPE
               SYNTAX  INTEGER {
                  online(1),
                  goOffline(2)
               }
               ACCESS  read-write
               STATUS  mandatory
               DESCRIPTION
               "To take offline enter a 2"
               ::=  {  sensorSmokeEntry 8  }

            sensorSmokePort OBJECT-TYPE
               SYNTAX  INTEGER (0..65534)
               ACCESS  read-only
               STATUS  mandatory
               DESCRIPTION
               "Sensor port"
               ::=  {  sensorSmokeEntry 35 }

            sensorSmokeSubPort OBJECT-TYPE
               SYNTAX  INTEGER (0..65534)
               ACCESS  read-only
               STATUS  mandatory
               DESCRIPTION
               "Sensor sub port"
               ::=  {  sensorSmokeEntry 36 }

            sensorSmokeDeviceIndex OBJECT-TYPE
               SYNTAX  INTEGER (0..65534)
               ACCESS  read-only
               STATUS  mandatory
               DESCRIPTION
               "Device Index of sensor"
               ::=  {  sensorSmokeEntry 37 }

            sensorSmokeCriticalDesc OBJECT-TYPE
               SYNTAX  DisplayString
               ACCESS  read-write
               STATUS  mandatory
               DESCRIPTION
               "A Critical Description of this sensor"
               ::=  {  sensorSmokeEntry  46  }               

            sensorSmokeNormalDesc OBJECT-TYPE
               SYNTAX  DisplayString
               ACCESS  read-write
               STATUS  mandatory
               DESCRIPTION
               "A Normal Description of this sensor"
               ::=  {  sensorSmokeEntry  48  }
        
            sensorSmokeCriticalColor OBJECT-TYPE
               SYNTAX  INTEGER
               ACCESS  read-write
               STATUS  mandatory
               DESCRIPTION
               "A Critical Color of this sensor"
               ::=  {  sensorSmokeEntry  54  }               

            sensorSmokeNormalColor OBJECT-TYPE
               SYNTAX  INTEGER
               ACCESS  read-write
               STATUS  mandatory
               DESCRIPTION
               "A Normal Color of this sensor"
               ::=  {  sensorSmokeEntry  56  }   

            sensorSmokeAcknowledge OBJECT-TYPE
               SYNTAX  INTEGER {
                  acked(2)
               }
               ACCESS  read-write
               STATUS  mandatory
               DESCRIPTION
               "Smoke sensor acknowledge"
               ::=  {  sensorSmokeEntry 70 }

            sensorSmokeId OBJECT-TYPE
               SYNTAX  INTEGER
               ACCESS  read-only
               STATUS  mandatory
               DESCRIPTION
               "The Sensor ID of this sensor, used to identify which sensor it is in the system configuration."
               ::= { sensorSmokeEntry 1000 }

--/* End of sensorSmokeEntry */

--/* Begin of sensorThermostatEntry */
         sensorThermostatTable OBJECT-TYPE
            SYNTAX  SEQUENCE OF SensorThermostatEntry
            ACCESS  not-accessible
            STATUS  mandatory
            DESCRIPTION
            "This table contains the property and reading value for every sensor."
            ::=  {  secSensor 20   }

         sensorThermostatEntry OBJECT-TYPE
            SYNTAX  SensorThermostatEntry
            ACCESS  not-accessible
            STATUS  mandatory
            DESCRIPTION
            "This is an entry in the sensorTemperatureEntry Table"
            INDEX         { sensorThermostatIndex }
            ::=  {  sensorThermostatTable 1 }

         SensorThermostatEntry ::= SEQUENCE {
               sensorThermostatIndex
                  INTEGER,
               sensorThermostatDescription
                  DisplayString,
               sensorThermostatDegree
                  INTEGER,
               sensorThermostatStatus
                  INTEGER,
               sensorThermostatGoOffline
                  INTEGER,
               sensorThermostatLowCritical
                  INTEGER,
               sensorThermostatLowWarning
                  INTEGER,
               sensorThermostatHighWarning
                  INTEGER,
               sensorThermostatHighCritical
                  INTEGER,
               sensorThermostatRearm
                  INTEGER,
               sensorThermostatDelayError
                  INTEGER,
               sensorThermostatDelayNormal
                  INTEGER,
               sensorThermostatDelayLowCritical
                  INTEGER,
               sensorThermostatDelayLowWarning
                  INTEGER,
               sensorThermostatDelayHighWarning
                  INTEGER,
               sensorThermostatDelayHighCritical
                  INTEGER,
               sensorThermostatPort
                  INTEGER,
               sensorThermostatSubPort
                  INTEGER,
               sensorThermostatDeviceIndex
                  INTEGER,
               sensorThermostatDisplayStyle
                  INTEGER,
               sensorThermostatHighCriticalDesc 
                  DisplayString,
               sensorThermostatLowCriticalDesc 
                  DisplayString,
               sensorThermostatNormalDesc 
                  DisplayString,
               sensorThermostatLowWarningDesc 
                  DisplayString,   
               sensorThermostatHighWarningDesc 
                  DisplayString,
               sensorThermostatSensorErrorDesc 
                  DisplayString,
               sensorThermostatHighCriticalColor 
                  INTEGER,
               sensorThermostatLowCriticalColor 
                  INTEGER,
               sensorThermostatNormalColor 
                  INTEGER,
               sensorThermostatLowWarningColor 
                  INTEGER,   
               sensorThermostatHighWarningColor 
                  INTEGER,
               sensorThermostatSensorErrorColor 
                  INTEGER,            
               sensorThermostatAcknowledge
                  INTEGER,
               sensorThermostatId
                  INTEGER
            }

            sensorThermostatIndex OBJECT-TYPE
               SYNTAX  INTEGER (1..65535)
               ACCESS  read-only
               STATUS  mandatory
               DESCRIPTION
               "The index into the sensor table"
               ::=  {  sensorThermostatEntry 1   }

            sensorThermostatDescription OBJECT-TYPE
               SYNTAX  DisplayString
               ACCESS  read-write
               STATUS  mandatory
               DESCRIPTION
               "A Description of this sensor"
               ::=  {  sensorThermostatEntry 2   }

            sensorThermostatDegree OBJECT-TYPE
               SYNTAX  INTEGER
               ACCESS  read-only
               STATUS  mandatory
               DESCRIPTION
               "The degrees in this sensor"
               ::=  {  sensorThermostatEntry 4   }

            sensorThermostatStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorThermostatEntry 6   }

            sensorThermostatGoOffline OBJECT-TYPE
               SYNTAX  INTEGER {
                  online(1),
                  goOffline(2)
               }
               ACCESS  read-write
               STATUS  mandatory
               DESCRIPTION
               "To take offline enter a 2"
               ::=  {  sensorThermostatEntry 8   }

            sensorThermostatLowCritical OBJECT-TYPE
               SYNTAX  INTEGER
               ACCESS  read-write
               STATUS  mandatory
               DESCRIPTION
               "How cold this sensor gets before it sends a critical event"
               ::=  {  sensorThermostatEntry 9   }

            sensorThermostatLowWarning OBJECT-TYPE
               SYNTAX  INTEGER
               ACCESS  read-write
               STATUS  mandatory
               DESCRIPTION
               "How cold this sensor gets before it sends a warning"
               ::=  {  sensorThermostatEntry 10   }
   
            sensorThermostatHighWarning OBJECT-TYPE
               SYNTAX  INTEGER
               ACCESS  read-write
               STATUS  mandatory
               DESCRIPTION
               "How hot this sensor gets before it sends a warning"
               ::=  {  sensorThermostatEntry 11   }  

            sensorThermostatHighCritical OBJECT-TYPE
               SYNTAX  INTEGER
               ACCESS  read-write
               STATUS  mandatory
               DESCRIPTION
               "How hot this sensor gets before it sends a critical event"
               ::=  {  sensorThermostatEntry 12   }   

            sensorThermostatRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorThermostatEntry 13   }

            sensorThermostatDelayError OBJECT-TYPE
               SYNTAX  INTEGER (0..65534)
               ACCESS  read-write
               STATUS  mandatory
               DESCRIPTION
               "Time in seconds after the sensor has been in error status before report as an error"
               ::=  {  sensorThermostatEntry 14   }

            sensorThermostatDelayNormal OBJECT-TYPE
               SYNTAX  INTEGER (0..65534)
               ACCESS  read-write
               STATUS  mandatory
               DESCRIPTION
               "Time in seconds after the sensor change from error to normal before report as normal"
               ::=  {  sensorThermostatEntry 15   }

            sensorThermostatDelayLowCritical OBJECT-TYPE
               SYNTAX INTEGER (0..65535)
               ACCESS read-write
               STATUS mandatory
               DESCRIPTION
               "Continuous time for this sensor to be in Low Critical before accepting new Status."
               ::= {  sensorThermostatEntry 16 }
               
            sensorThermostatDelayLowWarning OBJECT-TYPE
               SYNTAX INTEGER (0..65535)
               ACCESS read-write
               STATUS mandatory
               DESCRIPTION
               "Continuous time for this sensor to be in Low Warning before accepting new Status."
               ::= {  sensorThermostatEntry 17 }

            sensorThermostatDelayHighWarning OBJECT-TYPE
               SYNTAX INTEGER (0..65535)
               ACCESS read-write
               STATUS mandatory
               DESCRIPTION
               "Continuous time for this sensor to be in High Warning before accepting new Status."
               ::= {  sensorThermostatEntry 18 }

            sensorThermostatDelayHighCritical OBJECT-TYPE
               SYNTAX INTEGER (0..65535)
               ACCESS read-write
               STATUS mandatory
               DESCRIPTION
               "Continuous time for this sensor to be in High Critical before accepting new Status."
               ::= {  sensorThermostatEntry 19 }

            sensorThermostatPort OBJECT-TYPE
               SYNTAX  INTEGER (0..65534)
               ACCESS  read-only
               STATUS  mandatory
               DESCRIPTION
               "Sensor port"
               ::=  {  sensorThermostatEntry 35 }

            sensorThermostatSubPort OBJECT-TYPE
               SYNTAX  INTEGER (0..65534)
               ACCESS  read-only
               STATUS  mandatory
               DESCRIPTION
               "Sensor sub port"
               ::=  {  sensorThermostatEntry 36 }

            sensorThermostatDeviceIndex OBJECT-TYPE
               SYNTAX  INTEGER (0..65534)
               ACCESS  read-only
               STATUS  mandatory
               DESCRIPTION
               "Device Index of sensor"
               ::=  {  sensorThermostatEntry 37 }
               
            sensorThermostatDisplayStyle OBJECT-TYPE
               SYNTAX  INTEGER {
                  basic(0),
                  gauge(1)
               }
               ACCESS  read-write
               STATUS  mandatory
               DESCRIPTION
               "Thermostat display style"
               ::=  {  sensorThermostatEntry 45 } 

            sensorThermostatHighCriticalDesc OBJECT-TYPE
               SYNTAX  DisplayString
               ACCESS  read-write
               STATUS  mandatory
               DESCRIPTION
               "A HighCritical Description of this sensor"
               ::=  {  sensorThermostatEntry  46  }               

            sensorThermostatLowCriticalDesc OBJECT-TYPE
               SYNTAX  DisplayString
               ACCESS  read-write
               STATUS  mandatory
               DESCRIPTION
               "A LowCritical Description of this sensor"
               ::=  {  sensorThermostatEntry  47  }

            sensorThermostatNormalDesc OBJECT-TYPE
               SYNTAX  DisplayString
               ACCESS  read-write
               STATUS  mandatory
               DESCRIPTION
               "A Normal Description of this sensor"
               ::=  {  sensorThermostatEntry  48  }
               
            sensorThermostatLowWarningDesc OBJECT-TYPE
               SYNTAX  DisplayString
               ACCESS  read-write
               STATUS  mandatory
               DESCRIPTION
               "A LowWarning Description of this sensor"
               ::=  {  sensorThermostatEntry  49  }
               
            sensorThermostatHighWarningDesc OBJECT-TYPE
               SYNTAX  DisplayString
               ACCESS  read-write
               STATUS  mandatory
               DESCRIPTION
               "A HighWarning Description of this sensor"
               ::=  {  sensorThermostatEntry  50  }
               
            sensorThermostatSensorErrorDesc OBJECT-TYPE
               SYNTAX  DisplayString
               ACCESS  read-write
               STATUS  mandatory
               DESCRIPTION
               "A SensorError Description of this sensor"
               ::=  {  sensorThermostatEntry  51  }  

            sensorThermostatHighCriticalColor OBJECT-TYPE
               SYNTAX  INTEGER
               ACCESS  read-write
               STATUS  mandatory
               DESCRIPTION
               "A HighCritical Color of this sensor"
               ::=  {  sensorThermostatEntry  54  }               

            sensorThermostatLowCriticalColor OBJECT-TYPE
               SYNTAX  INTEGER
               ACCESS  read-write
               STATUS  mandatory
               DESCRIPTION
               "A LowCritical Color of this sensor"
               ::=  {  sensorThermostatEntry  55  }

            sensorThermostatNormalColor OBJECT-TYPE
               SYNTAX  INTEGER
               ACCESS  read-write
               STATUS  mandatory
               DESCRIPTION
               "A Normal Color of this sensor"
               ::=  {  sensorThermostatEntry  56  }
               
            sensorThermostatLowWarningColor OBJECT-TYPE
               SYNTAX  INTEGER
               ACCESS  read-write
               STATUS  mandatory
               DESCRIPTION
               "A LowWarning Color of this sensor"
               ::=  {  sensorThermostatEntry  57  }
               
            sensorThermostatHighWarningColor OBJECT-TYPE
               SYNTAX  INTEGER
               ACCESS  read-write
               STATUS  mandatory
               DESCRIPTION
               "A HighWarning Color of this sensor"
               ::=  {  sensorThermostatEntry  58  }
               
            sensorThermostatSensorErrorColor OBJECT-TYPE
               SYNTAX  INTEGER
               ACCESS  read-write
               STATUS  mandatory
               DESCRIPTION
               "A SensorError Color of this sensor"
               ::=  {  sensorThermostatEntry  59  }  
         
            sensorThermostatAcknowledge OBJECT-TYPE
               SYNTAX  INTEGER {
                  acked(2)
               }
               ACCESS  read-write
               STATUS  mandatory
               DESCRIPTION
               "Thermostat sensor acknowledge"
               ::=  {  sensorThermostatEntry 70 }

            sensorThermostatId OBJECT-TYPE
               SYNTAX  INTEGER
               ACCESS  read-only
               STATUS  mandatory
               DESCRIPTION
               "The Sensor ID of this sensor, used to identify which sensor it is in the system configuration."
               ::= { sensorThermostatEntry 1000 }

--/* End of sensorThermostatEntry */

--/* Begin of sensorWaterRopeEntry */
         sensorWaterRopeTable OBJECT-TYPE
            SYNTAX  SEQUENCE OF SensorWaterRopeEntry
            ACCESS  not-accessible
            STATUS  mandatory
            DESCRIPTION
            "This table contains the property and reading value for every sensor."
            ::=  {  secSensor 21   }

         sensorWaterRopeEntry OBJECT-TYPE
            SYNTAX  SensorWaterRopeEntry
            ACCESS  not-accessible
            STATUS  mandatory
            DESCRIPTION
            "This is an entry in the SensorWaterRopeEntry Table"
            INDEX         { sensorWaterRopeIndex }
            ::=  {  sensorWaterRopeTable 1 }

         SensorWaterRopeEntry ::= SEQUENCE {
               sensorWaterRopeIndex
                  INTEGER,
               sensorWaterRopeDescription
                  DisplayString,
               sensorWaterRopeLeakLocation
                  INTEGER,
               sensorWaterRopeUnit
                  DisplayString,
               sensorWaterRopeStatus
                  INTEGER,
               sensorWaterRopeGoOffline
                  INTEGER,
               sensorWaterRopeRaw
                  INTEGER,
               sensorWaterRopeDeviceIndex
                  INTEGER,               
               sensorWaterRopeCriticalDesc 
                  DisplayString,
               sensorWaterRopeNormalDesc 
                  DisplayString,
               sensorWaterRopeSensorErrorDesc 
                  DisplayString,
               sensorWaterRopeCriticalColor 
                  INTEGER,
               sensorWaterRopeNormalColor 
                  INTEGER,
               sensorWaterRopeSensorErrorColor 
                  INTEGER,
               sensorWaterRopeAcknowledge
                  INTEGER,
               sensorWaterRopeLength
                  INTEGER,
               sensorWaterRopeImpedance
                  INTEGER,
               sensorWaterRopeType
                  INTEGER,
               sensorWaterRopeId
                  INTEGER
            }

            sensorWaterRopeIndex OBJECT-TYPE
               SYNTAX  INTEGER (1..65535)
               ACCESS  read-only
               STATUS  mandatory
               DESCRIPTION
               "The index into the sensor table"
               ::=  {  sensorWaterRopeEntry 1   }

            sensorWaterRopeDescription OBJECT-TYPE
               SYNTAX  DisplayString
               ACCESS  read-write
               STATUS  mandatory
               DESCRIPTION
               "A Description of this sensor"
               ::=  {  sensorWaterRopeEntry 2   }

            sensorWaterRopeLeakLocation OBJECT-TYPE
               SYNTAX INTEGER
               ACCESS read-only
               STATUS mandatory
               DESCRIPTION
               "Location of leakage of water rope sensor."
               ::= {  sensorWaterRopeEntry 4 }

            sensorWaterRopeUnit OBJECT-TYPE
               SYNTAX  DisplayString
               ACCESS  read-write
               STATUS  mandatory
               DESCRIPTION
               "Display unit of water rope sensor."
               ::=  {  sensorWaterRopeEntry 5   }

            sensorWaterRopeStatus OBJECT-TYPE
               SYNTAX  INTEGER {
                  noStatus(1),
                  normal(2),
                  highCritical(4),
                  sensorError(7)
               }
               ACCESS  read-only
               STATUS  mandatory
               DESCRIPTION
               "The current status of this Sensor"
               ::=  {  sensorWaterRopeEntry 6  }

            sensorWaterRopeGoOffline OBJECT-TYPE
               SYNTAX  INTEGER {
                  online(1),
                  goOffline(2)
               }
               ACCESS  read-write
               STATUS  mandatory
               DESCRIPTION
               "To take offline enter a 2"
               ::=  {  sensorWaterRopeEntry 8  }
               
            sensorWaterRopeRaw OBJECT-TYPE
               SYNTAX INTEGER
               ACCESS read-only
               STATUS mandatory
               DESCRIPTION
               "Raw value of location or length in ohms"
               ::= {  sensorWaterRopeEntry 20 }

            sensorWaterRopeDeviceIndex OBJECT-TYPE
               SYNTAX  INTEGER (0..65534)
               ACCESS  read-only
               STATUS  mandatory
               DESCRIPTION
               "Device Index of sensor"
               ::=  {  sensorWaterRopeEntry 37 }
               
            sensorWaterRopeCriticalDesc OBJECT-TYPE
               SYNTAX  DisplayString
               ACCESS  read-write
               STATUS  mandatory
               DESCRIPTION
               "A Critical Description of this sensor"
               ::=  {  sensorWaterRopeEntry  46  }  
               
            sensorWaterRopeNormalDesc OBJECT-TYPE
               SYNTAX  DisplayString
               ACCESS  read-write
               STATUS  mandatory
               DESCRIPTION
               "A Normal Description of this sensor"
               ::=  {  sensorWaterRopeEntry  48  }
               
            sensorWaterRopeSensorErrorDesc OBJECT-TYPE
               SYNTAX  DisplayString
               ACCESS  read-write
               STATUS  mandatory
               DESCRIPTION
               "A SensorError Description of this sensor"
               ::=  {  sensorWaterRopeEntry  51  }  
               
            sensorWaterRopeCriticalColor OBJECT-TYPE
               SYNTAX  INTEGER
               ACCESS  read-write
               STATUS  mandatory
               DESCRIPTION
               "A Critical Color of this sensor"
               ::=  {  sensorWaterRopeEntry  54  }               

            sensorWaterRopeNormalColor OBJECT-TYPE
               SYNTAX  INTEGER
               ACCESS  read-write
               STATUS  mandatory
               DESCRIPTION
               "A Normal Color of this sensor"
               ::=  {  sensorWaterRopeEntry  56  }
               
            sensorWaterRopeSensorErrorColor OBJECT-TYPE
               SYNTAX  INTEGER
               ACCESS  read-write
               STATUS  mandatory
               DESCRIPTION
               "A SensorError Color of this sensor"
               ::=  {  sensorWaterRopeEntry  59  }    

            sensorWaterRopeAcknowledge OBJECT-TYPE
               SYNTAX  INTEGER {
                  acked(2)
               }
               ACCESS  read-write
               STATUS  mandatory
               DESCRIPTION
               "Water Rope sensor acknowledge"
               ::=  {  sensorWaterRopeEntry 70 }
            
            sensorWaterRopeLength OBJECT-TYPE
               SYNTAX INTEGER
               ACCESS read-only
               STATUS mandatory
               DESCRIPTION
               "Length of water rope sensor."
               ::= {  sensorWaterRopeEntry 100 }

            sensorWaterRopeImpedance OBJECT-TYPE
               SYNTAX INTEGER (0..65535)
               ACCESS read-write
               STATUS mandatory
               DESCRIPTION
               "Sensing wire impedance per meter value times 100"
               ::= {  sensorWaterRopeEntry 101 }            
 
            sensorWaterRopeType OBJECT-TYPE
               SYNTAX  INTEGER {
                  custom(0),
                  water(1),
                  fuel(2)
               }
               ACCESS read-write
               STATUS mandatory
               DESCRIPTION
               "Water rope sensing cable type"
               ::= {  sensorWaterRopeEntry 103 }                
               
            sensorWaterRopeId OBJECT-TYPE
               SYNTAX  INTEGER
               ACCESS  read-only
               STATUS  mandatory
               DESCRIPTION
               "The Sensor ID of this sensor, used to identify which sensor it is in the system configuration."
               ::= { sensorWaterRopeEntry 1000 }

--/* End of sensorWaterRopeEntry */

--/* Begin of sensorPowerEntry */
         sensorPowerTable OBJECT-TYPE
            SYNTAX  SEQUENCE OF SensorPowerEntry
            ACCESS  not-accessible
            STATUS  mandatory
            DESCRIPTION
            "This table contains the property and reading value for every sensor."
            ::=  {  secSensor 22   }

         sensorPowerEntry OBJECT-TYPE
            SYNTAX  SensorPowerEntry
            ACCESS  not-accessible
            STATUS  mandatory
            DESCRIPTION
            "This is an entry in the sensorPowerEntry Table"
            INDEX         { sensorPowerIndex }
            ::=  {  sensorPowerTable 1 }

         SensorPowerEntry ::= SEQUENCE {
               sensorPowerIndex
                  INTEGER,
               sensorPowerDescription
                  DisplayString,
               sensorPowerValue
                  INTEGER,
               sensorPowerUnit
                  DisplayString,
               sensorPowerStatus
                  INTEGER,
               sensorPowerGoOffline
                  INTEGER,
               sensorPowerLowCritical
                  INTEGER,
               sensorPowerLowWarning
                  INTEGER,
               sensorPowerHighWarning
                  INTEGER,
               sensorPowerHighCritical
                  INTEGER,
               sensorPowerRearm
                  INTEGER,
               sensorPowerDelayError
                  INTEGER,
               sensorPowerDelayNormal
                  INTEGER,
               sensorPowerDelayLowCritical
                  INTEGER,
               sensorPowerDelayLowWarning
                  INTEGER,
               sensorPowerDelayHighWarning
                  INTEGER,
               sensorPowerDelayHighCritical
                  INTEGER,
               sensorPowerPort
                  INTEGER,
               sensorPowerSubPort
                  INTEGER,
               sensorPowerDeviceIndex
                  INTEGER,
               sensorPowerTimeOut
                  INTEGER,
               sensorPowerInterval
                  INTEGER,
               sensorPowerErrorRetryNum
                  INTEGER,
               sensorPowerMaxValue
                  INTEGER,
               sensorPowerMinValue
                  INTEGER,
               sensorPowerDisplayStyle
                  INTEGER,
               sensorPowerHighCriticalDesc 
                  DisplayString,
               sensorPowerLowCriticalDesc 
                  DisplayString,
               sensorPowerNormalDesc 
                  DisplayString,
               sensorPowerLowWarningDesc 
                  DisplayString,   
               sensorPowerHighWarningDesc 
                  DisplayString,
               sensorPowerSensorErrorDesc 
                  DisplayString,
               sensorPowerHighCriticalColor 
                  INTEGER,
               sensorPowerLowCriticalColor 
                  INTEGER,
               sensorPowerNormalColor 
                  INTEGER,
               sensorPowerLowWarningColor 
                  INTEGER,   
               sensorPowerHighWarningColor 
                  INTEGER,
               sensorPowerSensorErrorColor 
                  INTEGER,
               sensorPowerValueFormatString 
                  DisplayString,
               sensorPowerValueFormatFloat
                  Opaque,
               sensorPowerAcknowledge
                  INTEGER,
               sensorPowerId
                  INTEGER
            }

            sensorPowerIndex OBJECT-TYPE
               SYNTAX  INTEGER (1..65535)
               ACCESS  read-only
               STATUS  mandatory
               DESCRIPTION
               "The index into the Switch sensor table"
               ::=  {  sensorPowerEntry 1   }

            sensorPowerDescription OBJECT-TYPE
               SYNTAX  DisplayString
               ACCESS  read-write
               STATUS  mandatory
               DESCRIPTION
               "A Description of this sensor Switch"
               ::=  {  sensorPowerEntry 2   }

            sensorPowerValue OBJECT-TYPE
               SYNTAX  INTEGER
               ACCESS  read-only
               STATUS  mandatory
               DESCRIPTION
               "The reading value in this sensor"
               ::=  {  sensorPowerEntry 4   }

            sensorPowerUnit OBJECT-TYPE
               SYNTAX  DisplayString
               ACCESS  read-write
               STATUS  mandatory
               DESCRIPTION
               "The unit string"
               ::=  {  sensorPowerEntry 5  }

            sensorPowerStatus OBJECT-TYPE
               SYNTAX  INTEGER {
                  noStatus(1),
                  normal(2),
                  highCritical(4),
                  lowCritical(6),
                  sensorError(7)
               }
               ACCESS  read-only
               STATUS  mandatory
               DESCRIPTION
               "The current status of this Sensor, only input switches have a status"
               ::=  {  sensorPowerEntry 6  }

            sensorPowerGoOffline OBJECT-TYPE
               SYNTAX  INTEGER {
                  online(1),
                  goOffline(2)
               }
               ACCESS  read-write
               STATUS  mandatory
               DESCRIPTION
               "To take offline enter a 2"
               ::=  {  sensorPowerEntry 8  }

            sensorPowerLowCritical OBJECT-TYPE
               SYNTAX  INTEGER
               ACCESS  read-write
               STATUS  mandatory
               DESCRIPTION
               "How cold this sensor gets before it sends a critical event"
               ::=  {  sensorPowerEntry 9   }

            sensorPowerLowWarning OBJECT-TYPE
               SYNTAX  INTEGER
               ACCESS  read-write
               STATUS  mandatory
               DESCRIPTION
               "How cold this sensor gets before it sends a warning"
               ::=  {  sensorPowerEntry 10   }
   
            sensorPowerHighWarning OBJECT-TYPE
               SYNTAX  INTEGER
               ACCESS  read-write
               STATUS  mandatory
               DESCRIPTION
               "How hot this sensor gets before it sends a warning"
               ::=  {  sensorPowerEntry 11   }  

            sensorPowerHighCritical OBJECT-TYPE
               SYNTAX  INTEGER
               ACCESS  read-write
               STATUS  mandatory
               DESCRIPTION
               "How hot this sensor gets before it sends a critical event"
               ::=  {  sensorPowerEntry 12   }   

            sensorPowerRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorPowerEntry 13   }

            sensorPowerDelayError OBJECT-TYPE
               SYNTAX  INTEGER (0..65534)
               ACCESS  read-write
               STATUS  mandatory
               DESCRIPTION
               "Time in seconds after the sensor has been in error status before report as an error"
               ::=  {  sensorPowerEntry 14   }

            sensorPowerDelayNormal OBJECT-TYPE
               SYNTAX  INTEGER (0..65534)
               ACCESS  read-write
               STATUS  mandatory
               DESCRIPTION
               "Time in seconds after the sensor change from error to normal before report as normal"
               ::=  {  sensorPowerEntry 15   }

            sensorPowerDelayLowCritical OBJECT-TYPE
               SYNTAX INTEGER (0..65535)
               ACCESS read-write
               STATUS mandatory
               DESCRIPTION
               "Continuous time for this sensor to be in Low Critical before accepting new Status."
               ::= {  sensorPowerEntry 16 }
               
            sensorPowerDelayLowWarning OBJECT-TYPE
               SYNTAX INTEGER (0..65535)
               ACCESS read-write
               STATUS mandatory
               DESCRIPTION
               "Continuous time for this sensor to be in Low Warning before accepting new Status."
               ::= {  sensorPowerEntry 17 }

            sensorPowerDelayHighWarning OBJECT-TYPE
               SYNTAX INTEGER (0..65535)
               ACCESS read-write
               STATUS mandatory
               DESCRIPTION
               "Continuous time for this sensor to be in High Warning before accepting new Status."
               ::= {  sensorPowerEntry 18 }

            sensorPowerDelayHighCritical OBJECT-TYPE
               SYNTAX INTEGER (0..65535)
               ACCESS read-write
               STATUS mandatory
               DESCRIPTION
               "Continuous time for this sensor to be in High Critical before accepting new Status."
               ::= {  sensorPowerEntry 19 }

            sensorPowerPort OBJECT-TYPE
               SYNTAX  INTEGER (0..65534)
               ACCESS  read-only
               STATUS  mandatory
               DESCRIPTION
               "Sensor port"
               ::=  {  sensorPowerEntry 35 }

            sensorPowerSubPort OBJECT-TYPE
               SYNTAX  INTEGER (0..65534)
               ACCESS  read-only
               STATUS  mandatory
               DESCRIPTION
               "Sensor sub port"
               ::=  {  sensorPowerEntry 36 }

            sensorPowerDeviceIndex OBJECT-TYPE
               SYNTAX  INTEGER (0..65534)
               ACCESS  read-only
               STATUS  mandatory
               DESCRIPTION
               "Device Index of sensor"
               ::=  {  sensorPowerEntry 37 }

            sensorPowerTimeOut OBJECT-TYPE
               SYNTAX  INTEGER (5..30)
               ACCESS  read-write
               STATUS  mandatory
               DESCRIPTION
               "The polling timeout of Power Sensor."
               ::=  {  sensorPowerEntry 38 }

            sensorPowerInterval OBJECT-TYPE
               SYNTAX  INTEGER (5..720)
               ACCESS  read-write
               STATUS  mandatory
               DESCRIPTION
               "The polling interval of Power Sensor."
               ::=  {  sensorPowerEntry 39 }

            sensorPowerErrorRetryNum OBJECT-TYPE
               SYNTAX  INTEGER
               ACCESS  read-write
               STATUS  mandatory
               DESCRIPTION
               "Number of retry before error."
               ::=  {  sensorPowerEntry 40 }
               
            sensorPowerMaxValue OBJECT-TYPE
               SYNTAX  INTEGER
               ACCESS  read-write
               STATUS  mandatory
               DESCRIPTION
               "The maximum scale of Power value."
               ::=  {  sensorPowerEntry 41   }

            sensorPowerMinValue OBJECT-TYPE
               SYNTAX  INTEGER
               ACCESS  read-write
               STATUS  mandatory
               DESCRIPTION
               "The minimum scale of Power value."
               ::=  {  sensorPowerEntry 42   }
               
            sensorPowerDisplayStyle OBJECT-TYPE
               SYNTAX  INTEGER {
                  basic(0),
                  gauge(1)
               }
               ACCESS  read-write
               STATUS  mandatory
               DESCRIPTION
               "Power display style."
               ::=  {  sensorPowerEntry 45 } 
               
            sensorPowerHighCriticalDesc OBJECT-TYPE
               SYNTAX  DisplayString
               ACCESS  read-write
               STATUS  mandatory
               DESCRIPTION
               "A HighCritical Description of this sensor"
               ::=  {  sensorPowerEntry  46  }               

            sensorPowerLowCriticalDesc OBJECT-TYPE
               SYNTAX  DisplayString
               ACCESS  read-write
               STATUS  mandatory
               DESCRIPTION
               "A LowCritical Description of this sensor"
               ::=  {  sensorPowerEntry  47  }

            sensorPowerNormalDesc OBJECT-TYPE
               SYNTAX  DisplayString
               ACCESS  read-write
               STATUS  mandatory
               DESCRIPTION
               "A Normal Description of this sensor"
               ::=  {  sensorPowerEntry  48  }
               
            sensorPowerLowWarningDesc OBJECT-TYPE
               SYNTAX  DisplayString
               ACCESS  read-write
               STATUS  mandatory
               DESCRIPTION
               "A LowWarning Description of this sensor"
               ::=  {  sensorPowerEntry  49  }
               
            sensorPowerHighWarningDesc OBJECT-TYPE
               SYNTAX  DisplayString
               ACCESS  read-write
               STATUS  mandatory
               DESCRIPTION
               "A HighWarning Description of this sensor"
               ::=  {  sensorPowerEntry  50  }
               
            sensorPowerSensorErrorDesc OBJECT-TYPE
               SYNTAX  DisplayString
               ACCESS  read-write
               STATUS  mandatory
               DESCRIPTION
               "A SensorError Description of this sensor"
               ::=  {  sensorPowerEntry  51  }  

            sensorPowerHighCriticalColor OBJECT-TYPE
               SYNTAX  INTEGER
               ACCESS  read-write
               STATUS  mandatory
               DESCRIPTION
               "A HighCritical Color of this sensor"
               ::=  {  sensorPowerEntry   54 }               

            sensorPowerLowCriticalColor OBJECT-TYPE
               SYNTAX  INTEGER
               ACCESS  read-write
               STATUS  mandatory
               DESCRIPTION
               "A LowCritical Color of this sensor"
               ::=  {  sensorPowerEntry  55  }

            sensorPowerNormalColor OBJECT-TYPE
               SYNTAX  INTEGER
               ACCESS  read-write
               STATUS  mandatory
               DESCRIPTION
               "A Normal Color of this sensor"
               ::=  {  sensorPowerEntry  56  }
               
            sensorPowerLowWarningColor OBJECT-TYPE
               SYNTAX  INTEGER
               ACCESS  read-write
               STATUS  mandatory
               DESCRIPTION
               "A LowWarning Color of this sensor"
               ::=  {  sensorPowerEntry  57  }
               
            sensorPowerHighWarningColor OBJECT-TYPE
               SYNTAX  INTEGER
               ACCESS  read-write
               STATUS  mandatory
               DESCRIPTION
               "A HighWarning Color of this sensor"
               ::=  {  sensorPowerEntry  58  }
               
            sensorPowerSensorErrorColor OBJECT-TYPE
               SYNTAX  INTEGER
               ACCESS  read-write
               STATUS  mandatory
               DESCRIPTION
               "A SensorError Color of this sensor"
               ::=  {  sensorPowerEntry  59  }

            sensorPowerValueFormatString OBJECT-TYPE
               SYNTAX  DisplayString
               ACCESS  read-only
               STATUS  mandatory
               DESCRIPTION
               "The string-based reading value in this sensor"
               ::=  {  sensorPowerEntry  66  }

            sensorPowerValueFormatFloat OBJECT-TYPE
               SYNTAX  Opaque (SIZE(4))
               ACCESS  read-only
               STATUS  mandatory
               DESCRIPTION
               "The floating-point IEEE Standard 754 reading value in this sensor"
               ::=  {  sensorPowerEntry  67  }

            sensorPowerAcknowledge OBJECT-TYPE
               SYNTAX  INTEGER {
                  acked(2)
               }
               ACCESS  read-write
               STATUS  mandatory
               DESCRIPTION
               "Power sensor acknowledge"
               ::=  {  sensorPowerEntry 70 }

            sensorPowerId OBJECT-TYPE
               SYNTAX  INTEGER
               ACCESS  read-only
               STATUS  mandatory
               DESCRIPTION
               "The Sensor ID of this sensor, used to identify which sensor it is in the system configuration."
               ::= { sensorPowerEntry 1000 }

--/* End of sensorPowerEntry */

--/* Begin of sensorFuelEntry */
         sensorFuelTable OBJECT-TYPE
            SYNTAX  SEQUENCE OF SensorFuelEntry
            ACCESS  not-accessible
            STATUS  mandatory
            DESCRIPTION
            "This table contains the property and reading value for every sensor."
            ::=  {  secSensor 24   }

         sensorFuelEntry OBJECT-TYPE
            SYNTAX  SensorFuelEntry
            ACCESS  not-accessible
            STATUS  mandatory
            DESCRIPTION
            "This is an entry in the SensorFuelEntry Table"
            INDEX         { sensorFuelIndex }
            ::=  {  sensorFuelTable 1 }

         SensorFuelEntry ::= SEQUENCE {
               sensorFuelIndex
                  INTEGER,
               sensorFuelDescription
                  DisplayString,
               sensorFuelValue
                  INTEGER,
               sensorFuelUnit
                  DisplayString,
               sensorFuelStatus
                  INTEGER,
               sensorFuelGoOffline
                  INTEGER,
               sensorFuelLowCritical
                  INTEGER,
               sensorFuelLowWarning
                  INTEGER,
               sensorFuelHighWarning
                  INTEGER,
               sensorFuelHighCritical
                  INTEGER,
               sensorFuelRearm
                  INTEGER,
               sensorFuelDelayError
                  INTEGER,
               sensorFuelDelayNormal
                  INTEGER,
               sensorFuelDelayLowCritical
                  INTEGER,
               sensorFuelDelayLowWarning
                  INTEGER,
               sensorFuelDelayHighWarning
                  INTEGER,
               sensorFuelDelayHighCritical
                  INTEGER,
               sensorFuelRaw
                  INTEGER,
               sensorFuelAmountMaxValue
                  INTEGER,
               sensorFuelAmountBaseValue
                  INTEGER,
               sensorFuelDeviceIndex
                  INTEGER,
               sensorFuelDisplayStyle
                  INTEGER,
               sensorFuelHighCriticalDesc 
                  DisplayString,
               sensorFuelLowCriticalDesc 
                  DisplayString,
               sensorFuelNormalDesc 
                  DisplayString,
               sensorFuelLowWarningDesc 
                  DisplayString,   
               sensorFuelHighWarningDesc 
                  DisplayString,
               sensorFuelSensorErrorDesc 
                  DisplayString,
               sensorFuelHighCriticalColor 
                  INTEGER,
               sensorFuelLowCriticalColor 
                  INTEGER,
               sensorFuelNormalColor 
                  INTEGER,
               sensorFuelLowWarningColor 
                  INTEGER,   
               sensorFuelHighWarningColor 
                  INTEGER,
               sensorFuelSensorErrorColor 
                  INTEGER,           
               sensorFuelAcknowledge
                  INTEGER,
               sensorFuelId
                  INTEGER
            }

            sensorFuelIndex OBJECT-TYPE
               SYNTAX  INTEGER (1..65535)
               ACCESS  read-only
               STATUS  mandatory
               DESCRIPTION
               "The index into the sensor table"
               ::=  {  sensorFuelEntry 1   }

            sensorFuelDescription OBJECT-TYPE
               SYNTAX  DisplayString
               ACCESS  read-write
               STATUS  mandatory
               DESCRIPTION
               "A Description of this sensor"
               ::=  {  sensorFuelEntry 2   }

            sensorFuelValue OBJECT-TYPE
               SYNTAX  INTEGER
               ACCESS  read-only
               STATUS  mandatory
               DESCRIPTION
               "The reading value in this sensor"
               ::=  {  sensorFuelEntry 4   }

            sensorFuelUnit OBJECT-TYPE
               SYNTAX  DisplayString
               ACCESS  read-write
               STATUS  mandatory
               DESCRIPTION
               "The unit string"
               ::=  {  sensorFuelEntry 5  }

            sensorFuelStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorFuelEntry 6   }

            sensorFuelGoOffline OBJECT-TYPE
               SYNTAX  INTEGER {
                  online(1),
                  goOffline(2)
               }
               ACCESS  read-write
               STATUS  mandatory
               DESCRIPTION
               "To take offline enter a 2"
               ::=  {  sensorFuelEntry 8   }

            sensorFuelLowCritical OBJECT-TYPE
               SYNTAX  INTEGER
               ACCESS  read-write
               STATUS  mandatory
               DESCRIPTION
               "Level value of this sensor gets before it sends a critical event"
               ::=  {  sensorFuelEntry 9   }

            sensorFuelLowWarning OBJECT-TYPE
               SYNTAX  INTEGER
               ACCESS  read-write
               STATUS  mandatory
               DESCRIPTION
               "Level value of this sensor gets before it sends a warning"
               ::=  {  sensorFuelEntry 10   }
   
            sensorFuelHighWarning OBJECT-TYPE
               SYNTAX  INTEGER
               ACCESS  read-write
               STATUS  mandatory
               DESCRIPTION
               "Level value of this sensor gets before it sends a warning"
               ::=  {  sensorFuelEntry 11   }  

            sensorFuelHighCritical OBJECT-TYPE
               SYNTAX  INTEGER
               ACCESS  read-write
               STATUS  mandatory
               DESCRIPTION
               "Level value of this sensor gets before it sends a critical event"
               ::=  {  sensorFuelEntry 12   }   

            sensorFuelRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorFuelEntry 13   }

            sensorFuelDelayError OBJECT-TYPE
               SYNTAX  INTEGER (0..65534)
               ACCESS  read-write
               STATUS  mandatory
               DESCRIPTION
               "Time in seconds after the sensor has been in error status before report as an error"
               ::=  {  sensorFuelEntry 14   }

            sensorFuelDelayNormal OBJECT-TYPE
               SYNTAX  INTEGER (0..65534)
               ACCESS  read-write
               STATUS  mandatory
               DESCRIPTION
               "Time in seconds after the sensor change from error to normal before report as normal"
               ::=  {  sensorFuelEntry 15   }

            sensorFuelDelayLowCritical OBJECT-TYPE
               SYNTAX INTEGER (0..65535)
               ACCESS read-write
               STATUS mandatory
               DESCRIPTION
               "Continuous time for this sensor to be in Low Critical before accepting new Status."
               ::= {  sensorFuelEntry 16 }
               
            sensorFuelDelayLowWarning OBJECT-TYPE
               SYNTAX INTEGER (0..65535)
               ACCESS read-write
               STATUS mandatory
               DESCRIPTION
               "Continuous time for this sensor to be in Low Warning before accepting new Status."
               ::= {  sensorFuelEntry 17 }

            sensorFuelDelayHighWarning OBJECT-TYPE
               SYNTAX INTEGER (0..65535)
               ACCESS read-write
               STATUS mandatory
               DESCRIPTION
               "Continuous time for this sensor to be in High Warning before accepting new Status."
               ::= {  sensorFuelEntry 18 }

            sensorFuelDelayHighCritical OBJECT-TYPE
               SYNTAX INTEGER (0..65535)
               ACCESS read-write
               STATUS mandatory
               DESCRIPTION
               "Continuous time for this sensor to be in High Critical before accepting new Status."
               ::= {  sensorFuelEntry 19 }

            sensorFuelRaw OBJECT-TYPE
               SYNTAX  INTEGER 
               ACCESS  read-only
               STATUS  mandatory
               DESCRIPTION
               "The unformatted, raw, A/D value in this sensor. Contains more resolution than the formated percentage."
               ::=  {  sensorFuelEntry 20   }

            sensorFuelAmountMaxValue OBJECT-TYPE
               SYNTAX  INTEGER
               ACCESS  read-write
               STATUS  mandatory
               DESCRIPTION
               "The maximum scale of value conversion."
               ::=  {  sensorFuelEntry 33   }

            sensorFuelAmountBaseValue OBJECT-TYPE
               SYNTAX  INTEGER
               ACCESS  read-write
               STATUS  mandatory
               DESCRIPTION
               "The base scale of value conversion."
               ::=  {  sensorFuelEntry 34   }

            sensorFuelDeviceIndex OBJECT-TYPE
               SYNTAX  INTEGER (0..65534)
               ACCESS  read-only
               STATUS  mandatory
               DESCRIPTION
               "Device Index of sensor"
               ::=  {  sensorFuelEntry 37 }
               
            sensorFuelDisplayStyle OBJECT-TYPE
               SYNTAX  INTEGER {
                  basic(0),
                  gauge(1)
               }
               ACCESS  read-write
               STATUS  mandatory
               DESCRIPTION
               "Fuel display style"
               ::=  {  sensorFuelEntry 45 }     

            sensorFuelHighCriticalDesc OBJECT-TYPE
               SYNTAX  DisplayString
               ACCESS  read-write
               STATUS  mandatory
               DESCRIPTION
               "A HighCritical Description of this sensor"
               ::=  {  sensorFuelEntry  46  }               

            sensorFuelLowCriticalDesc OBJECT-TYPE
               SYNTAX  DisplayString
               ACCESS  read-write
               STATUS  mandatory
               DESCRIPTION
               "A LowCritical Description of this sensor"
               ::=  {  sensorFuelEntry  47  }

            sensorFuelNormalDesc OBJECT-TYPE
               SYNTAX  DisplayString
               ACCESS  read-write
               STATUS  mandatory
               DESCRIPTION
               "A Normal Description of this sensor"
               ::=  {  sensorFuelEntry  48  }
               
            sensorFuelLowWarningDesc OBJECT-TYPE
               SYNTAX  DisplayString
               ACCESS  read-write
               STATUS  mandatory
               DESCRIPTION
               "A LowWarning Description of this sensor"
               ::=  {  sensorFuelEntry  49  }
               
            sensorFuelHighWarningDesc OBJECT-TYPE
               SYNTAX  DisplayString
               ACCESS  read-write
               STATUS  mandatory
               DESCRIPTION
               "A HighWarning Description of this sensor"
               ::=  {  sensorFuelEntry  50  }
               
            sensorFuelSensorErrorDesc OBJECT-TYPE
               SYNTAX  DisplayString
               ACCESS  read-write
               STATUS  mandatory
               DESCRIPTION
               "A SensorError Description of this sensor"
               ::=  {  sensorFuelEntry  51  }  

            sensorFuelHighCriticalColor OBJECT-TYPE
               SYNTAX  INTEGER
               ACCESS  read-write
               STATUS  mandatory
               DESCRIPTION
               "A HighCritical Color of this sensor"
               ::=  {  sensorFuelEntry  54  }               

            sensorFuelLowCriticalColor OBJECT-TYPE
               SYNTAX  INTEGER
               ACCESS  read-write
               STATUS  mandatory
               DESCRIPTION
               "A LowCritical Color of this sensor"
               ::=  {  sensorFuelEntry  55  }

            sensorFuelNormalColor OBJECT-TYPE
               SYNTAX  INTEGER
               ACCESS  read-write
               STATUS  mandatory
               DESCRIPTION
               "A Normal Color of this sensor"
               ::=  {  sensorFuelEntry  56  }
               
            sensorFuelLowWarningColor OBJECT-TYPE
               SYNTAX  INTEGER
               ACCESS  read-write
               STATUS  mandatory
               DESCRIPTION
               "A LowWarning Color of this sensor"
               ::=  {  sensorFuelEntry  57  }
               
            sensorFuelHighWarningColor OBJECT-TYPE
               SYNTAX  INTEGER
               ACCESS  read-write
               STATUS  mandatory
               DESCRIPTION
               "A HighWarning Color of this sensor"
               ::=  {  sensorFuelEntry  58  }
               
            sensorFuelSensorErrorColor OBJECT-TYPE
               SYNTAX  INTEGER
               ACCESS  read-write
               STATUS  mandatory
               DESCRIPTION
               "A SensorError Color of this sensor"
               ::=  {  sensorFuelEntry  59  }    

            sensorFuelAcknowledge OBJECT-TYPE
               SYNTAX  INTEGER {
                  acked(2)
               }
               ACCESS  read-write
               STATUS  mandatory
               DESCRIPTION
               "Fuel sensor acknowledge"
               ::=  {  sensorFuelEntry 70 }

            sensorFuelId OBJECT-TYPE
               SYNTAX  INTEGER
               ACCESS  read-only
               STATUS  mandatory
               DESCRIPTION
               "The Sensor ID of this sensor, used to identify which sensor it is in the system configuration."
               ::= { sensorFuelEntry 1000 }

--/* End of sensorFuelEntry */

--/* Begin of sensorTankSenderEntry */
         sensorTankSenderTable OBJECT-TYPE
            SYNTAX  SEQUENCE OF SensorTankSenderEntry
            ACCESS  not-accessible
            STATUS  mandatory
            DESCRIPTION
            "This table contains the property and reading value for every sensor."
            ::=  {  secSensor 26   }

         sensorTankSenderEntry OBJECT-TYPE
            SYNTAX  SensorTankSenderEntry
            ACCESS  not-accessible
            STATUS  mandatory
            DESCRIPTION
            "This is an entry in the sensorTankSenderEntry Table"
            INDEX         { sensorTankSenderIndex }
            ::=  {  sensorTankSenderTable 1 }

         SensorTankSenderEntry ::= SEQUENCE {
               sensorTankSenderIndex
                  INTEGER,
               sensorTankSenderDescription
                  DisplayString,
               sensorTankSenderValue
                  INTEGER,
               sensorTankSenderUnit
                  DisplayString,
               sensorTankSenderStatus
                  INTEGER,
               sensorTankSenderGoOffline
                  INTEGER,
               sensorTankSenderLowCritical
                  INTEGER,
               sensorTankSenderLowWarning
                  INTEGER,
               sensorTankSenderHighWarning
                  INTEGER,
               sensorTankSenderHighCritical
                  INTEGER,
               sensorTankSenderRearm
                  INTEGER,
               sensorTankSenderDelayError
                  INTEGER,
               sensorTankSenderDelayNormal
                  INTEGER,
               sensorTankSenderDelayLowCritical
                  INTEGER,
               sensorTankSenderDelayLowWarning
                  INTEGER,
               sensorTankSenderDelayHighWarning
                  INTEGER,
               sensorTankSenderDelayHighCritical
                  INTEGER,
               sensorTankSenderRaw
                  INTEGER,
               sensorTankSenderDeviceIndex
                  INTEGER,
               sensorTankSenderDisplayStyle
                  INTEGER,
               sensorTankSenderHighCriticalDesc 
                  DisplayString,
               sensorTankSenderLowCriticalDesc 
                  DisplayString,
               sensorTankSenderNormalDesc 
                  DisplayString,
               sensorTankSenderLowWarningDesc 
                  DisplayString,   
               sensorTankSenderHighWarningDesc 
                  DisplayString,
               sensorTankSenderSensorErrorDesc 
                  DisplayString,
               sensorTankSenderHighCriticalColor 
                  INTEGER,
               sensorTankSenderLowCriticalColor 
                  INTEGER,
               sensorTankSenderNormalColor 
                  INTEGER,
               sensorTankSenderLowWarningColor 
                  INTEGER,   
               sensorTankSenderHighWarningColor 
                  INTEGER,
               sensorTankSenderSensorErrorColor 
                  INTEGER,
               sensorTankSenderAcknowledge
                  INTEGER,
               sensorTankSenderId
                  INTEGER
            }

            sensorTankSenderIndex OBJECT-TYPE
               SYNTAX  INTEGER (1..65535)
               ACCESS  read-only
               STATUS  mandatory
               DESCRIPTION
               "The index into the sensor table"
               ::=  {  sensorTankSenderEntry 1   }

            sensorTankSenderDescription OBJECT-TYPE
               SYNTAX  DisplayString
               ACCESS  read-write
               STATUS  mandatory
               DESCRIPTION
               "A Description of this sensor"
               ::=  {  sensorTankSenderEntry 2   }

            sensorTankSenderValue OBJECT-TYPE
               SYNTAX  INTEGER
               ACCESS  read-only
               STATUS  mandatory
               DESCRIPTION
               "The reading value in this sensor"
               ::=  {  sensorTankSenderEntry 4   }

            sensorTankSenderUnit OBJECT-TYPE
               SYNTAX  DisplayString
               ACCESS  read-write
               STATUS  mandatory
               DESCRIPTION
               "The unit string"
               ::=  {  sensorTankSenderEntry 5  }

            sensorTankSenderStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorTankSenderEntry 6   }

            sensorTankSenderGoOffline OBJECT-TYPE
               SYNTAX  INTEGER {
                  online(1),
                  goOffline(2)
               }
               ACCESS  read-write
               STATUS  mandatory
               DESCRIPTION
               "To take offline enter a 2"
               ::=  {  sensorTankSenderEntry 8   }

            sensorTankSenderLowCritical OBJECT-TYPE
               SYNTAX  INTEGER
               ACCESS  read-write
               STATUS  mandatory
               DESCRIPTION
               "Level value of this sensor gets before it sends a critical event"
               ::=  {  sensorTankSenderEntry 9   }

            sensorTankSenderLowWarning OBJECT-TYPE
               SYNTAX  INTEGER
               ACCESS  read-write
               STATUS  mandatory
               DESCRIPTION
               "Level value of this sensor gets before it sends a warning"
               ::=  {  sensorTankSenderEntry 10   }
   
            sensorTankSenderHighWarning OBJECT-TYPE
               SYNTAX  INTEGER
               ACCESS  read-write
               STATUS  mandatory
               DESCRIPTION
               "Level value of this sensor gets before it sends a warning"
               ::=  {  sensorTankSenderEntry 11   }  

            sensorTankSenderHighCritical OBJECT-TYPE
               SYNTAX  INTEGER
               ACCESS  read-write
               STATUS  mandatory
               DESCRIPTION
               "Level value of this sensor gets before it sends a critical event"
               ::=  {  sensorTankSenderEntry 12   }   

            sensorTankSenderRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorTankSenderEntry 13   }

            sensorTankSenderDelayError OBJECT-TYPE
               SYNTAX  INTEGER (0..65534)
               ACCESS  read-write
               STATUS  mandatory
               DESCRIPTION
               "Time in seconds after the sensor has been in error status before report as an error"
               ::=  {  sensorTankSenderEntry 14   }

            sensorTankSenderDelayNormal OBJECT-TYPE
               SYNTAX  INTEGER (0..65534)
               ACCESS  read-write
               STATUS  mandatory
               DESCRIPTION
               "Time in seconds after the sensor change from error to normal before report as normal"
               ::=  {  sensorTankSenderEntry 15   }

            sensorTankSenderDelayLowCritical OBJECT-TYPE
               SYNTAX INTEGER (0..65535)
               ACCESS read-write
               STATUS mandatory
               DESCRIPTION
               "Continuous time for this sensor to be in Low Critical before accepting new Status."
               ::= {  sensorTankSenderEntry 16 }
               
            sensorTankSenderDelayLowWarning OBJECT-TYPE
               SYNTAX INTEGER (0..65535)
               ACCESS read-write
               STATUS mandatory
               DESCRIPTION
               "Continuous time for this sensor to be in Low Warning before accepting new Status."
               ::= {  sensorTankSenderEntry 17 }

            sensorTankSenderDelayHighWarning OBJECT-TYPE
               SYNTAX INTEGER (0..65535)
               ACCESS read-write
               STATUS mandatory
               DESCRIPTION
               "Continuous time for this sensor to be in High Warning before accepting new Status."
               ::= {  sensorTankSenderEntry 18 }

            sensorTankSenderDelayHighCritical OBJECT-TYPE
               SYNTAX INTEGER (0..65535)
               ACCESS read-write
               STATUS mandatory
               DESCRIPTION
               "Continuous time for this sensor to be in High Critical before accepting new Status."
               ::= {  sensorTankSenderEntry 19 }

            sensorTankSenderRaw OBJECT-TYPE
               SYNTAX  INTEGER 
               ACCESS  read-only
               STATUS  mandatory
               DESCRIPTION
               "The unformatted, raw, A/D value in this sensor. Contains more resolution than the formated percentage."
               ::=  {  sensorTankSenderEntry 20   }

            sensorTankSenderDeviceIndex OBJECT-TYPE
               SYNTAX  INTEGER (0..65534)
               ACCESS  read-only
               STATUS  mandatory
               DESCRIPTION
               "Device Index of sensor"
               ::=  {  sensorTankSenderEntry 37 }
               
            sensorTankSenderDisplayStyle OBJECT-TYPE
               SYNTAX  INTEGER {
                  basic(0),
                  gauge(1)
               }
               ACCESS  read-write
               STATUS  mandatory
               DESCRIPTION
               "TankSender display style"
               ::=  {  sensorTankSenderEntry 45 }     

            sensorTankSenderHighCriticalDesc OBJECT-TYPE
               SYNTAX  DisplayString
               ACCESS  read-write
               STATUS  mandatory
               DESCRIPTION
               "A HighCritical Description of this sensor"
               ::=  {  sensorTankSenderEntry  46  }               

            sensorTankSenderLowCriticalDesc OBJECT-TYPE
               SYNTAX  DisplayString
               ACCESS  read-write
               STATUS  mandatory
               DESCRIPTION
               "A LowCritical Description of this sensor"
               ::=  {  sensorTankSenderEntry  47  }

            sensorTankSenderNormalDesc OBJECT-TYPE
               SYNTAX  DisplayString
               ACCESS  read-write
               STATUS  mandatory
               DESCRIPTION
               "A Normal Description of this sensor"
               ::=  {  sensorTankSenderEntry  48  }
               
            sensorTankSenderLowWarningDesc OBJECT-TYPE
               SYNTAX  DisplayString
               ACCESS  read-write
               STATUS  mandatory
               DESCRIPTION
               "A LowWarning Description of this sensor"
               ::=  {  sensorTankSenderEntry  49  }
               
            sensorTankSenderHighWarningDesc OBJECT-TYPE
               SYNTAX  DisplayString
               ACCESS  read-write
               STATUS  mandatory
               DESCRIPTION
               "A HighWarning Description of this sensor"
               ::=  {  sensorTankSenderEntry  50  }
               
            sensorTankSenderSensorErrorDesc OBJECT-TYPE
               SYNTAX  DisplayString
               ACCESS  read-write
               STATUS  mandatory
               DESCRIPTION
               "A SensorError Description of this sensor"
               ::=  {  sensorTankSenderEntry  51  }  

            sensorTankSenderHighCriticalColor OBJECT-TYPE
               SYNTAX  INTEGER
               ACCESS  read-write
               STATUS  mandatory
               DESCRIPTION
               "A HighCritical Color of this sensor"
               ::=  {  sensorTankSenderEntry  54  }               

            sensorTankSenderLowCriticalColor OBJECT-TYPE
               SYNTAX  INTEGER
               ACCESS  read-write
               STATUS  mandatory
               DESCRIPTION
               "A LowCritical Color of this sensor"
               ::=  {  sensorTankSenderEntry  55  }

            sensorTankSenderNormalColor OBJECT-TYPE
               SYNTAX  INTEGER
               ACCESS  read-write
               STATUS  mandatory
               DESCRIPTION
               "A Normal Color of this sensor"
               ::=  {  sensorTankSenderEntry  56  }
               
            sensorTankSenderLowWarningColor OBJECT-TYPE
               SYNTAX  INTEGER
               ACCESS  read-write
               STATUS  mandatory
               DESCRIPTION
               "A LowWarning Color of this sensor"
               ::=  {  sensorTankSenderEntry  57  }
               
            sensorTankSenderHighWarningColor OBJECT-TYPE
               SYNTAX  INTEGER
               ACCESS  read-write
               STATUS  mandatory
               DESCRIPTION
               "A HighWarning Color of this sensor"
               ::=  {  sensorTankSenderEntry  58  }
               
            sensorTankSenderSensorErrorColor OBJECT-TYPE
               SYNTAX  INTEGER
               ACCESS  read-write
               STATUS  mandatory
               DESCRIPTION
               "A SensorError Color of this sensor"
               ::=  {  sensorTankSenderEntry  59  }    

            sensorTankSenderAcknowledge OBJECT-TYPE
               SYNTAX  INTEGER {
                  acked(2)
               }
               ACCESS  read-write
               STATUS  mandatory
               DESCRIPTION
               "Tank Sender sensor acknowledge"
               ::=  {  sensorTankSenderEntry 70 }

            sensorTankSenderId OBJECT-TYPE
               SYNTAX  INTEGER
               ACCESS  read-only
               STATUS  mandatory
               DESCRIPTION
               "The Sensor ID of this sensor, used to identify which sensor it is in the system configuration."
               ::= { sensorTankSenderEntry 1000 }

--/* End of sensorTankSenderEntry */

--/* Begin of sensorDoorEntry */
         sensorDoorTable OBJECT-TYPE
            SYNTAX  SEQUENCE OF SensorDoorEntry
            ACCESS  not-accessible
            STATUS  mandatory
            DESCRIPTION
            "This table contains the property and reading value for every sensor."
            ::=  {  secSensor 27   }

         sensorDoorEntry OBJECT-TYPE
            SYNTAX  SensorDoorEntry
            ACCESS  not-accessible
            STATUS  mandatory
            DESCRIPTION
            "This is an entry in the sensorDoorEntry Table"
            INDEX         { sensorDoorIndex }
            ::=  {  sensorDoorTable 1 }

         SensorDoorEntry ::= SEQUENCE {
               sensorDoorIndex
                  INTEGER,
               sensorDoorDescription
                  DisplayString,
               sensorDoorValue
                  INTEGER,
               sensorDoorStatus
                  INTEGER,
               sensorDoorUnlockPeriod
                  INTEGER,
               sensorDoorOpenPeriod
                  INTEGER,
               sensorDoorCmd
                  INTEGER,
               sensorDoorAcknowledge
                  INTEGER,
               sensorDoorId
                  INTEGER
            }

            sensorDoorIndex OBJECT-TYPE
               SYNTAX  INTEGER (1..65535)
               ACCESS  read-only
               STATUS  mandatory
               DESCRIPTION
               "The index into the sensor table"
               ::=  {  sensorDoorEntry 1   }

            sensorDoorDescription OBJECT-TYPE
               SYNTAX  DisplayString
               ACCESS  read-write
               STATUS  mandatory
               DESCRIPTION
               "A Description of this sensor"
               ::=  {  sensorDoorEntry 2   }

            sensorDoorValue OBJECT-TYPE
               SYNTAX  INTEGER
               ACCESS  read-only
               STATUS  mandatory
               DESCRIPTION
               "The reading value in this sensor"
               ::=  {  sensorDoorEntry 4   }

            sensorDoorStatus OBJECT-TYPE
               SYNTAX  INTEGER {
                  noStatus(1),
                  closed(2),
                  heldOpen(3),
                  fire(4),
                  opened(5),
                  forceOpened(6),
                  sensorError(7)
               }
               ACCESS  read-only
               STATUS  mandatory
               DESCRIPTION
               "The current status of this Sensor"
               ::=  {  sensorDoorEntry 6   }

            sensorDoorUnlockPeriod OBJECT-TYPE
               SYNTAX  INTEGER
               ACCESS  read-write
               STATUS  mandatory
               DESCRIPTION
               "Door unlock period"
               ::=  {  sensorDoorEntry 62   }

            sensorDoorOpenPeriod OBJECT-TYPE
               SYNTAX  INTEGER
               ACCESS  read-write
               STATUS  mandatory
               DESCRIPTION
               "Door open period"
               ::=  {  sensorDoorEntry 63   }
   
            sensorDoorCmd OBJECT-TYPE
               SYNTAX  INTEGER
               ACCESS  read-write
               STATUS  mandatory
               DESCRIPTION
               "Door command"
               ::=  {  sensorDoorEntry 64   }  

            sensorDoorAcknowledge OBJECT-TYPE
               SYNTAX  INTEGER {
                  acked(2)
               }
               ACCESS  read-write
               STATUS  mandatory
               DESCRIPTION
               "Door sensor acknowledge"
               ::=  {  sensorDoorEntry 70 }  

            sensorDoorId OBJECT-TYPE
               SYNTAX  INTEGER
               ACCESS  read-only
               STATUS  mandatory
               DESCRIPTION
               "The Sensor ID of this sensor, used to identify which sensor it is in the system configuration."
               ::= { sensorDoorEntry 1000 }

--/* End of sensorDoorEntry */

--/* Begin of sensorTemperatureArrayEntry */
         sensorTemperatureArrayTable OBJECT-TYPE
            SYNTAX  SEQUENCE OF SensorTemperatureArrayEntry
            ACCESS  not-accessible
            STATUS  mandatory
            DESCRIPTION
            "This table contains the property and reading value for every Temperature sensor."
            ::=  {  secSensor 28  }

         sensorTemperatureArrayEntry OBJECT-TYPE
            SYNTAX  SensorTemperatureArrayEntry
            ACCESS  not-accessible
            STATUS  mandatory
            DESCRIPTION
            "This is an entry in the sensorTemperatureArrayEntry Table"
            INDEX         { sensorTemperatureArrayIndex }
            ::=  {  sensorTemperatureArrayTable 1 }

         SensorTemperatureArrayEntry ::= SEQUENCE {
               sensorTemperatureArrayIndex
                  INTEGER,
               sensorTemperatureArrayDescription
                  DisplayString,
               sensorTemperatureArrayType
                  INTEGER,
               sensorTemperatureArrayDegree
                  INTEGER,
               sensorTemperatureArrayUnit
                  DisplayString,               
               sensorTemperatureArrayStatus
                  INTEGER,
               sensorTemperatureArrayGoOffline
                  INTEGER,
               sensorTemperatureArrayLowCritical
                  INTEGER,
               sensorTemperatureArrayLowWarning
                  INTEGER,
               sensorTemperatureArrayHighWarning
                  INTEGER,
               sensorTemperatureArrayHighCritical
                  INTEGER,
               sensorTemperatureArrayRearm
                  INTEGER,
               sensorTemperatureArrayDelayError
                  INTEGER,
               sensorTemperatureArrayDelayNormal
                  INTEGER,
               sensorTemperatureArrayDelayLowCritical
                  INTEGER,
               sensorTemperatureArrayDelayLowWarning
                  INTEGER,
               sensorTemperatureArrayDelayHighWarning
                  INTEGER,
               sensorTemperatureArrayDelayHighCritical
                  INTEGER,
               sensorTemperatureArrayRaw
                  INTEGER,
               sensorTemperatureArrayOffset
                  INTEGER,
               sensorTemperatureArrayPort
                  INTEGER,
               sensorTemperatureArraySubPort
                  INTEGER,
               sensorTemperatureArrayDeviceIndex
                  INTEGER,
               sensorTemperatureArrayDisplayStyle
                  INTEGER,
               sensorTemperatureArrayHighCriticalDesc 
                  DisplayString,
               sensorTemperatureArrayLowCriticalDesc 
                  DisplayString,
               sensorTemperatureArrayNormalDesc 
                  DisplayString,
               sensorTemperatureArrayLowWarningDesc 
                  DisplayString,   
               sensorTemperatureArrayHighWarningDesc 
                  DisplayString,
               sensorTemperatureArraySensorErrorDesc 
                  DisplayString,
               sensorTemperatureArrayHighCriticalColor 
                  INTEGER,
               sensorTemperatureArrayLowCriticalColor 
                  INTEGER,
               sensorTemperatureArrayNormalColor 
                  INTEGER,
               sensorTemperatureArrayLowWarningColor 
                  INTEGER,   
               sensorTemperatureArrayHighWarningColor 
                  INTEGER,
               sensorTemperatureArraySensorErrorColor 
                  INTEGER,                 
               sensorTemperatureArrayAcknowledge
                  INTEGER,
               sensorTemperatureArraySerialNumber
                  DisplayString,
               sensorTemperatureArrayId
                  INTEGER
            }

            sensorTemperatureArrayIndex OBJECT-TYPE
               SYNTAX  INTEGER (1..65535)
               ACCESS  read-only
               STATUS  mandatory
               DESCRIPTION
               "The index into the sensor table"
               ::=  {  sensorTemperatureArrayEntry 1   }

            sensorTemperatureArrayDescription OBJECT-TYPE
               SYNTAX  DisplayString
               ACCESS  read-write
               STATUS  mandatory
               DESCRIPTION
               "A Description of this sensor"
               ::=  {  sensorTemperatureArrayEntry 2   }

            sensorTemperatureArrayType OBJECT-TYPE
               SYNTAX  INTEGER {
                  arraytemp(23)
               }
               ACCESS  read-only
               STATUS  mandatory
               DESCRIPTION
               "Enter the type of this Sensor"
               ::=  {  sensorTemperatureArrayEntry 3  }

            sensorTemperatureArrayDegree OBJECT-TYPE
               SYNTAX  INTEGER
               ACCESS  read-only
               STATUS  mandatory
               DESCRIPTION
               "The degrees in this sensor"
               ::=  {  sensorTemperatureArrayEntry 4   }

            sensorTemperatureArrayUnit OBJECT-TYPE
               SYNTAX  DisplayString
               ACCESS  read-only
               STATUS  mandatory
               DESCRIPTION
               "The unit string"
               ::=  {  sensorTemperatureArrayEntry 5  }

            sensorTemperatureArrayStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorTemperatureArrayEntry 6   }
   
            sensorTemperatureArrayGoOffline OBJECT-TYPE
               SYNTAX  INTEGER {
                  online(1),
                  goOffline(2)
               }
               ACCESS  read-write
               STATUS  mandatory
               DESCRIPTION
               "To take offline enter a 2"
               ::=  {  sensorTemperatureArrayEntry 8   }

            sensorTemperatureArrayLowCritical OBJECT-TYPE
               SYNTAX  INTEGER
               ACCESS  read-write
               STATUS  mandatory
               DESCRIPTION
               "How cold this sensor gets before it sends a critical event"
               ::=  {  sensorTemperatureArrayEntry 9   }

            sensorTemperatureArrayLowWarning OBJECT-TYPE
               SYNTAX  INTEGER
               ACCESS  read-write
               STATUS  mandatory
               DESCRIPTION
               "How cold this sensor gets before it sends a warning"
               ::=  {  sensorTemperatureArrayEntry 10   }
   
            sensorTemperatureArrayHighWarning OBJECT-TYPE
               SYNTAX  INTEGER
               ACCESS  read-write
               STATUS  mandatory
               DESCRIPTION
               "How hot this sensor gets before it sends a warning"
               ::=  {  sensorTemperatureArrayEntry 11   }  

            sensorTemperatureArrayHighCritical OBJECT-TYPE
               SYNTAX  INTEGER
               ACCESS  read-write
               STATUS  mandatory
               DESCRIPTION
               "How hot this sensor gets before it sends a critical event"
               ::=  {  sensorTemperatureArrayEntry 12   }   

            sensorTemperatureArrayRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorTemperatureArrayEntry 13   }

            sensorTemperatureArrayDelayError OBJECT-TYPE
               SYNTAX  INTEGER (0..65534)
               ACCESS  read-write
               STATUS  mandatory
               DESCRIPTION
               "Time in seconds after the sensor has been in error status before report as an error"
               ::=  {  sensorTemperatureArrayEntry 14   }

            sensorTemperatureArrayDelayNormal OBJECT-TYPE
               SYNTAX  INTEGER (0..65534)
               ACCESS  read-write
               STATUS  mandatory
               DESCRIPTION
               "Time in seconds after the sensor change from error to normal before report as normal"
               ::=  {  sensorTemperatureArrayEntry 15   }

            sensorTemperatureArrayDelayLowCritical OBJECT-TYPE
               SYNTAX INTEGER (0..65535)
               ACCESS read-write
               STATUS mandatory
               DESCRIPTION
               "Continuous time for this sensor to be in Low Critical before accepting new Status."
               ::= {  sensorTemperatureArrayEntry 16 }
               
            sensorTemperatureArrayDelayLowWarning OBJECT-TYPE
               SYNTAX INTEGER (0..65535)
               ACCESS read-write
               STATUS mandatory
               DESCRIPTION
               "Continuous time for this sensor to be in Low Warning before accepting new Status."
               ::= {  sensorTemperatureArrayEntry 17 }

            sensorTemperatureArrayDelayHighWarning OBJECT-TYPE
               SYNTAX INTEGER (0..65535)
               ACCESS read-write
               STATUS mandatory
               DESCRIPTION
               "Continuous time for this sensor to be in High Warning before accepting new Status."
               ::= {  sensorTemperatureArrayEntry 18 }

            sensorTemperatureArrayDelayHighCritical OBJECT-TYPE
               SYNTAX INTEGER (0..65535)
               ACCESS read-write
               STATUS mandatory
               DESCRIPTION
               "Continuous time for this sensor to be in High Critical before accepting new Status."
               ::= {  sensorTemperatureArrayEntry 19 }

            sensorTemperatureArrayRaw OBJECT-TYPE
               SYNTAX  INTEGER 
               ACCESS  read-only
               STATUS  mandatory
               DESCRIPTION
               "The raw degree data from the temperature sensor, slightly higher resolution"
               ::=  {  sensorTemperatureArrayEntry 20 }

            sensorTemperatureArrayOffset OBJECT-TYPE
               SYNTAX  INTEGER
               ACCESS  read-write
               STATUS  mandatory
               DESCRIPTION
               "Temperature Offset reading"
               ::=  {  sensorTemperatureArrayEntry 21 }

            sensorTemperatureArrayPort OBJECT-TYPE
               SYNTAX  INTEGER (0..65534)
               ACCESS  read-only
               STATUS  mandatory
               DESCRIPTION
               "Sensor port"
               ::=  {  sensorTemperatureArrayEntry 35 }

            sensorTemperatureArraySubPort OBJECT-TYPE
               SYNTAX  INTEGER (0..65534)
               ACCESS  read-only
               STATUS  mandatory
               DESCRIPTION
               "Sensor sub port"
               ::=  {  sensorTemperatureArrayEntry 36 }

            sensorTemperatureArrayDeviceIndex OBJECT-TYPE
               SYNTAX  INTEGER (0..65534)
               ACCESS  read-only
               STATUS  mandatory
               DESCRIPTION
               "Device Index of sensor"
               ::=  {  sensorTemperatureArrayEntry 37 }
               
            sensorTemperatureArrayDisplayStyle OBJECT-TYPE
               SYNTAX  INTEGER {
                  basic(0),
                  gauge(1)
               }
               ACCESS  read-write
               STATUS  mandatory
               DESCRIPTION
               "Temperature display style"
               ::=  {  sensorTemperatureArrayEntry 45 }   

            sensorTemperatureArrayHighCriticalDesc OBJECT-TYPE
               SYNTAX  DisplayString
               ACCESS  read-write
               STATUS  mandatory
               DESCRIPTION
               "A HighCritical Description of this sensor"
               ::=  {  sensorTemperatureArrayEntry  46  }               

            sensorTemperatureArrayLowCriticalDesc OBJECT-TYPE
               SYNTAX  DisplayString
               ACCESS  read-write
               STATUS  mandatory
               DESCRIPTION
               "A LowCritical Description of this sensor"
               ::=  {  sensorTemperatureArrayEntry  47  }

            sensorTemperatureArrayNormalDesc OBJECT-TYPE
               SYNTAX  DisplayString
               ACCESS  read-write
               STATUS  mandatory
               DESCRIPTION
               "A Normal Description of this sensor"
               ::=  {  sensorTemperatureArrayEntry  48  }
               
            sensorTemperatureArrayLowWarningDesc OBJECT-TYPE
               SYNTAX  DisplayString
               ACCESS  read-write
               STATUS  mandatory
               DESCRIPTION
               "A LowWarning Description of this sensor"
               ::=  {  sensorTemperatureArrayEntry  49  }
               
            sensorTemperatureArrayHighWarningDesc OBJECT-TYPE
               SYNTAX  DisplayString
               ACCESS  read-write
               STATUS  mandatory
               DESCRIPTION
               "A HighWarning Description of this sensor"
               ::=  {  sensorTemperatureArrayEntry  50  }
               
            sensorTemperatureArraySensorErrorDesc OBJECT-TYPE
               SYNTAX  DisplayString
               ACCESS  read-write
               STATUS  mandatory
               DESCRIPTION
               "A SensorError Description of this sensor"
               ::=  {  sensorTemperatureArrayEntry  51  }

            sensorTemperatureArrayHighCriticalColor OBJECT-TYPE
               SYNTAX  INTEGER
               ACCESS  read-write
               STATUS  mandatory
               DESCRIPTION
               "A HighCritical Color of this sensor"
               ::=  {  sensorTemperatureArrayEntry  54  }               

            sensorTemperatureArrayLowCriticalColor OBJECT-TYPE
               SYNTAX  INTEGER
               ACCESS  read-write
               STATUS  mandatory
               DESCRIPTION
               "A LowCritical Color of this sensor"
               ::=  {  sensorTemperatureArrayEntry  55  }

            sensorTemperatureArrayNormalColor OBJECT-TYPE
               SYNTAX  INTEGER
               ACCESS  read-write
               STATUS  mandatory
               DESCRIPTION
               "A Normal Color of this sensor"
               ::=  {  sensorTemperatureArrayEntry  56  }
               
            sensorTemperatureArrayLowWarningColor OBJECT-TYPE
               SYNTAX  INTEGER
               ACCESS  read-write
               STATUS  mandatory
               DESCRIPTION
               "A LowWarning Color of this sensor"
               ::=  {  sensorTemperatureArrayEntry  57  }
               
            sensorTemperatureArrayHighWarningColor OBJECT-TYPE
               SYNTAX  INTEGER
               ACCESS  read-write
               STATUS  mandatory
               DESCRIPTION
               "A HighWarning Color of this sensor"
               ::=  {  sensorTemperatureArrayEntry  58  }
               
            sensorTemperatureArraySensorErrorColor OBJECT-TYPE
               SYNTAX  INTEGER
               ACCESS  read-write
               STATUS  mandatory
               DESCRIPTION
               "A SensorError Color of this sensor"
               ::=  {  sensorTemperatureArrayEntry  59  }    
               
            sensorTemperatureArrayAcknowledge OBJECT-TYPE
               SYNTAX  INTEGER {
                  acked(2)
               }
               ACCESS  read-write
               STATUS  mandatory
               DESCRIPTION
               "Temperature sensor acknowledge"
               ::=  {  sensorTemperatureArrayEntry 70 } 
               
            sensorTemperatureArraySerialNumber OBJECT-TYPE
               SYNTAX  DisplayString
               ACCESS  read-write
               STATUS  mandatory
               DESCRIPTION
               "Serial Number of Temperature Sensor
               x is Hex Digit xx-xx-xx-xx-xx-xx-xx-xx"
               ::=  {  sensorTemperatureArrayEntry 71 }                            
               
            sensorTemperatureArrayId OBJECT-TYPE
               SYNTAX  INTEGER
               ACCESS  read-only
               STATUS  mandatory
               DESCRIPTION
               "The Sensor ID of this sensor, used to identify which sensor it is in the system configuration."
               ::= { sensorTemperatureArrayEntry 1000 }

--/* End of sensorTemperatureArrayEntry */

--/* Begin of secNotification */

      secNotification OBJECT IDENTIFIER  ::=  {  securityProbe 4 }

         action OBJECT IDENTIFIER  ::=  {  secNotification 1 }

            actionTable OBJECT-TYPE
               SYNTAX  SEQUENCE OF ActionEntry
               ACCESS  not-accessible
               STATUS  mandatory
               DESCRIPTION
               "This table contains the property for every action of notification."
               ::=  {  action 1   }

            actionEntry OBJECT-TYPE
               SYNTAX  ActionEntry
               ACCESS  not-accessible
               STATUS  mandatory
               DESCRIPTION
               "This is an entry in the actionTable Table"
               INDEX         { actionIndex }
               ::=  {  actionTable 1 }

            ActionEntry ::= SEQUENCE {
                  actionIndex
                     INTEGER,
                  actionType
                     INTEGER,
                  actionName
                     DisplayString,
                  actionMaxResend
                     INTEGER,
                  actionResendInterval
                     INTEGER,
                  actionTest
                     INTEGER
            }

               actionIndex OBJECT-TYPE
                  SYNTAX  INTEGER (1..65535)
                  ACCESS  read-only
                  STATUS  mandatory
                  DESCRIPTION
                  "The index into the action table."
                  ::=  {  actionEntry 1   }

               actionType OBJECT-TYPE
                  SYNTAX  INTEGER {
                     trap(1),
                     email(2),
                     sms(3),
                     mms(4),
                     sound(5),
                     speech(6),
                     dial(7),
                     relay(8),
                     custom(9),
                     ftp(10),
                     event(11),
                     fax(12),
                     soundlog(13),
                     camera(14),
                     siren(15),
                     mobile(16),
                     shut(17),
                     windows(19),
                     skype(20),
                     drycontact(21),
                     ctrSensorAction(22)
                  }
                  ACCESS  read-only
                  STATUS  mandatory
                  DESCRIPTION
                  "The type of this action."
                  ::=  {  actionEntry 2  }

               actionName OBJECT-TYPE
                  SYNTAX  DisplayString
                  ACCESS  read-write
                  STATUS  mandatory
                  DESCRIPTION
                  "A name of this action."
                  ::=  {  actionEntry 3   }

               actionMaxResend OBJECT-TYPE
                  SYNTAX  INTEGER
                  ACCESS  read-write
                  STATUS  mandatory
                  DESCRIPTION
                  "The maximum number of times to resend action. If set to 0 only send once. The maximum value is 5."
                  ::=  {  actionEntry 4   }

               actionResendInterval OBJECT-TYPE
                  SYNTAX  INTEGER
                  ACCESS  read-write
                  STATUS  mandatory
                  DESCRIPTION
                  "How often to resend action. Enter the number of seconds from 15 to 65535."
                  ::=  {  actionEntry 5   }

               actionTest OBJECT-TYPE
                  SYNTAX  INTEGER
                  ACCESS  read-write
                  STATUS  mandatory
                  DESCRIPTION
                  "Do test an action of notification."
                  ::=  {  actionEntry 6  }

--/* End of secNotification */

--/* Begin of sensorByPort */
      sensorByPort OBJECT IDENTIFIER  ::=  {  securityProbe 5 }

         commonSensorTable OBJECT-TYPE
            SYNTAX  SEQUENCE OF CommonSensorEntry
            ACCESS  not-accessible
            STATUS  mandatory
            DESCRIPTION
            "This table contains the property and reading value for every Sensor."
            ::=  {  sensorByPort 1   }

--/* Begin of commonSensorEntry */

         commonSensorEntry OBJECT-TYPE
            SYNTAX  CommonSensorEntry
            ACCESS  not-accessible
            STATUS  mandatory
            DESCRIPTION
            "This is an entry in the commonSensorTable"
            INDEX         { commonSensorIndex }
            ::=  {  commonSensorTable 1 }

         CommonSensorEntry ::= SEQUENCE {
               commonSensorIndex
                  DisplayString,
               commonSensorDescription
                  DisplayString,
               commonSensorType
                  INTEGER,
               commonSensorValue
                  INTEGER,
               commonSensorUnit
                  DisplayString,
               commonSensorStatus
                  INTEGER,
               commonSensorGoOffline
                  INTEGER,
               commonSensorPort
                  INTEGER,
               commonSensorSubPort
                  INTEGER,
               commonSensorDeviceIndex
                  INTEGER,
               commonSensorDisplayStyle
                  INTEGER,
               commonSensorHighCriticalDescription
                  DisplayString,
               commonSensorLowCriticalDescription
                  DisplayString,
               commonSensorSensorNormalDescription
                  DisplayString,
               commonSensorLowWarningDescription
                  DisplayString,
               commonSensorHighWarningDescription
                  DisplayString,
               commonSensorSensorErrorDescription
                  DisplayString,
               commonSensorOnDescription
                  DisplayString,
               commonSensorOffDescription
                  DisplayString,
               commonSensorHighCriticalColor
                  INTEGER,
               commonSensorLowCriticalColor
                  INTEGER,
               commonSensorSensorNormalColor
                  INTEGER,
               commonSensorLowWarningColor
                  INTEGER,
               commonSensorHighWarningColor
                  INTEGER,
               commonSensorSensorErrorColor
                  INTEGER,
               commonSensorOnColor
                  INTEGER,
               commonSensorOffColor
                  INTEGER,
               commonSensorAcknowledge
                  INTEGER,
               commonSensorValueFormatFloat
                  Opaque,
               commonSensorId
                  INTEGER,
               commonSensorValueBroadcastInterval
                  INTEGER
         }

            commonSensorIndex OBJECT-TYPE
               SYNTAX  DisplayString
               ACCESS  read-only
               STATUS  mandatory
               DESCRIPTION
               "The Sensor Compound ID of this sensor, used to identify which sensor it is in the system configuration."
               ::=  {  commonSensorEntry 1   }

            commonSensorDescription OBJECT-TYPE
               SYNTAX  DisplayString
               ACCESS  read-write
               STATUS  mandatory
               DESCRIPTION
               "A Description of this sensor"
               ::=  {  commonSensorEntry 2   }

            commonSensorType OBJECT-TYPE
               SYNTAX  INTEGER {
                  temperature(1),
                  humidity(2),
                  temperature-dual(3),
                  four-20mA(4),
                  dcvoltage(5),
                  airflow(6),
                  io(7),
                  drycontact(8),
                  motion(9),
                  water(10),
                  security(11),
                  siren(12),
                  relay(13),
                  acvoltage(14),
                  vrms(15),
                  irms(16),
                  watt(17),
                  watthour(18),
                  xrelay(19),
                  thermocouple(20),
                  smoke(21),
                  drycontact-array(22),
                  temperature-array(23),
                  thermostat(128),
                  virtual(129),
                  sound(130),
                  softmotion(131),
                  camera-dummy(132),
                  board-state(133),
                  nosignal(224),
                  test(255)
               }
               ACCESS  read-only
               STATUS  mandatory
               DESCRIPTION
               "Enter the type of this Sensor"
               ::=  {  commonSensorEntry 3  }

            commonSensorValue OBJECT-TYPE
               SYNTAX  INTEGER
               ACCESS  read-only
               STATUS  mandatory
               DESCRIPTION
               "The value in this sensor"
               ::=  {  commonSensorEntry 4   }

            commonSensorUnit OBJECT-TYPE
               SYNTAX  DisplayString
               ACCESS  read-only
               STATUS  mandatory
               DESCRIPTION
               "The unit string"
               ::=  {  commonSensorEntry 5  }

            commonSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this sensor"
               ::=  {  commonSensorEntry 6   }

            commonSensorGoOffline OBJECT-TYPE
               SYNTAX  INTEGER {
                  online(1),
                  goOffline(2)
               }
               ACCESS  read-write
               STATUS  mandatory
               DESCRIPTION
               "To take offline enter a 2"
               ::=  {  commonSensorEntry 8   }

            commonSensorPort OBJECT-TYPE
               SYNTAX  INTEGER (0..65534)
               ACCESS  read-only
               STATUS  mandatory
               DESCRIPTION
               "Sensor port"
               ::=  {  commonSensorEntry 35 }

            commonSensorSubPort OBJECT-TYPE
               SYNTAX  INTEGER (0..65534)
               ACCESS  read-only
               STATUS  mandatory
               DESCRIPTION
               "Sensor sub port"
               ::=  {  commonSensorEntry 36 }

            commonSensorDeviceIndex OBJECT-TYPE
               SYNTAX  INTEGER (0..65534)
               ACCESS  read-only
               STATUS  mandatory
               DESCRIPTION
               "Device Index of sensor"
               ::=  {  commonSensorEntry 37 }

            commonSensorDisplayStyle OBJECT-TYPE
               SYNTAX  INTEGER {
                  basic(0),
                  gauge(1)
               }
               ACCESS  read-write
               STATUS  mandatory
               DESCRIPTION
               "Temperature display style"
               ::=  {  commonSensorEntry 45 }   

            commonSensorHighCriticalDescription OBJECT-TYPE
               SYNTAX  DisplayString
               ACCESS  read-write
               STATUS  mandatory
               DESCRIPTION
               "A HighCritical Description of this sensor"
               ::=  {  commonSensorEntry  46  }

            commonSensorLowCriticalDescription OBJECT-TYPE
               SYNTAX  DisplayString
               ACCESS  read-write
               STATUS  mandatory
               DESCRIPTION
               "A LowCritical Description of this sensor"
               ::=  {  commonSensorEntry  47  }

            commonSensorSensorNormalDescription OBJECT-TYPE
               SYNTAX  DisplayString
               ACCESS  read-write
               STATUS  mandatory
               DESCRIPTION
               "A Normal Description of this sensor"
               ::=  {  commonSensorEntry  48  }
               
            commonSensorLowWarningDescription OBJECT-TYPE
               SYNTAX  DisplayString
               ACCESS  read-write
               STATUS  mandatory
               DESCRIPTION
               "A LowWarning Description of this sensor"
               ::=  {  commonSensorEntry  49  }
               
            commonSensorHighWarningDescription OBJECT-TYPE
               SYNTAX  DisplayString
               ACCESS  read-write
               STATUS  mandatory
               DESCRIPTION
               "A HighWarning Description of this sensor"
               ::=  {  commonSensorEntry  50  }
               
            commonSensorSensorErrorDescription OBJECT-TYPE
               SYNTAX  DisplayString
               ACCESS  read-write
               STATUS  mandatory
               DESCRIPTION
               "A SensorError Description of this sensor"
               ::=  {  commonSensorEntry  51  }
               
            commonSensorOnDescription OBJECT-TYPE
               SYNTAX  DisplayString
               ACCESS  read-write
               STATUS  mandatory
               DESCRIPTION
               "A On Description of this sensor"
               ::=  {  commonSensorEntry  52  }     

            commonSensorOffDescription OBJECT-TYPE
               SYNTAX  DisplayString
               ACCESS  read-write
               STATUS  mandatory
               DESCRIPTION
               "A Off Description of this sensor"
               ::=  {  commonSensorEntry  53  }

            commonSensorHighCriticalColor OBJECT-TYPE
               SYNTAX  INTEGER
               ACCESS  read-write
               STATUS  mandatory
               DESCRIPTION
               "A HighCritical Color of this sensor"
               ::=  {  commonSensorEntry  54  }

            commonSensorLowCriticalColor OBJECT-TYPE
               SYNTAX  INTEGER
               ACCESS  read-write
               STATUS  mandatory
               DESCRIPTION
               "A LowCritical Color of this sensor"
               ::=  {  commonSensorEntry  55  }

            commonSensorSensorNormalColor OBJECT-TYPE
               SYNTAX  INTEGER
               ACCESS  read-write
               STATUS  mandatory
               DESCRIPTION
               "A Normal Color of this sensor"
               ::=  {  commonSensorEntry  56  }
               
            commonSensorLowWarningColor OBJECT-TYPE
               SYNTAX  INTEGER
               ACCESS  read-write
               STATUS  mandatory
               DESCRIPTION
               "A LowWarning Color of this sensor"
               ::=  {  commonSensorEntry  57  }
               
            commonSensorHighWarningColor OBJECT-TYPE
               SYNTAX  INTEGER
               ACCESS  read-write
               STATUS  mandatory
               DESCRIPTION
               "A HighWarning Color of this sensor"
               ::=  {  commonSensorEntry  58  }
               
            commonSensorSensorErrorColor OBJECT-TYPE
               SYNTAX  INTEGER
               ACCESS  read-write
               STATUS  mandatory
               DESCRIPTION
               "A SensorError Color of this sensor"
               ::=  {  commonSensorEntry  59  }
               
            commonSensorOnColor OBJECT-TYPE
               SYNTAX  INTEGER
               ACCESS  read-write
               STATUS  mandatory
               DESCRIPTION
               "A On Color of this sensor"
               ::=  {  commonSensorEntry  60  }

            commonSensorOffColor OBJECT-TYPE
               SYNTAX  INTEGER
               ACCESS  read-write
               STATUS  mandatory
               DESCRIPTION
               "A Off Color of this sensor"
               ::=  {  commonSensorEntry  61  }

            commonSensorAcknowledge OBJECT-TYPE
               SYNTAX  INTEGER {
                  acked(2)
               }
               ACCESS  read-write
               STATUS  mandatory
               DESCRIPTION
               "Sensor acknowledge"
               ::=  {  commonSensorEntry  70  }

            commonSensorValueFormatFloat OBJECT-TYPE
               SYNTAX  Opaque (SIZE(4))
               ACCESS  read-only
               STATUS  mandatory
               DESCRIPTION
               "The floating-point IEEE Standard 754 reading value in this sensor"
               ::=  {  commonSensorEntry  99  }

            commonSensorId OBJECT-TYPE
               SYNTAX  INTEGER
               ACCESS  read-only
               STATUS  mandatory
               DESCRIPTION
               "The Sensor ID of this sensor, used to identify which sensor it is in the system configuration."
               ::= { commonSensorEntry 1000 }

            commonSensorValueBroadcastInterval OBJECT-TYPE
               SYNTAX  INTEGER
               ACCESS  read-write
               STATUS  mandatory
               DESCRIPTION
               "The Sensor value broadcast inteval in seconds."
               ::= { commonSensorEntry 1002 }

--/* End of commonSensorEntry */

--/* Begin of temperatureSensorEntry */
         temperatureSensorTable OBJECT-TYPE
            SYNTAX  SEQUENCE OF TemperatureSensorEntry
            ACCESS  not-accessible
            STATUS  mandatory
            DESCRIPTION
            "This table contains the property and reading value for every Temperature sensor."
            ::=  {  sensorByPort 2   }

         temperatureSensorEntry OBJECT-TYPE
            SYNTAX  TemperatureSensorEntry
            ACCESS  not-accessible
            STATUS  mandatory
            DESCRIPTION
            "This is an entry in the temperatureSensorEntry Table"
            INDEX         { temperatureSensorIndex }
            ::=  {  temperatureSensorTable 1 }

         TemperatureSensorEntry ::= SEQUENCE {
               temperatureSensorIndex
                  DisplayString,
               temperatureSensorDescription
                  DisplayString,
               temperatureSensorType
                  INTEGER,
               temperatureSensorDegree
                  INTEGER,
               temperatureSensorUnit
                  DisplayString,               
               temperatureSensorStatus
                  INTEGER,
               temperatureSensorGoOffline
                  INTEGER,
               temperatureSensorLowCritical
                  INTEGER,
               temperatureSensorLowWarning
                  INTEGER,
               temperatureSensorHighWarning
                  INTEGER,
               temperatureSensorHighCritical
                  INTEGER,
               temperatureSensorRearm
                  INTEGER,
               temperatureSensorDelayError
                  INTEGER,
               temperatureSensorDelayNormal
                  INTEGER,
               temperatureSensorDelayLowCritical
                  INTEGER,
               temperatureSensorDelayLowWarning
                  INTEGER,
               temperatureSensorDelayHighWarning
                  INTEGER,
               temperatureSensorDelayHighCritical
                  INTEGER,
               temperatureSensorRaw
                  INTEGER,
               temperatureSensorOffset
                  INTEGER,
               temperatureSensorPort
                  INTEGER,
               temperatureSensorSubPort
                  INTEGER,
               temperatureSensorDeviceIndex
                  INTEGER,
               temperatureSensorDisplayStyle
                  INTEGER,
               temperatureSensorHighCriticalDesc 
                  DisplayString,
               temperatureSensorLowCriticalDesc 
                  DisplayString,
               temperatureSensorNormalDesc 
                  DisplayString,
               temperatureSensorLowWarningDesc 
                  DisplayString,   
               temperatureSensorHighWarningDesc 
                  DisplayString,
               temperatureSensorSensorErrorDesc 
                  DisplayString,
               temperatureSensorHighCriticalColor 
                  INTEGER,
               temperatureSensorLowCriticalColor 
                  INTEGER,
               temperatureSensorSensorNormalColor 
                  INTEGER,
               temperatureSensorLowWarningColor 
                  INTEGER,   
               temperatureSensorHighWarningColor 
                  INTEGER,
               temperatureSensorSensorErrorColor 
                  INTEGER,                 
               temperatureSensorAcknowledge
                  INTEGER,
               temperatureSensorSerialNumber
                  DisplayString,
               temperatureSensorId
                  INTEGER
            }

            temperatureSensorIndex OBJECT-TYPE
               SYNTAX  DisplayString
               ACCESS  read-only
               STATUS  mandatory
               DESCRIPTION
               "The Sensor Compound ID of this sensor, used to identify which sensor it is in the system configuration."
               ::=  {  temperatureSensorEntry 1   }

            temperatureSensorDescription OBJECT-TYPE
               SYNTAX  DisplayString
               ACCESS  read-write
               STATUS  mandatory
               DESCRIPTION
               "A Description of this sensor"
               ::=  {  temperatureSensorEntry 2   }

            temperatureSensorType OBJECT-TYPE
               SYNTAX  INTEGER {
                  temperature(1),
                  dualsensor(3),
                  thermocouple(20)
               }
               ACCESS  read-only
               STATUS  mandatory
               DESCRIPTION
               "Enter the type of this Sensor"
               ::=  {  temperatureSensorEntry 3  }

            temperatureSensorDegree OBJECT-TYPE
               SYNTAX  INTEGER
               ACCESS  read-only
               STATUS  mandatory
               DESCRIPTION
               "The degrees in this sensor"
               ::=  {  temperatureSensorEntry 4   }

            temperatureSensorUnit OBJECT-TYPE
               SYNTAX  DisplayString
               ACCESS  read-only
               STATUS  mandatory
               DESCRIPTION
               "The unit string"
               ::=  {  temperatureSensorEntry 5  }

            temperatureSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  temperatureSensorEntry 6   }
   
            temperatureSensorGoOffline OBJECT-TYPE
               SYNTAX  INTEGER {
                  online(1),
                  goOffline(2)
               }
               ACCESS  read-write
               STATUS  mandatory
               DESCRIPTION
               "To take offline enter a 2"
               ::=  {  temperatureSensorEntry 8   }

            temperatureSensorLowCritical OBJECT-TYPE
               SYNTAX  INTEGER
               ACCESS  read-write
               STATUS  mandatory
               DESCRIPTION
               "How cold this sensor gets before it sends a critical event"
               ::=  {  temperatureSensorEntry 9   }

            temperatureSensorLowWarning OBJECT-TYPE
               SYNTAX  INTEGER
               ACCESS  read-write
               STATUS  mandatory
               DESCRIPTION
               "How cold this sensor gets before it sends a warning"
               ::=  {  temperatureSensorEntry 10   }
   
            temperatureSensorHighWarning OBJECT-TYPE
               SYNTAX  INTEGER
               ACCESS  read-write
               STATUS  mandatory
               DESCRIPTION
               "How hot this sensor gets before it sends a warning"
               ::=  {  temperatureSensorEntry 11   }  

            temperatureSensorHighCritical OBJECT-TYPE
               SYNTAX  INTEGER
               ACCESS  read-write
               STATUS  mandatory
               DESCRIPTION
               "How hot this sensor gets before it sends a critical event"
               ::=  {  temperatureSensorEntry 12   }   

            temperatureSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  temperatureSensorEntry 13   }

            temperatureSensorDelayError OBJECT-TYPE
               SYNTAX  INTEGER (0..65534)
               ACCESS  read-write
               STATUS  mandatory
               DESCRIPTION
               "Time in seconds after the sensor has been in error status before report as an error"
               ::=  {  temperatureSensorEntry 14   }

            temperatureSensorDelayNormal OBJECT-TYPE
               SYNTAX  INTEGER (0..65534)
               ACCESS  read-write
               STATUS  mandatory
               DESCRIPTION
               "Time in seconds after the sensor change from error to normal before report as normal"
               ::=  {  temperatureSensorEntry 15   }

            temperatureSensorDelayLowCritical OBJECT-TYPE
               SYNTAX INTEGER (0..65535)
               ACCESS read-write
               STATUS mandatory
               DESCRIPTION
               "Continuous time for this sensor to be in Low Critical before accepting new Status."
               ::= {  temperatureSensorEntry 16 }
               
            temperatureSensorDelayLowWarning OBJECT-TYPE
               SYNTAX INTEGER (0..65535)
               ACCESS read-write
               STATUS mandatory
               DESCRIPTION
               "Continuous time for this sensor to be in Low Warning before accepting new Status."
               ::= {  temperatureSensorEntry 17 }

            temperatureSensorDelayHighWarning OBJECT-TYPE
               SYNTAX INTEGER (0..65535)
               ACCESS read-write
               STATUS mandatory
               DESCRIPTION
               "Continuous time for this sensor to be in High Warning before accepting new Status."
               ::= {  temperatureSensorEntry 18 }

            temperatureSensorDelayHighCritical OBJECT-TYPE
               SYNTAX INTEGER (0..65535)
               ACCESS read-write
               STATUS mandatory
               DESCRIPTION
               "Continuous time for this sensor to be in High Critical before accepting new Status."
               ::= {  temperatureSensorEntry 19 }

            temperatureSensorRaw OBJECT-TYPE
               SYNTAX  INTEGER 
               ACCESS  read-only
               STATUS  mandatory
               DESCRIPTION
               "The raw degree data from the temperature sensor, slightly higher resolution"
               ::=  {  temperatureSensorEntry 20 }

            temperatureSensorOffset OBJECT-TYPE
               SYNTAX  INTEGER
               ACCESS  read-write
               STATUS  mandatory
               DESCRIPTION
               "Temperature Offset reading"
               ::=  {  temperatureSensorEntry 21 }

            temperatureSensorPort OBJECT-TYPE
               SYNTAX  INTEGER (0..65534)
               ACCESS  read-only
               STATUS  mandatory
               DESCRIPTION
               "Sensor port"
               ::=  {  temperatureSensorEntry 35 }

            temperatureSensorSubPort OBJECT-TYPE
               SYNTAX  INTEGER (0..65534)
               ACCESS  read-only
               STATUS  mandatory
               DESCRIPTION
               "Sensor sub port"
               ::=  {  temperatureSensorEntry 36 }

            temperatureSensorDeviceIndex OBJECT-TYPE
               SYNTAX  INTEGER (0..65534)
               ACCESS  read-only
               STATUS  mandatory
               DESCRIPTION
               "Device Index of sensor"
               ::=  {  temperatureSensorEntry 37 }
               
            temperatureSensorDisplayStyle OBJECT-TYPE
               SYNTAX  INTEGER {
                  basic(0),
                  gauge(1)
               }
               ACCESS  read-write
               STATUS  mandatory
               DESCRIPTION
               "Temperature display style"
               ::=  {  temperatureSensorEntry 45 }   

            temperatureSensorHighCriticalDesc OBJECT-TYPE
               SYNTAX  DisplayString
               ACCESS  read-write
               STATUS  mandatory
               DESCRIPTION
               "A HighCritical Description of this sensor"
               ::=  {  temperatureSensorEntry  46  }               

            temperatureSensorLowCriticalDesc OBJECT-TYPE
               SYNTAX  DisplayString
               ACCESS  read-write
               STATUS  mandatory
               DESCRIPTION
               "A LowCritical Description of this sensor"
               ::=  {  temperatureSensorEntry  47  }

            temperatureSensorNormalDesc OBJECT-TYPE
               SYNTAX  DisplayString
               ACCESS  read-write
               STATUS  mandatory
               DESCRIPTION
               "A Normal Description of this sensor"
               ::=  {  temperatureSensorEntry  48  }
               
            temperatureSensorLowWarningDesc OBJECT-TYPE
               SYNTAX  DisplayString
               ACCESS  read-write
               STATUS  mandatory
               DESCRIPTION
               "A LowWarning Description of this sensor"
               ::=  {  temperatureSensorEntry  49  }
               
            temperatureSensorHighWarningDesc OBJECT-TYPE
               SYNTAX  DisplayString
               ACCESS  read-write
               STATUS  mandatory
               DESCRIPTION
               "A HighWarning Description of this sensor"
               ::=  {  temperatureSensorEntry  50  }
               
            temperatureSensorSensorErrorDesc OBJECT-TYPE
               SYNTAX  DisplayString
               ACCESS  read-write
               STATUS  mandatory
               DESCRIPTION
               "A SensorError Description of this sensor"
               ::=  {  temperatureSensorEntry  51  }

            temperatureSensorHighCriticalColor OBJECT-TYPE
               SYNTAX  INTEGER
               ACCESS  read-write
               STATUS  mandatory
               DESCRIPTION
               "A HighCritical Color of this sensor"
               ::=  {  temperatureSensorEntry  54  }               

            temperatureSensorLowCriticalColor OBJECT-TYPE
               SYNTAX  INTEGER
               ACCESS  read-write
               STATUS  mandatory
               DESCRIPTION
               "A LowCritical Color of this sensor"
               ::=  {  temperatureSensorEntry  55  }

            temperatureSensorSensorNormalColor OBJECT-TYPE
               SYNTAX  INTEGER
               ACCESS  read-write
               STATUS  mandatory
               DESCRIPTION
               "A Normal Color of this sensor"
               ::=  {  temperatureSensorEntry  56  }
               
            temperatureSensorLowWarningColor OBJECT-TYPE
               SYNTAX  INTEGER
               ACCESS  read-write
               STATUS  mandatory
               DESCRIPTION
               "A LowWarning Color of this sensor"
               ::=  {  temperatureSensorEntry  57  }
               
            temperatureSensorHighWarningColor OBJECT-TYPE
               SYNTAX  INTEGER
               ACCESS  read-write
               STATUS  mandatory
               DESCRIPTION
               "A HighWarning Color of this sensor"
               ::=  {  temperatureSensorEntry  58  }
               
            temperatureSensorSensorErrorColor OBJECT-TYPE
               SYNTAX  INTEGER
               ACCESS  read-write
               STATUS  mandatory
               DESCRIPTION
               "A SensorError Color of this sensor"
               ::=  {  temperatureSensorEntry  59  }    
               
            temperatureSensorAcknowledge OBJECT-TYPE
               SYNTAX  INTEGER {
                  acked(2)
               }
               ACCESS  read-write
               STATUS  mandatory
               DESCRIPTION
               "Temperature sensor acknowledge"
               ::=  {  temperatureSensorEntry 70 } 
               
            temperatureSensorSerialNumber OBJECT-TYPE
               SYNTAX  DisplayString
               ACCESS  read-write
               STATUS  mandatory
               DESCRIPTION
               "Serial Number of Temperature Sensor
               x is Hex Digit xx-xx-xx-xx-xx-xx-xx-xx"
               ::=  {  temperatureSensorEntry 71 }                            
               
            temperatureSensorId OBJECT-TYPE
               SYNTAX  INTEGER
               ACCESS  read-only
               STATUS  mandatory
               DESCRIPTION
               "The Sensor ID of this sensor, used to identify which sensor it is in the system configuration."
               ::= { temperatureSensorEntry 1000 }

--/* End of temperatureSensorEntry */

--/* Begin of humiditySensorEntry */
         humiditySensorTable OBJECT-TYPE
            SYNTAX  SEQUENCE OF HumiditySensorEntry
            ACCESS  not-accessible
            STATUS  mandatory
            DESCRIPTION
            "This table contains the property and reading value for every sensor."
            ::=  {  sensorByPort 3   }

         humiditySensorEntry OBJECT-TYPE
            SYNTAX  HumiditySensorEntry
            ACCESS  not-accessible
            STATUS  mandatory
            DESCRIPTION
            "This is an entry in the cmpTemperatureEntry Table"
            INDEX         { humiditySensorIndex }
            ::=  {  humiditySensorTable 1 }

         HumiditySensorEntry ::= SEQUENCE {
               humiditySensorIndex
                  DisplayString,
               humiditySensorDescription
                  DisplayString,
               humiditySensorPercent
                  INTEGER,
               humiditySensorUnit
                  DisplayString,
               humiditySensorStatus
                  INTEGER,
               humiditySensorGoOffline
                  INTEGER,
               humiditySensorLowCritical
                  INTEGER,
               humiditySensorLowWarning
                  INTEGER,
               humiditySensorHighWarning
                  INTEGER,
               humiditySensorHighCritical
                  INTEGER,
               humiditySensorRearm
                  INTEGER,
               humiditySensorDelayError
                  INTEGER,
               humiditySensorDelayNormal
                  INTEGER,
               humiditySensorDelayLowCritical
                  INTEGER,
               humiditySensorDelayLowWarning
                  INTEGER,
               humiditySensorDelayHighWarning
                  INTEGER,
               humiditySensorDelayHighCritical
                  INTEGER,
               humiditySensorRaw
                  INTEGER,
               humiditySensorOffset
                  INTEGER,
               humiditySensorPort
                  INTEGER,
               humiditySensorSubPort
                  INTEGER,
               humiditySensorDeviceIndex
                  INTEGER,
               humiditySensorDisplayStyle
                  INTEGER,
               humiditySensorHighCriticalDesc 
                  DisplayString,
               humiditySensorLowCriticalDesc 
                  DisplayString,
               humiditySensorNormalDesc 
                  DisplayString,
               humiditySensorLowWarningDesc 
                  DisplayString,   
               humiditySensorHighWarningDesc 
                  DisplayString,
               humiditySensorSensorErrorDesc 
                  DisplayString,
               humiditySensorHighCriticalColor 
                  INTEGER,
               humiditySensorLowCriticalColor 
                  INTEGER,
               humiditySensorSensorNormalColor 
                  INTEGER,
               humiditySensorLowWarningColor 
                  INTEGER,   
               humiditySensorHighWarningColor 
                  INTEGER,
               humiditySensorSensorErrorColor 
                  INTEGER,
               humiditySensorAcknowledge   
                  INTEGER,
               humiditySensorId
                  INTEGER
            }

            humiditySensorIndex OBJECT-TYPE
               SYNTAX  DisplayString
               ACCESS  read-only
               STATUS  mandatory
               DESCRIPTION
               "The Sensor Compound ID of this sensor, used to identify which sensor it is in the system configuration."
               ::=  {  humiditySensorEntry 1   }

            humiditySensorDescription OBJECT-TYPE
               SYNTAX  DisplayString
               ACCESS  read-write
               STATUS  mandatory
               DESCRIPTION
               "A Description of this sensor"
               ::=  {  humiditySensorEntry 2   }

            humiditySensorPercent OBJECT-TYPE
               SYNTAX  INTEGER
               ACCESS  read-only
               STATUS  mandatory
               DESCRIPTION
               "The relative humidity percentage measured by this sensor"
               ::=  {  humiditySensorEntry 4   }

            humiditySensorUnit OBJECT-TYPE
               SYNTAX  DisplayString
               ACCESS  read-write
               STATUS  mandatory
               DESCRIPTION
               "The unit string"
               ::=  {  humiditySensorEntry 5  }

            humiditySensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  humiditySensorEntry 6   }

            humiditySensorGoOffline OBJECT-TYPE
               SYNTAX  INTEGER {
                  online(1),
                  goOffline(2)
               }
               ACCESS  read-write
               STATUS  mandatory
               DESCRIPTION
               "To take offline enter a 2"
               ::=  {  humiditySensorEntry 8   }

            humiditySensorLowCritical OBJECT-TYPE
               SYNTAX  INTEGER
               ACCESS  read-write
               STATUS  mandatory
               DESCRIPTION
               "How cold this sensor gets before it sends a critical event"
               ::=  {  humiditySensorEntry 9   }

            humiditySensorLowWarning OBJECT-TYPE
               SYNTAX  INTEGER
               ACCESS  read-write
               STATUS  mandatory
               DESCRIPTION
               "How cold this sensor gets before it sends a warning"
               ::=  {  humiditySensorEntry 10   }
   
            humiditySensorHighWarning OBJECT-TYPE
               SYNTAX  INTEGER
               ACCESS  read-write
               STATUS  mandatory
               DESCRIPTION
               "How hot this sensor gets before it sends a warning"
               ::=  {  humiditySensorEntry 11   }  

            humiditySensorHighCritical OBJECT-TYPE
               SYNTAX  INTEGER
               ACCESS  read-write
               STATUS  mandatory
               DESCRIPTION
               "How hot this sensor gets before it sends a critical event"
               ::=  {  humiditySensorEntry 12   }   

            humiditySensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  humiditySensorEntry 13   }

            humiditySensorDelayError OBJECT-TYPE
               SYNTAX  INTEGER (0..65534)
               ACCESS  read-write
               STATUS  mandatory
               DESCRIPTION
               "Time in seconds after the sensor has been in error status before report as an error"
               ::=  {  humiditySensorEntry 14   }

            humiditySensorDelayNormal OBJECT-TYPE
               SYNTAX  INTEGER (0..65534)
               ACCESS  read-write
               STATUS  mandatory
               DESCRIPTION
               "Time in seconds after the sensor change from error to normal before report as normal"
               ::=  {  humiditySensorEntry 15   }

            humiditySensorDelayLowCritical OBJECT-TYPE
               SYNTAX INTEGER (0..65535)
               ACCESS read-write
               STATUS mandatory
               DESCRIPTION
               "Continuous time for this sensor to be in Low Critical before accepting new Status."
               ::= {  humiditySensorEntry 16 }
               
            humiditySensorDelayLowWarning OBJECT-TYPE
               SYNTAX INTEGER (0..65535)
               ACCESS read-write
               STATUS mandatory
               DESCRIPTION
               "Continuous time for this sensor to be in Low Warning before accepting new Status."
               ::= {  humiditySensorEntry 17 }

            humiditySensorDelayHighWarning OBJECT-TYPE
               SYNTAX INTEGER (0..65535)
               ACCESS read-write
               STATUS mandatory
               DESCRIPTION
               "Continuous time for this sensor to be in High Warning before accepting new Status."
               ::= {  humiditySensorEntry 18 }

            humiditySensorDelayHighCritical OBJECT-TYPE
               SYNTAX INTEGER (0..65535)
               ACCESS read-write
               STATUS mandatory
               DESCRIPTION
               "Continuous time for this sensor to be in High Critical before accepting new Status."
               ::= {  humiditySensorEntry 19 }

            humiditySensorRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  humiditySensorEntry 20   }

            humiditySensorOffset OBJECT-TYPE
               SYNTAX  INTEGER
               ACCESS  read-write
               STATUS  mandatory
               DESCRIPTION
               "Humidity Offset reading"
               ::=  {  humiditySensorEntry 21   }

            humiditySensorPort OBJECT-TYPE
               SYNTAX  INTEGER (0..65534)
               ACCESS  read-only
               STATUS  mandatory
               DESCRIPTION
               "Sensor port"
               ::=  {  humiditySensorEntry 35 }

            humiditySensorSubPort OBJECT-TYPE
               SYNTAX  INTEGER (0..65534)
               ACCESS  read-only
               STATUS  mandatory
               DESCRIPTION
               "Sensor sub port"
               ::=  {  humiditySensorEntry 36 }

            humiditySensorDeviceIndex OBJECT-TYPE
               SYNTAX  INTEGER (0..65534)
               ACCESS  read-only
               STATUS  mandatory
               DESCRIPTION
               "Device Index of sensor"
               ::=  {  humiditySensorEntry 37 }
               
            humiditySensorDisplayStyle OBJECT-TYPE
               SYNTAX  INTEGER {
                  basic(0),
                  gauge(1)
               }
               ACCESS  read-write
               STATUS  mandatory
               DESCRIPTION
               "Humidity display style"
               ::=  {  humiditySensorEntry 45 }           
               
            humiditySensorHighCriticalDesc OBJECT-TYPE
               SYNTAX  DisplayString
               ACCESS  read-write
               STATUS  mandatory
               DESCRIPTION
               "A HighCritical Description of this sensor"
               ::=  {  humiditySensorEntry  46  }               

            humiditySensorLowCriticalDesc OBJECT-TYPE
               SYNTAX  DisplayString
               ACCESS  read-write
               STATUS  mandatory
               DESCRIPTION
               "A LowCritical Description of this sensor"
               ::=  {  humiditySensorEntry  47  }

            humiditySensorNormalDesc OBJECT-TYPE
               SYNTAX  DisplayString
               ACCESS  read-write
               STATUS  mandatory
               DESCRIPTION
               "A Normal Description of this sensor"
               ::=  {  humiditySensorEntry  48  }
               
            humiditySensorLowWarningDesc OBJECT-TYPE
               SYNTAX  DisplayString
               ACCESS  read-write
               STATUS  mandatory
               DESCRIPTION
               "A LowWarning Description of this sensor"
               ::=  {  humiditySensorEntry  49  }
               
            humiditySensorHighWarningDesc OBJECT-TYPE
               SYNTAX  DisplayString
               ACCESS  read-write
               STATUS  mandatory
               DESCRIPTION
               "A HighWarning Description of this sensor"
               ::=  {  humiditySensorEntry  50  }
               
            humiditySensorSensorErrorDesc OBJECT-TYPE
               SYNTAX  DisplayString
               ACCESS  read-write
               STATUS  mandatory
               DESCRIPTION
               "A SensorError Description of this sensor"
               ::=  {  humiditySensorEntry  51  }  

            humiditySensorHighCriticalColor OBJECT-TYPE
               SYNTAX  INTEGER
               ACCESS  read-write
               STATUS  mandatory
               DESCRIPTION
               "A HighCritical Color of this sensor"
               ::=  {  humiditySensorEntry  54  }               

            humiditySensorLowCriticalColor OBJECT-TYPE
               SYNTAX  INTEGER
               ACCESS  read-write
               STATUS  mandatory
               DESCRIPTION
               "A LowCritical Color of this sensor"
               ::=  {  humiditySensorEntry  55  }

            humiditySensorSensorNormalColor OBJECT-TYPE
               SYNTAX  INTEGER
               ACCESS  read-write
               STATUS  mandatory
               DESCRIPTION
               "A Normal Color of this sensor"
               ::=  {  humiditySensorEntry  56  }
               
            humiditySensorLowWarningColor OBJECT-TYPE
               SYNTAX  INTEGER
               ACCESS  read-write
               STATUS  mandatory
               DESCRIPTION
               "A LowWarning Color of this sensor"
               ::=  {  humiditySensorEntry  57  }
               
            humiditySensorHighWarningColor OBJECT-TYPE
               SYNTAX  INTEGER
               ACCESS  read-write
               STATUS  mandatory
               DESCRIPTION
               "A HighWarning Color of this sensor"
               ::=  {  humiditySensorEntry  58  }
               
            humiditySensorSensorErrorColor OBJECT-TYPE
               SYNTAX  INTEGER
               ACCESS  read-write
               STATUS  mandatory
               DESCRIPTION
               "A SensorError Color of this sensor"
               ::=  {  humiditySensorEntry  59  }     

            humiditySensorAcknowledge OBJECT-TYPE
               SYNTAX  INTEGER {
                  acked(2)
               }
               ACCESS  read-write
               STATUS  mandatory
               DESCRIPTION
               "Humidity sensor acknowledge"
               ::=  {  humiditySensorEntry 70 }  

            humiditySensorId OBJECT-TYPE
               SYNTAX  INTEGER
               ACCESS  read-only
               STATUS  mandatory
               DESCRIPTION
               "The Sensor ID of this sensor, used to identify which sensor it is in the system configuration."
               ::= { humiditySensorEntry 1000 }

--/* End of humiditySensorEntry */

--/* Begin of dryContactSensorEntry */
         dryContactSensorTable OBJECT-TYPE
            SYNTAX  SEQUENCE OF DryContactSensorEntry
            ACCESS  not-accessible
            STATUS  mandatory
            DESCRIPTION
            "This table contains the property and reading value for every sensor."
            ::=  {  sensorByPort 4   }

         dryContactSensorEntry OBJECT-TYPE
            SYNTAX  DryContactSensorEntry
            ACCESS  not-accessible
            STATUS  mandatory
            DESCRIPTION
            "This is an entry in the sensorTemperatureEntry Table"
            INDEX         { dryContactSensorIndex }
            ::=  {  dryContactSensorTable 1 }

         DryContactSensorEntry ::= SEQUENCE {
               dryContactSensorIndex
                  DisplayString,
               dryContactSensorDescription
                  DisplayString,
               dryContactSensorType
                  INTEGER,
               dryContactSensorStatus
                  INTEGER,
               dryContactSensorGoOffline
                  INTEGER,
               dryContactSensorDirection
                  INTEGER,
               dryContactSensorNormalState
                  INTEGER,
               dryContactSensorControlMode
                  INTEGER,
               dryContactSensorOutputManualCycleTime
                  INTEGER,
               dryContactSensorOutputManualAction
                  INTEGER,
               dryContactSensorPort
                  INTEGER,
               dryContactSensorSubPort
                  INTEGER,
               dryContactSensorDeviceIndex
                  INTEGER,
               dryContactSensorCriticalDesc 
                  DisplayString,
               dryContactSensorNormalDesc 
                  DisplayString,
               dryContactSensorOnDesc
                  DisplayString,
               dryContactSensorOffDesc
                  DisplayString,
               dryContactSensorCriticalColor 
                  INTEGER,
               dryContactSensorNormalColor 
                  INTEGER,
               dryContactSensorOnColor
                  INTEGER,
               dryContactSensorOffColor
                  INTEGER,         
               dryContactSensorAcknowledge
                  INTEGER,
               dryContactSensorId
                  INTEGER
            }

            dryContactSensorIndex OBJECT-TYPE
               SYNTAX  DisplayString
               ACCESS  read-only
               STATUS  mandatory
               DESCRIPTION
               "The Sensor Compound ID of this sensor, used to identify which sensor it is in the system configuration."
               ::=  {  dryContactSensorEntry 1   }

            dryContactSensorDescription OBJECT-TYPE
               SYNTAX  DisplayString
               ACCESS  read-write
               STATUS  mandatory
               DESCRIPTION
               "A Description of this sensor Switch"
               ::=  {  dryContactSensorEntry 2   }

            dryContactSensorType OBJECT-TYPE
               SYNTAX  INTEGER {
                  drycontact-inout(7),
                  drycontact-input(8),
                  drycontact-array(22)
               }
               ACCESS  read-only
               STATUS  mandatory
               DESCRIPTION
               "Enter the type of this Sensor"
               ::=  {  dryContactSensorEntry 3  }

            dryContactSensorStatus OBJECT-TYPE
               SYNTAX  INTEGER {
                  noStatus(1),
                  normal(2),
                  highCritical(4),
                  lowCritical(6),
                  sensorError(7),
                  outputLow(8),
                  outputHigh(9)
               }
               ACCESS  read-only
               STATUS  mandatory
               DESCRIPTION
               "The current status of this Sensor, only input switches have a status"
               ::=  {  dryContactSensorEntry 6  }

            dryContactSensorGoOffline OBJECT-TYPE
               SYNTAX  INTEGER {
                  online(1),
                  goOffline(2)
               }
               ACCESS  read-write
               STATUS  mandatory
               DESCRIPTION
               "To take offline enter a 2"
               ::=  {  dryContactSensorEntry 8  }

            dryContactSensorDirection OBJECT-TYPE
               SYNTAX  INTEGER {
                  input(0),
                  output(1)
               }
               ACCESS  read-write
               STATUS  mandatory
               DESCRIPTION
               "To set a switch to input enter 0. To set a switch to output enter 1"
               ::=  {  dryContactSensorEntry 22  }

            dryContactSensorNormalState OBJECT-TYPE
               SYNTAX  INTEGER {
                  closed(0),
                  open(1)
               }
               ACCESS  read-write
               STATUS  mandatory
               DESCRIPTION
               "The normal state of an input switch. If an input switch is in this state it is normal, else it is critical. An open switch senses +5 volts. A closed switch senses 0 volts."
               ::=  {  dryContactSensorEntry 23  }
               
            dryContactSensorControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a sensor output."
               ::=  {  dryContactSensorEntry 24  }
               
            dryContactSensorOutputManualCycleTime OBJECT-TYPE
               SYNTAX  INTEGER (1..255)
               ACCESS  read-write
               STATUS  mandatory
               DESCRIPTION
               "Toggle period in seconds for Manual Cycle action."
               ::=  {  dryContactSensorEntry 25  }
               
            dryContactSensorOutputManualAction OBJECT-TYPE
               SYNTAX  INTEGER {
                  low(0),
                  high(1),
                  cycle-Low-High-Low(2),
                  cycle-High-Low-High(3)
               }
               ACCESS  read-write
               STATUS  mandatory
               DESCRIPTION
               "Control the sensor output manualy"
               ::=  {  dryContactSensorEntry 26  }

            dryContactSensorPort OBJECT-TYPE
               SYNTAX  INTEGER (0..65534)
               ACCESS  read-only
               STATUS  mandatory
               DESCRIPTION
               "Sensor port"
               ::=  {  dryContactSensorEntry 35 }

            dryContactSensorSubPort OBJECT-TYPE
               SYNTAX  INTEGER (0..65534)
               ACCESS  read-only
               STATUS  mandatory
               DESCRIPTION
               "Sensor sub port"
               ::=  {  dryContactSensorEntry 36 }

            dryContactSensorDeviceIndex OBJECT-TYPE
               SYNTAX  INTEGER (0..65534)
               ACCESS  read-only
               STATUS  mandatory
               DESCRIPTION
               "Device Index of sensor"
               ::=  {  dryContactSensorEntry 37 }
               
            dryContactSensorCriticalDesc OBJECT-TYPE
               SYNTAX  DisplayString
               ACCESS  read-write
               STATUS  mandatory
               DESCRIPTION
               "A Critical Description of this sensor"
               ::=  {  dryContactSensorEntry  46 } 

            dryContactSensorNormalDesc OBJECT-TYPE
               SYNTAX  DisplayString
               ACCESS  read-write
               STATUS  mandatory
               DESCRIPTION
               "A Normal Description of this sensor"
               ::=  {  dryContactSensorEntry  48  }

            dryContactSensorOnDesc OBJECT-TYPE
               SYNTAX  DisplayString
               ACCESS  read-write
               STATUS  mandatory
               DESCRIPTION
               "A On Description of this sensor"
               ::=  {  dryContactSensorEntry  52  }     

            dryContactSensorOffDesc OBJECT-TYPE
               SYNTAX  DisplayString
               ACCESS  read-write
               STATUS  mandatory
               DESCRIPTION
               "A Off Description of this sensor"
               ::=  {  dryContactSensorEntry  53  }                   

            dryContactSensorCriticalColor OBJECT-TYPE
               SYNTAX  INTEGER
               ACCESS  read-write
               STATUS  mandatory
               DESCRIPTION
               "A Critical Color of this sensor"
               ::=  {  dryContactSensorEntry  54  }               

            dryContactSensorNormalColor OBJECT-TYPE
               SYNTAX  INTEGER
               ACCESS  read-write
               STATUS  mandatory
               DESCRIPTION
               "A Normal Color of this sensor"
               ::=  {  dryContactSensorEntry  56  }

            dryContactSensorOnColor OBJECT-TYPE
               SYNTAX  INTEGER
               ACCESS  read-write
               STATUS  mandatory
               DESCRIPTION
               "A On Color of this sensor"
               ::=  {  dryContactSensorEntry  60  }    

            dryContactSensorOffColor OBJECT-TYPE
               SYNTAX  INTEGER
               ACCESS  read-write
               STATUS  mandatory
               DESCRIPTION
               "A Off Color of this sensor"
               ::=  {  dryContactSensorEntry  61  }      
        
            dryContactSensorAcknowledge OBJECT-TYPE
               SYNTAX  INTEGER {
                  acked(2)
               }
               ACCESS  read-write
               STATUS  mandatory
               DESCRIPTION
               "Dry Contact sensor acknowledge"
               ::=  {  dryContactSensorEntry 70 }
               
            dryContactSensorId OBJECT-TYPE
               SYNTAX  INTEGER
               ACCESS  read-only
               STATUS  mandatory
               DESCRIPTION
               "The Sensor ID of this sensor, used to identify which sensor it is in the system configuration."
               ::= { dryContactSensorEntry 1000 }

--/* End of dryContactSensorEntry */

--/* Begin of current4to20mASensorEntry */
         current4to20mASensorTable OBJECT-TYPE
            SYNTAX  SEQUENCE OF Current4to20mASensorEntry
            ACCESS  not-accessible
            STATUS  mandatory
            DESCRIPTION
            "This table contains the property and reading value for every sensor."
            ::=  {  sensorByPort 5   }

         current4to20mASensorEntry OBJECT-TYPE
            SYNTAX  Current4to20mASensorEntry
            ACCESS  not-accessible
            STATUS  mandatory
            DESCRIPTION
            "This is an entry in the sensorTemperatureEntry Table"
            INDEX         { current4to20mASensorIndex }
            ::=  {  current4to20mASensorTable 1 }

         Current4to20mASensorEntry ::= SEQUENCE {
               current4to20mASensorIndex
                  DisplayString,
               current4to20mASensorDescription
                  DisplayString,
               current4to20mASensorValue
                  INTEGER,
               current4to20mASensorUnit
                  DisplayString,
               current4to20mASensorStatus
                  INTEGER,
               current4to20mASensorGoOffline
                  INTEGER,
               current4to20mASensorLowCritical
                  INTEGER,
               current4to20mASensorLowWarning
                  INTEGER,
               current4to20mASensorHighWarning
                  INTEGER,
               current4to20mASensorHighCritical
                  INTEGER,
               current4to20mASensorRearm
                  INTEGER,
               current4to20mASensorDelayError
                  INTEGER,
               current4to20mASensorDelayNormal
                  INTEGER,
               current4to20mASensorDelayLowCritical
                  INTEGER,
               current4to20mASensorDelayLowWarning
                  INTEGER,
               current4to20mASensorDelayHighWarning
                  INTEGER,
               current4to20mASensorDelayHighCritical
                  INTEGER,
               current4to20mASensorRaw
                  INTEGER,
               current4to20mASensorOffset
                  INTEGER,
               current4to20mASensorAmountMaxVoltage
                  INTEGER,
               current4to20mASensorAmountBaseVoltage
                  INTEGER,
               current4to20mASensorPort
                  INTEGER,
               current4to20mASensorSubPort
                  INTEGER,
               current4to20mASensorDeviceIndex
                  INTEGER,
               current4to20mASensorMaxVoltage
                  INTEGER,
               current4to20mASensorBaseVoltage
                  INTEGER,
               current4to20mASensorDisplayStyle
                  INTEGER,
               current4to20mASensorHighCriticalDesc 
                  DisplayString,
               current4to20mASensorLowCriticalDesc 
                  DisplayString,
               current4to20mASensorNormalDesc 
                  DisplayString,
               current4to20mASensorLowWarningDesc 
                  DisplayString,   
               current4to20mASensorHighWarningDesc 
                  DisplayString,
               current4to20mASensorSensorErrorDesc 
                  DisplayString,
               current4to20mASensorHighCriticalColor 
                  INTEGER,
               current4to20mASensorLowCriticalColor 
                  INTEGER,
               current4to20mASensorNormalColor 
                  INTEGER,
               current4to20mASensorLowWarningColor 
                  INTEGER,   
               current4to20mASensorHighWarningColor 
                  INTEGER,
               current4to20mASensorSensorErrorColor 
                  INTEGER,
               current4to20mASensorAcknowledge     
                  INTEGER,
               current4to20mASensorId
                  INTEGER
            }

            current4to20mASensorIndex OBJECT-TYPE
               SYNTAX  DisplayString
               ACCESS  read-only
               STATUS  mandatory
               DESCRIPTION
               "The Sensor Compound ID of this sensor, used to identify which sensor it is in the system configuration."
               ::=  {  current4to20mASensorEntry 1   }

            current4to20mASensorDescription OBJECT-TYPE
               SYNTAX  DisplayString
               ACCESS  read-write
               STATUS  mandatory
               DESCRIPTION
               "A Description of this sensor"
               ::=  {  current4to20mASensorEntry 2   }

            current4to20mASensorValue OBJECT-TYPE
               SYNTAX  INTEGER
               ACCESS  read-only
               STATUS  mandatory
               DESCRIPTION
               "The reading value in this sensor"
               ::=  {  current4to20mASensorEntry 4   }

            current4to20mASensorUnit OBJECT-TYPE
               SYNTAX  DisplayString
               ACCESS  read-write
               STATUS  mandatory
               DESCRIPTION
               "The unit string"
               ::=  {  current4to20mASensorEntry 5  }

            current4to20mASensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  current4to20mASensorEntry 6   }

            current4to20mASensorGoOffline OBJECT-TYPE
               SYNTAX  INTEGER {
                  online(1),
                  goOffline(2)
               }
               ACCESS  read-write
               STATUS  mandatory
               DESCRIPTION
               "To take offline enter a 2"
               ::=  {  current4to20mASensorEntry 8   }

            current4to20mASensorLowCritical OBJECT-TYPE
               SYNTAX  INTEGER
               ACCESS  read-write
               STATUS  mandatory
               DESCRIPTION
               "How cold this sensor gets before it sends a critical event"
               ::=  {  current4to20mASensorEntry 9   }

            current4to20mASensorLowWarning OBJECT-TYPE
               SYNTAX  INTEGER
               ACCESS  read-write
               STATUS  mandatory
               DESCRIPTION
               "How cold this sensor gets before it sends a warning"
               ::=  {  current4to20mASensorEntry 10   }
   
            current4to20mASensorHighWarning OBJECT-TYPE
               SYNTAX  INTEGER
               ACCESS  read-write
               STATUS  mandatory
               DESCRIPTION
               "How hot this sensor gets before it sends a warning"
               ::=  {  current4to20mASensorEntry 11   }  

            current4to20mASensorHighCritical OBJECT-TYPE
               SYNTAX  INTEGER
               ACCESS  read-write
               STATUS  mandatory
               DESCRIPTION
               "How hot this sensor gets before it sends a critical event"
               ::=  {  current4to20mASensorEntry 12   }   

            current4to20mASensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  current4to20mASensorEntry 13   }

            current4to20mASensorDelayError OBJECT-TYPE
               SYNTAX  INTEGER (0..65534)
               ACCESS  read-write
               STATUS  mandatory
               DESCRIPTION
               "Time in seconds after the sensor has been in error status before report as an error"
               ::=  {  current4to20mASensorEntry 14   }

            current4to20mASensorDelayNormal OBJECT-TYPE
               SYNTAX  INTEGER (0..65534)
               ACCESS  read-write
               STATUS  mandatory
               DESCRIPTION
               "Time in seconds after the sensor change from error to normal before report as normal"
               ::=  {  current4to20mASensorEntry 15   }

            current4to20mASensorDelayLowCritical OBJECT-TYPE
               SYNTAX INTEGER (0..65535)
               ACCESS read-write
               STATUS mandatory
               DESCRIPTION
               "Continuous time for this sensor to be in Low Critical before accepting new Status."
               ::= {  current4to20mASensorEntry 16 }
               
            current4to20mASensorDelayLowWarning OBJECT-TYPE
               SYNTAX INTEGER (0..65535)
               ACCESS read-write
               STATUS mandatory
               DESCRIPTION
               "Continuous time for this sensor to be in Low Warning before accepting new Status."
               ::= {  current4to20mASensorEntry 17 }

            current4to20mASensorDelayHighWarning OBJECT-TYPE
               SYNTAX INTEGER (0..65535)
               ACCESS read-write
               STATUS mandatory
               DESCRIPTION
               "Continuous time for this sensor to be in High Warning before accepting new Status."
               ::= {  current4to20mASensorEntry 18 }

            current4to20mASensorDelayHighCritical OBJECT-TYPE
               SYNTAX INTEGER (0..65535)
               ACCESS read-write
               STATUS mandatory
               DESCRIPTION
               "Continuous time for this sensor to be in High Critical before accepting new Status."
               ::= {  current4to20mASensorEntry 19 }

            current4to20mASensorRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  current4to20mASensorEntry 20   }

            current4to20mASensorOffset OBJECT-TYPE
               SYNTAX  INTEGER
               ACCESS  read-write
               STATUS  mandatory
               DESCRIPTION
               "4to20mA Offset reading"
               ::=  {  current4to20mASensorEntry 21   }

            current4to20mASensorAmountMaxVoltage OBJECT-TYPE
               SYNTAX  INTEGER
               ACCESS  read-write
               STATUS  mandatory
               DESCRIPTION
               "The maximum scale of 4to20mA conversion."
               ::=  {  current4to20mASensorEntry 33   }

            current4to20mASensorAmountBaseVoltage OBJECT-TYPE
               SYNTAX  INTEGER
               ACCESS  read-write
               STATUS  mandatory
               DESCRIPTION
               "The base scale of 4to20mA conversion."
               ::=  {  current4to20mASensorEntry 34   }

            current4to20mASensorPort OBJECT-TYPE
               SYNTAX  INTEGER (0..65534)
               ACCESS  read-only
               STATUS  mandatory
               DESCRIPTION
               "Sensor port"
               ::=  {  current4to20mASensorEntry 35 }

            current4to20mASensorSubPort OBJECT-TYPE
               SYNTAX  INTEGER (0..65534)
               ACCESS  read-only
               STATUS  mandatory
               DESCRIPTION
               "Sensor sub port"
               ::=  {  current4to20mASensorEntry 36 }

            current4to20mASensorDeviceIndex OBJECT-TYPE
               SYNTAX  INTEGER (0..65534)
               ACCESS  read-only
               STATUS  mandatory
               DESCRIPTION
               "Device Index of sensor"
               ::=  {  current4to20mASensorEntry 37 }
               
            current4to20mASensorMaxVoltage OBJECT-TYPE
               SYNTAX  INTEGER
               ACCESS  read-write
               STATUS  mandatory
               DESCRIPTION
               "The max range for use in conversion."
               ::=  {  current4to20mASensorEntry 43   }

            current4to20mASensorBaseVoltage OBJECT-TYPE
               SYNTAX  INTEGER
               ACCESS  read-write
               STATUS  mandatory
               DESCRIPTION
               "The base range for use in conversion."
               ::=  {  current4to20mASensorEntry 44   }
               
            current4to20mASensorDisplayStyle OBJECT-TYPE
               SYNTAX  INTEGER {
                  basic(0),
                  gauge(1)
               }
               ACCESS  read-write
               STATUS  mandatory
               DESCRIPTION
               "4to20mA display style"
               ::=  {  current4to20mASensorEntry 45 }  
               
            current4to20mASensorHighCriticalDesc OBJECT-TYPE
               SYNTAX  DisplayString
               ACCESS  read-write
               STATUS  mandatory
               DESCRIPTION
               "A HighCritical Description of this sensor"
               ::=  {  current4to20mASensorEntry  46  }               

            current4to20mASensorLowCriticalDesc OBJECT-TYPE
               SYNTAX  DisplayString
               ACCESS  read-write
               STATUS  mandatory
               DESCRIPTION
               "A LowCritical Description of this sensor"
               ::=  {  current4to20mASensorEntry  47  }

            current4to20mASensorNormalDesc OBJECT-TYPE
               SYNTAX  DisplayString
               ACCESS  read-write
               STATUS  mandatory
               DESCRIPTION
               "A Normal Description of this sensor"
               ::=  {  current4to20mASensorEntry  48  }
               
            current4to20mASensorLowWarningDesc OBJECT-TYPE
               SYNTAX  DisplayString
               ACCESS  read-write
               STATUS  mandatory
               DESCRIPTION
               "A LowWarning Description of this sensor"
               ::=  {  current4to20mASensorEntry  49  }
               
            current4to20mASensorHighWarningDesc OBJECT-TYPE
               SYNTAX  DisplayString
               ACCESS  read-write
               STATUS  mandatory
               DESCRIPTION
               "A HighWarning Description of this sensor"
               ::=  {  current4to20mASensorEntry  50  }
               
            current4to20mASensorSensorErrorDesc OBJECT-TYPE
               SYNTAX  DisplayString
               ACCESS  read-write
               STATUS  mandatory
               DESCRIPTION
               "A SensorError Description of this sensor"
               ::=  {  current4to20mASensorEntry  51  }    

            current4to20mASensorHighCriticalColor OBJECT-TYPE
               SYNTAX  INTEGER
               ACCESS  read-write
               STATUS  mandatory
               DESCRIPTION
               "A HighCritical Color of this sensor"
               ::=  {  current4to20mASensorEntry  54  }               

            current4to20mASensorLowCriticalColor OBJECT-TYPE
               SYNTAX  INTEGER
               ACCESS  read-write
               STATUS  mandatory
               DESCRIPTION
               "A LowCritical Color of this sensor"
               ::=  {  current4to20mASensorEntry  55  }

            current4to20mASensorNormalColor OBJECT-TYPE
               SYNTAX  INTEGER
               ACCESS  read-write
               STATUS  mandatory
               DESCRIPTION
               "A Normal Color of this sensor"
               ::=  {  current4to20mASensorEntry  56  }
               
            current4to20mASensorLowWarningColor OBJECT-TYPE
               SYNTAX  INTEGER
               ACCESS  read-write
               STATUS  mandatory
               DESCRIPTION
               "A LowWarning Color of this sensor"
               ::=  {  current4to20mASensorEntry  57  }
               
            current4to20mASensorHighWarningColor OBJECT-TYPE
               SYNTAX  INTEGER
               ACCESS  read-write
               STATUS  mandatory
               DESCRIPTION
               "A HighWarning Color of this sensor"
               ::=  {  current4to20mASensorEntry  58  }
               
            current4to20mASensorSensorErrorColor OBJECT-TYPE
               SYNTAX  INTEGER
               ACCESS  read-write
               STATUS  mandatory
               DESCRIPTION
               "A SensorError Color of this sensor"
               ::=  {  current4to20mASensorEntry  59  }  
               
            current4to20mASensorAcknowledge OBJECT-TYPE
               SYNTAX  INTEGER {
                  acked(2)
               }
               ACCESS  read-write
               STATUS  mandatory
               DESCRIPTION
               "4to20mA sensor acknowledge"
               ::=  {  current4to20mASensorEntry 70 }  

            current4to20mASensorId OBJECT-TYPE
               SYNTAX  INTEGER
               ACCESS  read-only
               STATUS  mandatory
               DESCRIPTION
               "The Sensor ID of this sensor, used to identify which sensor it is in the system configuration."
               ::= { current4to20mASensorEntry 1000 }

--/* End of current4to20mASensorEntry */

--/* Begin of dcVoltageSensorEntry */
         dcVoltageSensorTable OBJECT-TYPE
            SYNTAX  SEQUENCE OF DcVoltageSensorEntry
            ACCESS  not-accessible
            STATUS  mandatory
            DESCRIPTION
            "This table contains the property and reading value for every sensor."
            ::=  {  sensorByPort 6   }

         dcVoltageSensorEntry OBJECT-TYPE
            SYNTAX  DcVoltageSensorEntry
            ACCESS  not-accessible
            STATUS  mandatory
            DESCRIPTION
            "This is an entry in the sensorTemperatureEntry Table"
            INDEX         { dcVoltageSensorIndex }
            ::=  {  dcVoltageSensorTable 1 }

         DcVoltageSensorEntry ::= SEQUENCE {
               dcVoltageSensorIndex
                  DisplayString,
               dcVoltageSensorDescription
                  DisplayString,
               dcVoltageSensorValue
                  INTEGER,
               dcVoltageSensorUnit
                  DisplayString,
               dcVoltageSensorStatus
                  INTEGER,
               dcVoltageSensorGoOffline
                  INTEGER,
               dcVoltageSensorLowCritical
                  INTEGER,
               dcVoltageSensorLowWarning
                  INTEGER,
               dcVoltageSensorHighWarning
                  INTEGER,
               dcVoltageSensorHighCritical
                  INTEGER,
               dcVoltageSensorRearm
                  INTEGER,
               dcVoltageSensorDelayError
                  INTEGER,
               dcVoltageSensorDelayNormal
                  INTEGER,
               dcVoltageSensorDelayLowCritical
                  INTEGER,
               dcVoltageSensorDelayLowWarning
                  INTEGER,
               dcVoltageSensorDelayHighWarning
                  INTEGER,
               dcVoltageSensorDelayHighCritical
                  INTEGER,
               dcVoltageSensorRaw
                  INTEGER,
               dcVoltageSensorOffset
                  INTEGER,
               dcVoltageSensorJumper
                  INTEGER,
               dcVoltageSensorAmountMaxVoltage
                  INTEGER,
               dcVoltageSensorAmountBaseVoltage
                  INTEGER,
               dcVoltageSensorPort
                  INTEGER,
               dcVoltageSensorSubPort
                  INTEGER,
               dcVoltageSensorDeviceIndex
                  INTEGER,
               dcVoltageSensorMaxVoltage
                  INTEGER,
               dcVoltageSensorBaseVoltage                  
                  INTEGER,
               dcVoltageSensorDisplayStyle
                  INTEGER,
               dcVoltageSensorHighCriticalDesc 
                  DisplayString,
               dcVoltageSensorLowCriticalDesc 
                  DisplayString,
               dcVoltageSensorNormalDesc 
                  DisplayString,
               dcVoltageSensorLowWarningDesc 
                  DisplayString,   
               dcVoltageSensorHighWarningDesc 
                  DisplayString,
               dcVoltageSensorSensorErrorDesc 
                  DisplayString,
               dcVoltageSensorHighCriticalColor 
                  INTEGER,
               dcVoltageSensorLowCriticalColor 
                  INTEGER,
               dcVoltageSensorNormalColor 
                  INTEGER,
               dcVoltageSensorLowWarningColor 
                  INTEGER,   
               dcVoltageSensorHighWarningColor 
                  INTEGER,
               dcVoltageSensorSensorErrorColor 
                  INTEGER,
               dcVoltageSensorAcknowledge
                  INTEGER,
               dcVoltageSensorId
                  INTEGER
            }

            dcVoltageSensorIndex OBJECT-TYPE
               SYNTAX  DisplayString
               ACCESS  read-only
               STATUS  mandatory
               DESCRIPTION
               "The Sensor Compound ID of this sensor, used to identify which sensor it is in the system configuration."
               ::=  {  dcVoltageSensorEntry 1   }

            dcVoltageSensorDescription OBJECT-TYPE
               SYNTAX  DisplayString
               ACCESS  read-write
               STATUS  mandatory
               DESCRIPTION
               "A Description of this sensor"
               ::=  {  dcVoltageSensorEntry 2   }

            dcVoltageSensorValue OBJECT-TYPE
               SYNTAX  INTEGER
               ACCESS  read-only
               STATUS  mandatory
               DESCRIPTION
               "The reading value in this sensor"
               ::=  {  dcVoltageSensorEntry 4   }

            dcVoltageSensorUnit OBJECT-TYPE
               SYNTAX  DisplayString
               ACCESS  read-write
               STATUS  mandatory
               DESCRIPTION
               "The unit string"
               ::=  {  dcVoltageSensorEntry 5  }

            dcVoltageSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  dcVoltageSensorEntry 6   }

            dcVoltageSensorGoOffline OBJECT-TYPE
               SYNTAX  INTEGER {
                  online(1),
                  goOffline(2)
               }
               ACCESS  read-write
               STATUS  mandatory
               DESCRIPTION
               "To take offline enter a 2"
               ::=  {  dcVoltageSensorEntry 8   }

            dcVoltageSensorLowCritical OBJECT-TYPE
               SYNTAX  INTEGER
               ACCESS  read-write
               STATUS  mandatory
               DESCRIPTION
               "How cold this sensor gets before it sends a critical event"
               ::=  {  dcVoltageSensorEntry 9   }

            dcVoltageSensorLowWarning OBJECT-TYPE
               SYNTAX  INTEGER
               ACCESS  read-write
               STATUS  mandatory
               DESCRIPTION
               "How cold this sensor gets before it sends a warning"
               ::=  {  dcVoltageSensorEntry 10   }
   
            dcVoltageSensorHighWarning OBJECT-TYPE
               SYNTAX  INTEGER
               ACCESS  read-write
               STATUS  mandatory
               DESCRIPTION
               "How hot this sensor gets before it sends a warning"
               ::=  {  dcVoltageSensorEntry 11   }  

            dcVoltageSensorHighCritical OBJECT-TYPE
               SYNTAX  INTEGER
               ACCESS  read-write
               STATUS  mandatory
               DESCRIPTION
               "How hot this sensor gets before it sends a critical event"
               ::=  {  dcVoltageSensorEntry 12   }   

            dcVoltageSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  dcVoltageSensorEntry 13   }

            dcVoltageSensorDelayError OBJECT-TYPE
               SYNTAX  INTEGER (0..65534)
               ACCESS  read-write
               STATUS  mandatory
               DESCRIPTION
               "Time in seconds after the sensor has been in error status before report as an error"
               ::=  {  dcVoltageSensorEntry 14   }

            dcVoltageSensorDelayNormal OBJECT-TYPE
               SYNTAX  INTEGER (0..65534)
               ACCESS  read-write
               STATUS  mandatory
               DESCRIPTION
               "Time in seconds after the sensor change from error to normal before report as normal"
               ::=  {  dcVoltageSensorEntry 15   }

            dcVoltageSensorDelayLowCritical OBJECT-TYPE
               SYNTAX INTEGER (0..65535)
               ACCESS read-write
               STATUS mandatory
               DESCRIPTION
               "Continuous time for this sensor to be in Low Critical before accepting new Status."
               ::= {  dcVoltageSensorEntry 16 }
               
            dcVoltageSensorDelayLowWarning OBJECT-TYPE
               SYNTAX INTEGER (0..65535)
               ACCESS read-write
               STATUS mandatory
               DESCRIPTION
               "Continuous time for this sensor to be in Low Warning before accepting new Status."
               ::= {  dcVoltageSensorEntry 17 }

            dcVoltageSensorDelayHighWarning OBJECT-TYPE
               SYNTAX INTEGER (0..65535)
               ACCESS read-write
               STATUS mandatory
               DESCRIPTION
               "Continuous time for this sensor to be in High Warning before accepting new Status."
               ::= {  dcVoltageSensorEntry 18 }

            dcVoltageSensorDelayHighCritical OBJECT-TYPE
               SYNTAX INTEGER (0..65535)
               ACCESS read-write
               STATUS mandatory
               DESCRIPTION
               "Continuous time for this sensor to be in High Critical before accepting new Status."
               ::= {  dcVoltageSensorEntry 19 }

            dcVoltageSensorRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  dcVoltageSensorEntry 20   }

            dcVoltageSensorOffset OBJECT-TYPE
               SYNTAX  INTEGER
               ACCESS  read-write
               STATUS  mandatory
               DESCRIPTION
               "DC voltage Offset reading"
               ::=  {  dcVoltageSensorEntry 21   }

            dcVoltageSensorJumper OBJECT-TYPE
               SYNTAX  INTEGER {
                  jumperAt-60(-600),
                  jumperAt-40(-400),
                  jumperAt-30(-300),
                  jumperAt-20(-200),
                  jumperAt-10(-100),                  
                  jumperAt10(100),
                  jumperAt20(200),
                  jumperAt30(300),
                  jumperAt40(400),
                  jumperAt60(600)                  
               }
               ACCESS  read-write
               STATUS  mandatory
               DESCRIPTION
               "Selected voltage scale (jumper 0) in DC voltage conversion."
               ::=  {  dcVoltageSensorEntry 32   }

            dcVoltageSensorAmountMaxVoltage OBJECT-TYPE
               SYNTAX  INTEGER
               ACCESS  read-write
               STATUS  mandatory
               DESCRIPTION
               "The maximum scale of DC voltage conversion."
               ::=  {  dcVoltageSensorEntry 33   }

            dcVoltageSensorAmountBaseVoltage OBJECT-TYPE
               SYNTAX  INTEGER
               ACCESS  read-write
               STATUS  mandatory
               DESCRIPTION
               "The base scale of DC voltage conversion."
               ::=  {  dcVoltageSensorEntry 34   }

            dcVoltageSensorPort OBJECT-TYPE
               SYNTAX  INTEGER (0..65534)
               ACCESS  read-only
               STATUS  mandatory
               DESCRIPTION
               "Sensor port"
               ::=  {  dcVoltageSensorEntry 35 }

            dcVoltageSensorSubPort OBJECT-TYPE
               SYNTAX  INTEGER (0..65534)
               ACCESS  read-only
               STATUS  mandatory
               DESCRIPTION
               "Sensor sub port"
               ::=  {  dcVoltageSensorEntry 36 }

            dcVoltageSensorDeviceIndex OBJECT-TYPE
               SYNTAX  INTEGER (0..65534)
               ACCESS  read-only
               STATUS  mandatory
               DESCRIPTION
               "Device Index of sensor"
               ::=  {  dcVoltageSensorEntry 37 }

            dcVoltageSensorMaxVoltage OBJECT-TYPE
               SYNTAX  INTEGER
               ACCESS  read-write
               STATUS  mandatory
               DESCRIPTION
               "The max voltage range for use in conversion."
               ::=  {  dcVoltageSensorEntry 43   }

            dcVoltageSensorBaseVoltage OBJECT-TYPE
               SYNTAX  INTEGER
               ACCESS  read-write
               STATUS  mandatory
               DESCRIPTION
               "The base voltage range for use in conversion."
               ::=  {  dcVoltageSensorEntry 44   }
               
            dcVoltageSensorDisplayStyle OBJECT-TYPE
               SYNTAX  INTEGER {
                  basic(0),
                  gauge(1)
               }
               ACCESS  read-write
               STATUS  mandatory
               DESCRIPTION
               "DCVoltage display style"
               ::=  {  dcVoltageSensorEntry 45 }
               
            dcVoltageSensorHighCriticalDesc OBJECT-TYPE
               SYNTAX  DisplayString
               ACCESS  read-write
               STATUS  mandatory
               DESCRIPTION
               "A HighCritical Description of this sensor"
               ::=  {  dcVoltageSensorEntry  46  }               

            dcVoltageSensorLowCriticalDesc OBJECT-TYPE
               SYNTAX  DisplayString
               ACCESS  read-write
               STATUS  mandatory
               DESCRIPTION
               "A LowCritical Description of this sensor"
               ::=  {  dcVoltageSensorEntry  47  }

            dcVoltageSensorNormalDesc OBJECT-TYPE
               SYNTAX  DisplayString
               ACCESS  read-write
               STATUS  mandatory
               DESCRIPTION
               "A Normal Description of this sensor"
               ::=  {  dcVoltageSensorEntry  48  }
               
            dcVoltageSensorLowWarningDesc OBJECT-TYPE
               SYNTAX  DisplayString
               ACCESS  read-write
               STATUS  mandatory
               DESCRIPTION
               "A LowWarning Description of this sensor"
               ::=  {  dcVoltageSensorEntry  49  }
               
            dcVoltageSensorHighWarningDesc OBJECT-TYPE
               SYNTAX  DisplayString
               ACCESS  read-write
               STATUS  mandatory
               DESCRIPTION
               "A HighWarning Description of this sensor"
               ::=  {  dcVoltageSensorEntry  50  }
               
            dcVoltageSensorSensorErrorDesc OBJECT-TYPE
               SYNTAX  DisplayString
               ACCESS  read-write
               STATUS  mandatory
               DESCRIPTION
               "A SensorError Description of this sensor"
               ::=  {  dcVoltageSensorEntry  51  }  

            dcVoltageSensorHighCriticalColor OBJECT-TYPE
               SYNTAX  INTEGER
               ACCESS  read-write
               STATUS  mandatory
               DESCRIPTION
               "A HighCritical Color of this sensor"
               ::=  {  dcVoltageSensorEntry  54  }               

            dcVoltageSensorLowCriticalColor OBJECT-TYPE
               SYNTAX  INTEGER
               ACCESS  read-write
               STATUS  mandatory
               DESCRIPTION
               "A LowCritical Color of this sensor"
               ::=  {  dcVoltageSensorEntry  55  }

            dcVoltageSensorNormalColor OBJECT-TYPE
               SYNTAX  INTEGER
               ACCESS  read-write
               STATUS  mandatory
               DESCRIPTION
               "A Normal Color of this sensor"
               ::=  {  dcVoltageSensorEntry  56  }
               
            dcVoltageSensorLowWarningColor OBJECT-TYPE
               SYNTAX  INTEGER
               ACCESS  read-write
               STATUS  mandatory
               DESCRIPTION
               "A LowWarning Color of this sensor"
               ::=  {  dcVoltageSensorEntry  57  }
               
            dcVoltageSensorHighWarningColor OBJECT-TYPE
               SYNTAX  INTEGER
               ACCESS  read-write
               STATUS  mandatory
               DESCRIPTION
               "A HighWarning Color of this sensor"
               ::=  {  dcVoltageSensorEntry  58  }
               
            dcVoltageSensorSensorErrorColor OBJECT-TYPE
               SYNTAX  INTEGER
               ACCESS  read-write
               STATUS  mandatory
               DESCRIPTION
               "A SensorError Color of this sensor"
               ::=  {  dcVoltageSensorEntry  59  }  
                
            dcVoltageSensorAcknowledge OBJECT-TYPE
               SYNTAX  INTEGER {
                  acked(2)
               }
               ACCESS  read-write
               STATUS  mandatory
               DESCRIPTION
               "DCvoltage sensor acknowledge"
               ::=  {  dcVoltageSensorEntry 70 }  

            dcVoltageSensorId OBJECT-TYPE
               SYNTAX  INTEGER
               ACCESS  read-only
               STATUS  mandatory
               DESCRIPTION
               "The Sensor ID of this sensor, used to identify which sensor it is in the system configuration."
               ::= { dcVoltageSensorEntry 1000 }

--/* End of dcVoltageSensorEntry */

--/* Begin of airflowSensorEntry */
         airflowSensorTable OBJECT-TYPE
            SYNTAX  SEQUENCE OF AirflowSensorEntry
            ACCESS  not-accessible
            STATUS  mandatory
            DESCRIPTION
            "This table contains the property and reading value for every sensor."
            ::=  {  sensorByPort 7   }

         airflowSensorEntry OBJECT-TYPE
            SYNTAX  AirflowSensorEntry
            ACCESS  not-accessible
            STATUS  mandatory
            DESCRIPTION
            "This is an entry in the sensorTemperatureEntry Table"
            INDEX         { airflowSensorIndex }
            ::=  {  airflowSensorTable 1 }

         AirflowSensorEntry ::= SEQUENCE {
               airflowSensorIndex
                  DisplayString,
               airflowSensorDescription
                  DisplayString,
               airflowSensorValue
                  INTEGER,
               airflowSensorStatus
                  INTEGER,
               airflowSensorGoOffline
                  INTEGER,
               airflowSensorLowCritical
                  INTEGER,
               airflowSensorLowWarning
                  INTEGER,
               airflowSensorHighWarning
                  INTEGER,
               airflowSensorHighCritical
                  INTEGER,
               airflowSensorRearm
                  INTEGER,
               airflowSensorDelayError
                  INTEGER,
               airflowSensorDelayNormal
                  INTEGER,
               airflowSensorDelayLowCritical
                  INTEGER,
               airflowSensorDelayLowWarning
                  INTEGER,
               airflowSensorDelayHighWarning
                  INTEGER,
               airflowSensorDelayHighCritical
                  INTEGER,
               airflowSensorRaw
                  INTEGER,
               airflowSensorPort
                  INTEGER,
               airflowSensorSubPort
                  INTEGER,
               airflowSensorDeviceIndex
                  INTEGER,
               airflowSensorDisplayStyle
                  INTEGER,
               airflowSensorHighCriticalDesc 
                  DisplayString,
               airflowSensorLowCriticalDesc 
                  DisplayString,
               airflowSensorNormalDesc 
                  DisplayString,
               airflowSensorLowWarningDesc 
                  DisplayString,   
               airflowSensorHighWarningDesc 
                  DisplayString,
               airflowSensorSensorErrorDesc 
                  DisplayString,
               airflowSensorHighCriticalColor 
                  INTEGER,
               airflowSensorLowCriticalColor 
                  INTEGER,
               airflowSensorNormalColor 
                  INTEGER,
               airflowSensorLowWarningColor 
                  INTEGER,   
               airflowSensorHighWarningColor 
                  INTEGER,
               airflowSensorSensorErrorColor 
                  INTEGER,
               airflowSensorAcknowledge  
                  INTEGER,
               airflowSensorId
                  INTEGER
            }

            airflowSensorIndex OBJECT-TYPE
               SYNTAX  DisplayString
               ACCESS  read-only
               STATUS  mandatory
               DESCRIPTION
               "The Sensor Compound ID of this sensor, used to identify which sensor it is in the system configuration."
               ::=  {  airflowSensorEntry 1   }

            airflowSensorDescription OBJECT-TYPE
               SYNTAX  DisplayString
               ACCESS  read-write
               STATUS  mandatory
               DESCRIPTION
               "A Description of this sensor Switch"
               ::=  {  airflowSensorEntry 2   }

            airflowSensorValue OBJECT-TYPE
               SYNTAX  INTEGER
               ACCESS  read-only
               STATUS  mandatory
               DESCRIPTION
               "The reading value in this sensor"
               ::=  {  airflowSensorEntry 4   }

            airflowSensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  airflowSensorEntry 6  }

            airflowSensorGoOffline OBJECT-TYPE
               SYNTAX  INTEGER {
                  online(1),
                  goOffline(2)
               }
               ACCESS  read-write
               STATUS  mandatory
               DESCRIPTION
               "To take offline enter a 2"
               ::=  {  airflowSensorEntry 8  }

            airflowSensorLowCritical OBJECT-TYPE
               SYNTAX  INTEGER
               ACCESS  read-write
               STATUS  mandatory
               DESCRIPTION
               "How cold this sensor gets before it sends a critical event"
               ::=  {  airflowSensorEntry 9   }

            airflowSensorLowWarning OBJECT-TYPE
               SYNTAX  INTEGER
               ACCESS  read-write
               STATUS  mandatory
               DESCRIPTION
               "How cold this sensor gets before it sends a warning"
               ::=  {  airflowSensorEntry 10   }
   
            airflowSensorHighWarning OBJECT-TYPE
               SYNTAX  INTEGER
               ACCESS  read-write
               STATUS  mandatory
               DESCRIPTION
               "How hot this sensor gets before it sends a warning"
               ::=  {  airflowSensorEntry 11   }  

            airflowSensorHighCritical OBJECT-TYPE
               SYNTAX  INTEGER
               ACCESS  read-write
               STATUS  mandatory
               DESCRIPTION
               "How hot this sensor gets before it sends a critical event"
               ::=  {  airflowSensorEntry 12   }   

            airflowSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  airflowSensorEntry 13   }

            airflowSensorDelayError OBJECT-TYPE
               SYNTAX  INTEGER (0..65534)
               ACCESS  read-write
               STATUS  mandatory
               DESCRIPTION
               "Time in seconds after the sensor has been in error status before report as an error"
               ::=  {  airflowSensorEntry 14   }

            airflowSensorDelayNormal OBJECT-TYPE
               SYNTAX  INTEGER (0..65534)
               ACCESS  read-write
               STATUS  mandatory
               DESCRIPTION
               "Time in seconds after the sensor change from error to normal before report as normal"
               ::=  {  airflowSensorEntry 15   }

            airflowSensorDelayLowCritical OBJECT-TYPE
               SYNTAX INTEGER (0..65535)
               ACCESS read-write
               STATUS mandatory
               DESCRIPTION
               "Continuous time for this sensor to be in Low Critical before accepting new Status."
               ::= {  airflowSensorEntry 16 }
               
            airflowSensorDelayLowWarning OBJECT-TYPE
               SYNTAX INTEGER (0..65535)
               ACCESS read-write
               STATUS mandatory
               DESCRIPTION
               "Continuous time for this sensor to be in Low Warning before accepting new Status."
               ::= {  airflowSensorEntry 17 }

            airflowSensorDelayHighWarning OBJECT-TYPE
               SYNTAX INTEGER (0..65535)
               ACCESS read-write
               STATUS mandatory
               DESCRIPTION
               "Continuous time for this sensor to be in High Warning before accepting new Status."
               ::= {  airflowSensorEntry 18 }

            airflowSensorDelayHighCritical OBJECT-TYPE
               SYNTAX INTEGER (0..65535)
               ACCESS read-write
               STATUS mandatory
               DESCRIPTION
               "Continuous time for this sensor to be in High Critical before accepting new Status."
               ::= {  airflowSensorEntry 19 }

            airflowSensorRaw OBJECT-TYPE
               SYNTAX  INTEGER
               ACCESS  read-only
               STATUS  mandatory
               DESCRIPTION
               "The unformatted, raw, A/D value in this sensor. Contains more resolution than the formated percentage. This number can go from 0 to 1023 depending on the input voltage"
               ::=  {  airflowSensorEntry 20   }

            airflowSensorPort OBJECT-TYPE
               SYNTAX  INTEGER (0..65534)
               ACCESS  read-only
               STATUS  mandatory
               DESCRIPTION
               "Sensor port"
               ::=  {  airflowSensorEntry 35 }

            airflowSensorSubPort OBJECT-TYPE
               SYNTAX  INTEGER (0..65534)
               ACCESS  read-only
               STATUS  mandatory
               DESCRIPTION
               "Sensor sub port"
               ::=  {  airflowSensorEntry 36 }

            airflowSensorDeviceIndex OBJECT-TYPE
               SYNTAX  INTEGER (0..65534)
               ACCESS  read-only
               STATUS  mandatory
               DESCRIPTION
               "Device Index of sensor"
               ::=  {  airflowSensorEntry 37 }

            airflowSensorDisplayStyle OBJECT-TYPE
               SYNTAX  INTEGER {
                  basic(0),
                  gauge(1)
               }
               ACCESS  read-write
               STATUS  mandatory
               DESCRIPTION
               "Airflow display style"
               ::=  {  airflowSensorEntry 45 }
               
            airflowSensorHighCriticalDesc OBJECT-TYPE
               SYNTAX  DisplayString
               ACCESS  read-write
               STATUS  mandatory
               DESCRIPTION
               "A HighCritical Description of this sensor"
               ::=  {  airflowSensorEntry  46  }               

            airflowSensorLowCriticalDesc OBJECT-TYPE
               SYNTAX  DisplayString
               ACCESS  read-write
               STATUS  mandatory
               DESCRIPTION
               "A LowCritical Description of this sensor"
               ::=  {  airflowSensorEntry  47  }

            airflowSensorNormalDesc OBJECT-TYPE
               SYNTAX  DisplayString
               ACCESS  read-write
               STATUS  mandatory
               DESCRIPTION
               "A Normal Description of this sensor"
               ::=  {  airflowSensorEntry  48  }
               
            airflowSensorLowWarningDesc OBJECT-TYPE
               SYNTAX  DisplayString
               ACCESS  read-write
               STATUS  mandatory
               DESCRIPTION
               "A LowWarning Description of this sensor"
               ::=  {  airflowSensorEntry  49  }
               
            airflowSensorHighWarningDesc OBJECT-TYPE
               SYNTAX  DisplayString
               ACCESS  read-write
               STATUS  mandatory
               DESCRIPTION
               "A HighWarning Description of this sensor"
               ::=  {  airflowSensorEntry  50  }
               
            airflowSensorSensorErrorDesc OBJECT-TYPE
               SYNTAX  DisplayString
               ACCESS  read-write
               STATUS  mandatory
               DESCRIPTION
               "A SensorError Description of this sensor"
               ::=  {  airflowSensorEntry  51  }  

            airflowSensorHighCriticalColor OBJECT-TYPE
               SYNTAX  INTEGER
               ACCESS  read-write
               STATUS  mandatory
               DESCRIPTION
               "A HighCritical Color of this sensor"
               ::=  {  airflowSensorEntry  54  }               

            airflowSensorLowCriticalColor OBJECT-TYPE
               SYNTAX  INTEGER
               ACCESS  read-write
               STATUS  mandatory
               DESCRIPTION
               "A LowCritical Color of this sensor"
               ::=  {  airflowSensorEntry  55  }

            airflowSensorNormalColor OBJECT-TYPE
               SYNTAX  INTEGER
               ACCESS  read-write
               STATUS  mandatory
               DESCRIPTION
               "A Normal Color of this sensor"
               ::=  {  airflowSensorEntry  56  }
               
            airflowSensorLowWarningColor OBJECT-TYPE
               SYNTAX  INTEGER
               ACCESS  read-write
               STATUS  mandatory
               DESCRIPTION
               "A LowWarning Color of this sensor"
               ::=  {  airflowSensorEntry  57  }
               
            airflowSensorHighWarningColor OBJECT-TYPE
               SYNTAX  INTEGER
               ACCESS  read-write
               STATUS  mandatory
               DESCRIPTION
               "A HighWarning Color of this sensor"
               ::=  {  airflowSensorEntry  58  }
               
            airflowSensorSensorErrorColor OBJECT-TYPE
               SYNTAX  INTEGER
               ACCESS  read-write
               STATUS  mandatory
               DESCRIPTION
               "A SensorError Color of this sensor"
               ::=  {  airflowSensorEntry  59  }   

            airflowSensorAcknowledge OBJECT-TYPE
               SYNTAX  INTEGER {
                  acked(2)
               }
               ACCESS  read-write
               STATUS  mandatory
               DESCRIPTION
               "Airflow sensor acknowledge"
               ::=  {  airflowSensorEntry 70 }
               
            airflowSensorId OBJECT-TYPE
               SYNTAX  INTEGER
               ACCESS  read-only
               STATUS  mandatory
               DESCRIPTION
               "The Sensor ID of this sensor, used to identify which sensor it is in the system configuration."
               ::= { airflowSensorEntry 1000 }

--/* End of airflowSensorEntry */

--/* Begin of motionSensorEntry */
         motionSensorTable OBJECT-TYPE
            SYNTAX  SEQUENCE OF MotionSensorEntry
            ACCESS  not-accessible
            STATUS  mandatory
            DESCRIPTION
            "This table contains the property and reading value for every sensor."
            ::=  {  sensorByPort 8   }

         motionSensorEntry OBJECT-TYPE
            SYNTAX  MotionSensorEntry
            ACCESS  not-accessible
            STATUS  mandatory
            DESCRIPTION
            "This is an entry in the sensorTemperatureEntry Table"
            INDEX         { motionSensorIndex }
            ::=  {  motionSensorTable 1 }

         MotionSensorEntry ::= SEQUENCE {
               motionSensorIndex
                  DisplayString,
               motionSensorDescription
                  DisplayString,
               motionSensorStatus
                  INTEGER,
               motionSensorGoOffline
                  INTEGER,
               motionSensorPort
                  INTEGER,
               motionSensorSubPort
                  INTEGER,
               motionSensorDeviceIndex
                  INTEGER,
               motionSensorCriticalDesc 
                  DisplayString,
               motionSensorNormalDesc 
                  DisplayString,
               motionSensorCriticalColor 
                  INTEGER,
               motionSensorNormalColor 
                  INTEGER,
               motionSensorAcknowledge
                  INTEGER,
               motionSensorId
                  INTEGER
            }

            motionSensorIndex OBJECT-TYPE
               SYNTAX  DisplayString
               ACCESS  read-only
               STATUS  mandatory
               DESCRIPTION
               "The Sensor Compound ID of this sensor, used to identify which sensor it is in the system configuration."
               ::=  {  motionSensorEntry 1   }

            motionSensorDescription OBJECT-TYPE
               SYNTAX  DisplayString
               ACCESS  read-write
               STATUS  mandatory
               DESCRIPTION
               "A Description of this sensor Switch"
               ::=  {  motionSensorEntry 2   }

            motionSensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  motionSensorEntry 6  }

            motionSensorGoOffline OBJECT-TYPE
               SYNTAX  INTEGER {
                  online(1),
                  goOffline(2)
               }
               ACCESS  read-write
               STATUS  mandatory
               DESCRIPTION
               "To take offline enter a 2"
               ::=  {  motionSensorEntry 8  }

            motionSensorPort OBJECT-TYPE
               SYNTAX  INTEGER (0..65534)
               ACCESS  read-only
               STATUS  mandatory
               DESCRIPTION
               "Sensor port"
               ::=  {  motionSensorEntry 35 }

            motionSensorSubPort OBJECT-TYPE
               SYNTAX  INTEGER (0..65534)
               ACCESS  read-only
               STATUS  mandatory
               DESCRIPTION
               "Sensor sub port"
               ::=  {  motionSensorEntry 36 }

            motionSensorDeviceIndex OBJECT-TYPE
               SYNTAX  INTEGER (0..65534)
               ACCESS  read-only
               STATUS  mandatory
               DESCRIPTION
               "Device Index of sensor"
               ::=  {  motionSensorEntry 37 }

            motionSensorCriticalDesc OBJECT-TYPE
               SYNTAX  DisplayString
               ACCESS  read-write
               STATUS  mandatory
               DESCRIPTION
               "A Critical Description of this sensor"
               ::=  {  motionSensorEntry  46  }

            motionSensorNormalDesc OBJECT-TYPE
               SYNTAX  DisplayString
               ACCESS  read-write
               STATUS  mandatory
               DESCRIPTION
               "A Normal Description of this sensor"
               ::=  {  motionSensorEntry  48  }
               
            motionSensorCriticalColor OBJECT-TYPE
               SYNTAX  INTEGER
               ACCESS  read-write
               STATUS  mandatory
               DESCRIPTION
               "A Critical Color of this sensor"
               ::=  {  motionSensorEntry  54  }
               
            motionSensorNormalColor OBJECT-TYPE
               SYNTAX  INTEGER
               ACCESS  read-write
               STATUS  mandatory
               DESCRIPTION
               "A Normal Color of this sensor"
               ::=  {  motionSensorEntry  56  }

            motionSensorAcknowledge OBJECT-TYPE
               SYNTAX  INTEGER {
                  acked(2)
               }
               ACCESS  read-write
               STATUS  mandatory
               DESCRIPTION
               "Motion sensor acknowledge"
               ::=  {  motionSensorEntry 70 }
               
            motionSensorId OBJECT-TYPE
               SYNTAX  INTEGER
               ACCESS  read-only
               STATUS  mandatory
               DESCRIPTION
               "The Sensor ID of this sensor, used to identify which sensor it is in the system configuration."
               ::= { motionSensorEntry 1000 }

--/* End of motionSensorEntry */

--/* Begin of waterSensorEntry */
         waterSensorTable OBJECT-TYPE
            SYNTAX  SEQUENCE OF WaterSensorEntry
            ACCESS  not-accessible
            STATUS  mandatory
            DESCRIPTION
            "This table contains the property and reading value for every sensor."
            ::=  {  sensorByPort 9   }

         waterSensorEntry OBJECT-TYPE
            SYNTAX  WaterSensorEntry
            ACCESS  not-accessible
            STATUS  mandatory
            DESCRIPTION
            "This is an entry in the sensorTemperatureEntry Table"
            INDEX         { waterSensorIndex }
            ::=  {  waterSensorTable 1 }

         WaterSensorEntry ::= SEQUENCE {
               waterSensorIndex
                  DisplayString,
               waterSensorDescription
                  DisplayString,
               waterSensorStatus
                  INTEGER,
               waterSensorGoOffline
                  INTEGER,
               waterSensorPort
                  INTEGER,
               waterSensorSubPort
                  INTEGER,
               waterSensorDeviceIndex
                  INTEGER,
               waterSensorCriticalDesc 
                  DisplayString,
               waterSensorNormalDesc 
                  DisplayString,
               waterSensorCriticalColor 
                  INTEGER,
               waterSensorNormalColor 
                  INTEGER,   
               waterSensorAcknowledge
                  INTEGER,
               waterSensorId
                  INTEGER
            }

            waterSensorIndex OBJECT-TYPE
               SYNTAX  DisplayString
               ACCESS  read-only
               STATUS  mandatory
               DESCRIPTION
               "The Sensor Compound ID of this sensor, used to identify which sensor it is in the system configuration."
               ::=  {  waterSensorEntry 1   }

            waterSensorDescription OBJECT-TYPE
               SYNTAX  DisplayString
               ACCESS  read-write
               STATUS  mandatory
               DESCRIPTION
               "A Description of this sensor Switch"
               ::=  {  waterSensorEntry 2   }

            waterSensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  waterSensorEntry 6  }

            waterSensorGoOffline OBJECT-TYPE
               SYNTAX  INTEGER {
                  online(1),
                  goOffline(2)
               }
               ACCESS  read-write
               STATUS  mandatory
               DESCRIPTION
               "To take offline enter a 2"
               ::=  {  waterSensorEntry 8  }

            waterSensorPort OBJECT-TYPE
               SYNTAX  INTEGER (0..65534)
               ACCESS  read-only
               STATUS  mandatory
               DESCRIPTION
               "Sensor port"
               ::=  {  waterSensorEntry 35 }

            waterSensorSubPort OBJECT-TYPE
               SYNTAX  INTEGER (0..65534)
               ACCESS  read-only
               STATUS  mandatory
               DESCRIPTION
               "Sensor sub port"
               ::=  {  waterSensorEntry 36 }

            waterSensorDeviceIndex OBJECT-TYPE
               SYNTAX  INTEGER (0..65534)
               ACCESS  read-only
               STATUS  mandatory
               DESCRIPTION
               "Device Index of sensor"
               ::=  {  waterSensorEntry 37 }
           
            waterSensorCriticalDesc OBJECT-TYPE
               SYNTAX  DisplayString
               ACCESS  read-write
               STATUS  mandatory
               DESCRIPTION
               "A Critical Description of this sensor"
               ::=  {  waterSensorEntry  46  }

            waterSensorNormalDesc OBJECT-TYPE
               SYNTAX  DisplayString
               ACCESS  read-write
               STATUS  mandatory
               DESCRIPTION
               "A Normal Description of this sensor"
               ::=  {  waterSensorEntry  48  }

            waterSensorCriticalColor OBJECT-TYPE
               SYNTAX  INTEGER
               ACCESS  read-write
               STATUS  mandatory
               DESCRIPTION
               "A Critical Color of this sensor"
               ::=  {  waterSensorEntry  54  }

            waterSensorNormalColor OBJECT-TYPE
               SYNTAX  INTEGER
               ACCESS  read-write
               STATUS  mandatory
               DESCRIPTION
               "A Normal Color of this sensor"
               ::=  {  waterSensorEntry  56  }

            waterSensorAcknowledge OBJECT-TYPE
               SYNTAX  INTEGER {
                  acked(2)
               }
               ACCESS  read-write
               STATUS  mandatory
               DESCRIPTION
               "Water sensor acknowledge"
               ::=  {  waterSensorEntry 70 }
               
            waterSensorId OBJECT-TYPE
               SYNTAX  INTEGER
               ACCESS  read-only
               STATUS  mandatory
               DESCRIPTION
               "The Sensor ID of this sensor, used to identify which sensor it is in the system configuration."
               ::= { waterSensorEntry 1000 }

--/* End of waterSensorEntry */

--/* Begin of securitySensorEntry */
         securitySensorTable OBJECT-TYPE
            SYNTAX  SEQUENCE OF SecuritySensorEntry
            ACCESS  not-accessible
            STATUS  mandatory
            DESCRIPTION
            "This table contains the property and reading value for every sensor."
            ::=  {  sensorByPort 10   }

         securitySensorEntry OBJECT-TYPE
            SYNTAX  SecuritySensorEntry
            ACCESS  not-accessible
            STATUS  mandatory
            DESCRIPTION
            "This is an entry in the sensorTemperatureEntry Table"
            INDEX         { securitySensorIndex }
            ::=  {  securitySensorTable 1 }

         SecuritySensorEntry ::= SEQUENCE {
               securitySensorIndex
                  DisplayString,
               securitySensorDescription
                  DisplayString,
               securitySensorStatus
                  INTEGER,
               securitySensorGoOffline
                  INTEGER,
               securitySensorPort
                  INTEGER,
               securitySensorSubPort
                  INTEGER,
               securitySensorDeviceIndex
                  INTEGER,
               securitySensorCriticalDesc 
                  DisplayString,
               securitySensorNormalDesc 
                  DisplayString,
               securitySensorCriticalColor 
                  INTEGER,
               securitySensorNormalColor 
                  INTEGER,                
               securitySensorAcknowledge
                  INTEGER,
               securitySensorId
                  INTEGER
            }

            securitySensorIndex OBJECT-TYPE
               SYNTAX  DisplayString
               ACCESS  read-only
               STATUS  mandatory
               DESCRIPTION
               "The Sensor Compound ID of this sensor, used to identify which sensor it is in the system configuration."
               ::=  {  securitySensorEntry 1   }

            securitySensorDescription OBJECT-TYPE
               SYNTAX  DisplayString
               ACCESS  read-write
               STATUS  mandatory
               DESCRIPTION
               "A Description of this sensor Switch"
               ::=  {  securitySensorEntry 2   }

            securitySensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  securitySensorEntry 6  }

            securitySensorGoOffline OBJECT-TYPE
               SYNTAX  INTEGER {
                  online(1),
                  goOffline(2)
               }
               ACCESS  read-write
               STATUS  mandatory
               DESCRIPTION
               "To take offline enter a 2"
               ::=  {  securitySensorEntry 8  }

            securitySensorPort OBJECT-TYPE
               SYNTAX  INTEGER (0..65534)
               ACCESS  read-only
               STATUS  mandatory
               DESCRIPTION
               "Sensor port"
               ::=  {  securitySensorEntry 35 }

            securitySensorSubPort OBJECT-TYPE
               SYNTAX  INTEGER (0..65534)
               ACCESS  read-only
               STATUS  mandatory
               DESCRIPTION
               "Sensor sub port"
               ::=  {  securitySensorEntry 36 }

            securitySensorDeviceIndex OBJECT-TYPE
               SYNTAX  INTEGER (0..65534)
               ACCESS  read-only
               STATUS  mandatory
               DESCRIPTION
               "Device Index of sensor"
               ::=  {  securitySensorEntry 37 }

            securitySensorCriticalDesc OBJECT-TYPE
               SYNTAX  DisplayString
               ACCESS  read-write
               STATUS  mandatory
               DESCRIPTION
               "A Critical Description of this sensor"
               ::=  {  securitySensorEntry  46  }               

            securitySensorNormalDesc OBJECT-TYPE
               SYNTAX  DisplayString
               ACCESS  read-write
               STATUS  mandatory
               DESCRIPTION
               "A Normal Description of this sensor"
               ::=  {  securitySensorEntry  48  }

            securitySensorCriticalColor OBJECT-TYPE
               SYNTAX  INTEGER
               ACCESS  read-write
               STATUS  mandatory
               DESCRIPTION
               "A Critical Color of this sensor"
               ::=  {  securitySensorEntry  54  }               

            securitySensorNormalColor OBJECT-TYPE
               SYNTAX  INTEGER
               ACCESS  read-write
               STATUS  mandatory
               DESCRIPTION
               "A Normal Color of this sensor"
               ::=  {  securitySensorEntry  56  } 

            securitySensorAcknowledge OBJECT-TYPE
               SYNTAX  INTEGER {
                  acked(2)
               }
               ACCESS  read-write
               STATUS  mandatory
               DESCRIPTION
               "Security sensor acknowledge"
               ::=  {  securitySensorEntry 70 }
               
            securitySensorId OBJECT-TYPE
               SYNTAX  INTEGER
               ACCESS  read-only
               STATUS  mandatory
               DESCRIPTION
               "The Sensor ID of this sensor, used to identify which sensor it is in the system configuration."
               ::= { securitySensorEntry 1000 }

--/* End of securitySensorEntry */

--/* Begin of sirenSensorEntry */
         sirenSensorTable OBJECT-TYPE
            SYNTAX  SEQUENCE OF SirenSensorEntry
            ACCESS  not-accessible
            STATUS  mandatory
            DESCRIPTION
            "This table contains the property and reading value for every sensor."
            ::=  {  sensorByPort 11   }

         sirenSensorEntry OBJECT-TYPE
            SYNTAX  SirenSensorEntry
            ACCESS  not-accessible
            STATUS  mandatory
            DESCRIPTION
            "This is an entry in the sensorTemperatureEntry Table"
            INDEX         { sirenSensorIndex }
            ::=  {  sirenSensorTable 1 }

         SirenSensorEntry ::= SEQUENCE {
               sirenSensorIndex
                  DisplayString,
               sirenSensorDescription
                  DisplayString,
               sirenSensorStatus
                  INTEGER,
               sirenSensorGoOffline
                  INTEGER,
               sirenSensorControlMode
                  INTEGER,
               sirenSensorManualCycleTime
                  INTEGER,
               sirenSensorManualAction
                  INTEGER,
               sirenSensorPort
                  INTEGER,
               sirenSensorSubPort
                  INTEGER,
               sirenSensorDeviceIndex
                  INTEGER,
               sirenSensorOnDesc 
                  DisplayString,
               sirenSensorOffDesc 
                  DisplayString,
               sirenSensorOnColor 
                  INTEGER,
               sirenSensorOffColor 
                  INTEGER,
               sirenSensorAcknowledge
                  INTEGER,
               sirenSensorId
                  INTEGER
            }

            sirenSensorIndex OBJECT-TYPE
               SYNTAX  DisplayString
               ACCESS  read-only
               STATUS  mandatory
               DESCRIPTION
               "The Sensor Compound ID of this sensor, used to identify which sensor it is in the system configuration."
               ::=  {  sirenSensorEntry 1   }

            sirenSensorDescription OBJECT-TYPE
               SYNTAX  DisplayString
               ACCESS  read-write
               STATUS  mandatory
               DESCRIPTION
               "A Description of this sensor Switch"
               ::=  {  sirenSensorEntry 2   }

            sirenSensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sirenSensorEntry 6  }

            sirenSensorGoOffline OBJECT-TYPE
               SYNTAX  INTEGER {
                  online(1),
                  goOffline(2)
               }
               ACCESS  read-write
               STATUS  mandatory
               DESCRIPTION
               "To take offline enter a 2"
               ::=  {  sirenSensorEntry 8  }

            sirenSensorControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a siren."
               ::=  {  sirenSensorEntry 24  }
               
            sirenSensorManualCycleTime OBJECT-TYPE
               SYNTAX  INTEGER (1..255)
               ACCESS  read-write
               STATUS  mandatory
               DESCRIPTION
               "Toggle period in seconds for Manual Cycle action."
               ::=  {  sirenSensorEntry 25  }
               
            sirenSensorManualAction OBJECT-TYPE
               SYNTAX  INTEGER {
                  turn-On(0),
                  turn-Off(1),
                  cycle-On-Off-On(2),
                  cycle-Off-On-Off(3)
               }
               ACCESS  read-write
               STATUS  mandatory
               DESCRIPTION
               "Control the siren manualy"
               ::=  {  sirenSensorEntry 26  }

            sirenSensorPort OBJECT-TYPE
               SYNTAX  INTEGER (0..65534)
               ACCESS  read-only
               STATUS  mandatory
               DESCRIPTION
               "Sensor port"
               ::=  {  sirenSensorEntry 35 }

            sirenSensorSubPort OBJECT-TYPE
               SYNTAX  INTEGER (0..65534)
               ACCESS  read-only
               STATUS  mandatory
               DESCRIPTION
               "Sensor sub port"
               ::=  {  sirenSensorEntry 36 }

            sirenSensorDeviceIndex OBJECT-TYPE
               SYNTAX  INTEGER (0..65534)
               ACCESS  read-only
               STATUS  mandatory
               DESCRIPTION
               "Device Index of sensor"
               ::=  {  sirenSensorEntry 37 }
              
            sirenSensorOnDesc OBJECT-TYPE
               SYNTAX  DisplayString
               ACCESS  read-write
               STATUS  mandatory
               DESCRIPTION
               "A On Description of this sensor"
               ::=  {  sirenSensorEntry  52  }

            sirenSensorOffDesc OBJECT-TYPE
               SYNTAX  DisplayString
               ACCESS  read-write
               STATUS  mandatory
               DESCRIPTION
               "A Off Description of this sensor"
               ::=  {  sirenSensorEntry  53  }

            sirenSensorOnColor OBJECT-TYPE
               SYNTAX  INTEGER
               ACCESS  read-write
               STATUS  mandatory
               DESCRIPTION
               "A On Color of this sensor"
               ::=  {  sirenSensorEntry  60  }

            sirenSensorOffColor OBJECT-TYPE
               SYNTAX  INTEGER
               ACCESS  read-write
               STATUS  mandatory
               DESCRIPTION
               "A Off Color of this sensor"
               ::=  {  sirenSensorEntry  61  }

            sirenSensorAcknowledge OBJECT-TYPE
               SYNTAX  INTEGER {
                  acked(2)
               }
               ACCESS  read-write
               STATUS  mandatory
               DESCRIPTION
               "Siren sensor acknowledge"
               ::=  {  sirenSensorEntry 70 }
               
            sirenSensorId OBJECT-TYPE
               SYNTAX  INTEGER
               ACCESS  read-only
               STATUS  mandatory
               DESCRIPTION
               "The Sensor ID of this sensor, used to identify which sensor it is in the system configuration."
               ::= { sirenSensorEntry 1000 }

--/* End of sirenSensorEntry */

--/* Begin of relaySensorEntry */
         relaySensorTable OBJECT-TYPE
            SYNTAX  SEQUENCE OF RelaySensorEntry
            ACCESS  not-accessible
            STATUS  mandatory
            DESCRIPTION
            "This table contains the property and reading value for every sensor."
            ::=  {  sensorByPort 12   }

         relaySensorEntry OBJECT-TYPE
            SYNTAX  RelaySensorEntry
            ACCESS  not-accessible
            STATUS  mandatory
            DESCRIPTION
            "This is an entry in the sensorTemperatureEntry Table"
            INDEX         { relaySensorIndex }
            ::=  {  relaySensorTable 1 }

         RelaySensorEntry ::= SEQUENCE {
               relaySensorIndex
                  DisplayString,
               relaySensorDescription
                  DisplayString,
               relaySensorType
                  INTEGER,
               relaySensorStatus
                  INTEGER,
               relaySensorGoOffline
                  INTEGER,
               relaySensorControlMode
                  INTEGER,
               relaySensorManualCycleTime
                  INTEGER,
               relaySensorManualAction
                  INTEGER,
               relaySensorPort
                  INTEGER,
               relaySensorSubPort
                  INTEGER,
               relaySensorDeviceIndex
                  INTEGER,
               relaySensorOnDesc 
                  DisplayString,
               relaySensorOffDesc 
                  DisplayString,
               relaySensorOnColor 
                  INTEGER,
               relaySensorOffColor 
                  INTEGER,        
               relaySensorAcknowledge
                  INTEGER,
               relaySensorId
                  INTEGER
            }

            relaySensorIndex OBJECT-TYPE
               SYNTAX  DisplayString
               ACCESS  read-only
               STATUS  mandatory
               DESCRIPTION
               "The Sensor Compound ID of this sensor, used to identify which sensor it is in the system configuration."
               ::=  {  relaySensorEntry 1   }

            relaySensorDescription OBJECT-TYPE
               SYNTAX  DisplayString
               ACCESS  read-write
               STATUS  mandatory
               DESCRIPTION
               "A Description of this sensor Switch"
               ::=  {  relaySensorEntry 2   }

            relaySensorType OBJECT-TYPE
               SYNTAX  INTEGER {
                  relay(13),
                  xrelay(19)
               }
               ACCESS  read-only
               STATUS  mandatory
               DESCRIPTION
               "Enter the type of this Sensor"
               ::=  {  relaySensorEntry 3  }

            relaySensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  relaySensorEntry 6  }

            relaySensorGoOffline OBJECT-TYPE
               SYNTAX  INTEGER {
                  online(1),
                  goOffline(2)
               }
               ACCESS  read-write
               STATUS  mandatory
               DESCRIPTION
               "To take offline enter a 2"
               ::=  {  relaySensorEntry 8  }

            relaySensorControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a relay."
               ::=  {  relaySensorEntry 24  }
               
            relaySensorManualCycleTime OBJECT-TYPE
               SYNTAX  INTEGER (1..255)
               ACCESS  read-write
               STATUS  mandatory
               DESCRIPTION
               "Toggle period in seconds for Manual Cycle action."
               ::=  {  relaySensorEntry 25  }
               
            relaySensorManualAction OBJECT-TYPE
               SYNTAX  INTEGER {
                  turn-On(0),
                  turn-Off(1),
                  cycle-On-Off-On(2),
                  cycle-Off-On-Off(3)
               }
               ACCESS  read-write
               STATUS  mandatory
               DESCRIPTION
               "Control the relay manualy"
               ::=  {  relaySensorEntry 26  }

            relaySensorPort OBJECT-TYPE
               SYNTAX  INTEGER (0..65534)
               ACCESS  read-only
               STATUS  mandatory
               DESCRIPTION
               "Sensor port"
               ::=  {  relaySensorEntry 35 }

            relaySensorSubPort OBJECT-TYPE
               SYNTAX  INTEGER (0..65534)
               ACCESS  read-only
               STATUS  mandatory
               DESCRIPTION
               "Sensor sub port"
               ::=  {  relaySensorEntry 36 }

            relaySensorDeviceIndex OBJECT-TYPE
               SYNTAX  INTEGER (0..65534)
               ACCESS  read-only
               STATUS  mandatory
               DESCRIPTION
               "Device Index of sensor"
               ::=  {  relaySensorEntry 37 }
               
            relaySensorOnDesc OBJECT-TYPE
               SYNTAX  DisplayString
               ACCESS  read-write
               STATUS  mandatory
               DESCRIPTION
               "A On Description of this sensor"
               ::=  {  relaySensorEntry  52  }               

            relaySensorOffDesc OBJECT-TYPE
               SYNTAX  DisplayString
               ACCESS  read-write
               STATUS  mandatory
               DESCRIPTION
               "A Off Description of this sensor"
               ::=  {  relaySensorEntry  53  }

            relaySensorOnColor OBJECT-TYPE
               SYNTAX  INTEGER
               ACCESS  read-write
               STATUS  mandatory
               DESCRIPTION
               "A On Color of this sensor"
               ::=  {  relaySensorEntry  60  }               

            relaySensorOffColor OBJECT-TYPE
               SYNTAX  INTEGER
               ACCESS  read-write
               STATUS  mandatory
               DESCRIPTION
               "A Off Color of this sensor"
               ::=  {  relaySensorEntry  61  }     

            relaySensorAcknowledge OBJECT-TYPE
               SYNTAX  INTEGER {
                  acked(2)
               }
               ACCESS  read-write
               STATUS  mandatory
               DESCRIPTION
               "Relay sensor acknowledge"
               ::=  {  relaySensorEntry 70 }  

            relaySensorId OBJECT-TYPE
               SYNTAX  INTEGER
               ACCESS  read-only
               STATUS  mandatory
               DESCRIPTION
               "The Sensor ID of this sensor, used to identify which sensor it is in the system configuration."
               ::= { relaySensorEntry 1000 }

--/* End of relaySensorEntry */

--/* Begin of acVoltageSensorEntry */
         acVoltageSensorTable OBJECT-TYPE
            SYNTAX  SEQUENCE OF AcVoltageSensorEntry
            ACCESS  not-accessible
            STATUS  mandatory
            DESCRIPTION
            "This table contains the property and reading value for every sensor."
            ::=  {  sensorByPort 13   }

         acVoltageSensorEntry OBJECT-TYPE
            SYNTAX  AcVoltageSensorEntry
            ACCESS  not-accessible
            STATUS  mandatory
            DESCRIPTION
            "This is an entry in the sensorTemperatureEntry Table"
            INDEX         { acVoltageSensorIndex }
            ::=  {  acVoltageSensorTable 1 }

         AcVoltageSensorEntry ::= SEQUENCE {
               acVoltageSensorIndex
                  DisplayString,
               acVoltageSensorDescription
                  DisplayString,
               acVoltageSensorStatus
                  INTEGER,
               acVoltageSensorGoOffline
                  INTEGER,
               acVoltageSensorPort
                  INTEGER,
               acVoltageSensorSubPort
                  INTEGER,
               acVoltageSensorDeviceIndex
                  INTEGER,
               acVoltageSensorCriticalDesc 
                  DisplayString,
               acVoltageSensorNormalDesc 
                  DisplayString,
               acVoltageSensorCriticalColor 
                  INTEGER,
               acVoltageSensorNormalColor 
                  INTEGER,
               acVoltageSensorAcknowledge
                  INTEGER,
               acVoltageSensorId
                  INTEGER
            }

            acVoltageSensorIndex OBJECT-TYPE
               SYNTAX  DisplayString
               ACCESS  read-only
               STATUS  mandatory
               DESCRIPTION
               "The Sensor Compound ID of this sensor, used to identify which sensor it is in the system configuration."
               ::=  {  acVoltageSensorEntry 1   }

            acVoltageSensorDescription OBJECT-TYPE
               SYNTAX  DisplayString
               ACCESS  read-write
               STATUS  mandatory
               DESCRIPTION
               "A Description of this sensor Switch"
               ::=  {  acVoltageSensorEntry 2   }

            acVoltageSensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  acVoltageSensorEntry 6  }

            acVoltageSensorGoOffline OBJECT-TYPE
               SYNTAX  INTEGER {
                  online(1),
                  goOffline(2)
               }
               ACCESS  read-write
               STATUS  mandatory
               DESCRIPTION
               "To put online enter a 1, to take offline enter a 2"
               ::=  {  acVoltageSensorEntry 8  }

            acVoltageSensorPort OBJECT-TYPE
               SYNTAX  INTEGER (0..65534)
               ACCESS  read-only
               STATUS  mandatory
               DESCRIPTION
               "Sensor port"
               ::=  {  acVoltageSensorEntry 35 }

            acVoltageSensorSubPort OBJECT-TYPE
               SYNTAX  INTEGER (0..65534)
               ACCESS  read-only
               STATUS  mandatory
               DESCRIPTION
               "Sensor sub port"
               ::=  {  acVoltageSensorEntry 36 }

            acVoltageSensorDeviceIndex OBJECT-TYPE
               SYNTAX  INTEGER (0..65534)
               ACCESS  read-only
               STATUS  mandatory
               DESCRIPTION
               "Device Index of sensor"
               ::=  {  acVoltageSensorEntry 37 }
               
            acVoltageSensorCriticalDesc OBJECT-TYPE
               SYNTAX  DisplayString
               ACCESS  read-write
               STATUS  mandatory
               DESCRIPTION
               "A Critical Description of this sensor"
               ::=  {  acVoltageSensorEntry  46  }               

            acVoltageSensorNormalDesc OBJECT-TYPE
               SYNTAX  DisplayString
               ACCESS  read-write
               STATUS  mandatory
               DESCRIPTION
               "A Normal Description of this sensor"
               ::=  {  acVoltageSensorEntry  48  }
               
            acVoltageSensorCriticalColor OBJECT-TYPE
               SYNTAX  INTEGER
               ACCESS  read-write
               STATUS  mandatory
               DESCRIPTION
               "A Critical Color of this sensor"
               ::=  {  acVoltageSensorEntry  54  }               

            acVoltageSensorNormalColor OBJECT-TYPE
               SYNTAX  INTEGER
               ACCESS  read-write
               STATUS  mandatory
               DESCRIPTION
               "A Normal Color of this sensor"
               ::=  {  acVoltageSensorEntry  56  }      

            acVoltageSensorAcknowledge OBJECT-TYPE
               SYNTAX  INTEGER {
                  acked(2)
               }
               ACCESS  read-write
               STATUS  mandatory
               DESCRIPTION
               "ACvoltage sensor acknowledge"
               ::=  {  acVoltageSensorEntry 70 }

            acVoltageSensorId OBJECT-TYPE
               SYNTAX  INTEGER
               ACCESS  read-only
               STATUS  mandatory
               DESCRIPTION
               "The Sensor ID of this sensor, used to identify which sensor it is in the system configuration."
               ::= { acVoltageSensorEntry 1000 }

--/* End of acVoltageSensorEntry */

--/* Begin of smokeSensorEntry */
         smokeSensorTable OBJECT-TYPE
            SYNTAX  SEQUENCE OF SmokeSensorEntry
            ACCESS  not-accessible
            STATUS  mandatory
            DESCRIPTION
            "This table contains the property and reading value for every sensor."
            ::=  {  sensorByPort 14   }

         smokeSensorEntry OBJECT-TYPE
            SYNTAX  SmokeSensorEntry
            ACCESS  not-accessible
            STATUS  mandatory
            DESCRIPTION
            "This is an entry in the sensorTemperatureEntry Table"
            INDEX         { smokeSensorIndex }
            ::=  {  smokeSensorTable 1 }

         SmokeSensorEntry ::= SEQUENCE {
               smokeSensorIndex
                  DisplayString,
               smokeSensorDescription
                  DisplayString,
               smokeSensorStatus
                  INTEGER,
               smokeSensorGoOffline
                  INTEGER,
               smokeSensorPort
                  INTEGER,
               smokeSensorSubPort
                  INTEGER,
               smokeSensorDeviceIndex
                  INTEGER,
               smokeSensorCriticalDesc 
                  DisplayString,
               smokeSensorNormalDesc 
                  DisplayString,
               smokeSensorCriticalColor 
                  INTEGER,
               smokeSensorNormalColor 
                  INTEGER,      
               smokeSensorAcknowledge
                  INTEGER,
               smokeSensorId
                  INTEGER
            }

            smokeSensorIndex OBJECT-TYPE
               SYNTAX  DisplayString
               ACCESS  read-only
               STATUS  mandatory
               DESCRIPTION
               "The Sensor Compound ID of this sensor, used to identify which sensor it is in the system configuration."
               ::=  {  smokeSensorEntry 1   }

            smokeSensorDescription OBJECT-TYPE
               SYNTAX  DisplayString
               ACCESS  read-write
               STATUS  mandatory
               DESCRIPTION
               "A Description of this sensor Switch"
               ::=  {  smokeSensorEntry 2   }

            smokeSensorStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  smokeSensorEntry 6  }

            smokeSensorGoOffline OBJECT-TYPE
               SYNTAX  INTEGER {
                  online(1),
                  goOffline(2)
               }
               ACCESS  read-write
               STATUS  mandatory
               DESCRIPTION
               "To take offline enter a 2"
               ::=  {  smokeSensorEntry 8  }

            smokeSensorPort OBJECT-TYPE
               SYNTAX  INTEGER (0..65534)
               ACCESS  read-only
               STATUS  mandatory
               DESCRIPTION
               "Sensor port"
               ::=  {  smokeSensorEntry 35 }

            smokeSensorSubPort OBJECT-TYPE
               SYNTAX  INTEGER (0..65534)
               ACCESS  read-only
               STATUS  mandatory
               DESCRIPTION
               "Sensor sub port"
               ::=  {  smokeSensorEntry 36 }

            smokeSensorDeviceIndex OBJECT-TYPE
               SYNTAX  INTEGER (0..65534)
               ACCESS  read-only
               STATUS  mandatory
               DESCRIPTION
               "Device Index of sensor"
               ::=  {  smokeSensorEntry 37 }

            smokeSensorCriticalDesc OBJECT-TYPE
               SYNTAX  DisplayString
               ACCESS  read-write
               STATUS  mandatory
               DESCRIPTION
               "A Critical Description of this sensor"
               ::=  {  smokeSensorEntry  46  }               

            smokeSensorNormalDesc OBJECT-TYPE
               SYNTAX  DisplayString
               ACCESS  read-write
               STATUS  mandatory
               DESCRIPTION
               "A Normal Description of this sensor"
               ::=  {  smokeSensorEntry  48  }
        
            smokeSensorCriticalColor OBJECT-TYPE
               SYNTAX  INTEGER
               ACCESS  read-write
               STATUS  mandatory
               DESCRIPTION
               "A Critical Color of this sensor"
               ::=  {  smokeSensorEntry  54  }               

            smokeSensorNormalColor OBJECT-TYPE
               SYNTAX  INTEGER
               ACCESS  read-write
               STATUS  mandatory
               DESCRIPTION
               "A Normal Color of this sensor"
               ::=  {  smokeSensorEntry  56  }   

            smokeSensorAcknowledge OBJECT-TYPE
               SYNTAX  INTEGER {
                  acked(2)
               }
               ACCESS  read-write
               STATUS  mandatory
               DESCRIPTION
               "Smoke sensor acknowledge"
               ::=  {  smokeSensorEntry 70 }

            smokeSensorId OBJECT-TYPE
               SYNTAX  INTEGER
               ACCESS  read-only
               STATUS  mandatory
               DESCRIPTION
               "The Sensor ID of this sensor, used to identify which sensor it is in the system configuration."
               ::= { smokeSensorEntry 1000 }

--/* End of smokeSensorEntry */

--/* Begin of thermostatSensorEntry */
         thermostatSensorTable OBJECT-TYPE
            SYNTAX  SEQUENCE OF ThermostatSensorEntry
            ACCESS  not-accessible
            STATUS  mandatory
            DESCRIPTION
            "This table contains the property and reading value for every sensor."
            ::=  {  sensorByPort 20   }

         thermostatSensorEntry OBJECT-TYPE
            SYNTAX  ThermostatSensorEntry
            ACCESS  not-accessible
            STATUS  mandatory
            DESCRIPTION
            "This is an entry in the sensorTemperatureEntry Table"
            INDEX         { thermostatSensorIndex }
            ::=  {  thermostatSensorTable 1 }

         ThermostatSensorEntry ::= SEQUENCE {
               thermostatSensorIndex
                  DisplayString,
               thermostatSensorDescription
                  DisplayString,
               thermostatSensorDegree
                  INTEGER,
               thermostatSensorStatus
                  INTEGER,
               thermostatSensorGoOffline
                  INTEGER,
               thermostatSensorLowCritical
                  INTEGER,
               thermostatSensorLowWarning
                  INTEGER,
               thermostatSensorHighWarning
                  INTEGER,
               thermostatSensorHighCritical
                  INTEGER,
               thermostatSensorRearm
                  INTEGER,
               thermostatSensorDelayError
                  INTEGER,
               thermostatSensorDelayNormal
                  INTEGER,
               thermostatSensorDelayLowCritical
                  INTEGER,
               thermostatSensorDelayLowWarning
                  INTEGER,
               thermostatSensorDelayHighWarning
                  INTEGER,
               thermostatSensorDelayHighCritical
                  INTEGER,
               thermostatSensorPort
                  INTEGER,
               thermostatSensorSubPort
                  INTEGER,
               thermostatSensorDeviceIndex
                  INTEGER,
               thermostatSensorDisplayStyle
                  INTEGER,
               thermostatSensorHighCriticalDesc 
                  DisplayString,
               thermostatSensorLowCriticalDesc 
                  DisplayString,
               thermostatSensorNormalDesc 
                  DisplayString,
               thermostatSensorLowWarningDesc 
                  DisplayString,   
               thermostatSensorHighWarningDesc 
                  DisplayString,
               thermostatSensorSensorErrorDesc 
                  DisplayString,
               thermostatSensorHighCriticalColor 
                  INTEGER,
               thermostatSensorLowCriticalColor 
                  INTEGER,
               thermostatSensorNormalColor 
                  INTEGER,
               thermostatSensorLowWarningColor 
                  INTEGER,   
               thermostatSensorHighWarningColor 
                  INTEGER,
               thermostatSensorSensorErrorColor 
                  INTEGER,            
               thermostatSensorAcknowledge
                  INTEGER,
               thermostatSensorId
                  INTEGER
            }

            thermostatSensorIndex OBJECT-TYPE
               SYNTAX  DisplayString
               ACCESS  read-only
               STATUS  mandatory
               DESCRIPTION
               "The Sensor Compound ID of this sensor, used to identify which sensor it is in the system configuration."
               ::=  {  thermostatSensorEntry 1   }

            thermostatSensorDescription OBJECT-TYPE
               SYNTAX  DisplayString
               ACCESS  read-write
               STATUS  mandatory
               DESCRIPTION
               "A Description of this sensor"
               ::=  {  thermostatSensorEntry 2   }

            thermostatSensorDegree OBJECT-TYPE
               SYNTAX  INTEGER
               ACCESS  read-only
               STATUS  mandatory
               DESCRIPTION
               "The degrees in this sensor"
               ::=  {  thermostatSensorEntry 4   }

            thermostatSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  thermostatSensorEntry 6   }

            thermostatSensorGoOffline OBJECT-TYPE
               SYNTAX  INTEGER {
                  online(1),
                  goOffline(2)
               }
               ACCESS  read-write
               STATUS  mandatory
               DESCRIPTION
               "To take offline enter a 2"
               ::=  {  thermostatSensorEntry 8   }

            thermostatSensorLowCritical OBJECT-TYPE
               SYNTAX  INTEGER
               ACCESS  read-write
               STATUS  mandatory
               DESCRIPTION
               "How cold this sensor gets before it sends a critical event"
               ::=  {  thermostatSensorEntry 9   }

            thermostatSensorLowWarning OBJECT-TYPE
               SYNTAX  INTEGER
               ACCESS  read-write
               STATUS  mandatory
               DESCRIPTION
               "How cold this sensor gets before it sends a warning"
               ::=  {  thermostatSensorEntry 10   }
   
            thermostatSensorHighWarning OBJECT-TYPE
               SYNTAX  INTEGER
               ACCESS  read-write
               STATUS  mandatory
               DESCRIPTION
               "How hot this sensor gets before it sends a warning"
               ::=  {  thermostatSensorEntry 11   }  

            thermostatSensorHighCritical OBJECT-TYPE
               SYNTAX  INTEGER
               ACCESS  read-write
               STATUS  mandatory
               DESCRIPTION
               "How hot this sensor gets before it sends a critical event"
               ::=  {  thermostatSensorEntry 12   }   

            thermostatSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  thermostatSensorEntry 13   }

            thermostatSensorDelayError OBJECT-TYPE
               SYNTAX  INTEGER (0..65534)
               ACCESS  read-write
               STATUS  mandatory
               DESCRIPTION
               "Time in seconds after the sensor has been in error status before report as an error"
               ::=  {  thermostatSensorEntry 14   }

            thermostatSensorDelayNormal OBJECT-TYPE
               SYNTAX  INTEGER (0..65534)
               ACCESS  read-write
               STATUS  mandatory
               DESCRIPTION
               "Time in seconds after the sensor change from error to normal before report as normal"
               ::=  {  thermostatSensorEntry 15   }

            thermostatSensorDelayLowCritical OBJECT-TYPE
               SYNTAX INTEGER (0..65535)
               ACCESS read-write
               STATUS mandatory
               DESCRIPTION
               "Continuous time for this sensor to be in Low Critical before accepting new Status."
               ::= {  thermostatSensorEntry 16 }
               
            thermostatSensorDelayLowWarning OBJECT-TYPE
               SYNTAX INTEGER (0..65535)
               ACCESS read-write
               STATUS mandatory
               DESCRIPTION
               "Continuous time for this sensor to be in Low Warning before accepting new Status."
               ::= {  thermostatSensorEntry 17 }

            thermostatSensorDelayHighWarning OBJECT-TYPE
               SYNTAX INTEGER (0..65535)
               ACCESS read-write
               STATUS mandatory
               DESCRIPTION
               "Continuous time for this sensor to be in High Warning before accepting new Status."
               ::= {  thermostatSensorEntry 18 }

            thermostatSensorDelayHighCritical OBJECT-TYPE
               SYNTAX INTEGER (0..65535)
               ACCESS read-write
               STATUS mandatory
               DESCRIPTION
               "Continuous time for this sensor to be in High Critical before accepting new Status."
               ::= {  thermostatSensorEntry 19 }

            thermostatSensorPort OBJECT-TYPE
               SYNTAX  INTEGER (0..65534)
               ACCESS  read-only
               STATUS  mandatory
               DESCRIPTION
               "Sensor port"
               ::=  {  thermostatSensorEntry 35 }

            thermostatSensorSubPort OBJECT-TYPE
               SYNTAX  INTEGER (0..65534)
               ACCESS  read-only
               STATUS  mandatory
               DESCRIPTION
               "Sensor sub port"
               ::=  {  thermostatSensorEntry 36 }

            thermostatSensorDeviceIndex OBJECT-TYPE
               SYNTAX  INTEGER (0..65534)
               ACCESS  read-only
               STATUS  mandatory
               DESCRIPTION
               "Device Index of sensor"
               ::=  {  thermostatSensorEntry 37 }
               
            thermostatSensorDisplayStyle OBJECT-TYPE
               SYNTAX  INTEGER {
                  basic(0),
                  gauge(1)
               }
               ACCESS  read-write
               STATUS  mandatory
               DESCRIPTION
               "Thermostat display style"
               ::=  {  thermostatSensorEntry 45 } 

            thermostatSensorHighCriticalDesc OBJECT-TYPE
               SYNTAX  DisplayString
               ACCESS  read-write
               STATUS  mandatory
               DESCRIPTION
               "A HighCritical Description of this sensor"
               ::=  {  thermostatSensorEntry  46  }               

            thermostatSensorLowCriticalDesc OBJECT-TYPE
               SYNTAX  DisplayString
               ACCESS  read-write
               STATUS  mandatory
               DESCRIPTION
               "A LowCritical Description of this sensor"
               ::=  {  thermostatSensorEntry  47  }

            thermostatSensorNormalDesc OBJECT-TYPE
               SYNTAX  DisplayString
               ACCESS  read-write
               STATUS  mandatory
               DESCRIPTION
               "A Normal Description of this sensor"
               ::=  {  thermostatSensorEntry  48  }
               
            thermostatSensorLowWarningDesc OBJECT-TYPE
               SYNTAX  DisplayString
               ACCESS  read-write
               STATUS  mandatory
               DESCRIPTION
               "A LowWarning Description of this sensor"
               ::=  {  thermostatSensorEntry  49  }
               
            thermostatSensorHighWarningDesc OBJECT-TYPE
               SYNTAX  DisplayString
               ACCESS  read-write
               STATUS  mandatory
               DESCRIPTION
               "A HighWarning Description of this sensor"
               ::=  {  thermostatSensorEntry  50  }
               
            thermostatSensorSensorErrorDesc OBJECT-TYPE
               SYNTAX  DisplayString
               ACCESS  read-write
               STATUS  mandatory
               DESCRIPTION
               "A SensorError Description of this sensor"
               ::=  {  thermostatSensorEntry  51  }  

            thermostatSensorHighCriticalColor OBJECT-TYPE
               SYNTAX  INTEGER
               ACCESS  read-write
               STATUS  mandatory
               DESCRIPTION
               "A HighCritical Color of this sensor"
               ::=  {  thermostatSensorEntry  54  }               

            thermostatSensorLowCriticalColor OBJECT-TYPE
               SYNTAX  INTEGER
               ACCESS  read-write
               STATUS  mandatory
               DESCRIPTION
               "A LowCritical Color of this sensor"
               ::=  {  thermostatSensorEntry  55  }

            thermostatSensorNormalColor OBJECT-TYPE
               SYNTAX  INTEGER
               ACCESS  read-write
               STATUS  mandatory
               DESCRIPTION
               "A Normal Color of this sensor"
               ::=  {  thermostatSensorEntry  56  }
               
            thermostatSensorLowWarningColor OBJECT-TYPE
               SYNTAX  INTEGER
               ACCESS  read-write
               STATUS  mandatory
               DESCRIPTION
               "A LowWarning Color of this sensor"
               ::=  {  thermostatSensorEntry  57  }
               
            thermostatSensorHighWarningColor OBJECT-TYPE
               SYNTAX  INTEGER
               ACCESS  read-write
               STATUS  mandatory
               DESCRIPTION
               "A HighWarning Color of this sensor"
               ::=  {  thermostatSensorEntry  58  }
               
            thermostatSensorSensorErrorColor OBJECT-TYPE
               SYNTAX  INTEGER
               ACCESS  read-write
               STATUS  mandatory
               DESCRIPTION
               "A SensorError Color of this sensor"
               ::=  {  thermostatSensorEntry  59  }  
         
            thermostatSensorAcknowledge OBJECT-TYPE
               SYNTAX  INTEGER {
                  acked(2)
               }
               ACCESS  read-write
               STATUS  mandatory
               DESCRIPTION
               "Thermostat sensor acknowledge"
               ::=  {  thermostatSensorEntry 70 }

            thermostatSensorId OBJECT-TYPE
               SYNTAX  INTEGER
               ACCESS  read-only
               STATUS  mandatory
               DESCRIPTION
               "The Sensor ID of this sensor, used to identify which sensor it is in the system configuration."
               ::= { thermostatSensorEntry 1000 }

--/* End of thermostatSensorEntry */

--/* Begin of waterRopeSensorEntry */
         waterRopeSensorTable OBJECT-TYPE
            SYNTAX  SEQUENCE OF WaterRopeSensorEntry
            ACCESS  not-accessible
            STATUS  mandatory
            DESCRIPTION
            "This table contains the property and reading value for every sensor."
            ::=  {  sensorByPort 21 }

         waterRopeSensorEntry OBJECT-TYPE
            SYNTAX  WaterRopeSensorEntry
            ACCESS  not-accessible
            STATUS  mandatory
            DESCRIPTION
            "This is an entry in the waterRopeSensorEntry Table"
            INDEX         { waterRopeSensorIndex }
            ::=  {  waterRopeSensorTable 1 }

         WaterRopeSensorEntry ::= SEQUENCE {
               waterRopeSensorIndex
                  DisplayString,
               waterRopeSensorDescription
                  DisplayString,
               waterRopeSensorLeakLocation
                  INTEGER,
               waterRopeSensorUnit
                  DisplayString,
               waterRopeSensorStatus
                  INTEGER,
               waterRopeSensorGoOffline
                  INTEGER,
               waterRopeSensorRaw
                  INTEGER,
               waterRopeSensorDeviceIndex
                  INTEGER,
               waterRopeSensorCriticalDesc
                  DisplayString,
               waterRopeSensorNormalDesc
                  DisplayString,
               waterRopeSensorSensorErrorDesc
                  DisplayString,
               waterRopeSensorCriticalColor
                  INTEGER,
               waterRopeSensorNormalColor
                  INTEGER,
               waterRopeSensorSensorErrorColor
                  INTEGER,
               waterRopeSensorAcknowledge
                  INTEGER,
               waterRopeSensorLength
                  INTEGER,
               waterRopeSensorImpedance
                  INTEGER,
               waterRopeSensorType
                  INTEGER,
               waterRopeSensorId
                  INTEGER
            }

            waterRopeSensorIndex OBJECT-TYPE
               SYNTAX  DisplayString
               ACCESS  read-only
               STATUS  mandatory
               DESCRIPTION
               "The Sensor Compound ID of this sensor, used to identify which sensor it is in the system configuration."
               ::=  {  waterRopeSensorEntry 1   }

            waterRopeSensorDescription OBJECT-TYPE
               SYNTAX  DisplayString
               ACCESS  read-write
               STATUS  mandatory
               DESCRIPTION
               "A Description of this sensor"
               ::=  {  waterRopeSensorEntry 2   }

            waterRopeSensorLeakLocation OBJECT-TYPE
               SYNTAX INTEGER
               ACCESS read-only
               STATUS mandatory
               DESCRIPTION
               "Location of leakage of water rope sensor."
               ::= {  waterRopeSensorEntry 4 }

            waterRopeSensorUnit OBJECT-TYPE
               SYNTAX  DisplayString
               ACCESS  read-write
               STATUS  mandatory
               DESCRIPTION
               "Display unit of water rope sensor."
               ::=  {  waterRopeSensorEntry 5   }

            waterRopeSensorStatus OBJECT-TYPE
               SYNTAX  INTEGER {
                  noStatus(1),
                  normal(2),
                  highCritical(4),
                  sensorError(7)
               }
               ACCESS  read-only
               STATUS  mandatory
               DESCRIPTION
               "The current status of this Sensor"
               ::=  {  waterRopeSensorEntry 6  }

            waterRopeSensorGoOffline OBJECT-TYPE
               SYNTAX  INTEGER {
                  online(1),
                  goOffline(2)
               }
               ACCESS  read-write
               STATUS  mandatory
               DESCRIPTION
               "To take offline enter a 2"
               ::=  {  waterRopeSensorEntry 8  }
               
            waterRopeSensorRaw OBJECT-TYPE
               SYNTAX INTEGER
               ACCESS read-only
               STATUS mandatory
               DESCRIPTION
               "Raw value of location or length in ohms"
               ::= {  waterRopeSensorEntry 20 }

            waterRopeSensorDeviceIndex OBJECT-TYPE
               SYNTAX  INTEGER (0..65534)
               ACCESS  read-only
               STATUS  mandatory
               DESCRIPTION
               "Device Index of sensor"
               ::=  {  waterRopeSensorEntry 37 }
               
            waterRopeSensorCriticalDesc OBJECT-TYPE
               SYNTAX  DisplayString
               ACCESS  read-write
               STATUS  mandatory
               DESCRIPTION
               "A Critical Description of this sensor"
               ::=  {  waterRopeSensorEntry  46  }
               
            waterRopeSensorNormalDesc OBJECT-TYPE
               SYNTAX  DisplayString
               ACCESS  read-write
               STATUS  mandatory
               DESCRIPTION
               "A Normal Description of this sensor"
               ::=  {  waterRopeSensorEntry  48  }
               
            waterRopeSensorSensorErrorDesc OBJECT-TYPE
               SYNTAX  DisplayString
               ACCESS  read-write
               STATUS  mandatory
               DESCRIPTION
               "A SensorError Description of this sensor"
               ::=  {  waterRopeSensorEntry  51  }  
               
            waterRopeSensorCriticalColor OBJECT-TYPE
               SYNTAX  INTEGER
               ACCESS  read-write
               STATUS  mandatory
               DESCRIPTION
               "A Critical Color of this sensor"
               ::=  {  waterRopeSensorEntry  54  }

            waterRopeSensorNormalColor OBJECT-TYPE
               SYNTAX  INTEGER
               ACCESS  read-write
               STATUS  mandatory
               DESCRIPTION
               "A Normal Color of this sensor"
               ::=  {  waterRopeSensorEntry  56  }
               
            waterRopeSensorSensorErrorColor OBJECT-TYPE
               SYNTAX  INTEGER
               ACCESS  read-write
               STATUS  mandatory
               DESCRIPTION
               "A SensorError Color of this sensor"
               ::=  {  waterRopeSensorEntry  59  }

            waterRopeSensorAcknowledge OBJECT-TYPE
               SYNTAX  INTEGER {
                  acked(2)
               }
               ACCESS  read-write
               STATUS  mandatory
               DESCRIPTION
               "Water Rope sensor acknowledge"
               ::=  {  waterRopeSensorEntry 70 }
            
            waterRopeSensorLength OBJECT-TYPE
               SYNTAX INTEGER
               ACCESS read-only
               STATUS mandatory
               DESCRIPTION
               "Length of water rope sensor."
               ::= {  waterRopeSensorEntry 100 }

            waterRopeSensorImpedance OBJECT-TYPE
               SYNTAX INTEGER (0..65535)
               ACCESS read-write
               STATUS mandatory
               DESCRIPTION
               "Sensing wire impedance per meter value times 100"
               ::= {  waterRopeSensorEntry 101 }
 
            waterRopeSensorType OBJECT-TYPE
               SYNTAX  INTEGER {
                  custom(0),
                  water(1),
                  fuel(2)
               }
               ACCESS read-write
               STATUS mandatory
               DESCRIPTION
               "Water rope sensing cable type"
               ::= {  waterRopeSensorEntry 103 }
               
            waterRopeSensorId OBJECT-TYPE
               SYNTAX  INTEGER
               ACCESS  read-only
               STATUS  mandatory
               DESCRIPTION
               "The Sensor ID of this sensor, used to identify which sensor it is in the system configuration."
               ::= { waterRopeSensorEntry 1000 }

--/* End of waterRopeSensorEntry */

--/* Begin of powerSensorEntry */
         powerSensorTable OBJECT-TYPE
            SYNTAX  SEQUENCE OF PowerSensorEntry
            ACCESS  not-accessible
            STATUS  mandatory
            DESCRIPTION
            "This table contains the property and reading value for every sensor."
            ::=  {  sensorByPort 22   }

         powerSensorEntry OBJECT-TYPE
            SYNTAX  PowerSensorEntry
            ACCESS  not-accessible
            STATUS  mandatory
            DESCRIPTION
            "This is an entry in the powerSensorEntry Table"
            INDEX         { powerSensorIndex }
            ::=  {  powerSensorTable 1 }

         PowerSensorEntry ::= SEQUENCE {
               powerSensorIndex
                  DisplayString,
               powerSensorDescription
                  DisplayString,
               powerSensorValue
                  INTEGER,
               powerSensorUnit
                  DisplayString,
               powerSensorStatus
                  INTEGER,
               powerSensorGoOffline
                  INTEGER,
               powerSensorLowCritical
                  INTEGER,
               powerSensorLowWarning
                  INTEGER,
               powerSensorHighWarning
                  INTEGER,
               powerSensorHighCritical
                  INTEGER,
               powerSensorRearm
                  INTEGER,
               powerSensorDelayError
                  INTEGER,
               powerSensorDelayNormal
                  INTEGER,
               powerSensorDelayLowCritical
                  INTEGER,
               powerSensorDelayLowWarning
                  INTEGER,
               powerSensorDelayHighWarning
                  INTEGER,
               powerSensorDelayHighCritical
                  INTEGER,
               powerSensorPort
                  INTEGER,
               powerSensorSubPort
                  INTEGER,
               powerSensorDeviceIndex
                  INTEGER,
               powerSensorTimeOut
                  INTEGER,
               powerSensorInterval
                  INTEGER,
               powerSensorErrorRetryNum
                  INTEGER,
               powerSensorMaxValue
                  INTEGER,
               powerSensorMinValue
                  INTEGER,
               powerSensorDisplayStyle
                  INTEGER,
               powerSensorHighCriticalDesc 
                  DisplayString,
               powerSensorLowCriticalDesc 
                  DisplayString,
               powerSensorNormalDesc 
                  DisplayString,
               powerSensorLowWarningDesc 
                  DisplayString,   
               powerSensorHighWarningDesc 
                  DisplayString,
               powerSensorSensorErrorDesc 
                  DisplayString,
               powerSensorHighCriticalColor 
                  INTEGER,
               powerSensorLowCriticalColor 
                  INTEGER,
               powerSensorNormalColor 
                  INTEGER,
               powerSensorLowWarningColor 
                  INTEGER,   
               powerSensorHighWarningColor 
                  INTEGER,
               powerSensorSensorErrorColor 
                  INTEGER,
               powerSensorValueFormatString 
                  DisplayString,
               powerSensorValueFormatFloat
                  Opaque,
               powerSensorAcknowledge
                  INTEGER,
               powerSensorId
                  INTEGER
            }

            powerSensorIndex OBJECT-TYPE
               SYNTAX  DisplayString
               ACCESS  read-only
               STATUS  mandatory
               DESCRIPTION
               "The Sensor Compound ID of this sensor, used to identify which sensor it is in the system configuration."
               ::=  {  powerSensorEntry 1   }

            powerSensorDescription OBJECT-TYPE
               SYNTAX  DisplayString
               ACCESS  read-write
               STATUS  mandatory
               DESCRIPTION
               "A Description of this sensor Switch"
               ::=  {  powerSensorEntry 2   }

            powerSensorValue OBJECT-TYPE
               SYNTAX  INTEGER
               ACCESS  read-only
               STATUS  mandatory
               DESCRIPTION
               "The reading value in this sensor"
               ::=  {  powerSensorEntry 4   }

            powerSensorUnit OBJECT-TYPE
               SYNTAX  DisplayString
               ACCESS  read-write
               STATUS  mandatory
               DESCRIPTION
               "The unit string"
               ::=  {  powerSensorEntry 5  }

            powerSensorStatus OBJECT-TYPE
               SYNTAX  INTEGER {
                  noStatus(1),
                  normal(2),
                  highCritical(4),
                  lowCritical(6),
                  sensorError(7)
               }
               ACCESS  read-only
               STATUS  mandatory
               DESCRIPTION
               "The current status of this Sensor, only input switches have a status"
               ::=  {  powerSensorEntry 6  }

            powerSensorGoOffline OBJECT-TYPE
               SYNTAX  INTEGER {
                  online(1),
                  goOffline(2)
               }
               ACCESS  read-write
               STATUS  mandatory
               DESCRIPTION
               "To take offline enter a 2"
               ::=  {  powerSensorEntry 8  }

            powerSensorLowCritical OBJECT-TYPE
               SYNTAX  INTEGER
               ACCESS  read-write
               STATUS  mandatory
               DESCRIPTION
               "How cold this sensor gets before it sends a critical event"
               ::=  {  powerSensorEntry 9   }

            powerSensorLowWarning OBJECT-TYPE
               SYNTAX  INTEGER
               ACCESS  read-write
               STATUS  mandatory
               DESCRIPTION
               "How cold this sensor gets before it sends a warning"
               ::=  {  powerSensorEntry 10   }
   
            powerSensorHighWarning OBJECT-TYPE
               SYNTAX  INTEGER
               ACCESS  read-write
               STATUS  mandatory
               DESCRIPTION
               "How hot this sensor gets before it sends a warning"
               ::=  {  powerSensorEntry 11   }  

            powerSensorHighCritical OBJECT-TYPE
               SYNTAX  INTEGER
               ACCESS  read-write
               STATUS  mandatory
               DESCRIPTION
               "How hot this sensor gets before it sends a critical event"
               ::=  {  powerSensorEntry 12   }   

            powerSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  powerSensorEntry 13   }

            powerSensorDelayError OBJECT-TYPE
               SYNTAX  INTEGER (0..65534)
               ACCESS  read-write
               STATUS  mandatory
               DESCRIPTION
               "Time in seconds after the sensor has been in error status before report as an error"
               ::=  {  powerSensorEntry 14   }

            powerSensorDelayNormal OBJECT-TYPE
               SYNTAX  INTEGER (0..65534)
               ACCESS  read-write
               STATUS  mandatory
               DESCRIPTION
               "Time in seconds after the sensor change from error to normal before report as normal"
               ::=  {  powerSensorEntry 15   }

            powerSensorDelayLowCritical OBJECT-TYPE
               SYNTAX INTEGER (0..65535)
               ACCESS read-write
               STATUS mandatory
               DESCRIPTION
               "Continuous time for this sensor to be in Low Critical before accepting new Status."
               ::= {  powerSensorEntry 16 }
               
            powerSensorDelayLowWarning OBJECT-TYPE
               SYNTAX INTEGER (0..65535)
               ACCESS read-write
               STATUS mandatory
               DESCRIPTION
               "Continuous time for this sensor to be in Low Warning before accepting new Status."
               ::= {  powerSensorEntry 17 }

            powerSensorDelayHighWarning OBJECT-TYPE
               SYNTAX INTEGER (0..65535)
               ACCESS read-write
               STATUS mandatory
               DESCRIPTION
               "Continuous time for this sensor to be in High Warning before accepting new Status."
               ::= {  powerSensorEntry 18 }

            powerSensorDelayHighCritical OBJECT-TYPE
               SYNTAX INTEGER (0..65535)
               ACCESS read-write
               STATUS mandatory
               DESCRIPTION
               "Continuous time for this sensor to be in High Critical before accepting new Status."
               ::= {  powerSensorEntry 19 }

            powerSensorPort OBJECT-TYPE
               SYNTAX  INTEGER (0..65534)
               ACCESS  read-only
               STATUS  mandatory
               DESCRIPTION
               "Sensor port"
               ::=  {  powerSensorEntry 35 }

            powerSensorSubPort OBJECT-TYPE
               SYNTAX  INTEGER (0..65534)
               ACCESS  read-only
               STATUS  mandatory
               DESCRIPTION
               "Sensor sub port"
               ::=  {  powerSensorEntry 36 }

            powerSensorDeviceIndex OBJECT-TYPE
               SYNTAX  INTEGER (0..65534)
               ACCESS  read-only
               STATUS  mandatory
               DESCRIPTION
               "Device Index of sensor"
               ::=  {  powerSensorEntry 37 }

            powerSensorTimeOut OBJECT-TYPE
               SYNTAX  INTEGER (5..30)
               ACCESS  read-write
               STATUS  mandatory
               DESCRIPTION
               "The polling timeout of Power Sensor."
               ::=  {  powerSensorEntry 38 }

            powerSensorInterval OBJECT-TYPE
               SYNTAX  INTEGER (5..720)
               ACCESS  read-write
               STATUS  mandatory
               DESCRIPTION
               "The polling interval of Power Sensor."
               ::=  {  powerSensorEntry 39 }

            powerSensorErrorRetryNum OBJECT-TYPE
               SYNTAX  INTEGER
               ACCESS  read-write
               STATUS  mandatory
               DESCRIPTION
               "Number of retry before error."
               ::=  {  powerSensorEntry 40 }
               
            powerSensorMaxValue OBJECT-TYPE
               SYNTAX  INTEGER
               ACCESS  read-write
               STATUS  mandatory
               DESCRIPTION
               "The maximum scale of Power value."
               ::=  {  powerSensorEntry 41   }

            powerSensorMinValue OBJECT-TYPE
               SYNTAX  INTEGER
               ACCESS  read-write
               STATUS  mandatory
               DESCRIPTION
               "The minimum scale of Power value."
               ::=  {  powerSensorEntry 42   }
               
            powerSensorDisplayStyle OBJECT-TYPE
               SYNTAX  INTEGER {
                  basic(0),
                  gauge(1)
               }
               ACCESS  read-write
               STATUS  mandatory
               DESCRIPTION
               "Power display style."
               ::=  {  powerSensorEntry 45 } 
               
            powerSensorHighCriticalDesc OBJECT-TYPE
               SYNTAX  DisplayString
               ACCESS  read-write
               STATUS  mandatory
               DESCRIPTION
               "A HighCritical Description of this sensor"
               ::=  {  powerSensorEntry  46  }               

            powerSensorLowCriticalDesc OBJECT-TYPE
               SYNTAX  DisplayString
               ACCESS  read-write
               STATUS  mandatory
               DESCRIPTION
               "A LowCritical Description of this sensor"
               ::=  {  powerSensorEntry  47  }

            powerSensorNormalDesc OBJECT-TYPE
               SYNTAX  DisplayString
               ACCESS  read-write
               STATUS  mandatory
               DESCRIPTION
               "A Normal Description of this sensor"
               ::=  {  powerSensorEntry  48  }
               
            powerSensorLowWarningDesc OBJECT-TYPE
               SYNTAX  DisplayString
               ACCESS  read-write
               STATUS  mandatory
               DESCRIPTION
               "A LowWarning Description of this sensor"
               ::=  {  powerSensorEntry  49  }
               
            powerSensorHighWarningDesc OBJECT-TYPE
               SYNTAX  DisplayString
               ACCESS  read-write
               STATUS  mandatory
               DESCRIPTION
               "A HighWarning Description of this sensor"
               ::=  {  powerSensorEntry  50  }
               
            powerSensorSensorErrorDesc OBJECT-TYPE
               SYNTAX  DisplayString
               ACCESS  read-write
               STATUS  mandatory
               DESCRIPTION
               "A SensorError Description of this sensor"
               ::=  {  powerSensorEntry  51  }  

            powerSensorHighCriticalColor OBJECT-TYPE
               SYNTAX  INTEGER
               ACCESS  read-write
               STATUS  mandatory
               DESCRIPTION
               "A HighCritical Color of this sensor"
               ::=  {  powerSensorEntry   54 }               

            powerSensorLowCriticalColor OBJECT-TYPE
               SYNTAX  INTEGER
               ACCESS  read-write
               STATUS  mandatory
               DESCRIPTION
               "A LowCritical Color of this sensor"
               ::=  {  powerSensorEntry  55  }

            powerSensorNormalColor OBJECT-TYPE
               SYNTAX  INTEGER
               ACCESS  read-write
               STATUS  mandatory
               DESCRIPTION
               "A Normal Color of this sensor"
               ::=  {  powerSensorEntry  56  }
               
            powerSensorLowWarningColor OBJECT-TYPE
               SYNTAX  INTEGER
               ACCESS  read-write
               STATUS  mandatory
               DESCRIPTION
               "A LowWarning Color of this sensor"
               ::=  {  powerSensorEntry  57  }
               
            powerSensorHighWarningColor OBJECT-TYPE
               SYNTAX  INTEGER
               ACCESS  read-write
               STATUS  mandatory
               DESCRIPTION
               "A HighWarning Color of this sensor"
               ::=  {  powerSensorEntry  58  }
               
            powerSensorSensorErrorColor OBJECT-TYPE
               SYNTAX  INTEGER
               ACCESS  read-write
               STATUS  mandatory
               DESCRIPTION
               "A SensorError Color of this sensor"
               ::=  {  powerSensorEntry  59  }

            powerSensorValueFormatString OBJECT-TYPE
               SYNTAX  DisplayString
               ACCESS  read-only
               STATUS  mandatory
               DESCRIPTION
               "The string-based reading value in this sensor"
               ::=  {  powerSensorEntry  66  }

            powerSensorValueFormatFloat OBJECT-TYPE
               SYNTAX  Opaque (SIZE(4))
               ACCESS  read-only
               STATUS  mandatory
               DESCRIPTION
               "The floating-point IEEE Standard 754 reading value in this sensor"
               ::=  {  powerSensorEntry  67  }

            powerSensorAcknowledge OBJECT-TYPE
               SYNTAX  INTEGER {
                  acked(2)
               }
               ACCESS  read-write
               STATUS  mandatory
               DESCRIPTION
               "Power sensor acknowledge"
               ::=  {  powerSensorEntry 70 }

            powerSensorId OBJECT-TYPE
               SYNTAX  INTEGER
               ACCESS  read-only
               STATUS  mandatory
               DESCRIPTION
               "The Sensor ID of this sensor, used to identify which sensor it is in the system configuration."
               ::= { powerSensorEntry 1000 }

--/* End of powerSensorEntry */

--/* Begin of fuelSensorEntry */
         fuelSensorTable OBJECT-TYPE
            SYNTAX  SEQUENCE OF FuelSensorEntry
            ACCESS  not-accessible
            STATUS  mandatory
            DESCRIPTION
            "This table contains the property and reading value for every sensor."
            ::=  {  sensorByPort 24   }

         fuelSensorEntry OBJECT-TYPE
            SYNTAX  FuelSensorEntry
            ACCESS  not-accessible
            STATUS  mandatory
            DESCRIPTION
            "This is an entry in the fuelSensorEntry Table"
            INDEX         { fuelSensorIndex }
            ::=  {  fuelSensorTable 1 }

         FuelSensorEntry ::= SEQUENCE {
               fuelSensorIndex
                  DisplayString,
               fuelSensorDescription
                  DisplayString,
               fuelSensorValue
                  INTEGER,
               fuelSensorUnit
                  DisplayString,
               fuelSensorStatus
                  INTEGER,
               fuelSensorGoOffline
                  INTEGER,
               fuelSensorLowCritical
                  INTEGER,
               fuelSensorLowWarning
                  INTEGER,
               fuelSensorHighWarning
                  INTEGER,
               fuelSensorHighCritical
                  INTEGER,
               fuelSensorRearm
                  INTEGER,
               fuelSensorDelayError
                  INTEGER,
               fuelSensorDelayNormal
                  INTEGER,
               fuelSensorDelayLowCritical
                  INTEGER,
               fuelSensorDelayLowWarning
                  INTEGER,
               fuelSensorDelayHighWarning
                  INTEGER,
               fuelSensorDelayHighCritical
                  INTEGER,
               fuelSensorRaw
                  INTEGER,
               fuelSensorAmountMaxValue
                  INTEGER,
               fuelSensorAmountBaseValue
                  INTEGER,
               fuelSensorDeviceIndex
                  INTEGER,
               fuelSensorDisplayStyle
                  INTEGER,
               fuelSensorHighCriticalDesc 
                  DisplayString,
               fuelSensorLowCriticalDesc 
                  DisplayString,
               fuelSensorNormalDesc 
                  DisplayString,
               fuelSensorLowWarningDesc 
                  DisplayString,   
               fuelSensorHighWarningDesc 
                  DisplayString,
               fuelSensorSensorErrorDesc 
                  DisplayString,
               fuelSensorHighCriticalColor 
                  INTEGER,
               fuelSensorLowCriticalColor 
                  INTEGER,
               fuelSensorNormalColor 
                  INTEGER,
               fuelSensorLowWarningColor 
                  INTEGER,   
               fuelSensorHighWarningColor 
                  INTEGER,
               fuelSensorSensorErrorColor 
                  INTEGER,           
               fuelSensorAcknowledge
                  INTEGER,
               fuelSensorId
                  INTEGER
            }

            fuelSensorIndex OBJECT-TYPE
               SYNTAX  DisplayString
               ACCESS  read-only
               STATUS  mandatory
               DESCRIPTION
               "The Sensor Compound ID of this sensor, used to identify which sensor it is in the system configuration."
               ::=  {  fuelSensorEntry 1   }

            fuelSensorDescription OBJECT-TYPE
               SYNTAX  DisplayString
               ACCESS  read-write
               STATUS  mandatory
               DESCRIPTION
               "A Description of this sensor"
               ::=  {  fuelSensorEntry 2   }

            fuelSensorValue OBJECT-TYPE
               SYNTAX  INTEGER
               ACCESS  read-only
               STATUS  mandatory
               DESCRIPTION
               "The reading value in this sensor"
               ::=  {  fuelSensorEntry 4   }

            fuelSensorUnit OBJECT-TYPE
               SYNTAX  DisplayString
               ACCESS  read-write
               STATUS  mandatory
               DESCRIPTION
               "The unit string"
               ::=  {  fuelSensorEntry 5  }

            fuelSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  fuelSensorEntry 6   }

            fuelSensorGoOffline OBJECT-TYPE
               SYNTAX  INTEGER {
                  online(1),
                  goOffline(2)
               }
               ACCESS  read-write
               STATUS  mandatory
               DESCRIPTION
               "To take offline enter a 2"
               ::=  {  fuelSensorEntry 8   }

            fuelSensorLowCritical OBJECT-TYPE
               SYNTAX  INTEGER
               ACCESS  read-write
               STATUS  mandatory
               DESCRIPTION
               "Level value of this sensor gets before it sends a critical event"
               ::=  {  fuelSensorEntry 9   }

            fuelSensorLowWarning OBJECT-TYPE
               SYNTAX  INTEGER
               ACCESS  read-write
               STATUS  mandatory
               DESCRIPTION
               "Level value of this sensor gets before it sends a warning"
               ::=  {  fuelSensorEntry 10   }
   
            fuelSensorHighWarning OBJECT-TYPE
               SYNTAX  INTEGER
               ACCESS  read-write
               STATUS  mandatory
               DESCRIPTION
               "Level value of this sensor gets before it sends a warning"
               ::=  {  fuelSensorEntry 11   }  

            fuelSensorHighCritical OBJECT-TYPE
               SYNTAX  INTEGER
               ACCESS  read-write
               STATUS  mandatory
               DESCRIPTION
               "Level value of this sensor gets before it sends a critical event"
               ::=  {  fuelSensorEntry 12   }   

            fuelSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  fuelSensorEntry 13   }

            fuelSensorDelayError OBJECT-TYPE
               SYNTAX  INTEGER (0..65534)
               ACCESS  read-write
               STATUS  mandatory
               DESCRIPTION
               "Time in seconds after the sensor has been in error status before report as an error"
               ::=  {  fuelSensorEntry 14   }

            fuelSensorDelayNormal OBJECT-TYPE
               SYNTAX  INTEGER (0..65534)
               ACCESS  read-write
               STATUS  mandatory
               DESCRIPTION
               "Time in seconds after the sensor change from error to normal before report as normal"
               ::=  {  fuelSensorEntry 15   }

            fuelSensorDelayLowCritical OBJECT-TYPE
               SYNTAX INTEGER (0..65535)
               ACCESS read-write
               STATUS mandatory
               DESCRIPTION
               "Continuous time for this sensor to be in Low Critical before accepting new Status."
               ::= {  fuelSensorEntry 16 }
               
            fuelSensorDelayLowWarning OBJECT-TYPE
               SYNTAX INTEGER (0..65535)
               ACCESS read-write
               STATUS mandatory
               DESCRIPTION
               "Continuous time for this sensor to be in Low Warning before accepting new Status."
               ::= {  fuelSensorEntry 17 }

            fuelSensorDelayHighWarning OBJECT-TYPE
               SYNTAX INTEGER (0..65535)
               ACCESS read-write
               STATUS mandatory
               DESCRIPTION
               "Continuous time for this sensor to be in High Warning before accepting new Status."
               ::= {  fuelSensorEntry 18 }

            fuelSensorDelayHighCritical OBJECT-TYPE
               SYNTAX INTEGER (0..65535)
               ACCESS read-write
               STATUS mandatory
               DESCRIPTION
               "Continuous time for this sensor to be in High Critical before accepting new Status."
               ::= {  fuelSensorEntry 19 }

            fuelSensorRaw OBJECT-TYPE
               SYNTAX  INTEGER 
               ACCESS  read-only
               STATUS  mandatory
               DESCRIPTION
               "The unformatted, raw, A/D value in this sensor. Contains more resolution than the formated percentage."
               ::=  {  fuelSensorEntry 20   }

            fuelSensorAmountMaxValue OBJECT-TYPE
               SYNTAX  INTEGER
               ACCESS  read-write
               STATUS  mandatory
               DESCRIPTION
               "The maximum scale of value conversion."
               ::=  {  fuelSensorEntry 33   }

            fuelSensorAmountBaseValue OBJECT-TYPE
               SYNTAX  INTEGER
               ACCESS  read-write
               STATUS  mandatory
               DESCRIPTION
               "The base scale of value conversion."
               ::=  {  fuelSensorEntry 34   }

            fuelSensorDeviceIndex OBJECT-TYPE
               SYNTAX  INTEGER (0..65534)
               ACCESS  read-only
               STATUS  mandatory
               DESCRIPTION
               "Device Index of sensor"
               ::=  {  fuelSensorEntry 37 }
               
            fuelSensorDisplayStyle OBJECT-TYPE
               SYNTAX  INTEGER {
                  basic(0),
                  gauge(1)
               }
               ACCESS  read-write
               STATUS  mandatory
               DESCRIPTION
               "Fuel display style"
               ::=  {  fuelSensorEntry 45 }     

            fuelSensorHighCriticalDesc OBJECT-TYPE
               SYNTAX  DisplayString
               ACCESS  read-write
               STATUS  mandatory
               DESCRIPTION
               "A HighCritical Description of this sensor"
               ::=  {  fuelSensorEntry  46  }               

            fuelSensorLowCriticalDesc OBJECT-TYPE
               SYNTAX  DisplayString
               ACCESS  read-write
               STATUS  mandatory
               DESCRIPTION
               "A LowCritical Description of this sensor"
               ::=  {  fuelSensorEntry  47  }

            fuelSensorNormalDesc OBJECT-TYPE
               SYNTAX  DisplayString
               ACCESS  read-write
               STATUS  mandatory
               DESCRIPTION
               "A Normal Description of this sensor"
               ::=  {  fuelSensorEntry  48  }
               
            fuelSensorLowWarningDesc OBJECT-TYPE
               SYNTAX  DisplayString
               ACCESS  read-write
               STATUS  mandatory
               DESCRIPTION
               "A LowWarning Description of this sensor"
               ::=  {  fuelSensorEntry  49  }
               
            fuelSensorHighWarningDesc OBJECT-TYPE
               SYNTAX  DisplayString
               ACCESS  read-write
               STATUS  mandatory
               DESCRIPTION
               "A HighWarning Description of this sensor"
               ::=  {  fuelSensorEntry  50  }
               
            fuelSensorSensorErrorDesc OBJECT-TYPE
               SYNTAX  DisplayString
               ACCESS  read-write
               STATUS  mandatory
               DESCRIPTION
               "A SensorError Description of this sensor"
               ::=  {  fuelSensorEntry  51  }  

            fuelSensorHighCriticalColor OBJECT-TYPE
               SYNTAX  INTEGER
               ACCESS  read-write
               STATUS  mandatory
               DESCRIPTION
               "A HighCritical Color of this sensor"
               ::=  {  fuelSensorEntry  54  }               

            fuelSensorLowCriticalColor OBJECT-TYPE
               SYNTAX  INTEGER
               ACCESS  read-write
               STATUS  mandatory
               DESCRIPTION
               "A LowCritical Color of this sensor"
               ::=  {  fuelSensorEntry  55  }

            fuelSensorNormalColor OBJECT-TYPE
               SYNTAX  INTEGER
               ACCESS  read-write
               STATUS  mandatory
               DESCRIPTION
               "A Normal Color of this sensor"
               ::=  {  fuelSensorEntry  56  }
               
            fuelSensorLowWarningColor OBJECT-TYPE
               SYNTAX  INTEGER
               ACCESS  read-write
               STATUS  mandatory
               DESCRIPTION
               "A LowWarning Color of this sensor"
               ::=  {  fuelSensorEntry  57  }
               
            fuelSensorHighWarningColor OBJECT-TYPE
               SYNTAX  INTEGER
               ACCESS  read-write
               STATUS  mandatory
               DESCRIPTION
               "A HighWarning Color of this sensor"
               ::=  {  fuelSensorEntry  58  }
               
            fuelSensorSensorErrorColor OBJECT-TYPE
               SYNTAX  INTEGER
               ACCESS  read-write
               STATUS  mandatory
               DESCRIPTION
               "A SensorError Color of this sensor"
               ::=  {  fuelSensorEntry  59  }    

            fuelSensorAcknowledge OBJECT-TYPE
               SYNTAX  INTEGER {
                  acked(2)
               }
               ACCESS  read-write
               STATUS  mandatory
               DESCRIPTION
               "Fuel sensor acknowledge"
               ::=  {  fuelSensorEntry 70 }

            fuelSensorId OBJECT-TYPE
               SYNTAX  INTEGER
               ACCESS  read-only
               STATUS  mandatory
               DESCRIPTION
               "The Sensor ID of this sensor, used to identify which sensor it is in the system configuration."
               ::= { fuelSensorEntry 1000 }

--/* End of fuelSensorEntry */

--/* Begin of tankSenderSensorEntry */
         tankSenderSensorTable OBJECT-TYPE
            SYNTAX  SEQUENCE OF TankSenderSensorEntry
            ACCESS  not-accessible
            STATUS  mandatory
            DESCRIPTION
            "This table contains the property and reading value for every sensor."
            ::=  {  sensorByPort 26   }

         tankSenderSensorEntry OBJECT-TYPE
            SYNTAX  TankSenderSensorEntry
            ACCESS  not-accessible
            STATUS  mandatory
            DESCRIPTION
            "This is an entry in the tankSenderSensorEntry Table"
            INDEX         { tankSenderSensorIndex }
            ::=  {  tankSenderSensorTable 1 }

         TankSenderSensorEntry ::= SEQUENCE {
               tankSenderSensorIndex
                  DisplayString,
               tankSenderSensorDescription
                  DisplayString,
               tankSenderSensorValue
                  INTEGER,
               tankSenderSensorUnit
                  DisplayString,
               tankSenderSensorStatus
                  INTEGER,
               tankSenderSensorGoOffline
                  INTEGER,
               tankSenderSensorLowCritical
                  INTEGER,
               tankSenderSensorLowWarning
                  INTEGER,
               tankSenderSensorHighWarning
                  INTEGER,
               tankSenderSensorHighCritical
                  INTEGER,
               tankSenderSensorRearm
                  INTEGER,
               tankSenderSensorDelayError
                  INTEGER,
               tankSenderSensorDelayNormal
                  INTEGER,
               tankSenderSensorDelayLowCritical
                  INTEGER,
               tankSenderSensorDelayLowWarning
                  INTEGER,
               tankSenderSensorDelayHighWarning
                  INTEGER,
               tankSenderSensorDelayHighCritical
                  INTEGER,
               tankSenderSensorRaw
                  INTEGER,
               tankSenderSensorDeviceIndex
                  INTEGER,
               tankSenderSensorDisplayStyle
                  INTEGER,
               tankSenderSensorHighCriticalDesc 
                  DisplayString,
               tankSenderSensorLowCriticalDesc 
                  DisplayString,
               tankSenderSensorNormalDesc 
                  DisplayString,
               tankSenderSensorLowWarningDesc 
                  DisplayString,   
               tankSenderSensorHighWarningDesc 
                  DisplayString,
               tankSenderSensorSensorErrorDesc 
                  DisplayString,
               tankSenderSensorHighCriticalColor 
                  INTEGER,
               tankSenderSensorLowCriticalColor 
                  INTEGER,
               tankSenderSensorNormalColor 
                  INTEGER,
               tankSenderSensorLowWarningColor 
                  INTEGER,   
               tankSenderSensorHighWarningColor 
                  INTEGER,
               tankSenderSensorSensorErrorColor 
                  INTEGER,             
               tankSenderSensorAcknowledge
                  INTEGER,
               tankSenderSensorId
                  INTEGER
            }

            tankSenderSensorIndex OBJECT-TYPE
               SYNTAX  DisplayString
               ACCESS  read-only
               STATUS  mandatory
               DESCRIPTION
               "The Sensor Compound ID of this sensor, used to identify which sensor it is in the system configuration."
               ::=  {  tankSenderSensorEntry 1   }

            tankSenderSensorDescription OBJECT-TYPE
               SYNTAX  DisplayString
               ACCESS  read-write
               STATUS  mandatory
               DESCRIPTION
               "A Description of this sensor"
               ::=  {  tankSenderSensorEntry 2   }

            tankSenderSensorValue OBJECT-TYPE
               SYNTAX  INTEGER
               ACCESS  read-only
               STATUS  mandatory
               DESCRIPTION
               "The reading value in this sensor"
               ::=  {  tankSenderSensorEntry 4   }

            tankSenderSensorUnit OBJECT-TYPE
               SYNTAX  DisplayString
               ACCESS  read-write
               STATUS  mandatory
               DESCRIPTION
               "The unit string"
               ::=  {  tankSenderSensorEntry 5  }

            tankSenderSensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  tankSenderSensorEntry 6   }

            tankSenderSensorGoOffline OBJECT-TYPE
               SYNTAX  INTEGER {
                  online(1),
                  goOffline(2)
               }
               ACCESS  read-write
               STATUS  mandatory
               DESCRIPTION
               "To take offline enter a 2"
               ::=  {  tankSenderSensorEntry 8   }

            tankSenderSensorLowCritical OBJECT-TYPE
               SYNTAX  INTEGER
               ACCESS  read-write
               STATUS  mandatory
               DESCRIPTION
               "Level value of this sensor gets before it sends a critical event"
               ::=  {  tankSenderSensorEntry 9   }

            tankSenderSensorLowWarning OBJECT-TYPE
               SYNTAX  INTEGER
               ACCESS  read-write
               STATUS  mandatory
               DESCRIPTION
               "Level value of this sensor gets before it sends a warning"
               ::=  {  tankSenderSensorEntry 10   }
   
            tankSenderSensorHighWarning OBJECT-TYPE
               SYNTAX  INTEGER
               ACCESS  read-write
               STATUS  mandatory
               DESCRIPTION
               "Level value of this sensor gets before it sends a warning"
               ::=  {  tankSenderSensorEntry 11   }  

            tankSenderSensorHighCritical OBJECT-TYPE
               SYNTAX  INTEGER
               ACCESS  read-write
               STATUS  mandatory
               DESCRIPTION
               "Level value of this sensor gets before it sends a critical event"
               ::=  {  tankSenderSensorEntry 12   }   

            tankSenderSensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  tankSenderSensorEntry 13   }

            tankSenderSensorDelayError OBJECT-TYPE
               SYNTAX  INTEGER (0..65534)
               ACCESS  read-write
               STATUS  mandatory
               DESCRIPTION
               "Time in seconds after the sensor has been in error status before report as an error"
               ::=  {  tankSenderSensorEntry 14   }

            tankSenderSensorDelayNormal OBJECT-TYPE
               SYNTAX  INTEGER (0..65534)
               ACCESS  read-write
               STATUS  mandatory
               DESCRIPTION
               "Time in seconds after the sensor change from error to normal before report as normal"
               ::=  {  tankSenderSensorEntry 15   }

            tankSenderSensorDelayLowCritical OBJECT-TYPE
               SYNTAX INTEGER (0..65535)
               ACCESS read-write
               STATUS mandatory
               DESCRIPTION
               "Continuous time for this sensor to be in Low Critical before accepting new Status."
               ::= {  tankSenderSensorEntry 16 }
               
            tankSenderSensorDelayLowWarning OBJECT-TYPE
               SYNTAX INTEGER (0..65535)
               ACCESS read-write
               STATUS mandatory
               DESCRIPTION
               "Continuous time for this sensor to be in Low Warning before accepting new Status."
               ::= {  tankSenderSensorEntry 17 }

            tankSenderSensorDelayHighWarning OBJECT-TYPE
               SYNTAX INTEGER (0..65535)
               ACCESS read-write
               STATUS mandatory
               DESCRIPTION
               "Continuous time for this sensor to be in High Warning before accepting new Status."
               ::= {  tankSenderSensorEntry 18 }

            tankSenderSensorDelayHighCritical OBJECT-TYPE
               SYNTAX INTEGER (0..65535)
               ACCESS read-write
               STATUS mandatory
               DESCRIPTION
               "Continuous time for this sensor to be in High Critical before accepting new Status."
               ::= {  tankSenderSensorEntry 19 }

            tankSenderSensorRaw OBJECT-TYPE
               SYNTAX  INTEGER 
               ACCESS  read-only
               STATUS  mandatory
               DESCRIPTION
               "The unformatted, raw, A/D value in this sensor. Contains more resolution than the formated percentage."
               ::=  {  tankSenderSensorEntry 20   }

            tankSenderSensorDeviceIndex OBJECT-TYPE
               SYNTAX  INTEGER (0..65534)
               ACCESS  read-only
               STATUS  mandatory
               DESCRIPTION
               "Device Index of sensor"
               ::=  {  tankSenderSensorEntry 37 }
               
            tankSenderSensorDisplayStyle OBJECT-TYPE
               SYNTAX  INTEGER {
                  basic(0),
                  gauge(1)
               }
               ACCESS  read-write
               STATUS  mandatory
               DESCRIPTION
               "TankSender display style"
               ::=  {  tankSenderSensorEntry 45 }     

            tankSenderSensorHighCriticalDesc OBJECT-TYPE
               SYNTAX  DisplayString
               ACCESS  read-write
               STATUS  mandatory
               DESCRIPTION
               "A HighCritical Description of this sensor"
               ::=  {  tankSenderSensorEntry  46  }               

            tankSenderSensorLowCriticalDesc OBJECT-TYPE
               SYNTAX  DisplayString
               ACCESS  read-write
               STATUS  mandatory
               DESCRIPTION
               "A LowCritical Description of this sensor"
               ::=  {  tankSenderSensorEntry  47  }

            tankSenderSensorNormalDesc OBJECT-TYPE
               SYNTAX  DisplayString
               ACCESS  read-write
               STATUS  mandatory
               DESCRIPTION
               "A Normal Description of this sensor"
               ::=  {  tankSenderSensorEntry  48  }
               
            tankSenderSensorLowWarningDesc OBJECT-TYPE
               SYNTAX  DisplayString
               ACCESS  read-write
               STATUS  mandatory
               DESCRIPTION
               "A LowWarning Description of this sensor"
               ::=  {  tankSenderSensorEntry  49  }
               
            tankSenderSensorHighWarningDesc OBJECT-TYPE
               SYNTAX  DisplayString
               ACCESS  read-write
               STATUS  mandatory
               DESCRIPTION
               "A HighWarning Description of this sensor"
               ::=  {  tankSenderSensorEntry  50  }
               
            tankSenderSensorSensorErrorDesc OBJECT-TYPE
               SYNTAX  DisplayString
               ACCESS  read-write
               STATUS  mandatory
               DESCRIPTION
               "A SensorError Description of this sensor"
               ::=  {  tankSenderSensorEntry  51  }  

            tankSenderSensorHighCriticalColor OBJECT-TYPE
               SYNTAX  INTEGER
               ACCESS  read-write
               STATUS  mandatory
               DESCRIPTION
               "A HighCritical Color of this sensor"
               ::=  {  tankSenderSensorEntry  54  }

            tankSenderSensorLowCriticalColor OBJECT-TYPE
               SYNTAX  INTEGER
               ACCESS  read-write
               STATUS  mandatory
               DESCRIPTION
               "A LowCritical Color of this sensor"
               ::=  {  tankSenderSensorEntry  55  }

            tankSenderSensorNormalColor OBJECT-TYPE
               SYNTAX  INTEGER
               ACCESS  read-write
               STATUS  mandatory
               DESCRIPTION
               "A Normal Color of this sensor"
               ::=  {  tankSenderSensorEntry  56  }
               
            tankSenderSensorLowWarningColor OBJECT-TYPE
               SYNTAX  INTEGER
               ACCESS  read-write
               STATUS  mandatory
               DESCRIPTION
               "A LowWarning Color of this sensor"
               ::=  {  tankSenderSensorEntry  57  }
               
            tankSenderSensorHighWarningColor OBJECT-TYPE
               SYNTAX  INTEGER
               ACCESS  read-write
               STATUS  mandatory
               DESCRIPTION
               "A HighWarning Color of this sensor"
               ::=  {  tankSenderSensorEntry  58  }
               
            tankSenderSensorSensorErrorColor OBJECT-TYPE
               SYNTAX  INTEGER
               ACCESS  read-write
               STATUS  mandatory
               DESCRIPTION
               "A SensorError Color of this sensor"
               ::=  {  tankSenderSensorEntry  59  }    

            tankSenderSensorAcknowledge OBJECT-TYPE
               SYNTAX  INTEGER {
                  acked(2)
               }
               ACCESS  read-write
               STATUS  mandatory
               DESCRIPTION
               "Tank Sender sensor acknowledge"
               ::=  {  tankSenderSensorEntry 70 }

            tankSenderSensorId OBJECT-TYPE
               SYNTAX  INTEGER
               ACCESS  read-only
               STATUS  mandatory
               DESCRIPTION
               "The Sensor ID of this sensor, used to identify which sensor it is in the system configuration."
               ::= { tankSenderSensorEntry 1000 }

--/* End of tankSenderSensorEntry */

--/* Begin of doorSensorEntry */
         doorSensorTable OBJECT-TYPE
            SYNTAX  SEQUENCE OF DoorSensorEntry
            ACCESS  not-accessible
            STATUS  mandatory
            DESCRIPTION
            "This table contains the property and reading value for every sensor."
            ::=  {  sensorByPort 27   }

         doorSensorEntry OBJECT-TYPE
            SYNTAX  DoorSensorEntry
            ACCESS  not-accessible
            STATUS  mandatory
            DESCRIPTION
            "This is an entry in the doorSensorEntry Table"
            INDEX         { doorSensorIndex }
            ::=  {  doorSensorTable 1 }

         DoorSensorEntry ::= SEQUENCE {
               doorSensorIndex
                  DisplayString,
               doorSensorDescription
                  DisplayString,
               doorSensorValue
                  INTEGER,
               doorSensorStatus
                  INTEGER,
               doorSensorUnlockPeriod
                  INTEGER,
               doorSensorOpenPeriod
                  INTEGER,
               doorSensorCmd
                  INTEGER,
               doorSensorAcknowledge
                  INTEGER,
               doorSensorId
                  INTEGER
            }

            doorSensorIndex OBJECT-TYPE
               SYNTAX  DisplayString
               ACCESS  read-only
               STATUS  mandatory
               DESCRIPTION
               "The Sensor Compound ID of this sensor, used to identify which sensor it is in the system configuration."
               ::=  {  doorSensorEntry 1   }

            doorSensorDescription OBJECT-TYPE
               SYNTAX  DisplayString
               ACCESS  read-write
               STATUS  mandatory
               DESCRIPTION
               "A Description of this sensor"
               ::=  {  doorSensorEntry 2   }

            doorSensorValue OBJECT-TYPE
               SYNTAX  INTEGER
               ACCESS  read-only
               STATUS  mandatory
               DESCRIPTION
               "The reading value in this sensor"
               ::=  {  doorSensorEntry 4   }

            doorSensorStatus OBJECT-TYPE
               SYNTAX  INTEGER {
                  noStatus(1),
                  closed(2),
                  heldOpen(3),
                  fire(4),
                  opened(5),
                  forceOpened(6),
                  sensorError(7)
               }
               ACCESS  read-only
               STATUS  mandatory
               DESCRIPTION
               "The current status of this Sensor"
               ::=  {  doorSensorEntry 6   }

            doorSensorUnlockPeriod OBJECT-TYPE
               SYNTAX  INTEGER
               ACCESS  read-write
               STATUS  mandatory
               DESCRIPTION
               "Door unlock period"
               ::=  {  doorSensorEntry 62   }

            doorSensorOpenPeriod OBJECT-TYPE
               SYNTAX  INTEGER
               ACCESS  read-write
               STATUS  mandatory
               DESCRIPTION
               "Door open period"
               ::=  {  doorSensorEntry 63   }
   
            doorSensorCmd OBJECT-TYPE
               SYNTAX  INTEGER
               ACCESS  read-write
               STATUS  mandatory
               DESCRIPTION
               "Door command"
               ::=  {  doorSensorEntry 64   }  

            doorSensorAcknowledge OBJECT-TYPE
               SYNTAX  INTEGER {
                  acked(2)
               }
               ACCESS  read-write
               STATUS  mandatory
               DESCRIPTION
               "Door sensor acknowledge"
               ::=  {  doorSensorEntry 70 }  

            doorSensorId OBJECT-TYPE
               SYNTAX  INTEGER
               ACCESS  read-only
               STATUS  mandatory
               DESCRIPTION
               "The Sensor ID of this sensor, used to identify which sensor it is in the system configuration."
               ::= { doorSensorEntry 1000 }

--/* End of doorSensorEntry */

--/* Begin of temperatureArraySensorEntry */
         temperatureArraySensorTable OBJECT-TYPE
            SYNTAX  SEQUENCE OF TemperatureArraySensorEntry
            ACCESS  not-accessible
            STATUS  mandatory
            DESCRIPTION
            "This table contains the property and reading value for every Temperature sensor."
            ::=  {  sensorByPort 28  }

         temperatureArraySensorEntry OBJECT-TYPE
            SYNTAX  TemperatureArraySensorEntry
            ACCESS  not-accessible
            STATUS  mandatory
            DESCRIPTION
            "This is an entry in the temperatureArraySensorEntry Table"
            INDEX         { temperatureArraySensorIndex }
            ::=  {  temperatureArraySensorTable 1 }

         TemperatureArraySensorEntry ::= SEQUENCE {
               temperatureArraySensorIndex
                  DisplayString,
               temperatureArraySensorDescription
                  DisplayString,
               temperatureArraySensorType
                  INTEGER,
               temperatureArraySensorDegree
                  INTEGER,
               temperatureArraySensorUnit
                  DisplayString,               
               temperatureArraySensorStatus
                  INTEGER,
               temperatureArraySensorGoOffline
                  INTEGER,
               temperatureArraySensorLowCritical
                  INTEGER,
               temperatureArraySensorLowWarning
                  INTEGER,
               temperatureArraySensorHighWarning
                  INTEGER,
               temperatureArraySensorHighCritical
                  INTEGER,
               temperatureArraySensorRearm
                  INTEGER,
               temperatureArraySensorDelayError
                  INTEGER,
               temperatureArraySensorDelayNormal
                  INTEGER,
               temperatureArraySensorDelayLowCritical
                  INTEGER,
               temperatureArraySensorDelayLowWarning
                  INTEGER,
               temperatureArraySensorDelayHighWarning
                  INTEGER,
               temperatureArraySensorDelayHighCritical
                  INTEGER,
               temperatureArraySensorRaw
                  INTEGER,
               temperatureArraySensorOffset
                  INTEGER,
               temperatureArraySensorPort
                  INTEGER,
               temperatureArraySensorSubPort
                  INTEGER,
               temperatureArraySensorDeviceIndex
                  INTEGER,
               temperatureArraySensorDisplayStyle
                  INTEGER,
               temperatureArraySensorHighCriticalDesc 
                  DisplayString,
               temperatureArraySensorLowCriticalDesc 
                  DisplayString,
               temperatureArraySensorNormalDesc 
                  DisplayString,
               temperatureArraySensorLowWarningDesc 
                  DisplayString,   
               temperatureArraySensorHighWarningDesc 
                  DisplayString,
               temperatureArraySensorSensorErrorDesc 
                  DisplayString,
               temperatureArraySensorHighCriticalColor 
                  INTEGER,
               temperatureArraySensorLowCriticalColor 
                  INTEGER,
               temperatureArraySensorSensorNormalColor 
                  INTEGER,
               temperatureArraySensorLowWarningColor 
                  INTEGER,   
               temperatureArraySensorHighWarningColor 
                  INTEGER,
               temperatureArraySensorSensorErrorColor 
                  INTEGER,                 
               temperatureArraySensorAcknowledge
                  INTEGER,
               temperatureArraySensorSerialNumber
                  DisplayString,
               temperatureArraySensorId
                  INTEGER
            }

            temperatureArraySensorIndex OBJECT-TYPE
               SYNTAX  DisplayString
               ACCESS  read-only
               STATUS  mandatory
               DESCRIPTION
               "The Sensor Compound ID of this sensor, used to identify which sensor it is in the system configuration."
               ::=  {  temperatureArraySensorEntry 1   }

            temperatureArraySensorDescription OBJECT-TYPE
               SYNTAX  DisplayString
               ACCESS  read-write
               STATUS  mandatory
               DESCRIPTION
               "A Description of this sensor"
               ::=  {  temperatureArraySensorEntry 2   }

            temperatureArraySensorType OBJECT-TYPE
               SYNTAX  INTEGER {
                  temperature(1),
                  dualsensor(3),
                  thermocouple(20)
               }
               ACCESS  read-only
               STATUS  mandatory
               DESCRIPTION
               "Enter the type of this Sensor"
               ::=  {  temperatureArraySensorEntry 3  }

            temperatureArraySensorDegree OBJECT-TYPE
               SYNTAX  INTEGER
               ACCESS  read-only
               STATUS  mandatory
               DESCRIPTION
               "The degrees in this sensor"
               ::=  {  temperatureArraySensorEntry 4   }

            temperatureArraySensorUnit OBJECT-TYPE
               SYNTAX  DisplayString
               ACCESS  read-only
               STATUS  mandatory
               DESCRIPTION
               "The unit string"
               ::=  {  temperatureArraySensorEntry 5  }

            temperatureArraySensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  temperatureArraySensorEntry 6   }
   
            temperatureArraySensorGoOffline OBJECT-TYPE
               SYNTAX  INTEGER {
                  online(1),
                  goOffline(2)
               }
               ACCESS  read-write
               STATUS  mandatory
               DESCRIPTION
               "To take offline enter a 2"
               ::=  {  temperatureArraySensorEntry 8   }

            temperatureArraySensorLowCritical OBJECT-TYPE
               SYNTAX  INTEGER
               ACCESS  read-write
               STATUS  mandatory
               DESCRIPTION
               "How cold this sensor gets before it sends a critical event"
               ::=  {  temperatureArraySensorEntry 9   }

            temperatureArraySensorLowWarning OBJECT-TYPE
               SYNTAX  INTEGER
               ACCESS  read-write
               STATUS  mandatory
               DESCRIPTION
               "How cold this sensor gets before it sends a warning"
               ::=  {  temperatureArraySensorEntry 10   }
   
            temperatureArraySensorHighWarning OBJECT-TYPE
               SYNTAX  INTEGER
               ACCESS  read-write
               STATUS  mandatory
               DESCRIPTION
               "How hot this sensor gets before it sends a warning"
               ::=  {  temperatureArraySensorEntry 11   }  

            temperatureArraySensorHighCritical OBJECT-TYPE
               SYNTAX  INTEGER
               ACCESS  read-write
               STATUS  mandatory
               DESCRIPTION
               "How hot this sensor gets before it sends a critical event"
               ::=  {  temperatureArraySensorEntry 12   }   

            temperatureArraySensorRearm OBJECT-TYPE
               SYNTAX  INTEGER
               ACCESS  read-write
               STATUS  mandatory
               DESCRIPTION
               "The number of degrees to rearm the status. For example if status goes from normal to warning, the temp must go down spTempRearm degrees below warning before the status goes to normal"
               ::=  {  temperatureArraySensorEntry 13   }

            temperatureArraySensorDelayError OBJECT-TYPE
               SYNTAX  INTEGER (0..65534)
               ACCESS  read-write
               STATUS  mandatory
               DESCRIPTION
               "Time in seconds after the sensor has been in error status before report as an error"
               ::=  {  temperatureArraySensorEntry 14   }

            temperatureArraySensorDelayNormal OBJECT-TYPE
               SYNTAX  INTEGER (0..65534)
               ACCESS  read-write
               STATUS  mandatory
               DESCRIPTION
               "Time in seconds after the sensor change from error to normal before report as normal"
               ::=  {  temperatureArraySensorEntry 15   }

            temperatureArraySensorDelayLowCritical OBJECT-TYPE
               SYNTAX INTEGER (0..65535)
               ACCESS read-write
               STATUS mandatory
               DESCRIPTION
               "Continuous time for this sensor to be in Low Critical before accepting new Status."
               ::= {  temperatureArraySensorEntry 16 }
               
            temperatureArraySensorDelayLowWarning OBJECT-TYPE
               SYNTAX INTEGER (0..65535)
               ACCESS read-write
               STATUS mandatory
               DESCRIPTION
               "Continuous time for this sensor to be in Low Warning before accepting new Status."
               ::= {  temperatureArraySensorEntry 17 }

            temperatureArraySensorDelayHighWarning OBJECT-TYPE
               SYNTAX INTEGER (0..65535)
               ACCESS read-write
               STATUS mandatory
               DESCRIPTION
               "Continuous time for this sensor to be in High Warning before accepting new Status."
               ::= {  temperatureArraySensorEntry 18 }

            temperatureArraySensorDelayHighCritical OBJECT-TYPE
               SYNTAX INTEGER (0..65535)
               ACCESS read-write
               STATUS mandatory
               DESCRIPTION
               "Continuous time for this sensor to be in High Critical before accepting new Status."
               ::= {  temperatureArraySensorEntry 19 }

            temperatureArraySensorRaw OBJECT-TYPE
               SYNTAX  INTEGER 
               ACCESS  read-only
               STATUS  mandatory
               DESCRIPTION
               "The raw degree data from the temperature sensor, slightly higher resolution"
               ::=  {  temperatureArraySensorEntry 20 }

            temperatureArraySensorOffset OBJECT-TYPE
               SYNTAX  INTEGER
               ACCESS  read-write
               STATUS  mandatory
               DESCRIPTION
               "Temperature Offset reading"
               ::=  {  temperatureArraySensorEntry 21 }

            temperatureArraySensorPort OBJECT-TYPE
               SYNTAX  INTEGER (0..65534)
               ACCESS  read-only
               STATUS  mandatory
               DESCRIPTION
               "Sensor port"
               ::=  {  temperatureArraySensorEntry 35 }

            temperatureArraySensorSubPort OBJECT-TYPE
               SYNTAX  INTEGER (0..65534)
               ACCESS  read-only
               STATUS  mandatory
               DESCRIPTION
               "Sensor sub port"
               ::=  {  temperatureArraySensorEntry 36 }

            temperatureArraySensorDeviceIndex OBJECT-TYPE
               SYNTAX  INTEGER (0..65534)
               ACCESS  read-only
               STATUS  mandatory
               DESCRIPTION
               "Device Index of sensor"
               ::=  {  temperatureArraySensorEntry 37 }
               
            temperatureArraySensorDisplayStyle OBJECT-TYPE
               SYNTAX  INTEGER {
                  basic(0),
                  gauge(1)
               }
               ACCESS  read-write
               STATUS  mandatory
               DESCRIPTION
               "Temperature display style"
               ::=  {  temperatureArraySensorEntry 45 }   

            temperatureArraySensorHighCriticalDesc OBJECT-TYPE
               SYNTAX  DisplayString
               ACCESS  read-write
               STATUS  mandatory
               DESCRIPTION
               "A HighCritical Description of this sensor"
               ::=  {  temperatureArraySensorEntry  46  }               

            temperatureArraySensorLowCriticalDesc OBJECT-TYPE
               SYNTAX  DisplayString
               ACCESS  read-write
               STATUS  mandatory
               DESCRIPTION
               "A LowCritical Description of this sensor"
               ::=  {  temperatureArraySensorEntry  47  }

            temperatureArraySensorNormalDesc OBJECT-TYPE
               SYNTAX  DisplayString
               ACCESS  read-write
               STATUS  mandatory
               DESCRIPTION
               "A Normal Description of this sensor"
               ::=  {  temperatureArraySensorEntry  48  }
               
            temperatureArraySensorLowWarningDesc OBJECT-TYPE
               SYNTAX  DisplayString
               ACCESS  read-write
               STATUS  mandatory
               DESCRIPTION
               "A LowWarning Description of this sensor"
               ::=  {  temperatureArraySensorEntry  49  }
               
            temperatureArraySensorHighWarningDesc OBJECT-TYPE
               SYNTAX  DisplayString
               ACCESS  read-write
               STATUS  mandatory
               DESCRIPTION
               "A HighWarning Description of this sensor"
               ::=  {  temperatureArraySensorEntry  50  }
               
            temperatureArraySensorSensorErrorDesc OBJECT-TYPE
               SYNTAX  DisplayString
               ACCESS  read-write
               STATUS  mandatory
               DESCRIPTION
               "A SensorError Description of this sensor"
               ::=  {  temperatureArraySensorEntry  51  }

            temperatureArraySensorHighCriticalColor OBJECT-TYPE
               SYNTAX  INTEGER
               ACCESS  read-write
               STATUS  mandatory
               DESCRIPTION
               "A HighCritical Color of this sensor"
               ::=  {  temperatureArraySensorEntry  54  }               

            temperatureArraySensorLowCriticalColor OBJECT-TYPE
               SYNTAX  INTEGER
               ACCESS  read-write
               STATUS  mandatory
               DESCRIPTION
               "A LowCritical Color of this sensor"
               ::=  {  temperatureArraySensorEntry  55  }

            temperatureArraySensorSensorNormalColor OBJECT-TYPE
               SYNTAX  INTEGER
               ACCESS  read-write
               STATUS  mandatory
               DESCRIPTION
               "A Normal Color of this sensor"
               ::=  {  temperatureArraySensorEntry  56  }
               
            temperatureArraySensorLowWarningColor OBJECT-TYPE
               SYNTAX  INTEGER
               ACCESS  read-write
               STATUS  mandatory
               DESCRIPTION
               "A LowWarning Color of this sensor"
               ::=  {  temperatureArraySensorEntry  57  }
               
            temperatureArraySensorHighWarningColor OBJECT-TYPE
               SYNTAX  INTEGER
               ACCESS  read-write
               STATUS  mandatory
               DESCRIPTION
               "A HighWarning Color of this sensor"
               ::=  {  temperatureArraySensorEntry  58  }
               
            temperatureArraySensorSensorErrorColor OBJECT-TYPE
               SYNTAX  INTEGER
               ACCESS  read-write
               STATUS  mandatory
               DESCRIPTION
               "A SensorError Color of this sensor"
               ::=  {  temperatureArraySensorEntry  59  }    
               
            temperatureArraySensorAcknowledge OBJECT-TYPE
               SYNTAX  INTEGER {
                  acked(2)
               }
               ACCESS  read-write
               STATUS  mandatory
               DESCRIPTION
               "Temperature sensor acknowledge"
               ::=  {  temperatureArraySensorEntry 70 } 
               
            temperatureArraySensorSerialNumber OBJECT-TYPE
               SYNTAX  DisplayString
               ACCESS  read-write
               STATUS  mandatory
               DESCRIPTION
               "Serial Number of Temperature Sensor
               x is Hex Digit xx-xx-xx-xx-xx-xx-xx-xx"
               ::=  {  temperatureArraySensorEntry 71 }
               
            temperatureArraySensorId OBJECT-TYPE
               SYNTAX  INTEGER
               ACCESS  read-only
               STATUS  mandatory
               DESCRIPTION
               "The Sensor ID of this sensor, used to identify which sensor it is in the system configuration."
               ::= { temperatureArraySensorEntry 1000 }

--/* End of temperatureArraySensorEntry */

--/* Begin of towerLEDTable */
         towerLEDTable OBJECT-TYPE
            SYNTAX  SEQUENCE OF TowerLEDEntry
            ACCESS  not-accessible
            STATUS  mandatory
            DESCRIPTION
            "This table contains the properties for each TowerLED sensor"
            ::= { sensors 29 }

         towerLEDEntry OBJECT-TYPE
            SYNTAX  TowerLEDEntry
            ACCESS  not-accessible
            STATUS  mandatory
            INDEX { towerLEDIndex }
            ::= { towerLEDTable 1 }

         TowerLEDEntry ::= SEQUENCE {
            towerLEDIndex
               DisplayString,
            towerLEDDescription
               DisplayString,
            towerLEDStatus
               INTEGER,
            towerLEDGoOffline
               INTEGER,
            towerLEDControlMode
               INTEGER,
            towerLEDGreenLEDControl
               INTEGER,
            towerLEDOrangeLEDControl
               INTEGER,
            towerLEDRedLEDControl
               INTEGER,
            towerLEDBuzzerEnable
               INTEGER,
            towerLEDPort
               INTEGER,
            towerLEDSubPort
               INTEGER,
            towerLEDId
               INTEGER
         }

         towerLEDIndex OBJECT-TYPE
            SYNTAX  DisplayString
            ACCESS  read-only
            STATUS  mandatory
            DESCRIPTION
            "The Sensor Compound ID of this sensor, used to identify which sensor it is in the system configuration."
            ::= { towerLEDEntry 1 }

         towerLEDDescription OBJECT-TYPE
            SYNTAX  DisplayString
            ACCESS  read-write
            STATUS  mandatory
            DESCRIPTION
            "The user specified description of this sensor. Unless specified, the default value is used."
            ::= { towerLEDEntry 2 }

         towerLEDStatus OBJECT-TYPE
            SYNTAX  INTEGER {
               noStatus(1),
               normal(2),
               sensorError(7)
            }
            ACCESS  read-only
            STATUS  mandatory
            DESCRIPTION
            "The current status of this sensor."
            ::= { towerLEDEntry 6 }

         towerLEDGoOffline OBJECT-TYPE
            SYNTAX  INTEGER {
               online(1),
               goOffline(2)
            }
            ACCESS  read-write
            STATUS  mandatory
            DESCRIPTION
            "Command to offline this sensor: use value '2' to set the sensor offline."
            ::= { towerLEDEntry 8 }

         towerLEDControlMode OBJECT-TYPE
            SYNTAX  INTEGER {
               standard(0),
               worst-status(1)
            }
            ACCESS  read-write
            STATUS  mandatory
            DESCRIPTION
            "The Control Mode for controlling towerLED sensor, it can be one of these: standard or worst-status"
            ::= { towerLEDEntry 72 }

         towerLEDGreenLEDControl OBJECT-TYPE
            SYNTAX  INTEGER {
               led-off(0),
               led-on(1),
               led-blink(2)
            }
            ACCESS  read-write
            STATUS  mandatory
            DESCRIPTION
            "LED control code to manage Green LED, it can be off, on or blink"
            ::= { towerLEDEntry 76 }

         towerLEDOrangeLEDControl OBJECT-TYPE
            SYNTAX  INTEGER {
               led-off(0),
               led-on(1),
               led-blink(2)
            }
            ACCESS  read-write
            STATUS  mandatory
            DESCRIPTION
            "LED control code to manage Orange LED, it can be off, on or blink"
            ::= { towerLEDEntry 75 }

         towerLEDRedLEDControl OBJECT-TYPE
            SYNTAX  INTEGER {
               led-off(0),
               led-on(1),
               led-blink(2)
            }
            ACCESS  read-write
            STATUS  mandatory
            DESCRIPTION
            "LED control code to manage Red LED, it can be off, on or blink"
            ::= { towerLEDEntry 74 }

         towerLEDBuzzerEnable OBJECT-TYPE
            SYNTAX  INTEGER {
               disabled(0),
               enabled(1)
            }
            ACCESS  read-write
            STATUS  mandatory
            DESCRIPTION
            "Enable internal TowerLED's buzzer"
            ::= { towerLEDEntry 73 }

         towerLEDPort OBJECT-TYPE
            SYNTAX  INTEGER
            ACCESS  read-only
            STATUS  mandatory
            DESCRIPTION
            "The device's sensor port number, where this sensor is plugged in to."
            ::= { towerLEDEntry 35 }

         towerLEDSubPort OBJECT-TYPE
            SYNTAX  INTEGER
            ACCESS  read-only
            STATUS  mandatory
            DESCRIPTION
            "The logical port number of this sensor in the array, or in a set of sensors."
            ::= { towerLEDEntry 36 }

         towerLEDId OBJECT-TYPE
            SYNTAX  INTEGER
            ACCESS  read-only
            STATUS  mandatory
            DESCRIPTION
            "The Sensor ID of this sensor, used to identify which sensor it is in the system configuration."
            ::= { towerLEDEntry 1000 }

--/* End of towerLEDTable */

--/* Begin of enumTable */
         enumTable OBJECT-TYPE
            SYNTAX  SEQUENCE OF EnumEntry
            ACCESS  not-accessible
            STATUS  mandatory
            DESCRIPTION
            "This table contains the properties for each Enum sensor"
            ::= { sensors 31 }

         enumEntry OBJECT-TYPE
            SYNTAX  EnumEntry
            ACCESS  not-accessible
            STATUS  mandatory
            INDEX { enumIndex }
            ::= { enumTable 1 }

         EnumEntry ::= SEQUENCE {
            enumIndex
               DisplayString,
            enumDescription
               DisplayString,
            enumStatus
               INTEGER,
            enumGoOffline
               INTEGER,
            enumPort
               INTEGER,
            enumSubPort
               INTEGER,
            enumSensorErrorDescription
               DisplayString,
            enumSensorErrorColor
               INTEGER,
            enumCustomStatusDescription0
               DisplayString,
            enumCustomStatusDescription1
               DisplayString,
            enumCustomStatusDescription2
               DisplayString,
            enumCustomStatusDescription3
               DisplayString,
            enumCustomStatusDescription4
               DisplayString,
            enumCustomStatusDescription5
               DisplayString,
            enumCustomStatusDescription6
               DisplayString,
            enumCustomStatusDescription7
               DisplayString,
            enumCustomStatusDescription8
               DisplayString,
            enumCustomStatusDescription9
               DisplayString,
            enumCustomStatusDescription10
               DisplayString,
            enumCustomStatusDescription11
               DisplayString,
            enumCustomStatusDescription12
               DisplayString,
            enumCustomStatusDescription13
               DisplayString,
            enumCustomStatusDescription14
               DisplayString,
            enumCustomStatusDescription15
               DisplayString,
            enumCustomStatusColor0
               INTEGER,
            enumCustomStatusColor1
               INTEGER,
            enumCustomStatusColor2
               INTEGER,
            enumCustomStatusColor3
               INTEGER,
            enumCustomStatusColor4
               INTEGER,
            enumCustomStatusColor5
               INTEGER,
            enumCustomStatusColor6
               INTEGER,
            enumCustomStatusColor7
               INTEGER,
            enumCustomStatusColor8
               INTEGER,
            enumCustomStatusColor9
               INTEGER,
            enumCustomStatusColor10
               INTEGER,
            enumCustomStatusColor11
               INTEGER,
            enumCustomStatusColor12
               INTEGER,
            enumCustomStatusColor13
               INTEGER,
            enumCustomStatusColor14
               INTEGER,
            enumCustomStatusColor15
               INTEGER,
            enumId
               INTEGER
         }

         enumIndex OBJECT-TYPE
            SYNTAX  DisplayString
            ACCESS  read-only
            STATUS  mandatory
            DESCRIPTION
            "The Sensor Compound ID of this sensor, used to identify which sensor it is in the system configuration."
            ::= { enumEntry 1 }

         enumDescription OBJECT-TYPE
            SYNTAX  DisplayString
            ACCESS  read-write
            STATUS  mandatory
            DESCRIPTION
            "The user specified description of this sensor. Unless specified, the default value is used."
            ::= { enumEntry 2 }

         enumStatus OBJECT-TYPE
            SYNTAX  INTEGER {
               noStatus(1),
               sensorError(7),
               customStatus0(16),
               customStatus1(17),
               customStatus2(18),
               customStatus3(19),
               customStatus4(20),
               customStatus5(21),
               customStatus6(22),
               customStatus7(23),
               customStatus8(24),
               customStatus9(25),
               customStatus10(26),
               customStatus11(27),
               customStatus12(28),
               customStatus13(29),
               customStatus14(30),
               customStatus15(31)
            }
            ACCESS  read-only
            STATUS  mandatory
            DESCRIPTION
            "The current status of this sensor."
            ::= { enumEntry 6 }

         enumGoOffline OBJECT-TYPE
            SYNTAX  INTEGER {
               online(1),
               goOffline(2)
            }
            ACCESS  read-write
            STATUS  mandatory
            DESCRIPTION
            "Command to offline this sensor: use value '2' to set the sensor offline."
            ::= { enumEntry 8 }

         enumPort OBJECT-TYPE
            SYNTAX  INTEGER
            ACCESS  read-only
            STATUS  mandatory
            DESCRIPTION
            "The device's sensor port number, where this sensor is plugged in to."
            ::= { enumEntry 35 }

         enumSubPort OBJECT-TYPE
            SYNTAX  INTEGER
            ACCESS  read-only
            STATUS  mandatory
            DESCRIPTION
            "The logical port number of this sensor in the array, or in a set of sensors."
            ::= { enumEntry 36 }

         enumSensorErrorDescription OBJECT-TYPE
            SYNTAX  DisplayString
            ACCESS  read-write
            STATUS  mandatory
            DESCRIPTION
            "The user specified 'Sensor Error' status description of this sensor. Unless specified, the default value is used."
            ::= { enumEntry 51 }

         enumSensorErrorColor OBJECT-TYPE
            SYNTAX  INTEGER
            ACCESS  read-write
            STATUS  mandatory
            DESCRIPTION
            "The user specified 'Sensor Error' status field color. The unit will show this color on its web interface and in DCIM. Unless specified, the default value is used."
            ::= { enumEntry 59 }

         enumCustomStatusDescription0 OBJECT-TYPE
            SYNTAX  DisplayString
            ACCESS  read-write
            STATUS  mandatory
            DESCRIPTION
            "The user specified custom status description of this sensor. Unless specified, the default value is used."
            ::= { enumEntry 120 }

         enumCustomStatusDescription1 OBJECT-TYPE
            SYNTAX  DisplayString
            ACCESS  read-write
            STATUS  mandatory
            DESCRIPTION
            "The user specified custom status description of this sensor. Unless specified, the default value is used."
            ::= { enumEntry 121 }

         enumCustomStatusDescription2 OBJECT-TYPE
            SYNTAX  DisplayString
            ACCESS  read-write
            STATUS  mandatory
            DESCRIPTION
            "The user specified custom status description of this sensor. Unless specified, the default value is used."
            ::= { enumEntry 122 }

         enumCustomStatusDescription3 OBJECT-TYPE
            SYNTAX  DisplayString
            ACCESS  read-write
            STATUS  mandatory
            DESCRIPTION
            "The user specified custom status description of this sensor. Unless specified, the default value is used."
            ::= { enumEntry 123 }

         enumCustomStatusDescription4 OBJECT-TYPE
            SYNTAX  DisplayString
            ACCESS  read-write
            STATUS  mandatory
            DESCRIPTION
            "The user specified custom status description of this sensor. Unless specified, the default value is used."
            ::= { enumEntry 124 }

         enumCustomStatusDescription5 OBJECT-TYPE
            SYNTAX  DisplayString
            ACCESS  read-write
            STATUS  mandatory
            DESCRIPTION
            "The user specified custom status description of this sensor. Unless specified, the default value is used."
            ::= { enumEntry 125 }

         enumCustomStatusDescription6 OBJECT-TYPE
            SYNTAX  DisplayString
            ACCESS  read-write
            STATUS  mandatory
            DESCRIPTION
            "The user specified custom status description of this sensor. Unless specified, the default value is used."
            ::= { enumEntry 126 }

         enumCustomStatusDescription7 OBJECT-TYPE
            SYNTAX  DisplayString
            ACCESS  read-write
            STATUS  mandatory
            DESCRIPTION
            "The user specified custom status description of this sensor. Unless specified, the default value is used."
            ::= { enumEntry 127 }

         enumCustomStatusDescription8 OBJECT-TYPE
            SYNTAX  DisplayString
            ACCESS  read-write
            STATUS  mandatory
            DESCRIPTION
            "The user specified custom status description of this sensor. Unless specified, the default value is used."
            ::= { enumEntry 128 }

         enumCustomStatusDescription9 OBJECT-TYPE
            SYNTAX  DisplayString
            ACCESS  read-write
            STATUS  mandatory
            DESCRIPTION
            "The user specified custom status description of this sensor. Unless specified, the default value is used."
            ::= { enumEntry 129 }

         enumCustomStatusDescription10 OBJECT-TYPE
            SYNTAX  DisplayString
            ACCESS  read-write
            STATUS  mandatory
            DESCRIPTION
            "The user specified custom status description of this sensor. Unless specified, the default value is used."
            ::= { enumEntry 130 }

         enumCustomStatusDescription11 OBJECT-TYPE
            SYNTAX  DisplayString
            ACCESS  read-write
            STATUS  mandatory
            DESCRIPTION
            "The user specified custom status description of this sensor. Unless specified, the default value is used."
            ::= { enumEntry 131 }

         enumCustomStatusDescription12 OBJECT-TYPE
            SYNTAX  DisplayString
            ACCESS  read-write
            STATUS  mandatory
            DESCRIPTION
            "The user specified custom status description of this sensor. Unless specified, the default value is used."
            ::= { enumEntry 132 }

         enumCustomStatusDescription13 OBJECT-TYPE
            SYNTAX  DisplayString
            ACCESS  read-write
            STATUS  mandatory
            DESCRIPTION
            "The user specified custom status description of this sensor. Unless specified, the default value is used."
            ::= { enumEntry 133 }

         enumCustomStatusDescription14 OBJECT-TYPE
            SYNTAX  DisplayString
            ACCESS  read-write
            STATUS  mandatory
            DESCRIPTION
            "The user specified custom status description of this sensor. Unless specified, the default value is used."
            ::= { enumEntry 134 }

         enumCustomStatusDescription15 OBJECT-TYPE
            SYNTAX  DisplayString
            ACCESS  read-write
            STATUS  mandatory
            DESCRIPTION
            "The user specified custom status description of this sensor. Unless specified, the default value is used."
            ::= { enumEntry 135 }

         enumCustomStatusColor0 OBJECT-TYPE
            SYNTAX  INTEGER
            ACCESS  read-write
            STATUS  mandatory
            DESCRIPTION
            "The user specified color for custom status. The unit will show this color on its web interface and in DCIM. Unless specified, the default value is used."
            ::= { enumEntry 140 }

         enumCustomStatusColor1 OBJECT-TYPE
            SYNTAX  INTEGER
            ACCESS  read-write
            STATUS  mandatory
            DESCRIPTION
            "The user specified color for custom status. The unit will show this color on its web interface and in DCIM. Unless specified, the default value is used."
            ::= { enumEntry 141 }

         enumCustomStatusColor2 OBJECT-TYPE
            SYNTAX  INTEGER
            ACCESS  read-write
            STATUS  mandatory
            DESCRIPTION
            "The user specified color for custom status. The unit will show this color on its web interface and in DCIM. Unless specified, the default value is used."
            ::= { enumEntry 142 }

         enumCustomStatusColor3 OBJECT-TYPE
            SYNTAX  INTEGER
            ACCESS  read-write
            STATUS  mandatory
            DESCRIPTION
            "The user specified color for custom status. The unit will show this color on its web interface and in DCIM. Unless specified, the default value is used."
            ::= { enumEntry 143 }

         enumCustomStatusColor4 OBJECT-TYPE
            SYNTAX  INTEGER
            ACCESS  read-write
            STATUS  mandatory
            DESCRIPTION
            "The user specified color for custom status. The unit will show this color on its web interface and in DCIM. Unless specified, the default value is used."
            ::= { enumEntry 144 }

         enumCustomStatusColor5 OBJECT-TYPE
            SYNTAX  INTEGER
            ACCESS  read-write
            STATUS  mandatory
            DESCRIPTION
            "The user specified color for custom status. The unit will show this color on its web interface and in DCIM. Unless specified, the default value is used."
            ::= { enumEntry 145 }

         enumCustomStatusColor6 OBJECT-TYPE
            SYNTAX  INTEGER
            ACCESS  read-write
            STATUS  mandatory
            DESCRIPTION
            "The user specified color for custom status. The unit will show this color on its web interface and in DCIM. Unless specified, the default value is used."
            ::= { enumEntry 146 }

         enumCustomStatusColor7 OBJECT-TYPE
            SYNTAX  INTEGER
            ACCESS  read-write
            STATUS  mandatory
            DESCRIPTION
            "The user specified color for custom status. The unit will show this color on its web interface and in DCIM. Unless specified, the default value is used."
            ::= { enumEntry 147 }

         enumCustomStatusColor8 OBJECT-TYPE
            SYNTAX  INTEGER
            ACCESS  read-write
            STATUS  mandatory
            DESCRIPTION
            "The user specified color for custom status. The unit will show this color on its web interface and in DCIM. Unless specified, the default value is used."
            ::= { enumEntry 148 }

         enumCustomStatusColor9 OBJECT-TYPE
            SYNTAX  INTEGER
            ACCESS  read-write
            STATUS  mandatory
            DESCRIPTION
            "The user specified color for custom status. The unit will show this color on its web interface and in DCIM. Unless specified, the default value is used."
            ::= { enumEntry 149 }

         enumCustomStatusColor10 OBJECT-TYPE
            SYNTAX  INTEGER
            ACCESS  read-write
            STATUS  mandatory
            DESCRIPTION
            "The user specified color for custom status. The unit will show this color on its web interface and in DCIM. Unless specified, the default value is used."
            ::= { enumEntry 150 }

         enumCustomStatusColor11 OBJECT-TYPE
            SYNTAX  INTEGER
            ACCESS  read-write
            STATUS  mandatory
            DESCRIPTION
            "The user specified color for custom status. The unit will show this color on its web interface and in DCIM. Unless specified, the default value is used."
            ::= { enumEntry 151 }

         enumCustomStatusColor12 OBJECT-TYPE
            SYNTAX  INTEGER
            ACCESS  read-write
            STATUS  mandatory
            DESCRIPTION
            "The user specified color for custom status. The unit will show this color on its web interface and in DCIM. Unless specified, the default value is used."
            ::= { enumEntry 152 }

         enumCustomStatusColor13 OBJECT-TYPE
            SYNTAX  INTEGER
            ACCESS  read-write
            STATUS  mandatory
            DESCRIPTION
            "The user specified color for custom status. The unit will show this color on its web interface and in DCIM. Unless specified, the default value is used."
            ::= { enumEntry 153 }

         enumCustomStatusColor14 OBJECT-TYPE
            SYNTAX  INTEGER
            ACCESS  read-write
            STATUS  mandatory
            DESCRIPTION
            "The user specified color for custom status. The unit will show this color on its web interface and in DCIM. Unless specified, the default value is used."
            ::= { enumEntry 154 }

         enumCustomStatusColor15 OBJECT-TYPE
            SYNTAX  INTEGER
            ACCESS  read-write
            STATUS  mandatory
            DESCRIPTION
            "The user specified color for custom status. The unit will show this color on its web interface and in DCIM. Unless specified, the default value is used."
            ::= { enumEntry 155 }

         enumId OBJECT-TYPE
            SYNTAX  INTEGER
            ACCESS  read-only
            STATUS  mandatory
            DESCRIPTION
            "The Sensor ID of this sensor, used to identify which sensor it is in the system configuration."
            ::= { enumEntry 1000 }

--/* End of enumTable */

--/* Begin of virtualAnalogSensorEntry */

         virtualSensor OBJECT IDENTIFIER ::= { sensorByPort 129 }

            virtualAnalogSensorTable OBJECT-TYPE
               SYNTAX  SEQUENCE OF VirtualAnalogSensorEntry
               ACCESS  not-accessible
               STATUS  mandatory
               DESCRIPTION
               "This table contains the data for every VirtualAnalog Sensor in the SensorArray. Each row in the table contains data for a different VirtualAnalog Sensor."
               ::=  {  virtualSensor 2  }

            virtualAnalogSensorEntry OBJECT-TYPE
               SYNTAX  VirtualAnalogSensorEntry
               ACCESS  not-accessible
               STATUS  mandatory
               DESCRIPTION
               "This is an entry in the virtualAnalogSensorEntry Table"
               INDEX         { virtualAnalogSensorIndex }
               ::=  { virtualAnalogSensorTable 1 }

            VirtualAnalogSensorEntry ::= SEQUENCE {
                  virtualAnalogSensorIndex
                     DisplayString,
                  virtualAnalogSensorDescription
                     DisplayString,
                  virtualAnalogSensorStatus
                     INTEGER,
                  virtualAnalogSensorOnline
                     INTEGER,
                  virtualAnalogSensorGoOnline
                     INTEGER,
                  virtualAnalogSensorHighWarning
                     INTEGER,
                  virtualAnalogSensorHighCritical
                     INTEGER,
                  virtualAnalogSensorLowWarning
                     INTEGER,
                  virtualAnalogSensorLowCritical
                     INTEGER,
                  virtualAnalogSensorRearm
                     INTEGER,
                  virtualAnalogSensorRaw
                     INTEGER,
                  virtualAnalogSensorEmailTrapLimit
                     INTEGER,
                  virtualAnalogSensorUnit
                     DisplayString,
                  virtualAnalogSensorAcknowledgement
                     INTEGER,
                  virtualAnalogSensorURL
                     DisplayString,
                  virtualAnalogSensorOpenURL
                     INTEGER,
                  virtualAnalogSensorContTimeHighCritical
                     INTEGER,
                  virtualAnalogSensorContTimeHighWarning
                     INTEGER,
                  virtualAnalogSensorContTimeNormal
                     INTEGER,
                  virtualAnalogSensorContTimeLowWarning
                     INTEGER,
                  virtualAnalogSensorContTimeLowCritical
                     INTEGER,
                  virtualAnalogSensorContTimeSensorError
                     INTEGER,
                  virtualAnalogSensorCalendar
                     INTEGER,
                  virtualAnalogSensorValueFactor
                     INTEGER,
                  virtualAnalogSensorId
                     INTEGER
            }

               virtualAnalogSensorIndex OBJECT-TYPE
                  SYNTAX  DisplayString
                  ACCESS  read-only
                  STATUS  mandatory
                  DESCRIPTION
                  "The Sensor Compound ID of this sensor, used to identify which sensor it is in the system configuration."
                  ::=  {  virtualAnalogSensorEntry 1   }

               virtualAnalogSensorDescription OBJECT-TYPE
                  SYNTAX  DisplayString
                  ACCESS  read-write
                  STATUS  mandatory
                  DESCRIPTION
                  "A Description of this sensor"
                  ::=  {  virtualAnalogSensorEntry 2   }

               virtualAnalogSensorStatus OBJECT-TYPE
                  SYNTAX  INTEGER {
                     noStatus(1),
                     normal(2),
                     highWarning(3),
                     highCritical(4),
                     lowWarning(5),
                     lowCritical(6),
                     sensorError(7)
                  }
                  ACCESS  read-only
                  STATUS  mandatory
                  DESCRIPTION
                  "The current status of this Sensor"
                  ::=  {  virtualAnalogSensorEntry 4   }

               virtualAnalogSensorOnline OBJECT-TYPE
                  SYNTAX  INTEGER {
                     online(1),
                     offline(2)
                  }
                  ACCESS  read-only
                  STATUS  mandatory
                  DESCRIPTION
                  "If this Sensor is currently online"
                     ::=  {  virtualAnalogSensorEntry 5   }

               virtualAnalogSensorGoOnline OBJECT-TYPE
                  SYNTAX  INTEGER {
                     goOnline(1),
                     goOffline(2)
                  }
                  ACCESS  read-write
                  STATUS  mandatory
                  DESCRIPTION
                  "To put online enter a 1, to take offline enter a 2"
                  ::=  {  virtualAnalogSensorEntry 6   }

               virtualAnalogSensorHighWarning OBJECT-TYPE
                  SYNTAX  INTEGER
                  ACCESS  read-write
                  STATUS  mandatory
                  DESCRIPTION
                  "How high the relative VirtualAnalog this sensor measures before it sends a warning"
                  ::=  {  virtualAnalogSensorEntry 7   }

               virtualAnalogSensorHighCritical OBJECT-TYPE
                  SYNTAX  INTEGER
                  ACCESS  read-write
                  STATUS  mandatory
                  DESCRIPTION
                  "How high the relative VirtualAnalog this sensor measures before it becomes critical"
                  ::=  {  virtualAnalogSensorEntry 8   }

               virtualAnalogSensorLowWarning OBJECT-TYPE
                  SYNTAX  INTEGER
                  ACCESS  read-write
                  STATUS  mandatory
                  DESCRIPTION
                  "How low the relative VirtualAnalog this sensor measures before it sends a warning"
                  ::=  {  virtualAnalogSensorEntry 9   }

               virtualAnalogSensorLowCritical OBJECT-TYPE
                  SYNTAX  INTEGER
                  ACCESS  read-write
                  STATUS  mandatory
                  DESCRIPTION
                  "How low the relative VirtualAnalog this sensor measures before it becomes critical"
                  ::=  {  virtualAnalogSensorEntry 10   }

               virtualAnalogSensorRearm OBJECT-TYPE
                  SYNTAX  INTEGER
                  ACCESS  read-write
                  STATUS  mandatory
                  DESCRIPTION
                  "The percent relative VirtualAnalog to rearm the status. For example if status goes from normal to warning, the VirtualAnalog must go down spAnalogueRearm below warning before the status goes to normal"
                  ::=  {  virtualAnalogSensorEntry 11   }

               virtualAnalogSensorRaw OBJECT-TYPE
                  SYNTAX  INTEGER 
                  ACCESS  read-only
                  STATUS  mandatory
                  DESCRIPTION
                  "The unformatted, raw, A/D value in this sensor. Contains more resolution than the formated percentage. This number can go from 0 to 1023 depending on the input voltage"
                  ::=  {  virtualAnalogSensorEntry 13   }

               virtualAnalogSensorEmailTrapLimit OBJECT-TYPE
                  SYNTAX  INTEGER {
                     disable(0),
                     enable(1)
                  }
                  ACCESS  read-write
                  STATUS  mandatory
                  DESCRIPTION
                  "Enable email/trap limit feature"
                  ::=  {  virtualAnalogSensorEntry 17   }

               virtualAnalogSensorUnit OBJECT-TYPE
                  SYNTAX  DisplayString
                  ACCESS  read-write
                  STATUS  mandatory
                  DESCRIPTION
                  "Display unit in VirtualAnalog."
                  ::=  {  virtualAnalogSensorEntry 27   }

               virtualAnalogSensorAcknowledgement OBJECT-TYPE
                  SYNTAX INTEGER {
                     ack(1)
                  }
                  ACCESS read-write
                  STATUS mandatory
                  DESCRIPTION
                  "Acknowledged sensor error and stop notification"
                  ::= {  virtualAnalogSensorEntry 41 }

               virtualAnalogSensorURL OBJECT-TYPE
                  SYNTAX DisplayString
                  ACCESS read-write
                  STATUS mandatory
                  DESCRIPTION
                  "Sensor URL link."
                  ::=  {  virtualAnalogSensorEntry 43   }

               virtualAnalogSensorOpenURL OBJECT-TYPE
                  SYNTAX INTEGER {
                     cur-window(0),
                     new-window(2)
                  }
                  ACCESS read-write
                  STATUS mandatory
                  DESCRIPTION
                  "Open URL in this browser or open in a new window."
                  ::=  {  virtualAnalogSensorEntry 44   }

               virtualAnalogSensorContTimeHighCritical OBJECT-TYPE
                  SYNTAX INTEGER (0..65535)
                  ACCESS read-write
                  STATUS mandatory
                  DESCRIPTION
                  "Continuous time for this sensor to be in High Critical before accepting new Status."
                  ::= {  virtualAnalogSensorEntry 45 }

               virtualAnalogSensorContTimeHighWarning OBJECT-TYPE
                  SYNTAX INTEGER (0..65535)
                  ACCESS read-write
                  STATUS mandatory
                  DESCRIPTION
                  "Continuous time for this sensor to be in High Warning before accepting new Status."
                  ::= {  virtualAnalogSensorEntry 46 }

               virtualAnalogSensorContTimeNormal OBJECT-TYPE
                  SYNTAX INTEGER (0..65535)
                  ACCESS read-write
                  STATUS mandatory
                  DESCRIPTION
                  "Continuous time for this sensor to be in Normal before accepting new Status."
                  ::= {  virtualAnalogSensorEntry 47 }

               virtualAnalogSensorContTimeLowWarning OBJECT-TYPE
                  SYNTAX INTEGER (0..65535)
                  ACCESS read-write
                  STATUS mandatory
                  DESCRIPTION
                  "Continuous time for this sensor to be in Low Warning before accepting new Status."
                  ::= {  virtualAnalogSensorEntry 48 }

               virtualAnalogSensorContTimeLowCritical OBJECT-TYPE
                  SYNTAX INTEGER (0..65535)
                  ACCESS read-write
                  STATUS mandatory
                  DESCRIPTION
                  "Continuous time for this sensor to be in Low Critical before accepting new Status."
                  ::= {  virtualAnalogSensorEntry 49 }

               virtualAnalogSensorContTimeSensorError OBJECT-TYPE
                  SYNTAX INTEGER (0..65535)
                  ACCESS read-write
                  STATUS mandatory
                  DESCRIPTION
                  "Continuous time for this sensor to be in Sensor Error before accepting new Status."
                  ::= {  virtualAnalogSensorEntry 50 }

               virtualAnalogSensorCalendar OBJECT-TYPE
                  SYNTAX INTEGER {
                     disable(0),
                     enable(1)
                  }
                  ACCESS read-write
                  STATUS mandatory
                  DESCRIPTION
                  "Enable or disable the calendar filtering working hours of sensor."
                  ::= {  virtualAnalogSensorEntry 51 }

               virtualAnalogSensorValueFactor OBJECT-TYPE
                  SYNTAX INTEGER {
                     x1(1),
                     x0-1(10),
                     x0-01(100),
                     x0-001(1000)
                  }
                  ACCESS read-write
                  STATUS mandatory
                  DESCRIPTION
                  "To change the ratio of value."
                  ::= {  virtualAnalogSensorEntry 52 }

               virtualAnalogSensorId OBJECT-TYPE
                  SYNTAX  INTEGER
                  ACCESS  read-only
                  STATUS  mandatory
                  DESCRIPTION
                  "The Sensor ID of this sensor, used to identify which sensor it is in the system configuration."
                  ::= { virtualAnalogSensorEntry 1000 }

--/* End of virtualAnalogSensorEntry */
--/* Begin of virtualSwitchrSensorEntry */

            virtualSwitchSensorTable OBJECT-TYPE
               SYNTAX  SEQUENCE OF VirtualSwitchSensorEntry
               ACCESS  not-accessible
               STATUS  mandatory
               DESCRIPTION
               "This table contains the data for every VirtualSwitch Sensor in the SensorArray. Each row in the table contains data for a different VirtualSwitch Sensor."
               ::=  {  virtualSensor 4  }

            virtualSwitchSensorEntry OBJECT-TYPE
               SYNTAX  VirtualSwitchSensorEntry
               ACCESS  not-accessible
               STATUS  mandatory
               DESCRIPTION
               "This is an entry in the virtualSwitchSensorEntry Table"
               INDEX         { virtualSwitchSensorIndex }
               ::=  { virtualSwitchSensorTable 1 }

            VirtualSwitchSensorEntry ::= SEQUENCE {
                  virtualSwitchSensorIndex
                     DisplayString,
                  virtualSwitchSensorDescription
                     DisplayString,
                  virtualSwitchSensorStatus
                     INTEGER,
                  virtualSwitchSensorOnline
                     INTEGER,
                  virtualSwitchSensorGoOnline
                     INTEGER,
                  virtualSwitchSensorEmailTrapLimit
                     INTEGER,
                  virtualSwitchSensorContTimeHighCritical
                     INTEGER,
                  virtualSwitchSensorContTimeNormal
                     INTEGER,                         
                  virtualSwitchSensorDescriptionCritical
                     DisplayString,
                  virtualSwitchSensorDescriptionNormal
                     DisplayString,                           
                  virtualSwitchSensorAcknowledgement
                     INTEGER,                             
                  virtualSwitchSensorURL
                     DisplayString,
                  virtualSwitchSensorOpenURL
                     INTEGER,
                  virtualSwitchSensorCalendar
                     INTEGER,
                  virtualSwitchSensorNormalState
                     INTEGER,
                  virtualSwitchSensorId
                     INTEGER
            }

               virtualSwitchSensorIndex OBJECT-TYPE
                  SYNTAX  DisplayString
                  ACCESS  read-only
                  STATUS  mandatory
                  DESCRIPTION
                  "The Sensor Compound ID of this sensor, used to identify which sensor it is in the system configuration."
                  ::=  {  virtualSwitchSensorEntry 1   }

               virtualSwitchSensorDescription OBJECT-TYPE
                  SYNTAX  DisplayString
                  ACCESS  read-write
                  STATUS  mandatory
                  DESCRIPTION
                  "A Description of this sensor"
                  ::=  {  virtualSwitchSensorEntry 2   }

               virtualSwitchSensorStatus OBJECT-TYPE
                  SYNTAX  INTEGER {
                     noStatus(1),
                     normal(2),
                     highWarning(3),
                     highCritical(4),
                     lowWarning(5),
                     lowCritical(6),
                     sensorError(7)
                  }
                  ACCESS  read-only
                  STATUS  mandatory
                  DESCRIPTION
                  "The current status of this Sensor"
                  ::=  {  virtualSwitchSensorEntry 4   }

               virtualSwitchSensorOnline OBJECT-TYPE
                  SYNTAX  INTEGER {
                     online(1),
                     offline(2)
                  }
                  ACCESS  read-only
                  STATUS  mandatory
                  DESCRIPTION
                  "If this Sensor is currently online"
                     ::=  {  virtualSwitchSensorEntry 5   }

               virtualSwitchSensorGoOnline OBJECT-TYPE
                  SYNTAX  INTEGER {
                     goOnline(1),
                     goOffline(2)
                  }
                  ACCESS  read-write
                  STATUS  mandatory
                  DESCRIPTION
                  "To put online enter a 1, to take offline enter a 2"
                  ::=  {  virtualSwitchSensorEntry 6   }

               virtualSwitchSensorEmailTrapLimit OBJECT-TYPE
                  SYNTAX  INTEGER {
                     disable(0),
                     enable(1)
                  }
                  ACCESS  read-write
                  STATUS  mandatory
                  DESCRIPTION
                  "Enable email/trap limit feature"
                  ::=  {  virtualSwitchSensorEntry 17   }

               virtualSwitchSensorContTimeHighCritical OBJECT-TYPE
                  SYNTAX  INTEGER (0..65534)
                  ACCESS  read-write
                  STATUS  mandatory
                  DESCRIPTION
                  "Continuous time for this sensor to be in High Critical before accepting new Status."
                  ::=  {  virtualSwitchSensorEntry 21   }

               virtualSwitchSensorContTimeNormal OBJECT-TYPE
                  SYNTAX INTEGER (0..65535)
                  ACCESS read-write
                  STATUS mandatory
                  DESCRIPTION
                  "Continuous time for this sensor to be in Normal before accepting new Status."
                  ::=  {  virtualSwitchSensorEntry 22   }

               virtualSwitchSensorDescriptionCritical OBJECT-TYPE
                  SYNTAX DisplayString
                  ACCESS read-write
                  STATUS mandatory
                  DESCRIPTION
                  "Description of status when the virsual switch is critical"
                  ::=  {  virtualSwitchSensorEntry 26   }

               virtualSwitchSensorDescriptionNormal OBJECT-TYPE
                  SYNTAX DisplayString
                  ACCESS read-write
                  STATUS mandatory
                  DESCRIPTION
                  "Description of status when the virsual switch is normal"
                  ::=  {  virtualSwitchSensorEntry 27   }

               virtualSwitchSensorAcknowledgement OBJECT-TYPE
                  SYNTAX INTEGER {
                     ack(1)
                  }
                  ACCESS read-write
                  STATUS mandatory
                  DESCRIPTION
                  "Acknowledged sensor error and stop notification"
                  ::= {  virtualSwitchSensorEntry 41 }

               virtualSwitchSensorURL OBJECT-TYPE
                  SYNTAX DisplayString
                  ACCESS read-write
                  STATUS mandatory
                  DESCRIPTION
                  "Sensor URL link."
                  ::=  {  virtualSwitchSensorEntry 43   }

               virtualSwitchSensorOpenURL OBJECT-TYPE
                  SYNTAX INTEGER {
                     cur-window(0),
                     new-window(2)
                  }
                  ACCESS read-write
                  STATUS mandatory
                  DESCRIPTION
                  "Open URL in this browser or open in a new window."
                  ::=  {  virtualSwitchSensorEntry 44   }

               virtualSwitchSensorCalendar OBJECT-TYPE
                  SYNTAX INTEGER {
                     disable(0),
                     enable(1)
                  }
                  ACCESS read-write
                  STATUS mandatory
                  DESCRIPTION
                  "Enable or disable the calendar filtering working hours of sensor."
                  ::= {  virtualSwitchSensorEntry 45 }

               virtualSwitchSensorNormalState OBJECT-TYPE
                  SYNTAX INTEGER
                  ACCESS read-write
                  STATUS mandatory
                  DESCRIPTION
                  "The normal state of a return of the virsual switch. If a return of the virsual switch is equal this normal state value, it is normal. Otherwise, it is critical."
                  ::= {  virtualSwitchSensorEntry 46 }

               virtualSwitchSensorId OBJECT-TYPE
                  SYNTAX  INTEGER
                  ACCESS  read-only
                  STATUS  mandatory
                  DESCRIPTION
                  "The Sensor ID of this sensor, used to identify which sensor it is in the system configuration."
                  ::= { virtualSwitchSensorEntry 1000 }

--/* End of virtualSwitchSensorEntry */

--
-- Varbinds used in TRAP Definitions
--

      sensorProbeTraps      OBJECT IDENTIFIER  ::=  {  sensorProbe 7   }

      spSensorStatus OBJECT-TYPE
            SYNTAX  INTEGER {
               noStatus(1),
               normal(2),
               highWarning(3),
               highCritical(4),
               lowWarning(5),
               lowCritical(6),
               sensorError(7),
               turnOn(8),
               turnOff(9)
            }
         ACCESS  read-only
         STATUS  mandatory
         DESCRIPTION
         "The current integer status of the sensor causing this trap to be sent"
         ::=  {  sensorProbeTraps 1  }
      
      spSensorValue OBJECT-TYPE
         SYNTAX  INTEGER
         ACCESS  read-only
         STATUS  mandatory
         DESCRIPTION
         "The current integer value of the sensor causing this trap to be sent"
         ::=  {  sensorProbeTraps 2  }
      
      spSensorLevelExceeded OBJECT-TYPE
         SYNTAX  INTEGER
         ACCESS  read-only
         STATUS  mandatory
         DESCRIPTION
         "The integer level that was exceeded causing this trap to be sent"
         ::=  {  sensorProbeTraps 3  }
      

      spSensorIndex OBJECT-TYPE
         SYNTAX  INTEGER
         ACCESS  read-only
         STATUS  mandatory
         DESCRIPTION
         "The integer index of the sensor causing this trap to be sent"
         ::=  {  sensorProbeTraps 4  }
      

      spSensorName OBJECT-TYPE
         SYNTAX  DisplayString
         ACCESS  read-only
         STATUS  mandatory
         DESCRIPTION
         "The name of the sensor causing this trap to be sent"
         ::=  {  sensorProbeTraps 5  }
      
      spSensorDescription OBJECT-TYPE
         SYNTAX  DisplayString
         ACCESS  read-only
         STATUS  mandatory
         DESCRIPTION
         "The description of the sensor causing this trap to be sent"
         ::=  {  sensorProbeTraps 6  }
      
      spSensorProbeKeepAlive OBJECT-TYPE
         SYNTAX  INTEGER
         ACCESS  read-only
         STATUS  mandatory
         DESCRIPTION
         "Keep alive trap to be sent"
         ::=  {  sensorProbeTraps 7  }
      
      spSensorType OBJECT-TYPE
         SYNTAX  INTEGER {
            temperature(1),
            humidity-dual(2),
            temperature-dual(3),
            four-20mA(4),
            dcvoltage(5),
            airflow(6),
            dry-inout(7),
            dry-in(8),
            motion(9),
            water(10),
            security(11),
            siren(12),
            relay(13),
            acvoltage(14),
            xrelay(19),
            thermocouple(20),
            smoke(21),
            drycontact-array(22),
            temperature-array(23),
            waterrope(24),
            fuellevel(25),
            tanksender(26),
            five-drycontacts(31),
            irms(34),
            vrms(35),
            watt(36),
            energy(37),
            powerfactor(38),
            reactive(39),
            cbstatus(40),
            handlelock(49),
            reader(50),
            air-pressure(51),
            ir-remote(52),
            digital-amp(53),
            digital-watt(54),
            valve-status(55),
            lcd(86),
            buzzer(87),
            tower-led(88),
            pulse-counter(89),
            flow(90),
            edge-counter(91),
            tanklevel-height(92),
            tanklevel-volume(93),
            diff-pressure(94),
            tanklevel-2m(95),
            tanklevel-5m(96),
            tanklevel-10m(97),
            tanklevel-15m(98),
            tanklevel-20m(99),
            ccmirms(118),
            thermostat(128),
            virtual(129),
            sound(130),
            software-motion(131),
            board-state(133),
            power-meter(134),
            access(137),
            door(138),
            fpreader(139)
         }
         ACCESS  read-only
         STATUS  mandatory
         DESCRIPTION
         "Type of this sensor"
         ::=  {  sensorProbeTraps 8  }
      
      spSensorStatusName OBJECT-TYPE
         SYNTAX  DisplayString
         ACCESS  read-only
         STATUS  mandatory
         DESCRIPTION
    "The current status of the sensor causing this trap to be sent"
         ::=  {  sensorProbeTraps 9  }
      
      spSensorSubIndex OBJECT-TYPE
         SYNTAX  INTEGER
         ACCESS  read-only
         STATUS  mandatory
         DESCRIPTION
    "The integer sub index of the sensor causing this trap to be sent. Only for temperaturearray and relayarray"
         ::=  {  sensorProbeTraps 10  }
      
      spBoardIndex OBJECT-TYPE
         SYNTAX  INTEGER
         ACCESS  read-only
         STATUS  mandatory
         DESCRIPTION
    "The integer index of the sensor board causing this trap to be sent."
         ::=  {  sensorProbeTraps 11  }

      spBoardDescription OBJECT-TYPE
         SYNTAX  DisplayString
         ACCESS  read-only
         STATUS  mandatory
         DESCRIPTION
    "The description of the sensor board causing this trap to be sent"
         ::=  {  sensorProbeTraps 12  }
      
      spEventTimeStamp OBJECT-TYPE
         SYNTAX  DisplayString
         ACCESS  read-only
         STATUS  mandatory
         DESCRIPTION
    "The time(MM/DD/YYYY HH:MM:SS) of an event causing this trap to be sent"
         ::=  {  sensorProbeTraps 13  }
   
      spEventClassNumber OBJECT-TYPE
         SYNTAX  INTEGER
         ACCESS  read-only
         STATUS  mandatory
         DESCRIPTION
    "The user-defined class number associated with this trap"
         ::=  {  sensorProbeTraps 14  }
   
      spEventClassName OBJECT-TYPE
         SYNTAX  DisplayString
         ACCESS  read-only
         STATUS  mandatory
         DESCRIPTION
    "The user-defined class Name associated with this trap"
         ::=  {  sensorProbeTraps 15  }
   
      spSensorDecimalValue OBJECT-TYPE
         SYNTAX  DisplayString
         ACCESS  read-only
         STATUS  mandatory
         DESCRIPTION
     "The current decimal value of the sensor causing this trap to be sent"
         ::=  {  sensorProbeTraps 16  }

      spSensorAliveHigh OBJECT-TYPE
         SYNTAX  INTEGER
         ACCESS  read-only
         STATUS  mandatory
         DESCRIPTION
         "The highest sensor value in the period"
         ::=  {  sensorProbeTraps 17  }

      spSensorAliveLow OBJECT-TYPE
         SYNTAX  INTEGER
         ACCESS  read-only
         STATUS  mandatory
         DESCRIPTION
         "The  lowset sensor value in the period"
         ::=  {  sensorProbeTraps 18  }

      spSensorSensorId OBJECT-TYPE
         SYNTAX  INTEGER
         ACCESS  read-only
         STATUS  mandatory
         DESCRIPTION
         "The sensor id of an event causing this trap to be sent"
         ::=  {  sensorProbeTraps 19  }

      spSensorAccessCardId OBJECT-TYPE
         SYNTAX  DisplayString
         ACCESS  read-only
         STATUS  mandatory
         DESCRIPTION
         "Access card id (this field will be 0 when it's not available)"
         ::=  {  sensorProbeTraps 20  }

      spSensorIndexSpp OBJECT-TYPE
         SYNTAX  DisplayString
         ACCESS  read-only
         STATUS  mandatory
         DESCRIPTION
         "Sensor Index String"
         ::=  {  sensorProbeTraps 21  }

      spPreviousSensorStatus OBJECT-TYPE
            SYNTAX  INTEGER {
               noStatus(1),
               normal(2),
               highWarning(3),
               highCritical(4),
               lowWarning(5),
               lowCritical(6),
               sensorError(7),
               turnOn(8),
               turnOff(9)
            }
         ACCESS  read-only
         STATUS  mandatory
         DESCRIPTION
         "The previous integer status of the sensor causing this trap to be sent"
         ::=  {  sensorProbeTraps 22  }
      
      spPreviousSensorStatusName OBJECT-TYPE
         SYNTAX  DisplayString
         ACCESS  read-only
         STATUS  mandatory
         DESCRIPTION
         "The previous status of the sensor causing this trap to be sent"
         ::=  {  sensorProbeTraps 23  }

   plusSeries OBJECT IDENTIFIER ::= { akcp 3 }

      summary       OBJECT IDENTIFIER ::= { plusSeries 1 }
      device        OBJECT IDENTIFIER ::= { plusSeries 2 }
      notifications OBJECT IDENTIFIER ::= { plusSeries 4 }
      sensors       OBJECT IDENTIFIER ::= { plusSeries 5 }
      virtual       OBJECT IDENTIFIER ::= { plusSeries 6 }

      config OBJECT IDENTIFIER ::= { device 1 }

         cfgServerAddress OBJECT-TYPE
            SYNTAX  IpAddress
            ACCESS  read-write
            STATUS  mandatory
            DESCRIPTION
            "The DCIM's IP Address that device is connected to."
            ::= { config 1 }

         cfgServerPort OBJECT-TYPE
            SYNTAX  INTEGER (0..65535)
            ACCESS  read-write
            STATUS  mandatory
            DESCRIPTION
            "The DCIM's Port that device is connected to. Default is 5000."
            ::= { config 2 }

         cfgDevicePassword OBJECT-TYPE
            SYNTAX  DisplayString
            ACCESS  write-only
            STATUS  mandatory
            DESCRIPTION
            "The local Administrator account's password for accessing the Web UI, Telnet and SSH services of the device. Default is 'public'."
            ::= { config 3 }

         cfgSystemDescription OBJECT-TYPE
            SYNTAX  DisplayString
            ACCESS  read-write
            STATUS  mandatory
            DESCRIPTION
            "The system's description of the device."
            ::= { config 8 }

         cfgSystemName OBJECT-TYPE
            SYNTAX  DisplayString
            ACCESS  read-write
            STATUS  mandatory
            DESCRIPTION
            "The system name for the device."
            ::= { config 9 }

         cfgSystemLocation OBJECT-TYPE
            SYNTAX  DisplayString
            ACCESS  read-write
            STATUS  mandatory
            DESCRIPTION
            "The system location for the device."
            ::= { config 10 }

         cfgSystemContact OBJECT-TYPE
            SYNTAX  DisplayString
            ACCESS  read-write
            STATUS  mandatory
            DESCRIPTION
            "The administrator contact for the system."
            ::= { config 11 }

         cfgIPAddress OBJECT-TYPE
            SYNTAX  IpAddress
            ACCESS  read-write
            STATUS  mandatory
            DESCRIPTION
            "The device's Ethernet IP Address."
            ::= { config 14 }

         cfgSubnetMask OBJECT-TYPE
            SYNTAX  IpAddress
            ACCESS  read-write
            STATUS  mandatory
            DESCRIPTION
            "The device's Ethernet Subnet Mask."
            ::= { config 15 }

         cfgDefaultGateway OBJECT-TYPE
            SYNTAX  IpAddress
            ACCESS  read-write
            STATUS  mandatory
            DESCRIPTION
            "The device's Ethernet Default Gateway."
            ::= { config 16 }

         cfgDefaultDNS OBJECT-TYPE
            SYNTAX  IpAddress
            ACCESS  read-write
            STATUS  mandatory
            DESCRIPTION
            "The device's Ethernet Default Domain Name System (DNS) for name resolution."
            ::= { config 17 }

         cfgDeviceUseDHCP OBJECT-TYPE
            SYNTAX  INTEGER {
               no(0),
               yes(1)
            }
            ACCESS  read-write
            STATUS  mandatory
            DESCRIPTION
            "Enable Ethernet Dynamic Host Configuration Protocol (DHCP) on the device; it will automatically provide IP Address for the device."
            ::= { config 18 }

         cfgNTPMode OBJECT-TYPE
            SYNTAX  INTEGER {
               do-not-use(0),
               one-time(1),
               on-system-start-up(2),
               once-a-month(3),
               once-a-week(4),
               once-a-day(5),
               once-a-hour(6),
               continuously(7)
            }
            ACCESS  read-write
            STATUS  mandatory
            DESCRIPTION
            "Network Time Protocol (NTP) Mode; this will define how often the device synchronizes time with the NTP Server."
            ::= { config 20 }

         cfgNTPServer1 OBJECT-TYPE
            SYNTAX  DisplayString
            ACCESS  read-write
            STATUS  mandatory
            DESCRIPTION
            "The first server that the device will synchronize time with, when NTP is enabled."
            ::= { config 21 }

         cfgNTPServer2 OBJECT-TYPE
            SYNTAX  DisplayString
            ACCESS  read-write
            STATUS  mandatory
            DESCRIPTION
            "The second server that the device will synchronize time with, when NTP is enabled."
            ::= { config 22 }

         cfgTimeZone OBJECT-TYPE
            SYNTAX  INTEGER (0..255)
            ACCESS  read-write
            STATUS  mandatory
            DESCRIPTION
            "The Time Zone of the device."
            ::= { config 23 }

         cfgGSMConnectionMethod OBJECT-TYPE
            SYNTAX  INTEGER {
               never-dial(0),
               dial-if-eth-failed(1),
               dial-only(2)
            }
            ACCESS  read-write
            STATUS  mandatory
            DESCRIPTION
            "The GSM Modem's Connection method. It will be defined when the device will be connecting via GSM's Modem."
            ::= { config 24 }

         cfgGSMConnectionType OBJECT-TYPE
            SYNTAX  INTEGER (0..255)
            ACCESS  read-write
            STATUS  mandatory
            DESCRIPTION
            "The GSM Modem's Connection type. It will be defined when the GSM Modem is always being used to connect, or depends on the Connection Method Setting."
            ::= { config 25 }

         cfgGSMInitString OBJECT-TYPE
            SYNTAX  DisplayString
            ACCESS  read-write
            STATUS  mandatory
            DESCRIPTION
            "The GSM Modem's Initialization String, a list of AT commands that will be sent when a connection to the modem is being established."
            ::= { config 26 }

         cfgGSMConnectionMode OBJECT-TYPE
            SYNTAX  INTEGER (0..255)
            ACCESS  read-write
            STATUS  mandatory
            DESCRIPTION
            "The GSM Modem's Connection Mode, it defines which GSM protocol will be used to transfer data."
            ::= { config 27 }

         cfgGSMAPN OBJECT-TYPE
            SYNTAX  DisplayString
            ACCESS  read-write
            STATUS  mandatory
            DESCRIPTION
            "Access Point Name (APN), the name of a gateway between a GSM, GPRS, 3G or 4G mobile network and another computer network, frequently the public Internet."
            ::= { config 28 }

         cfgGSMRetry OBJECT-TYPE
            SYNTAX  INTEGER (0..255)
            ACCESS  read-write
            STATUS  mandatory
            DESCRIPTION
            "The number of attempts that the GSM modem will use to redial if previous attempts have failed."
            ::= { config 29 }

         cfgGSMIdleTimeout OBJECT-TYPE
            SYNTAX  INTEGER (0..65535)
            ACCESS  read-write
            STATUS  mandatory
            DESCRIPTION
            "Time in seconds for the GSM modem to be idle before hanging up automatically."
            ::= { config 30 }

         cfgGSMLogin OBJECT-TYPE
            SYNTAX  DisplayString
            ACCESS  read-write
            STATUS  mandatory
            DESCRIPTION
            "GSM modem Point-to-Point Protocol (PPP)'s Login Name."
            ::= { config 31 }

         cfgGSMPassword OBJECT-TYPE
            SYNTAX  DisplayString
            ACCESS  write-only
            STATUS  mandatory
            DESCRIPTION
            "GSM Modem Point-to-Point Protocol (PPP)'s Password."
            ::= { config 32 }

         cfgGSMDNS OBJECT-TYPE
            SYNTAX  IpAddress
            ACCESS  read-write
            STATUS  mandatory
            DESCRIPTION
            "IP address for the Domain Name System (DNS) for GSM Modem Connection."
            ::= { config 33 }

         cfgWEBPasswordEnable OBJECT-TYPE
            SYNTAX  INTEGER {
               disable(0),
               enable(1)
            }
            ACCESS  read-write
            STATUS  mandatory
            DESCRIPTION
            "Enable/disable password checking for the Web UI."
            ::= { config 34 }

         cfgWEBPort OBJECT-TYPE
            SYNTAX  INTEGER (0..65535)
            ACCESS  read-write
            STATUS  mandatory
            DESCRIPTION
            "Web interface port (default value is 80)."
            ::= { config 35 }

         cfgWEBSecurePort OBJECT-TYPE
            SYNTAX  INTEGER (0..65535)
            ACCESS  read-write
            STATUS  mandatory
            DESCRIPTION
            "Secured Web interface port (default value is 443)."
            ::= { config 36 }

         cfgWEBSecureEnabled OBJECT-TYPE
            SYNTAX  INTEGER {
               disable(0),
               enable(1),
               useByDefault(2)
            }
            ACCESS  read-write
            STATUS  mandatory
            DESCRIPTION
            "Enable/disable Secured Web interface."
            ::= { config 37 }

         cfgWEBEnabled OBJECT-TYPE
            SYNTAX  INTEGER {
               disable(0),
               enable(1)
            }
            ACCESS  read-write
            STATUS  mandatory
            DESCRIPTION
            "Enable/disable Web interface."
            ::= { config 41 }

         cfgSNMPReadCommunity OBJECT-TYPE
            SYNTAX  DisplayString
            ACCESS  write-only
            STATUS  mandatory
            DESCRIPTION
            "SNMP read community, the community password for use with SNMP to read variables. Default is 'public'."
            ::= { config 42 }

         cfgSNMPWriteCommunity OBJECT-TYPE
            SYNTAX  DisplayString
            ACCESS  write-only
            STATUS  mandatory
            DESCRIPTION
            "SNMP write community, the community password for use with SNMP to write variables. Default is 'public'."
            ::= { config 43 }

         cfgSNMPv3Mode OBJECT-TYPE
            SYNTAX  INTEGER {
               authNoPriv(0),
               authPriv(1),
               noAuthNoPriv(2)
            }
            ACCESS  read-write
            STATUS  mandatory
            DESCRIPTION
            "Security Level for SNMPv3 to be used during communication."
            ::= { config 45 }

         cfgEMailEnable OBJECT-TYPE
            SYNTAX  INTEGER {
               disable(0),
               enable(1)
            }
            ACCESS  read-write
            STATUS  mandatory
            DESCRIPTION
            "Enable/disable the usage of the E-Mail feature on the device."
            ::= { config 47 }

         cfgSMTPServer OBJECT-TYPE
            SYNTAX  DisplayString
            ACCESS  read-write
            STATUS  mandatory
            DESCRIPTION
            "The name or IP address of the SMTP server, to be used for sending an E-Mail."
            ::= { config 48 }

         cfgSMTPPort OBJECT-TYPE
            SYNTAX  INTEGER (0..65535)
            ACCESS  read-write
            STATUS  mandatory
            DESCRIPTION
            "The port number for the SMTP connection. Default is 25."
            ::= { config 49 }

         cfgSMTPAuth OBJECT-TYPE
            SYNTAX  INTEGER {
               not-required(0),
               required(1)
            }
            ACCESS  read-write
            STATUS  mandatory
            DESCRIPTION
            "Enable/disable the SMTP authentication for the E-Mail service on the device."
            ::= { config 50 }

         cfgSMTPLogin OBJECT-TYPE
            SYNTAX  DisplayString
            ACCESS  read-write
            STATUS  mandatory
            DESCRIPTION
            "The user name for the SMTP server login."
            ::= { config 51 }

         cfgSMTPPassword OBJECT-TYPE
            SYNTAX  DisplayString
            ACCESS  write-only
            STATUS  mandatory
            DESCRIPTION
            "The user's password for the SMTP server login."
            ::= { config 52 }

         cfgEMailResendInterval OBJECT-TYPE
            SYNTAX  INTEGER
            ACCESS  read-write
            STATUS  mandatory
            ::= { config 55 }

         cfgEMailMaxResend OBJECT-TYPE
            SYNTAX  INTEGER
            ACCESS  read-write
            STATUS  mandatory
            ::= { config 56 }

         cfgKeepAliveTime OBJECT-TYPE
            SYNTAX  INTEGER
            ACCESS  read-write
            STATUS  mandatory
            DESCRIPTION
            "The DCIM's keep-alive time in seconds."
            ::= { config 78 }

         cfgHostID OBJECT-TYPE
            SYNTAX  INTEGER
            ACCESS  read-only
            STATUS  mandatory
            DESCRIPTION
            "Server host ID"
            ::= { config 79 }

         cfgHostUID OBJECT-TYPE
            SYNTAX  INTEGER
            ACCESS  read-only
            STATUS  mandatory
            DESCRIPTION
            "Server host update ID"
            ::= { config 80 }

         cfgHostSensorUID OBJECT-TYPE
            SYNTAX  INTEGER
            ACCESS  read-only
            STATUS  mandatory
            DESCRIPTION
            "Server host update ID for updating sensor and board properties"
            ::= { config 81 }

         cfgVPNServerPort OBJECT-TYPE
            SYNTAX  INTEGER (0..65535)
            ACCESS  read-write
            STATUS  mandatory
            DESCRIPTION
            "The VPN connection's port number on the DCIM. Default is 1194."
            ::= { config 83 }

         cfgVPNServerDNSName OBJECT-TYPE
            SYNTAX  DisplayString
            ACCESS  read-write
            STATUS  mandatory
            DESCRIPTION
            "The Domain Name System (DNS) name of the DCIM for the VPN connection."
            ::= { config 84 }

         cfgSMTPSSL OBJECT-TYPE
            SYNTAX  INTEGER {
               no-encryption(0),
               ssl-tls(1),
               starttls(2)
            }
            ACCESS  read-write
            STATUS  mandatory
            DESCRIPTION
            "The SMTP security level's protocol that will be used upon connection to an SMTP Server."
            ::= { config 87 }

         cfgVPNCipherType OBJECT-TYPE
            SYNTAX  INTEGER {
               none(0),
               blowfish(1),
               aes128(2),
               des-ede3(3)
            }
            ACCESS  read-write
            STATUS  mandatory
            DESCRIPTION
            "The VPN cipher protocol that will be used to communicate with the DCIM over the network."
            ::= { config 90 }

         cfgVPNPassword OBJECT-TYPE
            SYNTAX  DisplayString
            ACCESS  write-only
            STATUS  mandatory
            DESCRIPTION
            "The VPN Password for connecting to the DCIM's VPN server."
            ::= { config 91 }

         cfgVPNEnabled OBJECT-TYPE
            SYNTAX  INTEGER {
               no(0),
               yes(1)
            }
            ACCESS  read-write
            STATUS  mandatory
            DESCRIPTION
            "Enable/disable the VPN feature on the device. If enabled, the device will try to connect to the DCIM VPN server if the configuration is correct."
            ::= { config 92 }

         cfgSNMPPort OBJECT-TYPE
            SYNTAX  INTEGER (0..65535)
            ACCESS  read-write
            STATUS  mandatory
            DESCRIPTION
            "The port used for SNMP communication."
            ::= { config 93 }

         cfgSNMPv3EngineId OBJECT-TYPE
            SYNTAX  DisplayString
            ACCESS  read-write
            STATUS  mandatory
            DESCRIPTION
            "The Engine ID that will be used for connection with SNMPv3."
            ::= { config 94 }

         cfgSNMPv3UserName OBJECT-TYPE
            SYNTAX  DisplayString
            ACCESS  read-write
            STATUS  mandatory
            DESCRIPTION
            "The user name for connecting with SNMPv3 to this device."
            ::= { config 95 }

         cfgSNMPv3AuthProtocol OBJECT-TYPE
            SYNTAX  INTEGER {
               md5(0),
               sha1(1)
            }
            ACCESS  read-write
            STATUS  mandatory
            DESCRIPTION
            "The Authentication protocol that will be used with SNMPv3 connection (MD5 / SHA)."
            ::= { config 96 }

         cfgSNMPv3AuthPassword OBJECT-TYPE
            SYNTAX  Opaque
            ACCESS  write-only
            STATUS  mandatory
            DESCRIPTION
            "The SNMPv3 authentication password."
            ::= { config 97 }

         cfgSNMPv3PrivProtocol OBJECT-TYPE
            SYNTAX  INTEGER {
               des(0),
               aes(1)
            }
            ACCESS  read-write
            STATUS  mandatory
            DESCRIPTION
            "The SNMPv3 privacy protocol that will be used with SNMPv3 connection (DES / AES)."
            ::= { config 98 }

         cfgSNMPv3PrivPassword OBJECT-TYPE
            SYNTAX  Opaque
            ACCESS  write-only
            STATUS  mandatory
            DESCRIPTION
            "The SNMPv3 privacy password."
            ::= { config 99 }

         cfgSNMPv3AccessPrivelege OBJECT-TYPE
            SYNTAX  INTEGER {
               read-only(0),
               read-write(1)
            }
            ACCESS  read-write
            STATUS  mandatory
            DESCRIPTION
            "The access privilege of SNMPv3 (read only / read-write)."
            ::= { config 100 }

         cfgSNMPv1Disable OBJECT-TYPE
            SYNTAX  INTEGER {
               enable(0),
               disable(1)
            }
            ACCESS  read-write
            STATUS  mandatory
            DESCRIPTION
            "Disable SNMPv1 and SNMPv2c from being used."
            ::= { config 101 }

         cfgSNMPv3Disable OBJECT-TYPE
            SYNTAX  INTEGER {
               enable(0),
               disable(1)
            }
            ACCESS  read-write
            STATUS  mandatory
            DESCRIPTION
            "Disable SNMPv3 from being used."
            ::= { config 102 }

         cfgGraphDataCollectionPeriod OBJECT-TYPE
            SYNTAX  INTEGER (0..65535)
            ACCESS  read-write
            STATUS  mandatory
            DESCRIPTION
            "The graph data collection period in seconds. The more seconds you define, the more graph data can be stored."
            ::= { config 104 }

         cfgServiceTelnet OBJECT-TYPE
            SYNTAX  INTEGER {
               disable(0),
               enable(1)
            }
            ACCESS  read-write
            STATUS  mandatory
            DESCRIPTION
            "Enable/disable the Telnet service on the device."
            ::= { config 105 }

         cfgEnableNotiFilteringOnBoot OBJECT-TYPE
            SYNTAX  INTEGER {
               disable(0),
               enable(1)
            }
            ACCESS  read-write
            STATUS  mandatory
            DESCRIPTION
            "Enable/disable notifications filtering when the device is booting up. If enabled (set to nonzero) will trigger notification on device boot (initial sensor state change events). If disabled (set to zero) will filter notifications on software boot on initial sensor status change events. This is useful to avoid false notifications on initial sensor status change events."
            ::= { config 106 }

         cfgSystemURL OBJECT-TYPE
            SYNTAX  DisplayString
            ACCESS  read-write
            STATUS  mandatory
            DESCRIPTION
            "Custom URL what users can use in Email and SMS notifications to expand macro $[SYSURL]. It can point to a page on the device, or to any external URL."
            ::= { config 107 }

         cfgServerIntegrationEnabled OBJECT-TYPE
            SYNTAX  INTEGER {
               disabled(0),
               enabled(1)
            }
            ACCESS  read-write
            STATUS  mandatory
            DESCRIPTION
            "Enable/disable the DCIM Integration."
            ::= { config 108 }

         cfgServerIntegrationPort OBJECT-TYPE
            SYNTAX  INTEGER (0..65535)
            ACCESS  read-write
            STATUS  mandatory
            DESCRIPTION
            "Port for DCIM Integration."
            ::= { config 109 }

         cfgSMTPEMailFrom OBJECT-TYPE
            SYNTAX  DisplayString
            ACCESS  read-write
            STATUS  mandatory
            DESCRIPTION
            "The default E-mail address that will show in an E-mail's 'From' field and which will be used to send mail to support."
            ::= { config 110 }

         cfgSupportEMail OBJECT-TYPE
            SYNTAX  DisplayString
            ACCESS  read-write
            STATUS  mandatory
            DESCRIPTION
            "The E-mail address of the device's support department."
            ::= { config 111 }

         cfgDHCPHostName OBJECT-TYPE
            SYNTAX  DisplayString
            ACCESS  read-write
            STATUS  mandatory
            DESCRIPTION
            "DHCP hostname."
            ::= { config 137 }

         cfgLoginPageMessage OBJECT-TYPE
            SYNTAX  DisplayString
            ACCESS  read-write
            STATUS  mandatory
            DESCRIPTION
            "Customizable message on the login page."
            ::= { config 335 }

      licenses OBJECT IDENTIFIER ::= { device 2 }

--/* Begin of licenseTable */

         licenseTable OBJECT-TYPE
            SYNTAX  SEQUENCE OF LicenseEntry
            ACCESS  not-accessible
            STATUS  mandatory
            ::= { licenses 1 }

         licenseEntry OBJECT-TYPE
            SYNTAX  LicenseEntry
            ACCESS  not-accessible
            STATUS  mandatory
            INDEX { licenseIndex }
            ::= { licenseTable 1 }

         LicenseEntry ::= SEQUENCE {
            licenseIndex
               INTEGER,
            license5DC
               INTEGER,
            licenseSNMPv3
               INTEGER,
            licenseVPN
               INTEGER,
            licenseVSens
               INTEGER,
            licenseAccessUsers
               INTEGER,
            license3rdPartyPMS
               INTEGER,
            licenseIPv6
               INTEGER,
            licenseRadius
               INTEGER
         }

         licenseIndex OBJECT-TYPE
            SYNTAX  INTEGER (0..65535)
            ACCESS  read-only
            STATUS  mandatory
            ::= { licenseEntry 1 }

         license5DC OBJECT-TYPE
            SYNTAX  INTEGER
            ACCESS  read-only
            STATUS  mandatory
            ::= { licenseEntry 2 }

         licenseSNMPv3 OBJECT-TYPE
            SYNTAX  INTEGER {
               disallowed(0),
               allowed(1)
            }
            ACCESS  read-only
            STATUS  mandatory
            ::= { licenseEntry 4 }

         licenseVPN OBJECT-TYPE
            SYNTAX  INTEGER {
               disallowed(0),
               allowed(1)
            }
            ACCESS  read-only
            STATUS  mandatory
            ::= { licenseEntry 6 }

         licenseVSens OBJECT-TYPE
            SYNTAX  INTEGER
            ACCESS  read-only
            STATUS  mandatory
            ::= { licenseEntry 8 }

         licenseAccessUsers OBJECT-TYPE
            SYNTAX  INTEGER
            ACCESS  read-only
            STATUS  mandatory
            ::= { licenseEntry 10 }
            
         license3rdPartyPMS OBJECT-TYPE
            SYNTAX  INTEGER {
               disallowed(0),
               allowed(1)
            }
            ACCESS  read-only
            STATUS  mandatory
            ::= { licenseEntry 12 }

         licenseIPv6 OBJECT-TYPE
            SYNTAX  INTEGER {
               disallowed(0),
               allowed(1)
            }
            ACCESS  read-only
            STATUS  mandatory
            ::= { licenseEntry 13 }

         licenseRadius OBJECT-TYPE
            SYNTAX  INTEGER {
               disallowed(0),
               allowed(1)
            }
            ACCESS  read-only
            STATUS  mandatory
            ::= { licenseEntry 14 }

--/* End of licenseTable */

         lic5DCTotal OBJECT-TYPE
            SYNTAX  INTEGER
            ACCESS  read-only
            STATUS  mandatory
            ::= { licenses 2 }

         lic5DCUsed OBJECT-TYPE
            SYNTAX  INTEGER
            ACCESS  read-only
            STATUS  mandatory
            ::= { licenses 3 }

         licSNMPv3 OBJECT-TYPE
            SYNTAX  INTEGER {
               forbidden(0),
               allowed(1)
            }
            ACCESS  read-only
            STATUS  mandatory
            ::= { licenses 4 }

         licVPN OBJECT-TYPE
            SYNTAX  INTEGER {
               forbidden(0),
               allowed(1)
            }
            ACCESS  read-only
            STATUS  mandatory
            ::= { licenses 6 }

         licVSensTotal OBJECT-TYPE
            SYNTAX  INTEGER
            ACCESS  read-only
            STATUS  mandatory
            ::= { licenses 8 }

         licVSensUsed OBJECT-TYPE
            SYNTAX  INTEGER
            ACCESS  read-only
            STATUS  mandatory
            ::= { licenses 9 }

         licAccessUsersTotal OBJECT-TYPE
            SYNTAX  INTEGER
            ACCESS  read-only
            STATUS  mandatory
            ::= { licenses 10 }

         licAccessUsersUsed OBJECT-TYPE
            SYNTAX  INTEGER
            ACCESS  read-only
            STATUS  mandatory
            ::= { licenses 11 }
            
         lic3rdPartyPMS OBJECT-TYPE
            SYNTAX  INTEGER {
               forbidden(0),
               allowed(1)
            }
            ACCESS  read-only
            STATUS  mandatory
            ::= { licenses 12 }

         licIPv6 OBJECT-TYPE
            SYNTAX  INTEGER {
               forbidden(0),
               allowed(1)
            }
            ACCESS  read-only
            STATUS  mandatory
            ::= { licenses 13 }

         licRadius OBJECT-TYPE
            SYNTAX  INTEGER {
               forbidden(0),
               allowed(1)
            }
            ACCESS  read-only
            STATUS  mandatory
            ::= { licenses 14 }

         licAddKey OBJECT-TYPE
            SYNTAX  DisplayString
            ACCESS  write-only
            STATUS  mandatory
            ::= { licenses 1000 }

--/* Begin of commonTable */

         commonTable OBJECT-TYPE
            SYNTAX  SEQUENCE OF CommonEntry
            ACCESS  not-accessible
            STATUS  mandatory
            DESCRIPTION
            "This table contains the properties for each any sensor"
            ::= { sensors 1 }

         commonEntry OBJECT-TYPE
            SYNTAX  CommonEntry
            ACCESS  not-accessible
            STATUS  mandatory
            INDEX { commonIndex }
            ::= { commonTable 1 }

         CommonEntry ::= SEQUENCE {
            commonIndex
               DisplayString,
            commonDescription
               DisplayString,
            commonType
               INTEGER,
            commonValue
               INTEGER,
            commonUnit
               DisplayString,
            commonStatus
               INTEGER,
            commonGoOffline
               INTEGER,
            commonRaw
               INTEGER,
            commonPort
               INTEGER,
            commonSubPort
               INTEGER,
            commonDisplayStyle
               INTEGER,
            commonHighCriticalDescription
               DisplayString,
            commonLowCriticalDescription
               DisplayString,
            commonSensorNormalDescription
               DisplayString,
            commonLowWarningDescription
               DisplayString,
            commonHighWarningDescription
               DisplayString,
            commonSensorErrorDescription
               DisplayString,
            commonOnDescription
               DisplayString,
            commonOffDescription
               DisplayString,
            commonHighCriticalColor
               INTEGER,
            commonLowCriticalColor
               INTEGER,
            commonSensorNormalColor
               INTEGER,
            commonLowWarningColor
               INTEGER,
            commonHighWarningColor
               INTEGER,
            commonSensorErrorColor
               INTEGER,
            commonOnColor
               INTEGER,
            commonOffColor
               INTEGER,
            commonAcknowledge
               INTEGER,
            commonValueFormatFloat
               Opaque,
            commonId
               INTEGER,
            commonSensorValueBroadcastInterval
               INTEGER
         }

         commonIndex OBJECT-TYPE
            SYNTAX  DisplayString
            ACCESS  read-only
            STATUS  mandatory
            DESCRIPTION
            "The Sensor Compound ID of this sensor, used to identify which sensor it is in the system configuration."
            ::= { commonEntry 1 }

         commonDescription OBJECT-TYPE
            SYNTAX  DisplayString
            ACCESS  read-write
            STATUS  mandatory
            DESCRIPTION
            "The user specified description of this sensor. Unless specified, the default value is used."
            ::= { commonEntry 2 }

         commonType OBJECT-TYPE
            SYNTAX  INTEGER {
               temperature(1),
               humidity-dual(2),
               temperature-dual(3),
               four-20mA(4),
               dcvoltage(5),
               airflow(6),
               dry-inout(7),
               dry-in(8),
               motion(9),
               water(10),
               security(11),
               siren(12),
               relay(13),
               acvoltage(14),
               xrelay(19),
               thermocouple(20),
               smoke(21),
               drycontact-array(22),
               temperature-array(23),
               waterrope(24),
               fuellevel(25),
               tanksender(26),
               five-drycontacts(31),
               irms(34),
               vrms(35),
               watt(36),
               energy(37),
               powerfactor(38),
               reactive(39),
               cbstatus(40),
               handlelock(49),
               reader(50),
               air-pressure(51),
               ir-remote(52),
               digital-amp(53),
               digital-watt(54),
               valve-status(55),
               lcd(86),
               buzzer(87),
               tower-led(88),
               pulse-counter(89),
               flow(90),
               edge-counter(91),
               tanklevel-height(92),
               tanklevel-volume(93),
               diff-pressure(94),
               tanklevel-2m(95),
               tanklevel-5m(96),
               tanklevel-10m(97),
               tanklevel-15m(98),
               tanklevel-20m(99),
               ccmirms(118),
               thermostat(128),
               virtual(129),
               sound(130),
               software-motion(131),
               board-state(133),
               power-meter(134),
               access(137),
               door(138),
               fpreader(139)
            }
            ACCESS  read-only
            STATUS  mandatory
            DESCRIPTION
            "The type of the sensor; it represents the sensor's functionality."
            ::= { commonEntry 3 }

         commonValue OBJECT-TYPE
            SYNTAX  INTEGER
            ACCESS  read-only
            STATUS  mandatory
            DESCRIPTION
            "The value reading for this sensor; it's a different measure for each sensor type."
            ::= { commonEntry 4 }

         commonUnit OBJECT-TYPE
            SYNTAX  DisplayString
            ACCESS  read-only
            STATUS  mandatory
            DESCRIPTION
            "The sensor's value unit; it defines the sensor value's reading unit."
            ::= { commonEntry 5 }

         commonStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { commonEntry 6 }

         commonGoOffline OBJECT-TYPE
            SYNTAX  INTEGER {
               online(1),
               goOffline(2)
            }
            ACCESS  read-write
            STATUS  mandatory
            DESCRIPTION
            "Command to offline this sensor: use value '2' to set the sensor offline."
            ::= { commonEntry 8 }

         commonRaw OBJECT-TYPE
            SYNTAX  INTEGER
            ACCESS  read-only
            STATUS  mandatory
            DESCRIPTION
            "The sensor's unformatted (raw) value that is being read directly from sensor, before it is converted to the preferred value."
            ::= { commonEntry 20 }

         commonPort OBJECT-TYPE
            SYNTAX  INTEGER
            ACCESS  read-only
            STATUS  mandatory
            DESCRIPTION
            "The device's sensor port number, where this sensor is plugged in to."
            ::= { commonEntry 35 }

         commonSubPort OBJECT-TYPE
            SYNTAX  INTEGER
            ACCESS  read-only
            STATUS  mandatory
            DESCRIPTION
            "The logical port number of this sensor in the array, or in a set of sensors."
            ::= { commonEntry 36 }

         commonDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { commonEntry 45 }

         commonHighCriticalDescription OBJECT-TYPE
            SYNTAX  DisplayString
            ACCESS  read-write
            STATUS  mandatory
            DESCRIPTION
            "The user specified 'High Critical' status description of this sensor. Unless specified, the default value is used."
            ::= { commonEntry 46 }

         commonLowCriticalDescription OBJECT-TYPE
            SYNTAX  DisplayString
            ACCESS  read-write
            STATUS  mandatory
            DESCRIPTION
            "The user specified 'Low Critical' status description of this sensor. Unless specified, the default value is used."
            ::= { commonEntry 47 }

         commonSensorNormalDescription OBJECT-TYPE
            SYNTAX  DisplayString
            ACCESS  read-write
            STATUS  mandatory
            DESCRIPTION
            "The user specified 'Normal' status description of this sensor. Unless specified, the default value is used."
            ::= { commonEntry 48 }

         commonLowWarningDescription OBJECT-TYPE
            SYNTAX  DisplayString
            ACCESS  read-write
            STATUS  mandatory
            DESCRIPTION
            "The user specified 'Low Warning' status description of this sensor. Unless specified, the default value is used."
            ::= { commonEntry 49 }

         commonHighWarningDescription OBJECT-TYPE
            SYNTAX  DisplayString
            ACCESS  read-write
            STATUS  mandatory
            DESCRIPTION
            "The user specified 'High Warning' status description of this sensor. Unless specified, the default value is used."
            ::= { commonEntry 50 }

         commonSensorErrorDescription OBJECT-TYPE
            SYNTAX  DisplayString
            ACCESS  read-write
            STATUS  mandatory
            DESCRIPTION
            "The user specified 'Sensor Error' status description of this sensor. Unless specified, the default value is used."
            ::= { commonEntry 51 }

         commonOnDescription OBJECT-TYPE
            SYNTAX  DisplayString
            ACCESS  read-write
            STATUS  mandatory
            DESCRIPTION
            "The user specified 'On' status description of this sensor. Unless specified, the default value is used."
            ::= { commonEntry 52 }

         commonOffDescription OBJECT-TYPE
            SYNTAX  DisplayString
            ACCESS  read-write
            STATUS  mandatory
            DESCRIPTION
            "The user specified 'Off' Description of this sensor. Unless specified, the default value is used."
            ::= { commonEntry 53 }

         commonHighCriticalColor OBJECT-TYPE
            SYNTAX  INTEGER
            ACCESS  read-write
            STATUS  mandatory
            DESCRIPTION
            "The user specified 'High Critical' status field color. The unit will show this color on its web interface and in DCIM. Unless specified, the default value is used."
            ::= { commonEntry 54 }

         commonLowCriticalColor OBJECT-TYPE
            SYNTAX  INTEGER
            ACCESS  read-write
            STATUS  mandatory
            DESCRIPTION
            "The user specified 'Low Critical' status field color. The unit will show this color on its web interface and in DCIM. Unless specified, the default value is used."
            ::= { commonEntry 55 }

         commonSensorNormalColor OBJECT-TYPE
            SYNTAX  INTEGER
            ACCESS  read-write
            STATUS  mandatory
            DESCRIPTION
            "The user specified 'Normal' status field color. The unit will show this color on its web interface and in DCIM. Unless specified, the default value is used."
            ::= { commonEntry 56 }

         commonLowWarningColor OBJECT-TYPE
            SYNTAX  INTEGER
            ACCESS  read-write
            STATUS  mandatory
            DESCRIPTION
            "The user specified 'Low Warning' status field color. The unit will show this color on its web interface and in DCIM. Unless specified, the default value is used."
            ::= { commonEntry 57 }

         commonHighWarningColor OBJECT-TYPE
            SYNTAX  INTEGER
            ACCESS  read-write
            STATUS  mandatory
            DESCRIPTION
            "The user specified 'High Warning' status field color. The unit will show this color on its web interface and in DCIM. Unless specified, the default value is used."
            ::= { commonEntry 58 }

         commonSensorErrorColor OBJECT-TYPE
            SYNTAX  INTEGER
            ACCESS  read-write
            STATUS  mandatory
            DESCRIPTION
            "The user specified 'Sensor Error' status field color. The unit will show this color on its web interface and in DCIM. Unless specified, the default value is used."
            ::= { commonEntry 59 }

         commonOnColor OBJECT-TYPE
            SYNTAX  INTEGER
            ACCESS  read-write
            STATUS  mandatory
            DESCRIPTION
            "The user specified 'On' status field color. The unit will show this color on its web interface and in DCIM. Unless specified, the default value is used."
            ::= { commonEntry 60 }

         commonOffColor OBJECT-TYPE
            SYNTAX  INTEGER
            ACCESS  read-write
            STATUS  mandatory
            DESCRIPTION
            "The user specified 'Off' status field color. The unit will show this color on its web interface and in DCIM. Unless specified, the default value is used."
            ::= { commonEntry 61 }

         commonAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { commonEntry 70 }

         commonValueFormatFloat OBJECT-TYPE
            SYNTAX  Opaque (SIZE(4))
            ACCESS  read-only
            STATUS  mandatory
            DESCRIPTION
            "The floating-point IEEE 754 Standard reading value for this sensor (in commonValue float form instead of integer)."
            ::= { commonEntry 99 }

         commonId OBJECT-TYPE
            SYNTAX  INTEGER
            ACCESS  read-only
            STATUS  mandatory
            DESCRIPTION
            "The Sensor ID of this sensor, used to identify which sensor it is in the system configuration."
            ::= { commonEntry 1000 }

         commonSensorValueBroadcastInterval OBJECT-TYPE
            SYNTAX  INTEGER
            ACCESS  read-write
            STATUS  mandatory
            DESCRIPTION
            "The Sensor value broadcast inteval in seconds."
            ::= { commonEntry 1002 }

--/* End of commonTable */

--/* Begin of temperatureTable */

         temperatureTable OBJECT-TYPE
            SYNTAX  SEQUENCE OF TemperatureEntry
            ACCESS  not-accessible
            STATUS  mandatory
            DESCRIPTION
            "This table contains the properties for each temperature sensor"
            ::= { sensors 2 }

         temperatureEntry OBJECT-TYPE
            SYNTAX  TemperatureEntry
            ACCESS  not-accessible
            STATUS  mandatory
            INDEX { temperatureIndex }
            ::= { temperatureTable 1 }

         TemperatureEntry ::= SEQUENCE {
            temperatureIndex
               DisplayString,
            temperatureDescription
               DisplayString,
            temperatureType
               INTEGER,
            temperatureDegree
               INTEGER,
            temperatureUnit
               DisplayString,
            temperatureStatus
               INTEGER,
            temperatureGoOffline
               INTEGER,
            temperatureLowCritical
               INTEGER,
            temperatureLowWarning
               INTEGER,
            temperatureHighWarning
               INTEGER,
            temperatureHighCritical
               INTEGER,
            temperatureRearm
               INTEGER,
            temperatureDelayError
               INTEGER,
            temperatureDelayNormal
               INTEGER,
            temperatureDelayLowCritical
               INTEGER,
            temperatureDelayLowWarning
               INTEGER,
            temperatureDelayHighWarning
               INTEGER,
            temperatureDelayHighCritical
               INTEGER,
            temperatureRaw
               INTEGER,
            temperatureOffset
               INTEGER,
            temperaturePort
               INTEGER,
            temperatureSubPort
               INTEGER,
            temperatureDisplayStyle
               INTEGER,
            temperatureHighCriticalDescription
               DisplayString,
            temperatureLowCriticalDescription
               DisplayString,
            temperatureSensorNormalDescription
               DisplayString,
            temperatureLowWarningDescription
               DisplayString,
            temperatureHighWarningDescription
               DisplayString,
            temperatureSensorErrorDescription
               DisplayString,
            temperatureHighCriticalColor
               INTEGER,
            temperatureLowCriticalColor
               INTEGER,
            temperatureSensorNormalColor
               INTEGER,
            temperatureLowWarningColor
               INTEGER,
            temperatureHighWarningColor
               INTEGER,
            temperatureSensorErrorColor
               INTEGER,
            temperatureAcknowledge
               INTEGER,
            temperatureSerialNumber
               DisplayString,
            temperatureId
               INTEGER
         }

         temperatureIndex OBJECT-TYPE
            SYNTAX  DisplayString
            ACCESS  read-only
            STATUS  mandatory
            DESCRIPTION
            "The Sensor Compound ID of this sensor, used to identify which sensor it is in the system configuration."
            ::= { temperatureEntry 1 }

         temperatureDescription OBJECT-TYPE
            SYNTAX  DisplayString
            ACCESS  read-write
            STATUS  mandatory
            DESCRIPTION
            "The user specified description of this sensor. Unless specified, the default value is used."
            ::= { temperatureEntry 2 }

         temperatureType OBJECT-TYPE
            SYNTAX  INTEGER {
               temperature(1),
               temperature-dual(3),
               thermocouple(20),
               temperature-array(23)
            }
            ACCESS  read-only
            STATUS  mandatory
            DESCRIPTION
            "The type of the sensor; it represents the sensor's functionality. For the temperature sensor, it has 3 sub-types: Normal temperature sensor, Dual sensor, and Thermocouple sensor."
            ::= { temperatureEntry 3 }

         temperatureDegree OBJECT-TYPE
            SYNTAX  INTEGER
            ACCESS  read-only
            STATUS  mandatory
            DESCRIPTION
            "The temperature degree value in numerical reading."
            ::= { temperatureEntry 4 }

         temperatureUnit OBJECT-TYPE
            SYNTAX  DisplayString
            ACCESS  read-write
            STATUS  mandatory
            DESCRIPTION
            "The sensor's value unit string, in what the sensor's value is read in. For the temperature sensor it can be Celsius or Fahrenheit."
            ::= { temperatureEntry 5 }

         temperatureStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { temperatureEntry 6 }

         temperatureGoOffline OBJECT-TYPE
            SYNTAX  INTEGER {
               online(1),
               goOffline(2)
            }
            ACCESS  read-write
            STATUS  mandatory
            DESCRIPTION
            "Command to offline this sensor: use value '2' to set the sensor offline."
            ::= { temperatureEntry 8 }

         temperatureLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { temperatureEntry 9 }

         temperatureLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { temperatureEntry 10 }

         temperatureHighWarning OBJECT-TYPE
            SYNTAX  INTEGER
            ACCESS  read-write
            STATUS  mandatory
            DESCRIPTION
            "The user specified 'High Warning' value of this sensor. The unit will check the current reading against this value, and send an alert if it's configured. Unless specified, the default value is used."
            ::= { temperatureEntry 11 }

         temperatureHighCritical OBJECT-TYPE
            SYNTAX  INTEGER
            ACCESS  read-write
            STATUS  mandatory
            DESCRIPTION
            "The user specified 'High Critical' value of this sensor. The unit will check the current reading against this value, and send an alert if it's configured. Unless specified, the default value is used."
            ::= { temperatureEntry 12 }

         temperatureRearm OBJECT-TYPE
            SYNTAX  INTEGER
            ACCESS  read-write
            STATUS  mandatory
            DESCRIPTION
            "This value tells how many degrees the sensor has to reach beyond the threshold value, before changing to a new status. Useful to prevent the quick fluctuation of readings."
            ::= { temperatureEntry 13 }

         temperatureDelayError OBJECT-TYPE
            SYNTAX  INTEGER
            ACCESS  read-write
            STATUS  mandatory
            DESCRIPTION
            "The time in seconds (continuous time) that the sensor has to be in 'Error' status before its status is changed."
            ::= { temperatureEntry 14 }

         temperatureDelayNormal OBJECT-TYPE
            SYNTAX  INTEGER
            ACCESS  read-write
            STATUS  mandatory
            DESCRIPTION
            "The time in seconds (continuous time) that the sensor has to be in 'Normal' status before its status is changed."
            ::= { temperatureEntry 15 }

         temperatureDelayLowCritical OBJECT-TYPE
            SYNTAX  INTEGER
            ACCESS  read-write
            STATUS  mandatory
            DESCRIPTION
            "The time in seconds (continuous time) that the sensor has to be in 'Low Critical' status before its status is changed."
            ::= { temperatureEntry 16 }

         temperatureDelayLowWarning OBJECT-TYPE
            SYNTAX  INTEGER
            ACCESS  read-write
            STATUS  mandatory
            DESCRIPTION
            "The time in seconds (continuous time) that the sensor has to be in 'Low Warning' status before its status is changed."
            ::= { temperatureEntry 17 }

         temperatureDelayHighWarning OBJECT-TYPE
            SYNTAX  INTEGER
            ACCESS  read-write
            STATUS  mandatory
            DESCRIPTION
            "The time in seconds (continuous time) that the sensor has to be in 'High Warning' status before its status is changed."
            ::= { temperatureEntry 18 }

         temperatureDelayHighCritical OBJECT-TYPE
            SYNTAX  INTEGER
            ACCESS  read-write
            STATUS  mandatory
            DESCRIPTION
            "The time in seconds (continuous time) that the sensor has to be in 'High Critical' status before its status is changed."
            ::= { temperatureEntry 19 }

         temperatureRaw OBJECT-TYPE
            SYNTAX  INTEGER
            ACCESS  read-only
            STATUS  mandatory
            DESCRIPTION
            "The sensor's unformatted (raw) value that is being read directly from sensor, before it is converted to the preferred value."
            ::= { temperatureEntry 20 }

         temperatureOffset OBJECT-TYPE
            SYNTAX  INTEGER
            ACCESS  read-write
            STATUS  mandatory
            DESCRIPTION
            "The offset value for this sensor. It's used to adjust the reading value in case the reading is incorrect."
            ::= { temperatureEntry 21 }

         temperaturePort OBJECT-TYPE
            SYNTAX  INTEGER
            ACCESS  read-only
            STATUS  mandatory
            DESCRIPTION
            "The device's sensor port number, where this sensor is plugged in to."
            ::= { temperatureEntry 35 }

         temperatureSubPort OBJECT-TYPE
            SYNTAX  INTEGER
            ACCESS  read-only
            STATUS  mandatory
            DESCRIPTION
            "The logical port number of this sensor in the array, or in a set of sensors. For Temperature Sensor, it's for the array of Temperature Sensors and Dual Sensors.  For example x.1, x.2, x.3 ..."
            ::= { temperatureEntry 36 }

         temperatureDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { temperatureEntry 45 }

         temperatureHighCriticalDescription OBJECT-TYPE
            SYNTAX  DisplayString
            ACCESS  read-write
            STATUS  mandatory
            DESCRIPTION
            "The user specified 'High Critical' status description of this sensor. Unless specified, the default value is used."
            ::= { temperatureEntry 46 }

         temperatureLowCriticalDescription OBJECT-TYPE
            SYNTAX  DisplayString
            ACCESS  read-write
            STATUS  mandatory
            DESCRIPTION
            "The user specified 'Low Critical' status description of this sensor. Unless specified, the default value is used."
            ::= { temperatureEntry 47 }

         temperatureSensorNormalDescription OBJECT-TYPE
            SYNTAX  DisplayString
            ACCESS  read-write
            STATUS  mandatory
            DESCRIPTION
            "The user specified 'Normal' status description of this sensor. Unless specified, the default value is used."
            ::= { temperatureEntry 48 }

         temperatureLowWarningDescription OBJECT-TYPE
            SYNTAX  DisplayString
            ACCESS  read-write
            STATUS  mandatory
            DESCRIPTION
            "The user specified 'Low Warning' status description of this sensor. Unless specified, the default value is used."
            ::= { temperatureEntry 49 }

         temperatureHighWarningDescription OBJECT-TYPE
            SYNTAX  DisplayString
            ACCESS  read-write
            STATUS  mandatory
            DESCRIPTION
            "The user specified 'High Warning' status description of this sensor. Unless specified, the default value is used."
            ::= { temperatureEntry 50 }

         temperatureSensorErrorDescription OBJECT-TYPE
            SYNTAX  DisplayString
            ACCESS  read-write
            STATUS  mandatory
            DESCRIPTION
            "The user specified 'Sensor Error' status description of this sensor. Unless specified, the default value is used."
            ::= { temperatureEntry 51 }

         temperatureHighCriticalColor OBJECT-TYPE
            SYNTAX  INTEGER
            ACCESS  read-write
            STATUS  mandatory
            DESCRIPTION
            "The user specified 'High Critical' status field color. The unit will show this color on its web interface and in DCIM. Unless specified, the default value is used."
            ::= { temperatureEntry 54 }

         temperatureLowCriticalColor OBJECT-TYPE
            SYNTAX  INTEGER
            ACCESS  read-write
            STATUS  mandatory
            DESCRIPTION
            "The user specified 'Low Critical' status field color. The unit will show this color on its web interface and in DCIM. Unless specified, the default value is used."
            ::= { temperatureEntry 55 }

         temperatureSensorNormalColor OBJECT-TYPE
            SYNTAX  INTEGER
            ACCESS  read-write
            STATUS  mandatory
            DESCRIPTION
            "The user specified 'Normal' status field color. The unit will show this color on its web interface and in DCIM. Unless specified, the default value is used."
            ::= { temperatureEntry 56 }

         temperatureLowWarningColor OBJECT-TYPE
            SYNTAX  INTEGER
            ACCESS  read-write
            STATUS  mandatory
            DESCRIPTION
            "The user specified 'Low Warning' status field color. The unit will show this color on its web interface and in DCIM. Unless specified, the default value is used."
            ::= { temperatureEntry 57 }

         temperatureHighWarningColor OBJECT-TYPE
            SYNTAX  INTEGER
            ACCESS  read-write
            STATUS  mandatory
            DESCRIPTION
            "The user specified 'High Warning' status field color. The unit will show this color on its web interface and in DCIM. Unless specified, the default value is used."
            ::= { temperatureEntry 58 }

         temperatureSensorErrorColor OBJECT-TYPE
            SYNTAX  INTEGER
            ACCESS  read-write
            STATUS  mandatory
            DESCRIPTION
            "The user specified 'Sensor Error' status field color. The unit will show this color on its web interface and in DCIM. Unless specified, the default value is used."
            ::= { temperatureEntry 59 }

         temperatureAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { temperatureEntry 70 }

         temperatureSerialNumber OBJECT-TYPE
            SYNTAX  DisplayString
            ACCESS  read-write
            STATUS  mandatory
            DESCRIPTION
            "The serial number of temperature sensor, used to indicate which sensor it is in an array. It matches the MAC ID of the sensor for a DCT sensor array."
            ::= { temperatureEntry 71 }

         temperatureId OBJECT-TYPE
            SYNTAX  INTEGER
            ACCESS  read-only
            STATUS  mandatory
            DESCRIPTION
            "The Sensor ID of this sensor, used to identify which sensor it is in the system configuration."
            ::= { temperatureEntry 1000 }

--/* End of temperatureTable */

--/* Begin of humidityTable */

         humidityTable OBJECT-TYPE
            SYNTAX  SEQUENCE OF HumidityEntry
            ACCESS  not-accessible
            STATUS  mandatory
            DESCRIPTION
            "This table contains the properties for each humidity sensor"
            ::= { sensors 3 }

         humidityEntry OBJECT-TYPE
            SYNTAX  HumidityEntry
            ACCESS  not-accessible
            STATUS  mandatory
            INDEX { humidityIndex }
            ::= { humidityTable 1 }

         HumidityEntry ::= SEQUENCE {
            humidityIndex
               DisplayString,
            humidityDescription
               DisplayString,
            humidityPercent
               INTEGER,
            humidityUnit
               DisplayString,
            humidityStatus
               INTEGER,
            humidityGoOffline
               INTEGER,
            humidityLowCritical
               INTEGER,
            humidityLowWarning
               INTEGER,
            humidityHighWarning
               INTEGER,
            humidityHighCritical
               INTEGER,
            humidityRearm
               INTEGER,
            humidityDelayError
               INTEGER,
            humidityDelayNormal
               INTEGER,
            humidityDelayLowCritical
               INTEGER,
            humidityDelayLowWarning
               INTEGER,
            humidityDelayHighWarning
               INTEGER,
            humidityDelayHighCritical
               INTEGER,
            humidityRaw
               INTEGER,
            humidityOffset
               INTEGER,
            humidityPort
               INTEGER,
            humiditySubPort
               INTEGER,
            humidityDisplayStyle
               INTEGER,
            humidityHighCriticalDescription
               DisplayString,
            humidityLowCriticalDescription
               DisplayString,
            humiditySensorNormalDescription
               DisplayString,
            humidityLowWarningDescription
               DisplayString,
            humidityHighWarningDescription
               DisplayString,
            humiditySensorErrorDescription
               DisplayString,
            humidityHighCriticalColor
               INTEGER,
            humidityLowCriticalColor
               INTEGER,
            humiditySensorNormalColor
               INTEGER,
            humidityLowWarningColor
               INTEGER,
            humidityHighWarningColor
               INTEGER,
            humiditySensorErrorColor
               INTEGER,
            humidityAcknowledge
               INTEGER,
            humidityId
               INTEGER
         }

         humidityIndex OBJECT-TYPE
            SYNTAX  DisplayString
            ACCESS  read-only
            STATUS  mandatory
            DESCRIPTION
            "The Sensor Compound ID of this sensor, used to identify which sensor it is in the system configuration."
            ::= { humidityEntry 1 }

         humidityDescription OBJECT-TYPE
            SYNTAX  DisplayString
            ACCESS  read-write
            STATUS  mandatory
            DESCRIPTION
            "The user specified description of this sensor. Unless specified, the default value is used."
            ::= { humidityEntry 2 }

         humidityPercent OBJECT-TYPE
            SYNTAX  INTEGER
            ACCESS  read-only
            STATUS  mandatory
            DESCRIPTION
            "The relative humidity percentage measured by this sensor"
            ::= { humidityEntry 4 }

         humidityUnit OBJECT-TYPE
            SYNTAX  DisplayString
            ACCESS  read-only
            STATUS  mandatory
            DESCRIPTION
            "The sensor's value unit string, in what the sensor's value is read in."
            ::= { humidityEntry 5 }

         humidityStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { humidityEntry 6 }

         humidityGoOffline OBJECT-TYPE
            SYNTAX  INTEGER {
               online(1),
               goOffline(2)
            }
            ACCESS  read-write
            STATUS  mandatory
            DESCRIPTION
            "Command to offline this sensor: use value '2' to set the sensor offline."
            ::=  { humidityEntry 8 }

         humidityLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { humidityEntry 9 }

         humidityLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { humidityEntry 10 }

         humidityHighWarning OBJECT-TYPE
            SYNTAX  INTEGER
            ACCESS  read-write
            STATUS  mandatory
            DESCRIPTION
            "The user specified 'High Warning' value of this sensor. The unit will check the current reading against this value, and send an alert if it's configured. Unless specified, the default value is used."
            ::= { humidityEntry 11 }

         humidityHighCritical OBJECT-TYPE
            SYNTAX  INTEGER
            ACCESS  read-write
            STATUS  mandatory
            DESCRIPTION
            "The user specified 'High Critical' value of this sensor. The unit will check the current reading against this value, and send an alert if it's configured. Unless specified, the default value is used."
            ::= { humidityEntry 12 }

         humidityRearm OBJECT-TYPE
            SYNTAX  INTEGER
            ACCESS  read-write
            STATUS  mandatory
            DESCRIPTION
            "This value tells how many percentage the sensor has to reach beyond the threshold value, before changing to a new status. Useful to prevent the quick fluctuation of readings."
            ::= { humidityEntry 13 }

         humidityDelayError OBJECT-TYPE
            SYNTAX  INTEGER
            ACCESS  read-write
            STATUS  mandatory
            DESCRIPTION
            "The time in seconds (continuous time) that the sensor has to be in 'Error' status before its status is changed."
            ::= { humidityEntry 14 }

         humidityDelayNormal OBJECT-TYPE
            SYNTAX  INTEGER
            ACCESS  read-write
            STATUS  mandatory
            DESCRIPTION
            "The time in seconds (continuous time) that the sensor has to be in 'Normal' status before its status is changed."
            ::= { humidityEntry 15 }

         humidityDelayLowCritical OBJECT-TYPE
            SYNTAX INTEGER
            ACCESS read-write
            STATUS mandatory
            DESCRIPTION
            "The time in seconds (continuous time) that the sensor has to be in 'Low Critical' status before its status is changed."
            ::= { humidityEntry 16 }

         humidityDelayLowWarning OBJECT-TYPE
            SYNTAX INTEGER
            ACCESS read-write
            STATUS mandatory
            DESCRIPTION
            "The time in seconds (continuous time) that the sensor has to be in 'Low Warning' status before its status is changed."
            ::= { humidityEntry 17 }

         humidityDelayHighWarning OBJECT-TYPE
            SYNTAX INTEGER
            ACCESS read-write
            STATUS mandatory
            DESCRIPTION
            "The time in seconds (continuous time) that the sensor has to be in 'High Warning' status before its status is changed."
            ::= { humidityEntry 18 }

         humidityDelayHighCritical OBJECT-TYPE
            SYNTAX INTEGER
            ACCESS read-write
            STATUS mandatory
            DESCRIPTION
            "The time in seconds (continuous time) that the sensor has to be in 'High Critical' status before its status is changed."
            ::= { humidityEntry 19 }

         humidityRaw OBJECT-TYPE
            SYNTAX  INTEGER
            ACCESS  read-only
            STATUS  mandatory
            DESCRIPTION
            "The sensor's unformatted (raw) value that is being read directly from sensor, before it is converted to the preferred value."
            ::= { humidityEntry 20 }

         humidityOffset OBJECT-TYPE
            SYNTAX  INTEGER
            ACCESS  read-write
            STATUS  mandatory
            DESCRIPTION
            "The offset value for this sensor. It's used to adjust the reading value in case the reading is incorrect."
            ::= { humidityEntry 21 }

         humidityPort OBJECT-TYPE
            SYNTAX  INTEGER
            ACCESS  read-only
            STATUS  mandatory
            DESCRIPTION
            "The device's sensor port number, where this sensor is plugged in to."
            ::= { humidityEntry 35 }

         humiditySubPort OBJECT-TYPE
            SYNTAX  INTEGER
            ACCESS  read-only
            STATUS  mandatory
            DESCRIPTION
            "The logical port number of this sensor in the array, or in a set of sensors. For Humidity Sensor, it's for the Dual Sensors."
            ::= { humidityEntry 36 }

         humidityDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { humidityEntry 45 }

         humidityHighCriticalDescription OBJECT-TYPE
            SYNTAX  DisplayString
            ACCESS  read-write
            STATUS  mandatory
            DESCRIPTION
            "The user specified 'High Critical' status description of this sensor. Unless specified, the default value is used."
            ::= { humidityEntry 46 }

         humidityLowCriticalDescription OBJECT-TYPE
            SYNTAX  DisplayString
            ACCESS  read-write
            STATUS  mandatory
            DESCRIPTION
            "The user specified 'Low Critical' status description of this sensor. Unless specified, the default value is used."
            ::= { humidityEntry 47 }

         humiditySensorNormalDescription OBJECT-TYPE
            SYNTAX  DisplayString
            ACCESS  read-write
            STATUS  mandatory
            DESCRIPTION
            "The user specified 'Normal' status description of this sensor. Unless specified, the default value is used."
            ::= { humidityEntry 48 }

         humidityLowWarningDescription OBJECT-TYPE
            SYNTAX  DisplayString
            ACCESS  read-write
            STATUS  mandatory
            DESCRIPTION
            "The user specified 'Low Warning' status description of this sensor. Unless specified, the default value is used."
            ::= { humidityEntry 49 }

         humidityHighWarningDescription OBJECT-TYPE
            SYNTAX  DisplayString
            ACCESS  read-write
            STATUS  mandatory
            DESCRIPTION
            "The user specified 'High Warning' status description of this sensor. Unless specified, the default value is used."
            ::= { humidityEntry 50 }

         humiditySensorErrorDescription OBJECT-TYPE
            SYNTAX  DisplayString
            ACCESS  read-write
            STATUS  mandatory
            DESCRIPTION
            "The user specified 'Sensor Error' status description of this sensor. Unless specified, the default value is used."
            ::= { humidityEntry 51 }

         humidityHighCriticalColor OBJECT-TYPE
            SYNTAX  INTEGER
            ACCESS  read-write
            STATUS  mandatory
            DESCRIPTION
            "The user specified 'High Critical' status field color. The unit will show this color on its web interface and in DCIM. Unless specified, the default value is used."
            ::= { humidityEntry 54 }

         humidityLowCriticalColor OBJECT-TYPE
            SYNTAX  INTEGER
            ACCESS  read-write
            STATUS  mandatory
            DESCRIPTION
            "The user specified 'Low Critical' status field color. The unit will show this color on its web interface and in DCIM. Unless specified, the default value is used."
            ::= { humidityEntry 55 }

         humiditySensorNormalColor OBJECT-TYPE
            SYNTAX  INTEGER
            ACCESS  read-write
            STATUS  mandatory
            DESCRIPTION
            "The user specified 'Normal' status field color. The unit will show this color on its web interface and in DCIM. Unless specified, the default value is used."
            ::= { humidityEntry 56 }

         humidityLowWarningColor OBJECT-TYPE
            SYNTAX  INTEGER
            ACCESS  read-write
            STATUS  mandatory
            DESCRIPTION
            "The user specified 'Low Warning' status field color. The unit will show this color on its web interface and in DCIM. Unless specified, the default value is used."
            ::= { humidityEntry 57 }

         humidityHighWarningColor OBJECT-TYPE
            SYNTAX  INTEGER
            ACCESS  read-write
            STATUS  mandatory
            DESCRIPTION
            "The user specified 'High Warning' status field color. The unit will show this color on its web interface and in DCIM. Unless specified, the default value is used."
            ::= { humidityEntry 58 }

         humiditySensorErrorColor OBJECT-TYPE
            SYNTAX  INTEGER
            ACCESS  read-write
            STATUS  mandatory
            DESCRIPTION
            "The user specified 'Sensor Error' status field color. The unit will show this color on its web interface and in DCIM. Unless specified, the default value is used."
            ::= { humidityEntry 59 }

         humidityAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { humidityEntry 70 }

         humidityId OBJECT-TYPE
            SYNTAX  INTEGER
            ACCESS  read-only
            STATUS  mandatory
            DESCRIPTION
            "The Sensor ID of this sensor, used to identify which sensor it is in the system configuration."
            ::= { humidityEntry 1000 }

--/* End of humidityTable */

--/* Begin of drycontactTable */
         drycontactTable OBJECT-TYPE
            SYNTAX  SEQUENCE OF DrycontactEntry
            ACCESS  not-accessible
            STATUS  mandatory
            DESCRIPTION
            "This table contains the properties for each drycontact sensor"
            ::= { sensors 4 }

         drycontactEntry OBJECT-TYPE
            SYNTAX  DrycontactEntry
            ACCESS  not-accessible
            STATUS  mandatory
            INDEX { drycontactIndex }
            ::= { drycontactTable 1 }

         DrycontactEntry ::= SEQUENCE {
            drycontactIndex
               DisplayString,
            drycontactDescription
               DisplayString,
            drycontactType
               INTEGER,
            drycontactStatus
               INTEGER,
            drycontactGoOffline
               INTEGER,
            drycontactDirection
               INTEGER,
            drycontactNormalState
               INTEGER,
            drycontactControlMode
               INTEGER,
            drycontactOutputManualCycleTime
               INTEGER,
            drycontactOutputManualAction
               INTEGER,
            drycontactPort
               INTEGER,
            drycontactSubPort
               INTEGER,
            drycontactCriticalDescription
               DisplayString,
            drycontactNormalDescription
               DisplayString,
            drycontactOnDescription
               DisplayString,
            drycontactOffDescription
               DisplayString,
            drycontactCriticalColor 
               INTEGER,
            drycontactNormalColor 
               INTEGER,
            drycontactOnColor
               INTEGER,
            drycontactOffColor
               INTEGER,
            drycontactAcknowledge
               INTEGER,
            drycontactId
               INTEGER
         }

         drycontactIndex OBJECT-TYPE
            SYNTAX  DisplayString
            ACCESS  read-only
            STATUS  mandatory
            DESCRIPTION
            "The Sensor Compound ID of this sensor, used to identify which sensor it is in the system configuration."
            ::= { drycontactEntry 1 }

         drycontactDescription OBJECT-TYPE
            SYNTAX  DisplayString
            ACCESS  read-write
            STATUS  mandatory
            DESCRIPTION
            "The user specified description of this sensor. Unless specified, the default value is used."
            ::= { drycontactEntry 2 }

         drycontactType OBJECT-TYPE
            SYNTAX  INTEGER {
               drycontact-inout(7),
               drycontact-input(8),
               drycontact-array(22)
            }
            ACCESS  read-only
            STATUS  mandatory
            DESCRIPTION
            "The type of the sensor; it represents the sensor's functionality. For the drycontact sensor, it has 3 sub-types: drycontact-input, drycontact-output and drycontact-array."
            ::= { drycontactEntry 3 }

         drycontactStatus OBJECT-TYPE
            SYNTAX  INTEGER {
               noStatus(1),
               normal(2),
               highCritical(4),
               lowCritical(6),
               sensorError(7),
               outputLow(8),
               outputHigh(9)
            }
            ACCESS  read-only
            STATUS  mandatory
            DESCRIPTION
            "The current status of this sensor."
            ::= { drycontactEntry 6 }

         drycontactGoOffline OBJECT-TYPE
            SYNTAX  INTEGER {
               online(1),
               goOffline(2)
            }
            ACCESS  read-write
            STATUS  mandatory
            DESCRIPTION
            "Command to offline this sensor: use value '2' to set the sensor offline."
            ::= { drycontactEntry 8 }

         drycontactDirection OBJECT-TYPE
            SYNTAX  INTEGER {
               input(0),
               output(1)
            }
            ACCESS  read-write
            STATUS  mandatory
            DESCRIPTION
            "The functional direction of this drycontact sensors: use value '0' for input drycontact and '1' for output drycontact"
            ::= { drycontactEntry 22 }

         drycontactNormalState OBJECT-TYPE
            SYNTAX  INTEGER {
               closed(0),
               open(1)
            }
            ACCESS  read-write
            STATUS  mandatory
            DESCRIPTION
            "The normal state of the input drycontact. If an input switch is in this state it is normal, else it is critical. An open drycontact senses +5 volts. A closed drycontact senses 0 volts."
            ::= { drycontactEntry 23 }

         drycontactControlMode OBJECT-TYPE
            SYNTAX  INTEGER {
               manual-control(0),
               sensor-control(1),
               time-control(2),
               thermostat-control(3)
            }
            ACCESS  read-write
            STATUS  mandatory
            DESCRIPTION
            "The Control Mode for controlling this drycontact sensor with, it can be one of these: Manual, Notification, Time, Thermostat."
            ::= { drycontactEntry 24 }

         drycontactOutputManualCycleTime OBJECT-TYPE
            SYNTAX  INTEGER
            ACCESS  read-write
            STATUS  mandatory
            DESCRIPTION
            "The time in seconds that the drycontact will stay in a state, before changing to the next state in case the cycle action have been used."
            ::= { drycontactEntry 25 }

         drycontactOutputManualAction OBJECT-TYPE
            SYNTAX  INTEGER {
               low(0),
               high(1),
               cycle-Low-High-Low(2),
               cycle-High-Low-High(3)
            }
            ACCESS  read-write
            STATUS  mandatory
            DESCRIPTION
            "The manual output control for the drycontact state: Low, High, Toggle Low-High, Toggle High-Low."
            ::= { drycontactEntry 26 }

         drycontactPort OBJECT-TYPE
            SYNTAX  INTEGER
            ACCESS  read-only
            STATUS  mandatory
            DESCRIPTION
            "The device's sensor port number, where this sensor is plugged in to."
            ::= { drycontactEntry 35 }

         drycontactSubPort OBJECT-TYPE
            SYNTAX  INTEGER
            ACCESS  read-only
            STATUS  mandatory
            DESCRIPTION
            "The logical port number of this sensor in the array, or in a set of sensors."
            ::= { drycontactEntry 36 }

         drycontactCriticalDescription OBJECT-TYPE
            SYNTAX  DisplayString
            ACCESS  read-write
            STATUS  mandatory
            DESCRIPTION
            "The user specified 'Critical' status description of this sensor. Unless specified, the default value is used."
            ::= { drycontactEntry 46 }

         drycontactNormalDescription OBJECT-TYPE
            SYNTAX  DisplayString
            ACCESS  read-write
            STATUS  mandatory
            DESCRIPTION
            "The user specified 'Normal' status description of this sensor. Unless specified, the default value is used."
            ::= { drycontactEntry 48 }

         drycontactOnDescription OBJECT-TYPE
            SYNTAX  DisplayString
            ACCESS  read-write
            STATUS  mandatory
            DESCRIPTION
            "The user specified 'On' status description of this sensor. Unless specified, the default value is used."
            ::= { drycontactEntry 52 }

         drycontactOffDescription OBJECT-TYPE
            SYNTAX  DisplayString
            ACCESS  read-write
            STATUS  mandatory
            DESCRIPTION
            "The user specified 'Off' status description of this sensor. Unless specified, the default value is used."
            ::= { drycontactEntry 53 }

         drycontactCriticalColor OBJECT-TYPE
            SYNTAX  INTEGER
            ACCESS  read-write
            STATUS  mandatory
            DESCRIPTION
            "The user specified 'Critical' status field color. The unit will show this color on its web interface and in DCIM. Unless specified, the default value is used."
            ::= { drycontactEntry 54 }

         drycontactNormalColor OBJECT-TYPE
            SYNTAX  INTEGER
            ACCESS  read-write
            STATUS  mandatory
            DESCRIPTION
            "The user specified 'Normal' status field color. The unit will show this color on its web interface and in DCIM. Unless specified, the default value is used."
            ::= { drycontactEntry 56 }

         drycontactOnColor OBJECT-TYPE
            SYNTAX  INTEGER
            ACCESS  read-write
            STATUS  mandatory
            DESCRIPTION
            "The user specified 'On' status field color. The unit will show this color on its web interface and in DCIM. Unless specified, the default value is used."
            ::= { drycontactEntry 60 }

         drycontactOffColor OBJECT-TYPE
            SYNTAX  INTEGER
            ACCESS  read-write
            STATUS  mandatory
            DESCRIPTION
            "The user specified 'Off' status field color. The unit will show this color on its web interface and in DCIM. Unless specified, the default value is used."
            ::= { drycontactEntry 61 }

         drycontactAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { drycontactEntry 70 }

         drycontactId OBJECT-TYPE
            SYNTAX  INTEGER
            ACCESS  read-only
            STATUS  mandatory
            DESCRIPTION
            "The Sensor ID of this sensor, used to identify which sensor it is in the system configuration."
            ::= { drycontactEntry 1000 }

--/* End of drycontactTable */

--/* Begin of current4to20mATable */
         current4to20mATable OBJECT-TYPE
            SYNTAX  SEQUENCE OF Current4to20mAEntry
            ACCESS  not-accessible
            STATUS  mandatory
            DESCRIPTION
            "This table contains the properties for each 4-20mAmp sensor"
            ::= { sensors 5 }

         current4to20mAEntry OBJECT-TYPE
            SYNTAX  Current4to20mAEntry
            ACCESS  not-accessible
            STATUS  mandatory
            INDEX { current4to20mAIndex }
            ::= { current4to20mATable 1 }

         Current4to20mAEntry ::= SEQUENCE {
            current4to20mAIndex
               DisplayString,
            current4to20mADescription
               DisplayString,
            current4to20mAValue
               INTEGER,
            current4to20mAUnit
               DisplayString,
            current4to20mAStatus
               INTEGER,
            current4to20mAGoOffline
               INTEGER,
            current4to20mALowCritical
               INTEGER,
            current4to20mALowWarning
               INTEGER,
            current4to20mAHighWarning
               INTEGER,
            current4to20mAHighCritical
               INTEGER,
            current4to20mARearm
               INTEGER,
            current4to20mADelayError
               INTEGER,
            current4to20mADelayNormal
               INTEGER,
            current4to20mADelayLowCritical
               INTEGER,
            current4to20mADelayLowWarning
               INTEGER,
            current4to20mADelayHighWarning
               INTEGER,
            current4to20mADelayHighCritical
               INTEGER,
            current4to20mARaw
               INTEGER,
            current4to20mAOffset
               INTEGER,
            current4to20mAAmountMaxVoltage
               INTEGER,
            current4to20mAAmountBaseVoltage
               INTEGER,
            current4to20mAPort
               INTEGER,
            current4to20mASubPort
               INTEGER,
            current4to20mAMaxVoltage
               INTEGER,
            current4to20mABaseVoltage
               INTEGER,
            current4to20mADisplayStyle
               INTEGER,
            current4to20mAHighCriticalDescription
               DisplayString,
            current4to20mALowCriticalDescription
               DisplayString,
            current4to20mANormalDescription
               DisplayString,
            current4to20mALowWarningDescription
               DisplayString,   
            current4to20mAHighWarningDescription
               DisplayString,
            current4to20mASensorErrorDescription
               DisplayString,
            current4to20mAHighCriticalColor 
               INTEGER,
            current4to20mALowCriticalColor 
               INTEGER,
            current4to20mANormalColor 
               INTEGER,
            current4to20mALowWarningColor 
               INTEGER,   
            current4to20mAHighWarningColor 
               INTEGER,
            current4to20mASensorErrorColor 
               INTEGER,
            current4to20mAAcknowledge
               INTEGER,
            current4to20mAId
               INTEGER
         }

         current4to20mAIndex OBJECT-TYPE
            SYNTAX  DisplayString
            ACCESS  read-only
            STATUS  mandatory
            DESCRIPTION
            "The Sensor Compound ID of this sensor, used to identify which sensor it is in the system configuration."
            ::= { current4to20mAEntry 1 }

         current4to20mADescription OBJECT-TYPE
            SYNTAX  DisplayString
            ACCESS  read-write
            STATUS  mandatory
            DESCRIPTION
            "The user specified description of this sensor. Unless specified, the default value is used."
            ::= { current4to20mAEntry 2 }

         current4to20mAValue OBJECT-TYPE
            SYNTAX  INTEGER
            ACCESS  read-only
            STATUS  mandatory
            DESCRIPTION
            "The value in numerical reading."
            ::= { current4to20mAEntry 4 }

         current4to20mAUnit OBJECT-TYPE
            SYNTAX  DisplayString
            ACCESS  read-write
            STATUS  mandatory
            DESCRIPTION
            "The sensor's value unit string, in what the sensor's value is read in."
            ::= { current4to20mAEntry 5 }

         current4to20mAStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { current4to20mAEntry 6 }

         current4to20mAGoOffline OBJECT-TYPE
            SYNTAX  INTEGER {
               online(1),
               goOffline(2)
            }
            ACCESS  read-write
            STATUS  mandatory
            DESCRIPTION
            "Command to offline this sensor: use value '2' to set the sensor offline."
            ::= { current4to20mAEntry 8 }

         current4to20mALowCritical OBJECT-TYPE
            SYNTAX  INTEGER
            ACCESS  read-write
            STATUS  mandatory
            DESCRIPTION
            "The user specified 'Low Critical' value of this sensor. The unit will check the current reading against this value, and send an alert if it's configured. Unless specified, the default value is used."
            ::= { current4to20mAEntry 9 }

         current4to20mALowWarning OBJECT-TYPE
            SYNTAX  INTEGER
            ACCESS  read-write
            STATUS  mandatory
            DESCRIPTION
            "The user specified 'Low Warning' value of this sensor. The unit will check the current reading against this value, and send an alert if it's configured. Unless specified, the default value is used."
            ::= { current4to20mAEntry 10 }

         current4to20mAHighWarning OBJECT-TYPE
            SYNTAX  INTEGER
            ACCESS  read-write
            STATUS  mandatory
            DESCRIPTION
            "The user specified 'High Warning' value of this sensor. The unit will check the current reading against this value, and send an alert if it's configured. Unless specified, the default value is used."
            ::= { current4to20mAEntry 11 }

         current4to20mAHighCritical OBJECT-TYPE
            SYNTAX  INTEGER
            ACCESS  read-write
            STATUS  mandatory
            DESCRIPTION
            "The user specified 'High Critical' value of this sensor. The unit will check the current reading against this value, and send an alert if it's configured. Unless specified, the default value is used."
            ::= { current4to20mAEntry 12 }

         current4to20mARearm OBJECT-TYPE
            SYNTAX  INTEGER
            ACCESS  read-write
            STATUS  mandatory
            DESCRIPTION
            "This value tells how many values the sensor has to reach beyond the threshold value, before changing to a new status. Useful to prevent the quick fluctuation of readings."
            ::= { current4to20mAEntry 13 }

         current4to20mADelayError OBJECT-TYPE
            SYNTAX  INTEGER
            ACCESS  read-write
            STATUS  mandatory
            DESCRIPTION
            "The time in seconds (continuous time) that the sensor has to be in 'Error' status before its status is changed."
            ::= { current4to20mAEntry 14 }

         current4to20mADelayNormal OBJECT-TYPE
            SYNTAX  INTEGER
            ACCESS  read-write
            STATUS  mandatory
            DESCRIPTION
            "The time in seconds (continuous time) that the sensor has to be in 'Normal' status before its status is changed."
            ::= { current4to20mAEntry 15 }

         current4to20mADelayLowCritical OBJECT-TYPE
            SYNTAX INTEGER
            ACCESS read-write
            STATUS mandatory
            DESCRIPTION
            "The time in seconds (continuous time) that the sensor has to be in 'Low Critical' status before its status is changed."
            ::= { current4to20mAEntry 16 }

         current4to20mADelayLowWarning OBJECT-TYPE
            SYNTAX INTEGER
            ACCESS read-write
            STATUS mandatory
            DESCRIPTION
            "The time in seconds (continuous time) that the sensor has to be in 'Low Warning' status before its status is changed."
            ::= { current4to20mAEntry 17 }

         current4to20mADelayHighWarning OBJECT-TYPE
            SYNTAX INTEGER
            ACCESS read-write
            STATUS mandatory
            DESCRIPTION
            "The time in seconds (continuous time) that the sensor has to be in 'High Warning' status before its status is changed."
            ::= { current4to20mAEntry 18 }

         current4to20mADelayHighCritical OBJECT-TYPE
            SYNTAX INTEGER
            ACCESS read-write
            STATUS mandatory
            DESCRIPTION
            "The time in seconds (continuous time) that the sensor has to be in 'High Critical' status before its status is changed."
            ::= { current4to20mAEntry 19 }

         current4to20mARaw OBJECT-TYPE
            SYNTAX  INTEGER 
            ACCESS  read-only
            STATUS  mandatory
            DESCRIPTION
            "The sensor's unformatted (raw) value that is being read directly from sensor, before it is converted to the preferred value."
            ::= { current4to20mAEntry 20 }

         current4to20mAOffset OBJECT-TYPE
            SYNTAX  INTEGER
            ACCESS  read-write
            STATUS  mandatory
            DESCRIPTION
            "The offset value for this sensor. It's used to adjust the reading value in case the reading is incorrect."
            ::= { current4to20mAEntry 21 }

         current4to20mAAmountMaxVoltage OBJECT-TYPE
            SYNTAX  INTEGER
            ACCESS  read-write
            STATUS  mandatory
            DESCRIPTION
            "The maximum scale of 4to20mA conversion."
            ::= { current4to20mAEntry 33 }

         current4to20mAAmountBaseVoltage OBJECT-TYPE
            SYNTAX  INTEGER
            ACCESS  read-write
            STATUS  mandatory
            DESCRIPTION
            "The base scale of 4to20mA conversion."
            ::= { current4to20mAEntry 34 }

         current4to20mAPort OBJECT-TYPE
            SYNTAX  INTEGER
            ACCESS  read-only
            STATUS  mandatory
            DESCRIPTION
            "The device's sensor port number, where this sensor is plugged in to."
            ::= { current4to20mAEntry 35 }

         current4to20mASubPort OBJECT-TYPE
            SYNTAX  INTEGER
            ACCESS  read-only
            STATUS  mandatory
            DESCRIPTION
            "The logical port number of this sensor in the array, or in a set of sensors. For Temperature Sensor, it's for the array of Temperature Sensors and Dual Sensors.  For example x.1, x.2, x.3 ..."
            ::= { current4to20mAEntry 36 }

         current4to20mAMaxVoltage OBJECT-TYPE
            SYNTAX  INTEGER
            ACCESS  read-write
            STATUS  mandatory
            DESCRIPTION
            "The maximum range for use in conversion."
            ::= { current4to20mAEntry 43 }

         current4to20mABaseVoltage OBJECT-TYPE
            SYNTAX  INTEGER
            ACCESS  read-write
            STATUS  mandatory
            DESCRIPTION
            "The base range for use in conversion."
            ::= { current4to20mAEntry 44 }

         current4to20mADisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { current4to20mAEntry 45 }

         current4to20mAHighCriticalDescription OBJECT-TYPE
            SYNTAX  DisplayString
            ACCESS  read-write
            STATUS  mandatory
            DESCRIPTION
            "The user specified 'High Critical' status description of this sensor. Unless specified, the default value is used."
            ::=  { current4to20mAEntry 46 }

         current4to20mALowCriticalDescription OBJECT-TYPE
            SYNTAX  DisplayString
            ACCESS  read-write
            STATUS  mandatory
            DESCRIPTION
            "The user specified 'Low Critical' status description of this sensor. Unless specified, the default value is used."
            ::= { current4to20mAEntry 47 }

         current4to20mANormalDescription OBJECT-TYPE
            SYNTAX  DisplayString
            ACCESS  read-write
            STATUS  mandatory
            DESCRIPTION
            "The user specified 'Normal' status description of this sensor. Unless specified, the default value is used."
            ::= { current4to20mAEntry 48 }

         current4to20mALowWarningDescription OBJECT-TYPE
            SYNTAX  DisplayString
            ACCESS  read-write
            STATUS  mandatory
            DESCRIPTION
            "The user specified 'Low Warning' status description of this sensor. Unless specified, the default value is used."
            ::= { current4to20mAEntry 49 }

         current4to20mAHighWarningDescription OBJECT-TYPE
            SYNTAX  DisplayString
            ACCESS  read-write
            STATUS  mandatory
            DESCRIPTION
            "The user specified 'High Warning' status description of this sensor. Unless specified, the default value is used."
            ::= { current4to20mAEntry 50 }

         current4to20mASensorErrorDescription OBJECT-TYPE
            SYNTAX  DisplayString
            ACCESS  read-write
            STATUS  mandatory
            DESCRIPTION
            "The user specified 'Sensor Error' status description of this sensor. Unless specified, the default value is used."
            ::= { current4to20mAEntry 51 }

         current4to20mAHighCriticalColor OBJECT-TYPE
            SYNTAX  INTEGER
            ACCESS  read-write
            STATUS  mandatory
            DESCRIPTION
            "The user specified 'High Critical' status field color. The unit will show this color on its web interface and in DCIM. Unless specified, the default value is used."
            ::= { current4to20mAEntry 54 }

         current4to20mALowCriticalColor OBJECT-TYPE
            SYNTAX  INTEGER
            ACCESS  read-write
            STATUS  mandatory
            DESCRIPTION
            "The user specified 'Low Critical' status field color. The unit will show this color on its web interface and in DCIM. Unless specified, the default value is used."
            ::= { current4to20mAEntry 55 }

         current4to20mANormalColor OBJECT-TYPE
            SYNTAX  INTEGER
            ACCESS  read-write
            STATUS  mandatory
            DESCRIPTION
            "The user specified 'Normal' status field color. The unit will show this color on its web interface and in DCIM. Unless specified, the default value is used."
            ::= { current4to20mAEntry 56 }

         current4to20mALowWarningColor OBJECT-TYPE
            SYNTAX  INTEGER
            ACCESS  read-write
            STATUS  mandatory
            DESCRIPTION
            "The user specified 'Low Warning' status field color. The unit will show this color on its web interface and in DCIM. Unless specified, the default value is used."
            ::= { current4to20mAEntry 57 }

         current4to20mAHighWarningColor OBJECT-TYPE
            SYNTAX  INTEGER
            ACCESS  read-write
            STATUS  mandatory
            DESCRIPTION
            "The user specified 'High Warning' status field color. The unit will show this color on its web interface and in DCIM. Unless specified, the default value is used."
            ::= { current4to20mAEntry 58 }

         current4to20mASensorErrorColor OBJECT-TYPE
            SYNTAX  INTEGER
            ACCESS  read-write
            STATUS  mandatory
            DESCRIPTION
            "The user specified 'Sensor Error' status field color. The unit will show this color on its web interface and in DCIM. Unless specified, the default value is used."
            ::= { current4to20mAEntry 59 }

         current4to20mAAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { current4to20mAEntry 70 }

         current4to20mAId OBJECT-TYPE
            SYNTAX  INTEGER
            ACCESS  read-only
            STATUS  mandatory
            DESCRIPTION
            "The Sensor ID of this sensor, used to identify which sensor it is in the system configuration."
            ::= { current4to20mAEntry 1000 }

--/* End of current4to20mATable */

--/* Begin of dcVoltageTable */
         dcVoltageTable OBJECT-TYPE
            SYNTAX  SEQUENCE OF DcVoltageEntry
            ACCESS  not-accessible
            STATUS  mandatory
            DESCRIPTION
            "This table contains the properties for each DC voltage sensor"
            ::= { sensors 6 }

         dcVoltageEntry OBJECT-TYPE
            SYNTAX  DcVoltageEntry
            ACCESS  not-accessible
            STATUS  mandatory
            INDEX { dcVoltageIndex }
            ::= { dcVoltageTable 1 }

         DcVoltageEntry ::= SEQUENCE {
            dcVoltageIndex
               DisplayString,
            dcVoltageDescription
               DisplayString,
            dcVoltageValue
               INTEGER,
            dcVoltageUnit
               DisplayString,
            dcVoltageStatus
               INTEGER,
            dcVoltageGoOffline
               INTEGER,
            dcVoltageLowCritical
               INTEGER,
            dcVoltageLowWarning
               INTEGER,
            dcVoltageHighWarning
               INTEGER,
            dcVoltageHighCritical
               INTEGER,
            dcVoltageRearm
               INTEGER,
            dcVoltageDelayError
               INTEGER,
            dcVoltageDelayNormal
               INTEGER,
            dcVoltageDelayLowCritical
               INTEGER,
            dcVoltageDelayLowWarning
               INTEGER,
            dcVoltageDelayHighWarning
               INTEGER,
            dcVoltageDelayHighCritical
               INTEGER,
            dcVoltageRaw
               INTEGER,
            dcVoltageOffset
               INTEGER,
            dcVoltageJumper
               INTEGER,
            dcVoltageAmountMaxVoltage
               INTEGER,
            dcVoltageAmountBaseVoltage
               INTEGER,
            dcVoltagePort
               INTEGER,
            dcVoltageSubPort
               INTEGER,
            dcVoltageMaxVoltage
               INTEGER,
            dcVoltageBaseVoltage
               INTEGER,
            dcVoltageDisplayStyle
               INTEGER,
            dcVoltageHighCriticalDescription
               DisplayString,
            dcVoltageLowCriticalDescription
               DisplayString,
            dcVoltageNormalDescription
               DisplayString,
            dcVoltageLowWarningDescription
               DisplayString,   
            dcVoltageHighWarningDescription
               DisplayString,
            dcVoltageSensorErrorDescription
               DisplayString,
            dcVoltageHighCriticalColor 
               INTEGER,
            dcVoltageLowCriticalColor 
               INTEGER,
            dcVoltageNormalColor 
               INTEGER,
            dcVoltageLowWarningColor 
               INTEGER,   
            dcVoltageHighWarningColor 
               INTEGER,
            dcVoltageSensorErrorColor 
               INTEGER,
            dcVoltageAcknowledge
               INTEGER,
            dcVoltageId
               INTEGER
         }

         dcVoltageIndex OBJECT-TYPE
            SYNTAX  DisplayString
            ACCESS  read-only
            STATUS  mandatory
            DESCRIPTION
            "The Sensor Compound ID of this sensor, used to identify which sensor it is in the system configuration."
            ::= { dcVoltageEntry 1 }

         dcVoltageDescription OBJECT-TYPE
            SYNTAX  DisplayString
            ACCESS  read-write
            STATUS  mandatory
            DESCRIPTION
            "The user specified description of this sensor. Unless specified, the default value is used."
            ::= { dcVoltageEntry 2 }

         dcVoltageValue OBJECT-TYPE
            SYNTAX  INTEGER
            ACCESS  read-only
            STATUS  mandatory
            DESCRIPTION
            "The value in numerical reading."
            ::= { dcVoltageEntry 4 }

         dcVoltageUnit OBJECT-TYPE
            SYNTAX  DisplayString
            ACCESS  read-write
            STATUS  mandatory
            DESCRIPTION
            "The sensor's value unit string, in what the sensor's value is read in."
            ::= { dcVoltageEntry 5 }

         dcVoltageStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { dcVoltageEntry 6 }

         dcVoltageGoOffline OBJECT-TYPE
            SYNTAX  INTEGER {
               online(1),
               goOffline(2)
            }
            ACCESS  read-write
            STATUS  mandatory
            DESCRIPTION
            "Command to offline this sensor: use value '2' to set the sensor offline."
            ::= { dcVoltageEntry 8 }

         dcVoltageLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { dcVoltageEntry 9 }

         dcVoltageLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { dcVoltageEntry 10 }

         dcVoltageHighWarning OBJECT-TYPE
            SYNTAX  INTEGER
            ACCESS  read-write
            STATUS  mandatory
            DESCRIPTION
            "The user specified 'High Warning' value of this sensor. The unit will check the current reading against this value, and send an alert if it's configured. Unless specified, the default value is used."
            ::= { dcVoltageEntry 11 }

         dcVoltageHighCritical OBJECT-TYPE
            SYNTAX  INTEGER
            ACCESS  read-write
            STATUS  mandatory
            DESCRIPTION
            "The user specified 'High Critical' value of this sensor. The unit will check the current reading against this value, and send an alert if it's configured. Unless specified, the default value is used."
            ::= { dcVoltageEntry 12 }

         dcVoltageRearm OBJECT-TYPE
            SYNTAX  INTEGER
            ACCESS  read-write
            STATUS  mandatory
            DESCRIPTION
            "This value tells how many values the sensor has to reach beyond the threshold value, before changing to a new status. Useful to prevent the quick fluctuation of readings."
            ::= { dcVoltageEntry 13 }

         dcVoltageDelayError OBJECT-TYPE
            SYNTAX  INTEGER
            ACCESS  read-write
            STATUS  mandatory
            DESCRIPTION
            "The time in seconds (continuous time) that the sensor has to be in 'Error' status before its status is changed."
            ::= { dcVoltageEntry 14 }

         dcVoltageDelayNormal OBJECT-TYPE
            SYNTAX  INTEGER
            ACCESS  read-write
            STATUS  mandatory
            DESCRIPTION
            "The time in seconds (continuous time) that the sensor has to be in 'Normal' status before its status is changed."
            ::= { dcVoltageEntry 15 }

         dcVoltageDelayLowCritical OBJECT-TYPE
            SYNTAX INTEGER
            ACCESS read-write
            STATUS mandatory
            DESCRIPTION
            "The time in seconds (continuous time) that the sensor has to be in 'Low Critical' status before its status is changed."
            ::= { dcVoltageEntry 16 }

         dcVoltageDelayLowWarning OBJECT-TYPE
            SYNTAX INTEGER
            ACCESS read-write
            STATUS mandatory
            DESCRIPTION
            "The time in seconds (continuous time) that the sensor has to be in 'Low Warning' status before its status is changed."
            ::= { dcVoltageEntry 17 }

         dcVoltageDelayHighWarning OBJECT-TYPE
            SYNTAX INTEGER
            ACCESS read-write
            STATUS mandatory
            DESCRIPTION
            "The time in seconds (continuous time) that the sensor has to be in 'High Warning' status before its status is changed."
            ::= { dcVoltageEntry 18 }

         dcVoltageDelayHighCritical OBJECT-TYPE
            SYNTAX INTEGER
            ACCESS read-write
            STATUS mandatory
            DESCRIPTION
            "The time in seconds (continuous time) that the sensor has to be in 'High Critical' status before its status is changed."
            ::= { dcVoltageEntry 19 }

         dcVoltageRaw OBJECT-TYPE
            SYNTAX  INTEGER 
            ACCESS  read-only
            STATUS  mandatory
            DESCRIPTION
            "The sensor's unformatted (raw) value that is being read directly from sensor, before it is converted to the preferred value."
            ::= { dcVoltageEntry 20 }

         dcVoltageOffset OBJECT-TYPE
            SYNTAX  INTEGER
            ACCESS  read-write
            STATUS  mandatory
            DESCRIPTION
            "The offset value for this sensor. It's used to adjust the reading value in case the reading is incorrect."
            ::= { dcVoltageEntry 21 }

         dcVoltageJumper OBJECT-TYPE
            SYNTAX  INTEGER {
               jumperAt-60(-600),
               jumperAt-40(-400),
               jumperAt-30(-300),
               jumperAt-20(-200),
               jumperAt-10(-100),
               jumperAt10(100),
               jumperAt20(200),
               jumperAt30(300),
               jumperAt40(400),
               jumperAt60(600)
            }
            ACCESS  read-write
            STATUS  mandatory
            DESCRIPTION
            "Selected voltage scale (jumper 0) in DC voltage conversion."
            ::= { dcVoltageEntry 32 }

         dcVoltageAmountMaxVoltage OBJECT-TYPE
            SYNTAX  INTEGER
            ACCESS  read-write
            STATUS  mandatory
            DESCRIPTION
            "The maximum scale of DC voltage conversion."
            ::= { dcVoltageEntry 33 }

         dcVoltageAmountBaseVoltage OBJECT-TYPE
            SYNTAX  INTEGER
            ACCESS  read-write
            STATUS  mandatory
            DESCRIPTION
            "The base scale of DC voltage conversion."
            ::= { dcVoltageEntry 34 }

         dcVoltagePort OBJECT-TYPE
            SYNTAX  INTEGER
            ACCESS  read-only
            STATUS  mandatory
            DESCRIPTION
            "The device's sensor port number, where this sensor is plugged in to."
            ::= { dcVoltageEntry 35 }

         dcVoltageSubPort OBJECT-TYPE
            SYNTAX  INTEGER
            ACCESS  read-only
            STATUS  mandatory
            DESCRIPTION
            "The logical port number of this sensor in the array, or in a set of sensors. For Temperature Sensor, it's for the array of Temperature Sensors and Dual Sensors.  For example x.1, x.2, x.3 ..."
            ::= { dcVoltageEntry 36 }

         dcVoltageMaxVoltage OBJECT-TYPE
            SYNTAX  INTEGER
            ACCESS  read-write
            STATUS  mandatory
            DESCRIPTION
            "The maximum voltage range for use in conversion."
            ::= { dcVoltageEntry 43 }

         dcVoltageBaseVoltage OBJECT-TYPE
            SYNTAX  INTEGER
            ACCESS  read-write
            STATUS  mandatory
            DESCRIPTION
            "The base voltage range for use in conversion."
            ::= { dcVoltageEntry 44 }

         dcVoltageDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { dcVoltageEntry 45 }

         dcVoltageHighCriticalDescription OBJECT-TYPE
            SYNTAX  DisplayString
            ACCESS  read-write
            STATUS  mandatory
            DESCRIPTION
            "The user specified 'High Critical' status description of this sensor. Unless specified, the default value is used."
            ::= { dcVoltageEntry 46 }

         dcVoltageLowCriticalDescription OBJECT-TYPE
            SYNTAX  DisplayString
            ACCESS  read-write
            STATUS  mandatory
            DESCRIPTION
            "The user specified 'Low Critical' status description of this sensor. Unless specified, the default value is used."
            ::= { dcVoltageEntry 47 }

         dcVoltageNormalDescription OBJECT-TYPE
            SYNTAX  DisplayString
            ACCESS  read-write
            STATUS  mandatory
            DESCRIPTION
            "The user specified 'Normal' status description of this sensor. Unless specified, the default value is used."
            ::= { dcVoltageEntry 48 }

         dcVoltageLowWarningDescription OBJECT-TYPE
            SYNTAX  DisplayString
            ACCESS  read-write
            STATUS  mandatory
            DESCRIPTION
            "The user specified 'Low Warning' status description of this sensor. Unless specified, the default value is used."
            ::= { dcVoltageEntry 49 }

         dcVoltageHighWarningDescription OBJECT-TYPE
            SYNTAX  DisplayString
            ACCESS  read-write
            STATUS  mandatory
            DESCRIPTION
            "The user specified 'High Warning' status description of this sensor. Unless specified, the default value is used."
            ::= { dcVoltageEntry 50 }

         dcVoltageSensorErrorDescription OBJECT-TYPE
            SYNTAX  DisplayString
            ACCESS  read-write
            STATUS  mandatory
            DESCRIPTION
            "The user specified 'Sensor Error' status description of this sensor. Unless specified, the default value is used."
            ::= { dcVoltageEntry 51 }

         dcVoltageHighCriticalColor OBJECT-TYPE
            SYNTAX  INTEGER
            ACCESS  read-write
            STATUS  mandatory
            DESCRIPTION
            "The user specified 'High Critical' status field color. The unit will show this color on its web interface and in DCIM. Unless specified, the default value is used."
            ::= { dcVoltageEntry 54 }

         dcVoltageLowCriticalColor OBJECT-TYPE
            SYNTAX  INTEGER
            ACCESS  read-write
            STATUS  mandatory
            DESCRIPTION
            "The user specified 'Low Critical' status field color. The unit will show this color on its web interface and in DCIM. Unless specified, the default value is used."
            ::= { dcVoltageEntry 55 }

         dcVoltageNormalColor OBJECT-TYPE
            SYNTAX  INTEGER
            ACCESS  read-write
            STATUS  mandatory
            DESCRIPTION
            "The user specified 'Normal' status field color. The unit will show this color on its web interface and in DCIM. Unless specified, the default value is used."
            ::= { dcVoltageEntry 56 }

         dcVoltageLowWarningColor OBJECT-TYPE
            SYNTAX  INTEGER
            ACCESS  read-write
            STATUS  mandatory
            DESCRIPTION
            "The user specified 'Low Warning' status field color. The unit will show this color on its web interface and in DCIM. Unless specified, the default value is used."
            ::= { dcVoltageEntry 57 }

         dcVoltageHighWarningColor OBJECT-TYPE
            SYNTAX  INTEGER
            ACCESS  read-write
            STATUS  mandatory
            DESCRIPTION
            "The user specified 'High Warning' status field color. The unit will show this color on its web interface and in DCIM. Unless specified, the default value is used."
            ::= { dcVoltageEntry 58 }

         dcVoltageSensorErrorColor OBJECT-TYPE
            SYNTAX  INTEGER
            ACCESS  read-write
            STATUS  mandatory
            DESCRIPTION
            "The user specified 'Sensor Error' status field color. The unit will show this color on its web interface and in DCIM. Unless specified, the default value is used."
            ::= { dcVoltageEntry 59 }

         dcVoltageAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { dcVoltageEntry 70 }

         dcVoltageId OBJECT-TYPE
            SYNTAX  INTEGER
            ACCESS  read-only
            STATUS  mandatory
            DESCRIPTION
            "The Sensor ID of this sensor, used to identify which sensor it is in the system configuration."
            ::= { dcVoltageEntry 1000 }

--/* End of dcVoltageTable */

--/* Begin of airflowTable */
         airflowTable OBJECT-TYPE
            SYNTAX  SEQUENCE OF AirflowEntry
            ACCESS  not-accessible
            STATUS  mandatory
            DESCRIPTION
            "This table contains the properties for each airflow sensor"
            ::= { sensors 7 }

         airflowEntry OBJECT-TYPE
            SYNTAX  AirflowEntry
            ACCESS  not-accessible
            STATUS  mandatory
            INDEX { airflowIndex }
            ::= { airflowTable 1 }

         AirflowEntry ::= SEQUENCE {
            airflowIndex
               DisplayString,
            airflowDescription
               DisplayString,
            airflowValue
               INTEGER,
            airflowStatus
               INTEGER,
            airflowGoOffline
               INTEGER,
            airflowLowCritical
               INTEGER,
            airflowLowWarning
               INTEGER,
            airflowHighWarning
               INTEGER,
            airflowHighCritical
               INTEGER,
            airflowRearm
               INTEGER,
            airflowDelayError
               INTEGER,
            airflowDelayNormal
               INTEGER,
            airflowDelayLowCritical
               INTEGER,
            airflowDelayLowWarning
               INTEGER,
            airflowDelayHighWarning
               INTEGER,
            airflowDelayHighCritical
               INTEGER,
            airflowRaw
               INTEGER,
            airflowPort
               INTEGER,
            airflowSubPort
               INTEGER,
            airflowDisplayStyle
               INTEGER,
            airflowHighCriticalDescription
               DisplayString,
            airflowLowCriticalDescription
               DisplayString,
            airflowNormalDescription
               DisplayString,
            airflowLowWarningDescription
               DisplayString,   
            airflowHighWarningDescription
               DisplayString,
            airflowSensorErrorDescription
               DisplayString,
            airflowHighCriticalColor 
               INTEGER,
            airflowLowCriticalColor 
               INTEGER,
            airflowNormalColor 
               INTEGER,
            airflowLowWarningColor 
               INTEGER,   
            airflowHighWarningColor 
               INTEGER,
            airflowSensorErrorColor 
               INTEGER,
            airflowAcknowledge
               INTEGER,
            airflowId
               INTEGER
         }

         airflowIndex OBJECT-TYPE
            SYNTAX  DisplayString
            ACCESS  read-only
            STATUS  mandatory
            DESCRIPTION
            "The Sensor Compound ID of this sensor, used to identify which sensor it is in the system configuration."
            ::= { airflowEntry 1 }

         airflowDescription OBJECT-TYPE
            SYNTAX  DisplayString
            ACCESS  read-write
            STATUS  mandatory
            DESCRIPTION
            "The user specified description of this sensor. Unless specified, the default value is used."
            ::= { airflowEntry 2 }

         airflowValue OBJECT-TYPE
            SYNTAX  INTEGER
            ACCESS  read-only
            STATUS  mandatory
            DESCRIPTION
            "The value in numerical reading."
            ::= { airflowEntry 4 }

         airflowStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { airflowEntry 6 }

         airflowGoOffline OBJECT-TYPE
            SYNTAX  INTEGER {
               online(1),
               goOffline(2)
            }
            ACCESS  read-write
            STATUS  mandatory
            DESCRIPTION
            "Command to offline this sensor: use value '2' to set the sensor offline."
            ::= { airflowEntry 8 }

         airflowLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { airflowEntry 9 }

         airflowLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { airflowEntry 10 }

         airflowHighWarning OBJECT-TYPE
            SYNTAX  INTEGER
            ACCESS  read-write
            STATUS  mandatory
            DESCRIPTION
            "The user specified 'High Warning' value of this sensor. The unit will check the current reading against this value, and send an alert if it's configured. Unless specified, the default value is used."
            ::= { airflowEntry 11 }

         airflowHighCritical OBJECT-TYPE
            SYNTAX  INTEGER
            ACCESS  read-write
            STATUS  mandatory
            DESCRIPTION
            "The user specified 'High Critical' value of this sensor. The unit will check the current reading against this value, and send an alert if it's configured. Unless specified, the default value is used."
            ::= { airflowEntry 12 }

         airflowRearm OBJECT-TYPE
            SYNTAX  INTEGER
            ACCESS  read-write
            STATUS  mandatory
            DESCRIPTION
            "This value tells how many values the sensor has to reach beyond the threshold value, before changing to a new status. Useful to prevent the quick fluctuation of readings."
            ::= { airflowEntry 13 }

         airflowDelayError OBJECT-TYPE
            SYNTAX  INTEGER
            ACCESS  read-write
            STATUS  mandatory
            DESCRIPTION
            "The time in seconds (continuous time) that the sensor has to be in 'Error' status before its status is changed."
            ::= { airflowEntry 14 }

         airflowDelayNormal OBJECT-TYPE
            SYNTAX  INTEGER
            ACCESS  read-write
            STATUS  mandatory
            DESCRIPTION
            "The time in seconds (continuous time) that the sensor has to be in 'Normal' status before its status is changed."
            ::= { airflowEntry 15 }

         airflowDelayLowCritical OBJECT-TYPE
            SYNTAX INTEGER
            ACCESS read-write
            STATUS mandatory
            DESCRIPTION
            "The time in seconds (continuous time) that the sensor has to be in 'Low Critical' status before its status is changed."
            ::= { airflowEntry 16 }

         airflowDelayLowWarning OBJECT-TYPE
            SYNTAX INTEGER
            ACCESS read-write
            STATUS mandatory
            DESCRIPTION
            "The time in seconds (continuous time) that the sensor has to be in 'Low Warning' status before its status is changed."
            ::= { airflowEntry 17 }

         airflowDelayHighWarning OBJECT-TYPE
            SYNTAX INTEGER
            ACCESS read-write
            STATUS mandatory
            DESCRIPTION
            "The time in seconds (continuous time) that the sensor has to be in 'High Warning' status before its status is changed."
            ::= { airflowEntry 18 }

         airflowDelayHighCritical OBJECT-TYPE
            SYNTAX INTEGER
            ACCESS read-write
            STATUS mandatory
            DESCRIPTION
            "The time in seconds (continuous time) that the sensor has to be in 'High Critical' status before its status is changed."
            ::= { airflowEntry 19 }

         airflowRaw OBJECT-TYPE
            SYNTAX  INTEGER
            ACCESS  read-only
            STATUS  mandatory
            DESCRIPTION
            "The sensor's unformatted (raw) value that is being read directly from sensor, before it is converted to the preferred value."
            ::= { airflowEntry 20 }

         airflowPort OBJECT-TYPE
            SYNTAX  INTEGER
            ACCESS  read-only
            STATUS  mandatory
            DESCRIPTION
            "The device's sensor port number, where this sensor is plugged in to."
            ::= { airflowEntry 35 }

         airflowSubPort OBJECT-TYPE
            SYNTAX  INTEGER
            ACCESS  read-only
            STATUS  mandatory
            DESCRIPTION
            "The logical port number of this sensor in the array, or in a set of sensors."
            ::= { airflowEntry 36 }

         airflowDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { airflowEntry 45 }

         airflowHighCriticalDescription OBJECT-TYPE
            SYNTAX  DisplayString
            ACCESS  read-write
            STATUS  mandatory
            DESCRIPTION
            "The user specified 'High Critical' status description of this sensor. Unless specified, the default value is used."
            ::= { airflowEntry 46 }

         airflowLowCriticalDescription OBJECT-TYPE
            SYNTAX  DisplayString
            ACCESS  read-write
            STATUS  mandatory
            DESCRIPTION
            "The user specified 'Low Critical' status description of this sensor. Unless specified, the default value is used."
            ::= { airflowEntry 47 }

         airflowNormalDescription OBJECT-TYPE
            SYNTAX  DisplayString
            ACCESS  read-write
            STATUS  mandatory
            DESCRIPTION
            "The user specified 'Normal' status description of this sensor. Unless specified, the default value is used."
            ::= { airflowEntry 48 }

         airflowLowWarningDescription OBJECT-TYPE
            SYNTAX  DisplayString
            ACCESS  read-write
            STATUS  mandatory
            DESCRIPTION
            "The user specified 'Low Warning' status description of this sensor. Unless specified, the default value is used."
            ::= { airflowEntry 49 }

         airflowHighWarningDescription OBJECT-TYPE
            SYNTAX  DisplayString
            ACCESS  read-write
            STATUS  mandatory
            DESCRIPTION
            "The user specified 'High Warning' status description of this sensor. Unless specified, the default value is used."
            ::= { airflowEntry 50 }

         airflowSensorErrorDescription OBJECT-TYPE
            SYNTAX  DisplayString
            ACCESS  read-write
            STATUS  mandatory
            DESCRIPTION
            "The user specified 'Sensor Error' status description of this sensor. Unless specified, the default value is used."
            ::= { airflowEntry 51 }

         airflowHighCriticalColor OBJECT-TYPE
            SYNTAX  INTEGER
            ACCESS  read-write
            STATUS  mandatory
            DESCRIPTION
            "The user specified 'High Critical' status field color. The unit will show this color on its web interface and in DCIM. Unless specified, the default value is used."
            ::= { airflowEntry 54 }

         airflowLowCriticalColor OBJECT-TYPE
            SYNTAX  INTEGER
            ACCESS  read-write
            STATUS  mandatory
            DESCRIPTION
            "The user specified 'Low Critical' status field color. The unit will show this color on its web interface and in DCIM. Unless specified, the default value is used."
            ::= { airflowEntry 55 }

         airflowNormalColor OBJECT-TYPE
            SYNTAX  INTEGER
            ACCESS  read-write
            STATUS  mandatory
            DESCRIPTION
            "The user specified 'Normal' status field color. The unit will show this color on its web interface and in DCIM. Unless specified, the default value is used."
            ::= { airflowEntry 56 }

         airflowLowWarningColor OBJECT-TYPE
            SYNTAX  INTEGER
            ACCESS  read-write
            STATUS  mandatory
            DESCRIPTION
            "The user specified 'Low Warning' status field color. The unit will show this color on its web interface and in DCIM. Unless specified, the default value is used."
            ::= { airflowEntry 57 }

         airflowHighWarningColor OBJECT-TYPE
            SYNTAX  INTEGER
            ACCESS  read-write
            STATUS  mandatory
            DESCRIPTION
            "The user specified 'High Warning' status field color. The unit will show this color on its web interface and in DCIM. Unless specified, the default value is used."
            ::= { airflowEntry 58 }

         airflowSensorErrorColor OBJECT-TYPE
            SYNTAX  INTEGER
            ACCESS  read-write
            STATUS  mandatory
            DESCRIPTION
            "The user specified 'Sensor Error' status field color. The unit will show this color on its web interface and in DCIM. Unless specified, the default value is used."
            ::= { airflowEntry 59 }

         airflowAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { airflowEntry 70 }

         airflowId OBJECT-TYPE
            SYNTAX  INTEGER
            ACCESS  read-only
            STATUS  mandatory
            DESCRIPTION
            "The Sensor ID of this sensor, used to identify which sensor it is in the system configuration."
            ::= { airflowEntry 1000 }

--/* End of airflowTable */

--/* Begin of motionTable */
         motionTable OBJECT-TYPE
            SYNTAX  SEQUENCE OF MotionEntry
            ACCESS  not-accessible
            STATUS  mandatory
            DESCRIPTION
            "This table contains the property and reading value for every sensor."
            ::= { sensors 8 }

         motionEntry OBJECT-TYPE
            SYNTAX  MotionEntry
            ACCESS  not-accessible
            STATUS  mandatory
            INDEX { motionIndex }
            ::= { motionTable 1 }

         MotionEntry ::= SEQUENCE {
               motionIndex
                  DisplayString,
               motionDescription
                  DisplayString,
               motionStatus
                  INTEGER,
               motionGoOffline
                  INTEGER,
               motionPort
                  INTEGER,
               motionSubPort
                  INTEGER,
               motionCriticalDescription
                  DisplayString,
               motionNormalDescription
                  DisplayString,
               motionCriticalColor
                  INTEGER,
               motionNormalColor
                  INTEGER,
               motionAcknowledge
                  INTEGER,
               motionId
                  INTEGER
            }

            motionIndex OBJECT-TYPE
               SYNTAX  DisplayString
               ACCESS  read-only
               STATUS  mandatory
               DESCRIPTION
               "The Sensor Compound ID of this sensor, used to identify which sensor it is in the system configuration."
               ::= { motionEntry 1 }

            motionDescription OBJECT-TYPE
               SYNTAX  DisplayString
               ACCESS  read-write
               STATUS  mandatory
               DESCRIPTION
               "A Description of this sensor Switch"
               ::= { motionEntry 2 }

            motionStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::= { motionEntry 6 }

            motionGoOffline OBJECT-TYPE
               SYNTAX  INTEGER {
                  online(1),
                  goOffline(2)
               }
               ACCESS  read-write
               STATUS  mandatory
               DESCRIPTION
               "To take offline enter a 2"
               ::= { motionEntry 8 }

            motionPort OBJECT-TYPE
               SYNTAX  INTEGER
               ACCESS  read-only
               STATUS  mandatory
               DESCRIPTION
               "Sensor port"
               ::= { motionEntry 35 }

            motionSubPort OBJECT-TYPE
               SYNTAX  INTEGER
               ACCESS  read-only
               STATUS  mandatory
               DESCRIPTION
               "Sensor sub port"
               ::= { motionEntry 36 }

            motionCriticalDescription OBJECT-TYPE
               SYNTAX  DisplayString
               ACCESS  read-write
               STATUS  mandatory
               DESCRIPTION
               "A Critical Description of this sensor"
               ::= { motionEntry 46 }

            motionNormalDescription OBJECT-TYPE
               SYNTAX  DisplayString
               ACCESS  read-write
               STATUS  mandatory
               DESCRIPTION
               "A Normal Description of this sensor"
               ::= { motionEntry 48 }

            motionCriticalColor OBJECT-TYPE
               SYNTAX  INTEGER
               ACCESS  read-write
               STATUS  mandatory
               DESCRIPTION
               "A Critical Color of this sensor"
               ::=  { motionEntry 54 }

            motionNormalColor OBJECT-TYPE
               SYNTAX  INTEGER
               ACCESS  read-write
               STATUS  mandatory
               DESCRIPTION
               "A Normal Color of this sensor"
               ::= { motionEntry 56 }

            motionAcknowledge OBJECT-TYPE
               SYNTAX  INTEGER {
                  acked(2)
               }
               ACCESS  read-write
               STATUS  mandatory
               DESCRIPTION
               "Motion sensor acknowledge"
               ::= { motionEntry 70 }

            motionId OBJECT-TYPE
               SYNTAX  INTEGER
               ACCESS  read-only
               STATUS  mandatory
               DESCRIPTION
               "The Sensor ID of this sensor, used to identify which sensor it is in the system configuration."
               ::= { motionEntry 1000 }

--/* End of motionTable */

--/* Begin of waterTable */
         waterTable OBJECT-TYPE
            SYNTAX  SEQUENCE OF WaterEntry
            ACCESS  not-accessible
            STATUS  mandatory
            DESCRIPTION
            "This table contains the properties for each water sensor"
            ::= { sensors 9 }

         waterEntry OBJECT-TYPE
            SYNTAX  WaterEntry
            ACCESS  not-accessible
            STATUS  mandatory
            INDEX { waterIndex }
            ::= { waterTable 1 }

         WaterEntry ::= SEQUENCE {
            waterIndex
               DisplayString,
            waterDescription
               DisplayString,
            waterStatus
               INTEGER,
            waterGoOffline
               INTEGER,
            waterPort
               INTEGER,
            waterSubPort
               INTEGER,
            waterCriticalDescription
               DisplayString,
            waterNormalDescription
               DisplayString,
            waterCriticalColor
               INTEGER,
            waterNormalColor
               INTEGER,   
            waterAcknowledge
               INTEGER,
            waterId
               INTEGER
         }

         waterIndex OBJECT-TYPE
            SYNTAX  DisplayString
            ACCESS  read-only
            STATUS  mandatory
            DESCRIPTION
            "The Sensor Compound ID of this sensor, used to identify which sensor it is in the system configuration."
            ::= { waterEntry 1 }

         waterDescription OBJECT-TYPE
            SYNTAX  DisplayString
            ACCESS  read-write
            STATUS  mandatory
            DESCRIPTION
            "The user specified description of this sensor. Unless specified, the default value is used."
            ::= { waterEntry 2 }

         waterStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { waterEntry 6 }

         waterGoOffline OBJECT-TYPE
            SYNTAX  INTEGER {
               online(1),
               goOffline(2)
            }
            ACCESS  read-write
            STATUS  mandatory
            DESCRIPTION
            "Command to offline this sensor: use value '2' to set the sensor offline."
            ::= { waterEntry 8 }

         waterPort OBJECT-TYPE
            SYNTAX  INTEGER
            ACCESS  read-only
            STATUS  mandatory
            DESCRIPTION
            "The device's sensor port number, where this sensor is plugged in to."
            ::= { waterEntry 35 }

         waterSubPort OBJECT-TYPE
            SYNTAX  INTEGER
            ACCESS  read-only
            STATUS  mandatory
            DESCRIPTION
            "The logical port number of this sensor in the array, or in a set of sensors. For Temperature Sensor, it's for the array of Temperature Sensors and Dual Sensors.  For example x.1, x.2, x.3 ..."
            ::= { waterEntry 36 }

         waterCriticalDescription OBJECT-TYPE
            SYNTAX  DisplayString
            ACCESS  read-write
            STATUS  mandatory
            DESCRIPTION
            "The user specified 'Critical' status description of this sensor. Unless specified, the default value is used."
            ::= { waterEntry 46 }

         waterNormalDescription OBJECT-TYPE
            SYNTAX  DisplayString
            ACCESS  read-write
            STATUS  mandatory
            DESCRIPTION
            "The user specified 'Normal' status description of this sensor. Unless specified, the default value is used."
            ::= { waterEntry 48 }

         waterCriticalColor OBJECT-TYPE
            SYNTAX  INTEGER
            ACCESS  read-write
            STATUS  mandatory
            DESCRIPTION
            "The user specified 'Critical' status field color. The unit will show this color on its web interface and in DCIM. Unless specified, the default value is used."
            ::= { waterEntry 54 }

         waterNormalColor OBJECT-TYPE
            SYNTAX  INTEGER
            ACCESS  read-write
            STATUS  mandatory
            DESCRIPTION
            "The user specified 'Normal' status field color. The unit will show this color on its web interface and in DCIM. Unless specified, the default value is used."
            ::= { waterEntry 56 }

         waterAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { waterEntry 70 }

         waterId OBJECT-TYPE
            SYNTAX  INTEGER
            ACCESS  read-only
            STATUS  mandatory
            DESCRIPTION
            "The Sensor ID of this sensor, used to identify which sensor it is in the system configuration."
            ::= { waterEntry 1000 }

--/* End of waterTable */

--/* Begin of securityTable */
         securityTable OBJECT-TYPE
            SYNTAX  SEQUENCE OF SecurityEntry
            ACCESS  not-accessible
            STATUS  mandatory
            DESCRIPTION
            "This table contains the properties for each security sensor"
            ::= { sensors 10 }

         securityEntry OBJECT-TYPE
            SYNTAX  SecurityEntry
            ACCESS  not-accessible
            STATUS  mandatory
            INDEX { securityIndex }
            ::= { securityTable 1 }

         SecurityEntry ::= SEQUENCE {
            securityIndex
               DisplayString,
            securityDescription
               DisplayString,
            securityStatus
               INTEGER,
            securityGoOffline
               INTEGER,
            securityPort
               INTEGER,
            securitySubPort
               INTEGER,
            securityCriticalDescription
               DisplayString,
            securityNormalDescription
               DisplayString,
            securityCriticalColor 
               INTEGER,
            securityNormalColor 
               INTEGER,
            securityAcknowledge
               INTEGER,
            securityId
               INTEGER
         }

         securityIndex OBJECT-TYPE
            SYNTAX  DisplayString
            ACCESS  read-only
            STATUS  mandatory
            DESCRIPTION
            "The Sensor Compound ID of this sensor, used to identify which sensor it is in the system configuration."
            ::= { securityEntry 1 }

         securityDescription OBJECT-TYPE
            SYNTAX  DisplayString
            ACCESS  read-write
            STATUS  mandatory
            DESCRIPTION
            "The user specified description of this sensor. Unless specified, the default value is used."
            ::= { securityEntry 2 }

         securityStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { securityEntry 6 }

         securityGoOffline OBJECT-TYPE
            SYNTAX  INTEGER {
               online(1),
               goOffline(2)
            }
            ACCESS  read-write
            STATUS  mandatory
            DESCRIPTION
            "Command to offline this sensor: use value '2' to set the sensor offline."
            ::= { securityEntry 8 }

         securityPort OBJECT-TYPE
            SYNTAX  INTEGER
            ACCESS  read-only
            STATUS  mandatory
            DESCRIPTION
            "The device's sensor port number, where this sensor is plugged in to."
            ::= { securityEntry 35 }

         securitySubPort OBJECT-TYPE
            SYNTAX  INTEGER
            ACCESS  read-only
            STATUS  mandatory
            DESCRIPTION
            "The logical port number of this sensor in the array, or in a set of sensors."
            ::= { securityEntry 36 }

         securityCriticalDescription OBJECT-TYPE
            SYNTAX  DisplayString
            ACCESS  read-write
            STATUS  mandatory
            DESCRIPTION
            "The user specified 'Critical' status description of this sensor. Unless specified, the default value is used."
            ::= { securityEntry 46 }

         securityNormalDescription OBJECT-TYPE
            SYNTAX  DisplayString
            ACCESS  read-write
            STATUS  mandatory
            DESCRIPTION
            "The user specified 'Normal' status description of this sensor. Unless specified, the default value is used."
            ::= { securityEntry 48 }

         securityCriticalColor OBJECT-TYPE
            SYNTAX  INTEGER
            ACCESS  read-write
            STATUS  mandatory
            DESCRIPTION
            "The user specified 'Critical' status field color. The unit will show this color on its web interface and in DCIM. Unless specified, the default value is used."
            ::= { securityEntry 54 }

         securityNormalColor OBJECT-TYPE
            SYNTAX  INTEGER
            ACCESS  read-write
            STATUS  mandatory
            DESCRIPTION
            "The user specified 'Normal' status field color. The unit will show this color on its web interface and in DCIM. Unless specified, the default value is used."
            ::= { securityEntry 56 }

         securityAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { securityEntry 70 }

         securityId OBJECT-TYPE
            SYNTAX  INTEGER
            ACCESS  read-only
            STATUS  mandatory
            DESCRIPTION
            "The Sensor ID of this sensor, used to identify which sensor it is in the system configuration."
            ::= { securityEntry 1000 }

--/* End of securityTable */

--/* Begin of sirenTable */
         sirenTable OBJECT-TYPE
            SYNTAX  SEQUENCE OF SirenEntry
            ACCESS  not-accessible
            STATUS  mandatory
            DESCRIPTION
            "This table contains the property and reading value for siren sensor."
            ::= { sensors 11 }

         sirenEntry OBJECT-TYPE
            SYNTAX  SirenEntry
            ACCESS  not-accessible
            STATUS  mandatory
            INDEX { sirenIndex }
            ::= { sirenTable 1 }

         SirenEntry ::= SEQUENCE {
            sirenIndex
               DisplayString,
            sirenDescription
               DisplayString,
            sirenStatus
               INTEGER,
            sirenGoOffline
               INTEGER,
            sirenControlMode
               INTEGER,
            sirenManualCycleTime
               INTEGER,
            sirenManualAction
               INTEGER,
            sirenPort
               INTEGER,
            sirenSubPort
               INTEGER,
            sirenOnDescription
               DisplayString,
            sirenOffDescription
               DisplayString,
            sirenOnColor 
               INTEGER,
            sirenOffColor 
               INTEGER,
            sirenAcknowledge
               INTEGER,
            sirenId
               INTEGER
         }

         sirenIndex OBJECT-TYPE
            SYNTAX  DisplayString
            ACCESS  read-only
            STATUS  mandatory
            DESCRIPTION
            "The Sensor Compound ID of this sensor, used to identify which sensor it is in the system configuration."
            ::= { sirenEntry 1 }

         sirenDescription OBJECT-TYPE
            SYNTAX  DisplayString
            ACCESS  read-write
            STATUS  mandatory
            DESCRIPTION
            "The user specified description of this sensor. Unless specified, the default value is used."
            ::= { sirenEntry 2 }

         sirenStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { sirenEntry 6 }

         sirenGoOffline OBJECT-TYPE
            SYNTAX  INTEGER {
               online(1),
               goOffline(2)
            }
            ACCESS  read-write
            STATUS  mandatory
            DESCRIPTION
            "Command to offline this sensor: use value '2' to set the sensor offline."
            ::= { sirenEntry 8 }

         sirenControlMode OBJECT-TYPE
            SYNTAX  INTEGER {
               manual-control(0),
               sensor-control(1),
               time-control(2),
               thermostat-control(3)
            }
            ACCESS  read-write
            STATUS  mandatory
            DESCRIPTION
            "The Control Mode for controlling this siren sensor with, it can be one of these: Manual, Notification, Time, Thermostat."
            ::= { sirenEntry 24 }

         sirenManualCycleTime OBJECT-TYPE
            SYNTAX  INTEGER (1..255)
            ACCESS  read-write
            STATUS  mandatory
            DESCRIPTION
            "The time in seconds that the relay will stay in a state, before changing to the next state in case the cycle action have been used."
            ::= { sirenEntry 25 }

         sirenManualAction OBJECT-TYPE
            SYNTAX  INTEGER {
               turn-On(0),
               turn-Off(1),
               cycle-On-Off-On(2),
               cycle-Off-On-Off(3)
            }
            ACCESS  read-write
            STATUS  mandatory
            DESCRIPTION
            "The manual control for the relay state: Off, On, Toggle Off-On, Toggle On-Off."
            ::= { sirenEntry 26 }

         sirenPort OBJECT-TYPE
            SYNTAX  INTEGER
            ACCESS  read-only
            STATUS  mandatory
            DESCRIPTION
            "The device's sensor port number, where this sensor is plugged in to."
            ::= { sirenEntry 35 }

         sirenSubPort OBJECT-TYPE
            SYNTAX  INTEGER
            ACCESS  read-only
            STATUS  mandatory
            DESCRIPTION
            "The logical port number of this sensor in the array, or in a set of sensors."
            ::= { sirenEntry 36 }

         sirenOnDescription OBJECT-TYPE
            SYNTAX  DisplayString
            ACCESS  read-write
            STATUS  mandatory
            DESCRIPTION
            "The user specified 'On' status description of this sensor. Unless specified, the default value is used."
            ::= { sirenEntry 52 }

         sirenOffDescription OBJECT-TYPE
            SYNTAX  DisplayString
            ACCESS  read-write
            STATUS  mandatory
            DESCRIPTION
            "The user specified 'Off' status description of this sensor. Unless specified, the default value is used."
            ::= { sirenEntry 53 }

         sirenOnColor OBJECT-TYPE
            SYNTAX  INTEGER
            ACCESS  read-write
            STATUS  mandatory
            DESCRIPTION
            "The user specified 'On' status field color. The unit will show this color on its web interface and in DCIM. Unless specified, the default value is used."
            ::= { sirenEntry 60 }

         sirenOffColor OBJECT-TYPE
            SYNTAX  INTEGER
            ACCESS  read-write
            STATUS  mandatory
            DESCRIPTION
            "The user specified 'Off' status field color. The unit will show this color on its web interface and in DCIM. Unless specified, the default value is used."
            ::= { sirenEntry 61 }

         sirenAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { sirenEntry 70 }

         sirenId OBJECT-TYPE
            SYNTAX  INTEGER
            ACCESS  read-only
            STATUS  mandatory
            DESCRIPTION
            "The Sensor ID of this sensor, used to identify which sensor it is in the system configuration."
            ::= { sirenEntry 1000 }

--/* End of sirenTable */

--/* Begin of relayTable */

         relayTable OBJECT-TYPE
            SYNTAX  SEQUENCE OF RelayEntry
            ACCESS  not-accessible
            STATUS  mandatory
            DESCRIPTION
            "This table contains the properties for each relay sensor"
            ::= { sensors 12 }

         relayEntry OBJECT-TYPE
            SYNTAX  RelayEntry
            ACCESS  not-accessible
            STATUS  mandatory
            INDEX { relayIndex }
            ::= { relayTable 1 }

         RelayEntry ::= SEQUENCE {
            relayIndex
               DisplayString,
            relayDescription
               DisplayString,
            relayType
               INTEGER,
            relayStatus
               INTEGER,
            relayGoOffline
               INTEGER,
            relayControlMode
               INTEGER,
            relayManualCycleTime
               INTEGER,
            relayManualAction
               INTEGER,
            relayPort
               INTEGER,
            relaySubPort
               INTEGER,
            relayOnDesc
               DisplayString,
            relayOffDesc
               DisplayString,
            relayOnColor
               INTEGER,
            relayOffColor
               INTEGER,
            relayAcknowledge
               INTEGER,
            relayId
               INTEGER
         }

         relayIndex OBJECT-TYPE
            SYNTAX  DisplayString
            ACCESS  read-only
            STATUS  mandatory
            DESCRIPTION
            "The Sensor Compound ID of this sensor, used to identify which sensor it is in the system configuration."
            ::= { relayEntry 1 }

         relayDescription OBJECT-TYPE
            SYNTAX  DisplayString
            ACCESS  read-write
            STATUS  mandatory
            DESCRIPTION
            "The user specified description of this sensor. Unless specified, the default value is used."
            ::= { relayEntry 2 }

         relayType OBJECT-TYPE
            SYNTAX  INTEGER {
               relay(13),
               xrelay(19)
            }
            ACCESS  read-only
            STATUS  mandatory
            DESCRIPTION
            "The type of the sensor; it represents the sensor's functionality. For the relay sensor, it has 2 sub-type: normal relay, and xrelay."
            ::= { relayEntry 3 }

         relayStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { relayEntry 6 }

         relayGoOffline OBJECT-TYPE
            SYNTAX  INTEGER {
               online(1),
               goOffline(2)
            }
            ACCESS  read-write
            STATUS  mandatory
            DESCRIPTION
            "Command to offline this sensor: use value '2' to set the sensor offline."
            ::= { relayEntry 8 }

         relayControlMode OBJECT-TYPE
            SYNTAX  INTEGER {
               manual-control(0),
               sensor-control(1),
               time-control(2),
               thermostat-control(3)
            }
            ACCESS  read-write
            STATUS  mandatory
            DESCRIPTION
            "The Control Mode for controlling this relay sensor with, it can be one of these: Manual, Notification, Time, Thermostat."
            ::= { relayEntry 24 }

         relayManualCycleTime OBJECT-TYPE
            SYNTAX  INTEGER (1..255)
            ACCESS  read-write
            STATUS  mandatory
            DESCRIPTION
            "The time in seconds that the relay will stay in a state, before changing to the next state in case the cycle action have been used."
            ::= { relayEntry 25 }

         relayManualAction OBJECT-TYPE
            SYNTAX  INTEGER {
               turn-On(0),
               turn-Off(1),
               cycle-On-Off-On(2),
               cycle-Off-On-Off(3)
            }
            ACCESS  read-write
            STATUS  mandatory
            DESCRIPTION
            "The manual control for the relay state: Off, On, Toggle Off-On, Toggle On-Off."
            ::= { relayEntry 26 }

         relayPort OBJECT-TYPE
            SYNTAX  INTEGER
            ACCESS  read-only
            STATUS  mandatory
            DESCRIPTION
            "The device's sensor port number, where this sensor is plugged in to."
            ::= { relayEntry 35 }

         relaySubPort OBJECT-TYPE
            SYNTAX  INTEGER
            ACCESS  read-only
            STATUS  mandatory
            DESCRIPTION
            "The logical port number of this sensor on the array of a relay (xelay) sensor. For example x.1, x.2, x.3 ..."
            ::= { relayEntry 36 }

         relayOnDesc OBJECT-TYPE
            SYNTAX  DisplayString
            ACCESS  read-write
            STATUS  mandatory
            DESCRIPTION
            "The user specified 'On' status description of this sensor. Unless specified, the default value is used."
            ::= { relayEntry 52 }

         relayOffDesc OBJECT-TYPE
            SYNTAX  DisplayString
            ACCESS  read-write
            STATUS  mandatory
            DESCRIPTION
            "The user specified 'Off' Description of this sensor. Unless specified, the default value is used."
            ::= { relayEntry 53 }

         relayOnColor OBJECT-TYPE
            SYNTAX  INTEGER
            ACCESS  read-write
            STATUS  mandatory
            DESCRIPTION
            "The user specified 'On' status field color. The unit will show this color on its web interface and in DCIM. Unless specified, the default value is used."
            ::= { relayEntry 60 }

         relayOffColor OBJECT-TYPE
            SYNTAX  INTEGER
            ACCESS  read-write
            STATUS  mandatory
            DESCRIPTION
            "The user specified 'Off' status field color. The unit will show this color on its web interface and in DCIM. Unless specified, the default value is used."
            ::= { relayEntry 61 }

         relayAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { relayEntry 70 }

         relayId OBJECT-TYPE
            SYNTAX  INTEGER
            ACCESS  read-only
            STATUS  mandatory
            DESCRIPTION
            "The Sensor ID of this sensor, used to identify which sensor it is in the system configuration."
            ::= { relayEntry 1000 }

--/* End of relayTable */

--/* Begin of acVoltageTable */
         acVoltageTable OBJECT-TYPE
            SYNTAX  SEQUENCE OF AcVoltageEntry
            ACCESS  not-accessible
            STATUS  mandatory
            DESCRIPTION
            "This table contains the properties for each AC voltage sensor"
            ::= { sensors 13 }

         acVoltageEntry OBJECT-TYPE
            SYNTAX  AcVoltageEntry
            ACCESS  not-accessible
            STATUS  mandatory
            INDEX { acVoltageIndex }
            ::= { acVoltageTable 1 }

         AcVoltageEntry ::= SEQUENCE {
            acVoltageIndex
               DisplayString,
            acVoltageDescription
               DisplayString,
            acVoltageStatus
               INTEGER,
            acVoltageGoOffline
               INTEGER,
            acVoltagePort
               INTEGER,
            acVoltageSubPort
               INTEGER,
            acVoltageCriticalDescription
               DisplayString,
            acVoltageNormalDescription
               DisplayString,
            acVoltageCriticalColor 
               INTEGER,
            acVoltageNormalColor 
               INTEGER,
            acVoltageAcknowledge
               INTEGER,
            acVoltageId
               INTEGER
         }

         acVoltageIndex OBJECT-TYPE
            SYNTAX  DisplayString
            ACCESS  read-only
            STATUS  mandatory
            DESCRIPTION
            "The Sensor Compound ID of this sensor, used to identify which sensor it is in the system configuration."
            ::= { acVoltageEntry 1 }

         acVoltageDescription OBJECT-TYPE
            SYNTAX  DisplayString
            ACCESS  read-write
            STATUS  mandatory
            DESCRIPTION
            "The user specified description of this sensor. Unless specified, the default value is used."
            ::= { acVoltageEntry 2 }

         acVoltageStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { acVoltageEntry 6 }

         acVoltageGoOffline OBJECT-TYPE
            SYNTAX  INTEGER {
               online(1),
               goOffline(2)
            }
            ACCESS  read-write
            STATUS  mandatory
            DESCRIPTION
            "Command to offline this sensor: use value '2' to set the sensor offline."
            ::= { acVoltageEntry 8 }

         acVoltagePort OBJECT-TYPE
            SYNTAX  INTEGER
            ACCESS  read-only
            STATUS  mandatory
            DESCRIPTION
            "The device's sensor port number, where this sensor is plugged in to."
            ::= { acVoltageEntry 35 }

         acVoltageSubPort OBJECT-TYPE
            SYNTAX  INTEGER
            ACCESS  read-only
            STATUS  mandatory
            DESCRIPTION
            "The logical port number of this sensor on the array of sensors."
            ::= { acVoltageEntry 36 }

         acVoltageCriticalDescription OBJECT-TYPE
            SYNTAX  DisplayString
            ACCESS  read-write
            STATUS  mandatory
            DESCRIPTION
            "The user specified 'Critical' status description of this sensor. Unless specified, the default value is used."
            ::= { acVoltageEntry 46 }

         acVoltageNormalDescription OBJECT-TYPE
            SYNTAX  DisplayString
            ACCESS  read-write
            STATUS  mandatory
            DESCRIPTION
            "The user specified 'Normal' status description of this sensor. Unless specified, the default value is used."
            ::= { acVoltageEntry 48 }

         acVoltageCriticalColor OBJECT-TYPE
            SYNTAX  INTEGER
            ACCESS  read-write
            STATUS  mandatory
            DESCRIPTION
            "The user specified 'Critical' status field color. The unit will show this color on its web interface and in DCIM. Unless specified, the default value is used."
            ::= { acVoltageEntry 54 }

         acVoltageNormalColor OBJECT-TYPE
            SYNTAX  INTEGER
            ACCESS  read-write
            STATUS  mandatory
            DESCRIPTION
            "The user specified 'Normal' status field color. The unit will show this color on its web interface and in DCIM. Unless specified, the default value is used."
            ::= { acVoltageEntry 56 }

         acVoltageAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { acVoltageEntry 70 }

         acVoltageId OBJECT-TYPE
            SYNTAX  INTEGER
            ACCESS  read-only
            STATUS  mandatory
            DESCRIPTION
            "The Sensor ID of this sensor, used to identify which sensor it is in the system configuration."
            ::= { acVoltageEntry 1000 }

--/* End of acVoltageTable */

--/* Begin of smokeTable */
         smokeTable OBJECT-TYPE
            SYNTAX  SEQUENCE OF SmokeEntry
            ACCESS  not-accessible
            STATUS  mandatory
            DESCRIPTION
            "This table contains the properties for each smoke sensor"
            ::= { sensors 14 }

         smokeEntry OBJECT-TYPE
            SYNTAX  SmokeEntry
            ACCESS  not-accessible
            STATUS  mandatory
            INDEX { smokeIndex }
            ::= { smokeTable 1 }

         SmokeEntry ::= SEQUENCE {
            smokeIndex
               DisplayString,
            smokeDescription
               DisplayString,
            smokeStatus
               INTEGER,
            smokeGoOffline
               INTEGER,
            smokePort
               INTEGER,
            smokeSubPort
               INTEGER,
            smokeCriticalDescription
               DisplayString,
            smokeNormalDescription
               DisplayString,
            smokeCriticalColor
               INTEGER,
            smokeNormalColor 
               INTEGER,
            smokeAcknowledge
               INTEGER,
            smokeId
               INTEGER
         }

         smokeIndex OBJECT-TYPE
            SYNTAX  DisplayString
            ACCESS  read-only
            STATUS  mandatory
            DESCRIPTION
            "The Sensor Compound ID of this sensor, used to identify which sensor it is in the system configuration."
            ::= { smokeEntry 1 }

         smokeDescription OBJECT-TYPE
            SYNTAX  DisplayString
            ACCESS  read-write
            STATUS  mandatory
            DESCRIPTION
            "The user specified description of this sensor. Unless specified, the default value is used."
            ::= { smokeEntry 2 }

         smokeStatus OBJECT-TYPE
            SYNTAX  INTEGER {
               noStatus(1),
               normal(2),
               highCritical(4),
               lowCritical(6),
               sensorError(7),
               relayOn(8),
               relayOff(9)
            }
            ACCESS  read-only
            STATUS  mandatory
            DESCRIPTION
            "The current status of this sensor."
            ::= { smokeEntry 6 }

         smokeGoOffline OBJECT-TYPE
            SYNTAX  INTEGER {
               online(1),
               goOffline(2)
            }
            ACCESS  read-write
            STATUS  mandatory
            DESCRIPTION
            "Command to offline this sensor: use value '2' to set the sensor offline."
            ::= { smokeEntry 8 }

         smokePort OBJECT-TYPE
            SYNTAX  INTEGER
            ACCESS  read-only
            STATUS  mandatory
            DESCRIPTION
            "The device's sensor port number, where this sensor is plugged in to."
            ::= { smokeEntry 35 }

         smokeSubPort OBJECT-TYPE
            SYNTAX  INTEGER
            ACCESS  read-only
            STATUS  mandatory
            DESCRIPTION
            "The logical port number of this sensor in the array, or in a set of sensors."
            ::= { smokeEntry 36 }

         smokeCriticalDescription OBJECT-TYPE
            SYNTAX  DisplayString
            ACCESS  read-write
            STATUS  mandatory
            DESCRIPTION
            "The user specified 'Critical' status description of this sensor. Unless specified, the default value is used."
            ::= { smokeEntry 46 }

         smokeNormalDescription OBJECT-TYPE
            SYNTAX  DisplayString
            ACCESS  read-write
            STATUS  mandatory
            DESCRIPTION
            "The user specified 'Normal' status description of this sensor. Unless specified, the default value is used."
            ::= { smokeEntry 48 }
     
         smokeCriticalColor OBJECT-TYPE
            SYNTAX  INTEGER
            ACCESS  read-write
            STATUS  mandatory
            DESCRIPTION
            "The user specified 'Critical' status field color. The unit will show this color on its web interface and in DCIM. Unless specified, the default value is used."
            ::= { smokeEntry 54 }

         smokeNormalColor OBJECT-TYPE
            SYNTAX  INTEGER
            ACCESS  read-write
            STATUS  mandatory
            DESCRIPTION
            "The user specified 'Normal' status field color. The unit will show this color on its web interface and in DCIM. Unless specified, the default value is used."
            ::= { smokeEntry 56 }

         smokeAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { smokeEntry 70 }

         smokeId OBJECT-TYPE
            SYNTAX  INTEGER
            ACCESS  read-only
            STATUS  mandatory
            DESCRIPTION
            "The Sensor ID of this sensor, used to identify which sensor it is in the system configuration."
            ::= { smokeEntry 1000 }

--/* End of smokeTable */

--/* Begin of waterRopeTable */
         waterRopeTable OBJECT-TYPE
            SYNTAX  SEQUENCE OF WaterRopeEntry
            ACCESS  not-accessible
            STATUS  mandatory
            DESCRIPTION
            "This table contains the properties for each water rope sensor"
            ::= { sensors 21 }

         waterRopeEntry OBJECT-TYPE
            SYNTAX  WaterRopeEntry
            ACCESS  not-accessible
            STATUS  mandatory
            INDEX { waterRopeIndex }
            ::= { waterRopeTable 1 }

         WaterRopeEntry ::= SEQUENCE {
            waterRopeIndex
               DisplayString,
            waterRopeDescription
               DisplayString,
            waterRopeLeakLocation
               INTEGER,
            waterRopeUnit
               DisplayString,
            waterRopeStatus
               INTEGER,
            waterRopeGoOffline
               INTEGER,
            waterRopeRaw
               INTEGER,
            waterRopeCriticalDescription
               DisplayString,
            waterRopeNormalDescription
               DisplayString,
            waterRopeSensorErrorDescription
               DisplayString,
            waterRopeCriticalColor
               INTEGER,
            waterRopeNormalColor
               INTEGER,
            waterRopeSensorErrorColor
               INTEGER,
            waterRopeAcknowledge
               INTEGER,
            waterRopeLength
               INTEGER,
            waterRopeImpedance
               INTEGER,
            waterRopeType
               INTEGER,
            waterRopeId
               INTEGER
         }

         waterRopeIndex OBJECT-TYPE
            SYNTAX  DisplayString
            ACCESS  read-only
            STATUS  mandatory
            DESCRIPTION
            "The Sensor Compound ID of this sensor, used to identify which sensor it is in the system configuration."
            ::= { waterRopeEntry 1 }

         waterRopeDescription OBJECT-TYPE
            SYNTAX  DisplayString
            ACCESS  read-write
            STATUS  mandatory
            DESCRIPTION
            "The user specified description of this sensor. Unless specified, the default value is used."
            ::= { waterRopeEntry 2 }

         waterRopeLeakLocation OBJECT-TYPE
            SYNTAX INTEGER
            ACCESS read-only
            STATUS mandatory
            DESCRIPTION
            "Location of leakage from the begining of water rope sensor."
            ::= { waterRopeEntry 4 }

         waterRopeUnit OBJECT-TYPE
            SYNTAX  DisplayString
            ACCESS  read-write
            STATUS  mandatory
            DESCRIPTION
            "The sensor's value unit string, in what the sensor's value is read in."
            ::= { waterRopeEntry 5 }

         waterRopeStatus OBJECT-TYPE
            SYNTAX  INTEGER {
               noStatus(1),
               normal(2),
               highCritical(4),
               sensorError(7)
            }
            ACCESS  read-only
            STATUS  mandatory
            DESCRIPTION
            "The current status of this sensor."
            ::= { waterRopeEntry 6 }

         waterRopeGoOffline OBJECT-TYPE
            SYNTAX  INTEGER {
               online(1),
               goOffline(2)
            }
            ACCESS  read-write
            STATUS  mandatory
            DESCRIPTION
            "Command to offline this sensor: use value '2' to set the sensor offline."
            ::= { waterRopeEntry 8 }

         waterRopeRaw OBJECT-TYPE
            SYNTAX INTEGER
            ACCESS read-only
            STATUS mandatory
            DESCRIPTION
            "The sensor's unformatted (raw) value that is being read directly from sensor, before it is converted to the preferred value."
            ::= { waterRopeEntry 20 }

         waterRopeCriticalDescription OBJECT-TYPE
            SYNTAX  DisplayString
            ACCESS  read-write
            STATUS  mandatory
            DESCRIPTION
            "The user specified 'Critical' status description of this sensor. Unless specified, the default value is used."
            ::= { waterRopeEntry 46 }

         waterRopeNormalDescription OBJECT-TYPE
            SYNTAX  DisplayString
            ACCESS  read-write
            STATUS  mandatory
            DESCRIPTION
            "The user specified 'Normal' status description of this sensor. Unless specified, the default value is used."
            ::= { waterRopeEntry 48 }

         waterRopeSensorErrorDescription OBJECT-TYPE
            SYNTAX  DisplayString
            ACCESS  read-write
            STATUS  mandatory
            DESCRIPTION
            "The user specified 'Sensor Error' status description of this sensor. Unless specified, the default value is used."
            ::= { waterRopeEntry 51 }

         waterRopeCriticalColor OBJECT-TYPE
            SYNTAX  INTEGER
            ACCESS  read-write
            STATUS  mandatory
            DESCRIPTION
            "The user specified 'Critical' status field color. The unit will show this color on its web interface and in DCIM. Unless specified, the default value is used."
            ::= { waterRopeEntry 54 }

         waterRopeNormalColor OBJECT-TYPE
            SYNTAX  INTEGER
            ACCESS  read-write
            STATUS  mandatory
            DESCRIPTION
            "The user specified 'Normal' status field color. The unit will show this color on its web interface and in DCIM. Unless specified, the default value is used."
            ::= { waterRopeEntry 56 }

         waterRopeSensorErrorColor OBJECT-TYPE
            SYNTAX  INTEGER
            ACCESS  read-write
            STATUS  mandatory
            DESCRIPTION
            "The user specified 'Sensor Error' status field color. The unit will show this color on its web interface and in DCIM. Unless specified, the default value is used."
            ::=  { waterRopeEntry  59 }
               
         waterRopeAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { waterRopeEntry 70 }

         waterRopeLength OBJECT-TYPE
            SYNTAX INTEGER
            ACCESS read-only
            STATUS mandatory
            DESCRIPTION
            "Length of water rope sensor."
            ::= { waterRopeEntry 100 }

         waterRopeImpedance OBJECT-TYPE
            SYNTAX INTEGER
            ACCESS read-write
            STATUS mandatory
            DESCRIPTION
            "Sensing wire impedance per meter value times 100"
            ::= { waterRopeEntry 101 }

         waterRopeType OBJECT-TYPE
            SYNTAX  INTEGER {
               custom(0),
               water(1),
               fuel(2)
            }
            ACCESS read-write
            STATUS mandatory
            DESCRIPTION
            "The type of the sensor; it represents the sensor's functionality."
            ::= { waterRopeEntry 103 }
            
         waterRopeId OBJECT-TYPE
            SYNTAX  INTEGER
            ACCESS  read-only
            STATUS  mandatory
            DESCRIPTION
            "The Sensor ID of this sensor, used to identify which sensor it is in the system configuration."
            ::= { waterRopeEntry 1000 }

--/* End of waterRopeTable */

--/* Begin of powerTable */
         powerTable OBJECT-TYPE
            SYNTAX  SEQUENCE OF PowerEntry
            ACCESS  not-accessible
            STATUS  mandatory
            DESCRIPTION
            "This table contains the properties for each power sensor"
            ::= { sensors 22 }

         powerEntry OBJECT-TYPE
            SYNTAX  PowerEntry
            ACCESS  not-accessible
            STATUS  mandatory
            INDEX { powerIndex }
            ::= { powerTable 1 }

         PowerEntry ::= SEQUENCE {
            powerIndex
               DisplayString,
            powerDescription
               DisplayString,
            powerValue
               INTEGER,
            powerUnit
               DisplayString,
            powerStatus
               INTEGER,
            powerGoOffline
               INTEGER,
            powerLowCritical
               INTEGER,
            powerLowWarning
               INTEGER,
            powerHighWarning
               INTEGER,
            powerHighCritical
               INTEGER,
            powerRearm
               INTEGER,
            powerDelayError
               INTEGER,
            powerDelayNormal
               INTEGER,
            powerDelayLowCritical
               INTEGER,
            powerDelayLowWarning
               INTEGER,
            powerDelayHighWarning
               INTEGER,
            powerDelayHighCritical
               INTEGER,
            powerRaw
               INTEGER,
            powerPort
               INTEGER,
            powerSubPort
               INTEGER,
            powerDisplayStyle
               INTEGER,
            powerHighCriticalDescription
               DisplayString,
            powerLowCriticalDescription
               DisplayString,
            powerNormalDescription
               DisplayString,
            powerLowWarningDescription
               DisplayString,
            powerHighWarningDescription
               DisplayString,
            powerSensorErrorDescription
               DisplayString,
            powerHighCriticalColor
               INTEGER,
            powerLowCriticalColor
               INTEGER,
            powerNormalColor
               INTEGER,
            powerLowWarningColor
               INTEGER,   
            powerHighWarningColor
               INTEGER,
            powerSensorErrorColor
               INTEGER,
            powerValueFormatString
               DisplayString,
            powerValueFormatFloat
               Opaque,
            powerAcknowledge
               INTEGER,
            powerId
               INTEGER
         }

         powerIndex OBJECT-TYPE
            SYNTAX  DisplayString
            ACCESS  read-only
            STATUS  mandatory
            DESCRIPTION
            "The Sensor Compound ID of this sensor, used to identify which sensor it is in the system configuration."
            ::= { powerEntry 1 }

         powerDescription OBJECT-TYPE
            SYNTAX  DisplayString
            ACCESS  read-write
            STATUS  mandatory
            DESCRIPTION
            "The user specified description of this sensor. Unless specified, the default value is used."
            ::= { powerEntry 2 }

         powerValue OBJECT-TYPE
            SYNTAX  INTEGER
            ACCESS  read-only
            STATUS  mandatory
            DESCRIPTION
            "The value in numerical reading."
            ::= { powerEntry 4 }

         powerUnit OBJECT-TYPE
            SYNTAX  DisplayString
            ACCESS  read-only
            STATUS  mandatory
            DESCRIPTION
            "The sensor's value unit string, in what the sensor's value is read in."
            ::= { powerEntry 5 }

         powerStatus OBJECT-TYPE
            SYNTAX  INTEGER {
               noStatus(1),
               normal(2),
               highCritical(4),
               lowCritical(6),
               sensorError(7)
            }
            ACCESS  read-only
            STATUS  mandatory
            DESCRIPTION
            "The current status of this sensor."
            ::= { powerEntry 6 }

         powerGoOffline OBJECT-TYPE
            SYNTAX  INTEGER {
               online(1),
               goOffline(2)
            }
            ACCESS  read-write
            STATUS  mandatory
            DESCRIPTION
            "Command to offline this sensor: use value '2' to set the sensor offline."
            ::= { powerEntry 8 }

         powerLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { powerEntry 9 }

         powerLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { powerEntry 10 }

         powerHighWarning OBJECT-TYPE
            SYNTAX  INTEGER
            ACCESS  read-write
            STATUS  mandatory
            DESCRIPTION
            "The user specified 'High Warning' value of this sensor. The unit will check the current reading against this value, and send an alert if it's configured. Unless specified, the default value is used."
            ::= { powerEntry 11 }

         powerHighCritical OBJECT-TYPE
            SYNTAX  INTEGER
            ACCESS  read-write
            STATUS  mandatory
            DESCRIPTION
            "The user specified 'High Critical' value of this sensor. The unit will check the current reading against this value, and send an alert if it's configured. Unless specified, the default value is used."
            ::= { powerEntry 12 }

         powerRearm OBJECT-TYPE
            SYNTAX  INTEGER
            ACCESS  read-write
            STATUS  mandatory
            DESCRIPTION
            "This value tells how many value the sensor has to reach beyond the threshold value, before changing to a new status. Useful to prevent the quick fluctuation of readings."
            ::= { powerEntry 13 }

         powerDelayError OBJECT-TYPE
            SYNTAX  INTEGER (0..65534)
            ACCESS  read-write
            STATUS  mandatory
            DESCRIPTION
            "The time in seconds (continuous time) that the sensor has to be in 'Error' status before its status is changed."
            ::= { powerEntry 14 }

         powerDelayNormal OBJECT-TYPE
            SYNTAX  INTEGER (0..65534)
            ACCESS  read-write
            STATUS  mandatory
            DESCRIPTION
            "The time in seconds (continuous time) that the sensor has to be in 'Normal' status before its status is changed."
            ::= { powerEntry 15 }

         powerDelayLowCritical OBJECT-TYPE
            SYNTAX INTEGER (0..65535)
            ACCESS read-write
            STATUS mandatory
            DESCRIPTION
            "The time in seconds (continuous time) that the sensor has to be in 'Low Critical' status before its status is changed."
            ::= { powerEntry 16 }

         powerDelayLowWarning OBJECT-TYPE
            SYNTAX INTEGER (0..65535)
            ACCESS read-write
            STATUS mandatory
            DESCRIPTION
            "The time in seconds (continuous time) that the sensor has to be in 'Low Warning' status before its status is changed."
            ::= { powerEntry 17 }

         powerDelayHighWarning OBJECT-TYPE
            SYNTAX INTEGER (0..65535)
            ACCESS read-write
            STATUS mandatory
            DESCRIPTION
            "The time in seconds (continuous time) that the sensor has to be in 'High Warning' status before its status is changed."
            ::= { powerEntry 18 }

         powerDelayHighCritical OBJECT-TYPE
            SYNTAX INTEGER (0..65535)
            ACCESS read-write
            STATUS mandatory
            DESCRIPTION
            "The time in seconds (continuous time) that the sensor has to be in 'High Critical' status before its status is changed."
            ::= { powerEntry 19 }

         powerRaw OBJECT-TYPE
            SYNTAX  INTEGER
            ACCESS  read-only
            STATUS  mandatory
            DESCRIPTION
            "The sensor's unformatted (raw) value that is being read directly from sensor, before it is converted to the preferred value."
            ::= { powerEntry 20 }

         powerPort OBJECT-TYPE
            SYNTAX  INTEGER (0..65534)
            ACCESS  read-only
            STATUS  mandatory
            DESCRIPTION
            "The device's sensor port number, where this sensor is plugged in to."
            ::= { powerEntry 35 }

         powerSubPort OBJECT-TYPE
            SYNTAX  INTEGER (0..65534)
            ACCESS  read-only
            STATUS  mandatory
            DESCRIPTION
            "The logical port number of this sensor in the array, or in a set of sensors."
            ::= { powerEntry 36 }

         powerDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { powerEntry 45 } 

         powerHighCriticalDescription OBJECT-TYPE
            SYNTAX  DisplayString
            ACCESS  read-write
            STATUS  mandatory
            DESCRIPTION
            "The user specified 'High Critical' status description of this sensor. Unless specified, the default value is used."
            ::= { powerEntry 46 }

         powerLowCriticalDescription OBJECT-TYPE
            SYNTAX  DisplayString
            ACCESS  read-write
            STATUS  mandatory
            DESCRIPTION
            "The user specified 'Low Critical' status description of this sensor. Unless specified, the default value is used."
            ::= { powerEntry 47 }

         powerNormalDescription OBJECT-TYPE
            SYNTAX  DisplayString
            ACCESS  read-write
            STATUS  mandatory
            DESCRIPTION
            "The user specified 'Normal' status description of this sensor. Unless specified, the default value is used."
            ::= { powerEntry 48 }

         powerLowWarningDescription OBJECT-TYPE
            SYNTAX  DisplayString
            ACCESS  read-write
            STATUS  mandatory
            DESCRIPTION
            "The user specified 'Low Warning' status description of this sensor. Unless specified, the default value is used."
            ::= { powerEntry 49 }

         powerHighWarningDescription OBJECT-TYPE
            SYNTAX  DisplayString
            ACCESS  read-write
            STATUS  mandatory
            DESCRIPTION
            "The user specified 'High Warning' status description of this sensor. Unless specified, the default value is used."
            ::= { powerEntry 50 }

         powerSensorErrorDescription OBJECT-TYPE
            SYNTAX  DisplayString
            ACCESS  read-write
            STATUS  mandatory
            DESCRIPTION
            "The user specified 'Sensor Error' status description of this sensor. Unless specified, the default value is used."
            ::= { powerEntry 51 }

         powerHighCriticalColor OBJECT-TYPE
            SYNTAX  INTEGER
            ACCESS  read-write
            STATUS  mandatory
            DESCRIPTION
            "The user specified 'High Critical' status field color. The unit will show this color on its web interface and in DCIM. Unless specified, the default value is used."
            ::= { powerEntry 54 }

         powerLowCriticalColor OBJECT-TYPE
            SYNTAX  INTEGER
            ACCESS  read-write
            STATUS  mandatory
            DESCRIPTION
            "The user specified 'Low Critical' status field color. The unit will show this color on its web interface and in DCIM. Unless specified, the default value is used."
            ::= { powerEntry 55 }

         powerNormalColor OBJECT-TYPE
            SYNTAX  INTEGER
            ACCESS  read-write
            STATUS  mandatory
            DESCRIPTION
            "The user specified 'Normal' status field color. The unit will show this color on its web interface and in DCIM. Unless specified, the default value is used."
            ::= { powerEntry 56 }

         powerLowWarningColor OBJECT-TYPE
            SYNTAX  INTEGER
            ACCESS  read-write
            STATUS  mandatory
            DESCRIPTION
            "The user specified 'Low Warning' status field color. The unit will show this color on its web interface and in DCIM. Unless specified, the default value is used."
            ::= { powerEntry 57 }

         powerHighWarningColor OBJECT-TYPE
            SYNTAX  INTEGER
            ACCESS  read-write
            STATUS  mandatory
            DESCRIPTION
            "The user specified 'High Warning' status field color. The unit will show this color on its web interface and in DCIM. Unless specified, the default value is used."
            ::= { powerEntry 58 }
            
         powerSensorErrorColor OBJECT-TYPE
            SYNTAX  INTEGER
            ACCESS  read-write
            STATUS  mandatory
            DESCRIPTION
            "The user specified 'Sensor Error' status field color. The unit will show this color on its web interface and in DCIM. Unless specified, the default value is used."
            ::= { powerEntry 59 }

         powerValueFormatString OBJECT-TYPE
            SYNTAX  DisplayString
            ACCESS  read-only
            STATUS  mandatory
            DESCRIPTION
            "The string-based reading value in this sensor."
            ::= { powerEntry 66 }

         powerValueFormatFloat OBJECT-TYPE
            SYNTAX  Opaque (SIZE(4))
            ACCESS  read-only
            STATUS  mandatory
            DESCRIPTION
            "The floating-point IEEE Standard 754 reading value in this sensor."
            ::= { powerEntry 67 }

         powerAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { powerEntry 70 }

         powerId OBJECT-TYPE
            SYNTAX  INTEGER
            ACCESS  read-only
            STATUS  mandatory
            DESCRIPTION
            "The Sensor ID of this sensor, used to identify which sensor it is in the system configuration."
            ::= { powerEntry 1000 }

--/* End of powerTable */

--/* Begin of fuelTable */
         fuelTable OBJECT-TYPE
            SYNTAX  SEQUENCE OF FuelEntry
            ACCESS  not-accessible
            STATUS  mandatory
            DESCRIPTION
            "This table contains the properties for each fuel sensor"
            ::= { sensors 24 }

         fuelEntry OBJECT-TYPE
            SYNTAX  FuelEntry
            ACCESS  not-accessible
            STATUS  mandatory
            INDEX { fuelIndex }
            ::= { fuelTable 1 }

         FuelEntry ::= SEQUENCE {
            fuelIndex
               DisplayString,
            fuelDescription
               DisplayString,
            fuelValue
               INTEGER,
            fuelUnit
               DisplayString,
            fuelStatus
               INTEGER,
            fuelGoOffline
               INTEGER,
            fuelLowCritical
               INTEGER,
            fuelLowWarning
               INTEGER,
            fuelHighWarning
               INTEGER,
            fuelHighCritical
               INTEGER,
            fuelRearm
               INTEGER,
            fuelDelayError
               INTEGER,
            fuelDelayNormal
               INTEGER,
            fuelDelayLowCritical
               INTEGER,
            fuelDelayLowWarning
               INTEGER,
            fuelDelayHighWarning
               INTEGER,
            fuelDelayHighCritical
               INTEGER,
            fuelRaw
               INTEGER,
            fuelAmountMaxValue
               INTEGER,
            fuelAmountBaseValue
               INTEGER,
            fuelDisplayStyle
               INTEGER,
            fuelHighCriticalDescription
               DisplayString,
            fuelLowCriticalDescription
               DisplayString,
            fuelNormalDescription
               DisplayString,
            fuelLowWarningDescription
               DisplayString,
            fuelHighWarningDescription
               DisplayString,
            fuelSensorErrorDescription
               DisplayString,
            fuelHighCriticalColor
               INTEGER,
            fuelLowCriticalColor
               INTEGER,
            fuelNormalColor
               INTEGER,
            fuelLowWarningColor
               INTEGER,
            fuelHighWarningColor
               INTEGER,
            fuelSensorErrorColor
               INTEGER,
            fuelAcknowledge
               INTEGER,
            fuelId
               INTEGER
         }

         fuelIndex OBJECT-TYPE
            SYNTAX  DisplayString
            ACCESS  read-only
            STATUS  mandatory
            DESCRIPTION
            "The Sensor Compound ID of this sensor, used to identify which sensor it is in the system configuration."
            ::= { fuelEntry 1 }

         fuelDescription OBJECT-TYPE
            SYNTAX  DisplayString
            ACCESS  read-write
            STATUS  mandatory
            DESCRIPTION
            "The user specified description of this sensor. Unless specified, the default value is used."
            ::= { fuelEntry 2 }

         fuelValue OBJECT-TYPE
            SYNTAX  INTEGER
            ACCESS  read-only
            STATUS  mandatory
            DESCRIPTION
            "The reading value in this sensor"
            ::= { fuelEntry 4 }

         fuelUnit OBJECT-TYPE
            SYNTAX  DisplayString
            ACCESS  read-write
            STATUS  mandatory
            DESCRIPTION
            "The sensor's value unit string, in what the sensor's value is read in."
            ::= { fuelEntry 5 }

         fuelStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { fuelEntry 6 }

         fuelGoOffline OBJECT-TYPE
            SYNTAX  INTEGER {
               online(1),
               goOffline(2)
            }
            ACCESS  read-write
            STATUS  mandatory
            DESCRIPTION
            "Command to offline this sensor: use value '2' to set the sensor offline."
            ::= { fuelEntry 8 }

         fuelLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { fuelEntry 9 }

         fuelLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { fuelEntry 10 }

         fuelHighWarning OBJECT-TYPE
            SYNTAX  INTEGER
            ACCESS  read-write
            STATUS  mandatory
            DESCRIPTION
            "The user specified 'High Warning' value of this sensor. The unit will check the current reading against this value, and send an alert if it's configured. Unless specified, the default value is used."
            ::= { fuelEntry 11 }

         fuelHighCritical OBJECT-TYPE
            SYNTAX  INTEGER
            ACCESS  read-write
            STATUS  mandatory
            DESCRIPTION
            "The user specified 'High Critical' value of this sensor. The unit will check the current reading against this value, and send an alert if it's configured. Unless specified, the default value is used."
            ::= { fuelEntry 12 }

         fuelRearm OBJECT-TYPE
            SYNTAX  INTEGER
            ACCESS  read-write
            STATUS  mandatory
            DESCRIPTION
            "This value tells how many value the sensor has to reach beyond the threshold value, before changing to a new status. Useful to prevent the quick fluctuation of readings."
            ::= { fuelEntry 13 }

         fuelDelayError OBJECT-TYPE
            SYNTAX  INTEGER
            ACCESS  read-write
            STATUS  mandatory
            DESCRIPTION
            "The time in seconds (continuous time) that the sensor has to be in 'Error' status before its status is changed."
            ::= { fuelEntry 14 }

         fuelDelayNormal OBJECT-TYPE
            SYNTAX  INTEGER
            ACCESS  read-write
            STATUS  mandatory
            DESCRIPTION
            "The time in seconds (continuous time) that the sensor has to be in 'Normal' status before its status is changed."
            ::= { fuelEntry 15 }

         fuelDelayLowCritical OBJECT-TYPE
            SYNTAX INTEGER
            ACCESS read-write
            STATUS mandatory
            DESCRIPTION
            "The time in seconds (continuous time) that the sensor has to be in 'Low Critical' status before its status is changed."
            ::= { fuelEntry 16 }
            
         fuelDelayLowWarning OBJECT-TYPE
            SYNTAX INTEGER
            ACCESS read-write
            STATUS mandatory
            DESCRIPTION
            "The time in seconds (continuous time) that the sensor has to be in 'Low Warning' status before its status is changed."
            ::= { fuelEntry 17 }

         fuelDelayHighWarning OBJECT-TYPE
            SYNTAX INTEGER
            ACCESS read-write
            STATUS mandatory
            DESCRIPTION
            "The time in seconds (continuous time) that the sensor has to be in 'High Warning' status before its status is changed."
            ::= { fuelEntry 18 }

         fuelDelayHighCritical OBJECT-TYPE
            SYNTAX INTEGER
            ACCESS read-write
            STATUS mandatory
            DESCRIPTION
            "The time in seconds (continuous time) that the sensor has to be in 'High Critical' status before its status is changed."
            ::= { fuelEntry 19 }

         fuelRaw OBJECT-TYPE
            SYNTAX  INTEGER 
            ACCESS  read-only
            STATUS  mandatory
            DESCRIPTION
            "The sensor's unformatted (raw) value that is being read directly from sensor, before it is converted to the preferred value."
            ::= { fuelEntry 20 }

         fuelAmountMaxValue OBJECT-TYPE
            SYNTAX  INTEGER
            ACCESS  read-write
            STATUS  mandatory
            DESCRIPTION
            "The maximum scale of value conversion."
            ::= { fuelEntry 33 }

         fuelAmountBaseValue OBJECT-TYPE
            SYNTAX  INTEGER
            ACCESS  read-write
            STATUS  mandatory
            DESCRIPTION
            "The base scale of value conversion."
            ::= { fuelEntry 34 }

         fuelDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { fuelEntry 45 }

         fuelHighCriticalDescription OBJECT-TYPE
            SYNTAX  DisplayString
            ACCESS  read-write
            STATUS  mandatory
            DESCRIPTION
            "The user specified 'High Critical' status description of this sensor. Unless specified, the default value is used."
            ::= { fuelEntry 46 }

         fuelLowCriticalDescription OBJECT-TYPE
            SYNTAX  DisplayString
            ACCESS  read-write
            STATUS  mandatory
            DESCRIPTION
            "The user specified 'Low Critical' status description of this sensor. Unless specified, the default value is used."
            ::= { fuelEntry 47 }

         fuelNormalDescription OBJECT-TYPE
            SYNTAX  DisplayString
            ACCESS  read-write
            STATUS  mandatory
            DESCRIPTION
            "The user specified 'Normal' status description of this sensor. Unless specified, the default value is used."
            ::= { fuelEntry 48 }
            
         fuelLowWarningDescription OBJECT-TYPE
            SYNTAX  DisplayString
            ACCESS  read-write
            STATUS  mandatory
            DESCRIPTION
            "The user specified 'Low Warning' status description of this sensor. Unless specified, the default value is used."
            ::= { fuelEntry 49 }
            
         fuelHighWarningDescription OBJECT-TYPE
            SYNTAX  DisplayString
            ACCESS  read-write
            STATUS  mandatory
            DESCRIPTION
            "The user specified 'High Warning' status description of this sensor. Unless specified, the default value is used."
            ::= { fuelEntry 50 }
            
         fuelSensorErrorDescription OBJECT-TYPE
            SYNTAX  DisplayString
            ACCESS  read-write
            STATUS  mandatory
            DESCRIPTION
            "The user specified 'Sensor Error' status description of this sensor. Unless specified, the default value is used."
            ::=  { fuelEntry 51 }

         fuelHighCriticalColor OBJECT-TYPE
            SYNTAX  INTEGER
            ACCESS  read-write
            STATUS  mandatory
            DESCRIPTION
            "The user specified 'High Critical' status field color. The unit will show this color on its web interface and in DCIM. Unless specified, the default value is used."
            ::= { fuelEntry 54 }

         fuelLowCriticalColor OBJECT-TYPE
            SYNTAX  INTEGER
            ACCESS  read-write
            STATUS  mandatory
            DESCRIPTION
            "The user specified 'Low Critical' status field color. The unit will show this color on its web interface and in DCIM. Unless specified, the default value is used."
            ::= { fuelEntry 55 }

         fuelNormalColor OBJECT-TYPE
            SYNTAX  INTEGER
            ACCESS  read-write
            STATUS  mandatory
            DESCRIPTION
            "The user specified 'Normal' status field color. The unit will show this color on its web interface and in DCIM. Unless specified, the default value is used."
            ::= { fuelEntry 56 }

         fuelLowWarningColor OBJECT-TYPE
            SYNTAX  INTEGER
            ACCESS  read-write
            STATUS  mandatory
            DESCRIPTION
            "The user specified 'Low Warning' status field color. The unit will show this color on its web interface and in DCIM. Unless specified, the default value is used."
            ::= { fuelEntry 57 }

         fuelHighWarningColor OBJECT-TYPE
            SYNTAX  INTEGER
            ACCESS  read-write
            STATUS  mandatory
            DESCRIPTION
            "The user specified 'High Warning' status field color. The unit will show this color on its web interface and in DCIM. Unless specified, the default value is used."
            ::= { fuelEntry 58 }

         fuelSensorErrorColor OBJECT-TYPE
            SYNTAX  INTEGER
            ACCESS  read-write
            STATUS  mandatory
            DESCRIPTION
            "The user specified 'Sensor Error' status field color. The unit will show this color on its web interface and in DCIM. Unless specified, the default value is used."
            ::= { fuelEntry 59 }

         fuelAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { fuelEntry 70 }

         fuelId OBJECT-TYPE
            SYNTAX  INTEGER
            ACCESS  read-only
            STATUS  mandatory
            DESCRIPTION
            "The Sensor ID of this sensor, used to identify which sensor it is in the system configuration."
            ::= { fuelEntry 1000 }

--/* End of fuelTable */

--/* Begin of tankSenderTable */
         tankSenderTable OBJECT-TYPE
            SYNTAX  SEQUENCE OF TankSenderEntry
            ACCESS  not-accessible
            STATUS  mandatory
            DESCRIPTION
            "This table contains the property and reading value for every sensor."
            ::= { sensors 26 }

         tankSenderEntry OBJECT-TYPE
            SYNTAX  TankSenderEntry
            ACCESS  not-accessible
            STATUS  mandatory
            INDEX { tankSenderIndex }
            ::= { tankSenderTable 1 }

         TankSenderEntry ::= SEQUENCE {
               tankSenderIndex
                  DisplayString,
               tankSenderDescription
                  DisplayString,
               tankSenderValue
                  INTEGER,
               tankSenderUnit
                  DisplayString,
               tankSenderStatus
                  INTEGER,
               tankSenderGoOffline
                  INTEGER,
               tankSenderLowCritical
                  INTEGER,
               tankSenderLowWarning
                  INTEGER,
               tankSenderHighWarning
                  INTEGER,
               tankSenderHighCritical
                  INTEGER,
               tankSenderRearm
                  INTEGER,
               tankSenderDelayError
                  INTEGER,
               tankSenderDelayNormal
                  INTEGER,
               tankSenderDelayLowCritical
                  INTEGER,
               tankSenderDelayLowWarning
                  INTEGER,
               tankSenderDelayHighWarning
                  INTEGER,
               tankSenderDelayHighCritical
                  INTEGER,
               tankSenderRaw
                  INTEGER,
               tankSenderDisplayStyle
                  INTEGER,
               tankSenderHighCriticalDescription
                  DisplayString,
               tankSenderLowCriticalDescription
                  DisplayString,
               tankSenderNormalDescription
                  DisplayString,
               tankSenderLowWarningDescription
                  DisplayString,   
               tankSenderHighWarningDescription
                  DisplayString,
               tankSenderSensorErrorDescription
                  DisplayString,
               tankSenderHighCriticalColor
                  INTEGER,
               tankSenderLowCriticalColor
                  INTEGER,
               tankSenderNormalColor
                  INTEGER,
               tankSenderLowWarningColor
                  INTEGER,
               tankSenderHighWarningColor
                  INTEGER,
               tankSenderSensorErrorColor
                  INTEGER,
               tankSenderAcknowledge
                  INTEGER,
               tankSenderId
                  INTEGER
            }

         tankSenderIndex OBJECT-TYPE
            SYNTAX  DisplayString
            ACCESS  read-only
            STATUS  mandatory
            DESCRIPTION
            "The Sensor Compound ID of this sensor, used to identify which sensor it is in the system configuration."
            ::= { tankSenderEntry 1 }

         tankSenderDescription OBJECT-TYPE
            SYNTAX  DisplayString
            ACCESS  read-write
            STATUS  mandatory
            DESCRIPTION
            "The user specified description of this sensor. Unless specified, the default value is used."
            ::= { tankSenderEntry 2 }

         tankSenderValue OBJECT-TYPE
            SYNTAX  INTEGER
            ACCESS  read-only
            STATUS  mandatory
            DESCRIPTION
            "The sensor value in numerical reading."
            ::= { tankSenderEntry 4 }

         tankSenderUnit OBJECT-TYPE
            SYNTAX  DisplayString
            ACCESS  read-write
            STATUS  mandatory
            DESCRIPTION
         "The sensor's value unit string, in what the sensor's value is read in."
            ::= { tankSenderEntry 5 }

         tankSenderStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { tankSenderEntry 6 }

         tankSenderGoOffline OBJECT-TYPE
            SYNTAX  INTEGER {
               online(1),
               goOffline(2)
            }
            ACCESS  read-write
            STATUS  mandatory
            DESCRIPTION
            "Command to offline this sensor: use value '2' to set the sensor offline."
            ::= { tankSenderEntry 8 }

         tankSenderLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { tankSenderEntry 9 }

         tankSenderLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { tankSenderEntry 10 }

         tankSenderHighWarning OBJECT-TYPE
            SYNTAX  INTEGER
            ACCESS  read-write
            STATUS  mandatory
            DESCRIPTION
            "The user specified 'High Warning' value of this sensor. The unit will check the current reading against this value, and send an alert if it's configured. Unless specified, the default value is used."
            ::= { tankSenderEntry 11 }

         tankSenderHighCritical OBJECT-TYPE
            SYNTAX  INTEGER
            ACCESS  read-write
            STATUS  mandatory
            DESCRIPTION
            "The user specified 'High Critical' value of this sensor. The unit will check the current reading against this value, and send an alert if it's configured. Unless specified, the default value is used."
            ::= { tankSenderEntry 12 }

         tankSenderRearm OBJECT-TYPE
            SYNTAX  INTEGER
            ACCESS  read-write
            STATUS  mandatory
            DESCRIPTION
            "This value tells how many value the sensor has to reach beyond the threshold value, before changing to a new status. Useful to prevent the quick fluctuation of readings."
            ::= { tankSenderEntry 13 }

         tankSenderDelayError OBJECT-TYPE
            SYNTAX  INTEGER
            ACCESS  read-write
            STATUS  mandatory
            DESCRIPTION
            "The time in seconds (continuous time) that the sensor has to be in 'Error' status before its status is changed."
            ::= { tankSenderEntry 14 }

         tankSenderDelayNormal OBJECT-TYPE
            SYNTAX  INTEGER
            ACCESS  read-write
            STATUS  mandatory
            DESCRIPTION
            "The time in seconds (continuous time) that the sensor has to be in 'Normal' status before its status is changed."
            ::= { tankSenderEntry 15 }

         tankSenderDelayLowCritical OBJECT-TYPE
            SYNTAX INTEGER
            ACCESS read-write
            STATUS mandatory
            DESCRIPTION
            "The time in seconds (continuous time) that the sensor has to be in 'Low Critical' status before its status is changed."
            ::= { tankSenderEntry 16 }

         tankSenderDelayLowWarning OBJECT-TYPE
            SYNTAX INTEGER
            ACCESS read-write
            STATUS mandatory
            DESCRIPTION
            "The time in seconds (continuous time) that the sensor has to be in 'Low Warning' status before its status is changed."
            ::= { tankSenderEntry 17 }

         tankSenderDelayHighWarning OBJECT-TYPE
            SYNTAX INTEGER
            ACCESS read-write
            STATUS mandatory
            DESCRIPTION
            "The time in seconds (continuous time) that the sensor has to be in 'High Warning' status before its status is changed."
            ::= { tankSenderEntry 18 }

         tankSenderDelayHighCritical OBJECT-TYPE
            SYNTAX INTEGER
            ACCESS read-write
            STATUS mandatory
            DESCRIPTION
            "The time in seconds (continuous time) that the sensor has to be in 'High Critical' status before its status is changed."
            ::= { tankSenderEntry 19 }

         tankSenderRaw OBJECT-TYPE
            SYNTAX  INTEGER 
            ACCESS  read-only
            STATUS  mandatory
            DESCRIPTION
            "The sensor's unformatted (raw) value that is being read directly from sensor, before it is converted to the preferred value."
            ::= { tankSenderEntry 20 }

         tankSenderDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { tankSenderEntry 45 }

         tankSenderHighCriticalDescription OBJECT-TYPE
            SYNTAX  DisplayString
            ACCESS  read-write
            STATUS  mandatory
            DESCRIPTION
            "The user specified 'High Critical' status description of this sensor. Unless specified, the default value is used."
            ::= { tankSenderEntry 46 }

         tankSenderLowCriticalDescription OBJECT-TYPE
            SYNTAX  DisplayString
            ACCESS  read-write
            STATUS  mandatory
            DESCRIPTION
            "The user specified 'Low Critical' status description of this sensor. Unless specified, the default value is used."
            ::= { tankSenderEntry 47 }

         tankSenderNormalDescription OBJECT-TYPE
            SYNTAX  DisplayString
            ACCESS  read-write
            STATUS  mandatory
            DESCRIPTION
            "The user specified 'Normal' status description of this sensor. Unless specified, the default value is used."
            ::= { tankSenderEntry 48 }

         tankSenderLowWarningDescription OBJECT-TYPE
            SYNTAX  DisplayString
            ACCESS  read-write
            STATUS  mandatory
            DESCRIPTION
            "The user specified 'Low Warning' status description of this sensor. Unless specified, the default value is used."
            ::= { tankSenderEntry 49 }

         tankSenderHighWarningDescription OBJECT-TYPE
            SYNTAX  DisplayString
            ACCESS  read-write
            STATUS  mandatory
            DESCRIPTION
            "The user specified 'High Warning' status description of this sensor. Unless specified, the default value is used."
            ::= { tankSenderEntry 50 }

         tankSenderSensorErrorDescription OBJECT-TYPE
            SYNTAX  DisplayString
            ACCESS  read-write
            STATUS  mandatory
            DESCRIPTION
            "The user specified 'Sensor Error' status description of this sensor. Unless specified, the default value is used."
            ::= { tankSenderEntry 51 }

         tankSenderHighCriticalColor OBJECT-TYPE
            SYNTAX  INTEGER
            ACCESS  read-write
            STATUS  mandatory
            DESCRIPTION
            "The user specified 'High Critical' status field color. The unit will show this color on its web interface and in DCIM. Unless specified, the default value is used."
            ::= { tankSenderEntry 54 }

         tankSenderLowCriticalColor OBJECT-TYPE
            SYNTAX  INTEGER
            ACCESS  read-write
            STATUS  mandatory
            DESCRIPTION
            "The user specified 'Low Critical' status field color. The unit will show this color on its web interface and in DCIM. Unless specified, the default value is used."
            ::= { tankSenderEntry 55 }

         tankSenderNormalColor OBJECT-TYPE
            SYNTAX  INTEGER
            ACCESS  read-write
            STATUS  mandatory
            DESCRIPTION
            "The user specified 'Normal' status field color. The unit will show this color on its web interface and in DCIM. Unless specified, the default value is used."
            ::= { tankSenderEntry 56 }

         tankSenderLowWarningColor OBJECT-TYPE
            SYNTAX  INTEGER
            ACCESS  read-write
            STATUS  mandatory
            DESCRIPTION
            "The user specified 'Low Warning' status field color. The unit will show this color on its web interface and in DCIM. Unless specified, the default value is used."
            ::= { tankSenderEntry 57 }

         tankSenderHighWarningColor OBJECT-TYPE
            SYNTAX  INTEGER
            ACCESS  read-write
            STATUS  mandatory
            DESCRIPTION
            "The user specified 'High Warning' status field color. The unit will show this color on its web interface and in DCIM. Unless specified, the default value is used."
            ::= { tankSenderEntry 58 }

         tankSenderSensorErrorColor OBJECT-TYPE
            SYNTAX  INTEGER
            ACCESS  read-write
            STATUS  mandatory
            DESCRIPTION
            "The user specified 'Sensor Error' status field color. The unit will show this color on its web interface and in DCIM. Unless specified, the default value is used."
            ::= { tankSenderEntry 59 }

         tankSenderAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { tankSenderEntry 70 }

         tankSenderId OBJECT-TYPE
            SYNTAX  INTEGER
            ACCESS  read-only
            STATUS  mandatory
            DESCRIPTION
            "The Sensor ID of this sensor, used to identify which sensor it is in the system configuration."
            ::= { tankSenderEntry 1000 }

--/* End of tankSenderTable */

--/* Begin of doorTable */

         doorTable OBJECT-TYPE
            SYNTAX  SEQUENCE OF DoorEntry
            ACCESS  not-accessible
            STATUS  mandatory
            DESCRIPTION
            "This table contains the properties for each door sensor"
            ::= { sensors 27 }

         doorEntry OBJECT-TYPE
            SYNTAX  DoorEntry
            ACCESS  not-accessible
            STATUS  mandatory
            INDEX { doorIndex }
            ::= { doorTable 1 }

         DoorEntry ::= SEQUENCE {
            doorIndex
               DisplayString,
            doorDescription
               DisplayString,
            doorValue
               INTEGER,
            doorStatus
               INTEGER,
            doorUnlockPeriod
               INTEGER,
            doorOpenPeriod
               INTEGER,
            doorCmd
               INTEGER,
            doorAcknowledge
               INTEGER,
            doorId
               INTEGER
         }

         doorIndex OBJECT-TYPE
            SYNTAX  DisplayString
            ACCESS  read-only
            STATUS  mandatory
            DESCRIPTION
            "The Sensor Compound ID of this sensor, used to identify which sensor it is in the system configuration."
            ::= { doorEntry 1 }

         doorDescription OBJECT-TYPE
            SYNTAX  DisplayString
            ACCESS  read-write
            STATUS  mandatory
            DESCRIPTION
            "The user specified description of this sensor. Unless specified, the default value is used."
            ::= { doorEntry 2 }

         doorValue OBJECT-TYPE
            SYNTAX  INTEGER
            ACCESS  read-only
            STATUS  mandatory
            DESCRIPTION
            "The reading value for this sensor. It will be used to calculate the sensor status."
            ::= { doorEntry 4 }

         doorStatus OBJECT-TYPE
            SYNTAX  INTEGER {
               noStatus(1),
               closed(2),
               heldOpen(3),
               fire(4),
               opened(5),
               forceOpened(6),
               sensorError(7)
            }
            ACCESS  read-only
            STATUS  mandatory
            DESCRIPTION
            "The current status of this sensor."
            ::= { doorEntry 6 }

         doorUnlockPeriod OBJECT-TYPE
            SYNTAX  INTEGER
            ACCESS  read-write
            STATUS  mandatory
            DESCRIPTION
            "The time in seconds for the door to stay unlocked before it is automatically locked again."
            ::= { doorEntry 62 }

         doorOpenPeriod OBJECT-TYPE
            SYNTAX  INTEGER
            ACCESS  read-write
            STATUS  mandatory
            DESCRIPTION
            "The time in seconds for the door to stay in the 'Open' status before it sends the alert 'Door is held open'."
            ::= { doorEntry 63 }

         doorCmd OBJECT-TYPE
            SYNTAX  INTEGER {
               none(0),
               trig-open(1),
               trig-close(2)
            }
            ACCESS  write-only
            STATUS  mandatory
            DESCRIPTION
            "The Door Sensor's command, used to open/close the door."
            ::= { doorEntry 64 }

         doorAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { doorEntry 70 }

         doorId OBJECT-TYPE
            SYNTAX  INTEGER
            ACCESS  read-only
            STATUS  mandatory
            DESCRIPTION
            "The Sensor ID of this sensor, used to identify which sensor it is in the system configuration."
            ::= { doorEntry 1000 }

--/* End of doorTable */

--/* Begin of temperatureArrayTable */

         temperatureArrayTable OBJECT-TYPE
            SYNTAX  SEQUENCE OF TemperatureArrayEntry
            ACCESS  not-accessible
            STATUS  mandatory
            DESCRIPTION
            "This table contains the properties for each temperature array sensor"
            ::= { sensors 28 }

         temperatureArrayEntry OBJECT-TYPE
            SYNTAX  TemperatureArrayEntry
            ACCESS  not-accessible
            STATUS  mandatory
            INDEX { temperatureArrayIndex }
            ::= { temperatureArrayTable 1 }

         TemperatureArrayEntry ::= SEQUENCE {
            temperatureArrayIndex
               DisplayString,
            temperatureArrayDescription
               DisplayString,
            temperatureArrayType
               INTEGER,
            temperatureArrayDegree
               INTEGER,
            temperatureArrayUnit
               DisplayString,
            temperatureArrayStatus
               INTEGER,
            temperatureArrayGoOffline
               INTEGER,
            temperatureArrayLowCritical
               INTEGER,
            temperatureArrayLowWarning
               INTEGER,
            temperatureArrayHighWarning
               INTEGER,
            temperatureArrayHighCritical
               INTEGER,
            temperatureArrayRearm
               INTEGER,
            temperatureArrayDelayError
               INTEGER,
            temperatureArrayDelayNormal
               INTEGER,
            temperatureArrayDelayLowCritical
               INTEGER,
            temperatureArrayDelayLowWarning
               INTEGER,
            temperatureArrayDelayHighWarning
               INTEGER,
            temperatureArrayDelayHighCritical
               INTEGER,
            temperatureArrayRaw
               INTEGER,
            temperatureArrayOffset
               INTEGER,
            temperatureArrayPort
               INTEGER,
            temperatureArraySubPort
               INTEGER,
            temperatureArrayDisplayStyle
               INTEGER,
            temperatureArrayHighCriticalDescription
               DisplayString,
            temperatureArrayLowCriticalDescription
               DisplayString,
            temperatureArraySensorNormalDescription
               DisplayString,
            temperatureArrayLowWarningDescription
               DisplayString,
            temperatureArrayHighWarningDescription
               DisplayString,
            temperatureArraySensorErrorDescription
               DisplayString,
            temperatureArrayHighCriticalColor
               INTEGER,
            temperatureArrayLowCriticalColor
               INTEGER,
            temperatureArraySensorNormalColor
               INTEGER,
            temperatureArrayLowWarningColor
               INTEGER,
            temperatureArrayHighWarningColor
               INTEGER,
            temperatureArraySensorErrorColor
               INTEGER,
            temperatureArrayAcknowledge
               INTEGER,
            temperatureArraySerialNumber
               DisplayString,
            temperatureArrayId
               INTEGER
         }

         temperatureArrayIndex OBJECT-TYPE
            SYNTAX  DisplayString
            ACCESS  read-only
            STATUS  mandatory
            DESCRIPTION
            "The Sensor Compound ID of this sensor, used to identify which sensor it is in the system configuration."
            ::= { temperatureArrayEntry 1 }

         temperatureArrayDescription OBJECT-TYPE
            SYNTAX  DisplayString
            ACCESS  read-write
            STATUS  mandatory
            DESCRIPTION
            "The user specified description of this sensor. Unless specified, the default value is used."
            ::= { temperatureArrayEntry 2 }

         temperatureArrayType OBJECT-TYPE
            SYNTAX  INTEGER {
               temperature(1),
               thermocouple(20),
               arraytemp(23)
            }
            ACCESS  read-only
            STATUS  mandatory
            DESCRIPTION
            "The type of the sensor; it represents the sensor's functionality. For the temperature sensor, it has 3 sub-types: Normal temperature sensor, One-wire temperature sensor, and Thermocouple sensor."
            ::= { temperatureArrayEntry 3 }

         temperatureArrayDegree OBJECT-TYPE
            SYNTAX  INTEGER
            ACCESS  read-only
            STATUS  mandatory
            DESCRIPTION
            "The temperature degree value in numerical reading."
            ::= { temperatureArrayEntry 4 }

         temperatureArrayUnit OBJECT-TYPE
            SYNTAX  DisplayString
            ACCESS  read-write
            STATUS  mandatory
            DESCRIPTION
            "The sensor's value unit string, in what the sensor's value is read in. For the temperature sensor it can be Celsius or Fahrenheit."
            ::= { temperatureArrayEntry 5 }

         temperatureArrayStatus OBJECT-TYPE
            SYNTAX  INTEGER {
               noStatus(1),
               normal(2),
               highWarning(3),
               highCritical(4),
               lowWarning(5),
               lowCritical(6),
               sensorError(7)
            }
            ACCESS  read-only
            STATUS  mandatory
            DESCRIPTION
            "The current status of this sensor."
            ::= { temperatureArrayEntry 6 }

         temperatureArrayGoOffline OBJECT-TYPE
            SYNTAX  INTEGER {
               online(1),
               goOffline(2)
            }
            ACCESS  read-write
            STATUS  mandatory
            DESCRIPTION
            "Command to offline this sensor: use value '2' to set the sensor offline."
            ::= { temperatureArrayEntry 8 }

         temperatureArrayLowCritical OBJECT-TYPE
            SYNTAX  INTEGER
            ACCESS  read-write
            STATUS  mandatory
            DESCRIPTION
            "The user specified 'Low Critical' value of this sensor. The unit will check the current reading against this value, and send an alert if it's configured. Unless specified, the default value is used."
            ::= { temperatureArrayEntry 9 }

         temperatureArrayLowWarning OBJECT-TYPE
            SYNTAX  INTEGER
            ACCESS  read-write
            STATUS  mandatory
            DESCRIPTION
            "The user specified 'Low Warning' value of this sensor. The unit will check the current reading against this value, and send an alert if it's configured. Unless specified, the default value is used."
            ::= { temperatureArrayEntry 10 }

         temperatureArrayHighWarning OBJECT-TYPE
            SYNTAX  INTEGER
            ACCESS  read-write
            STATUS  mandatory
            DESCRIPTION
            "The user specified 'High Warning' value of this sensor. The unit will check the current reading against this value, and send an alert if it's configured. Unless specified, the default value is used."
            ::= { temperatureArrayEntry 11 }

         temperatureArrayHighCritical OBJECT-TYPE
            SYNTAX  INTEGER
            ACCESS  read-write
            STATUS  mandatory
            DESCRIPTION
            "The user specified 'High Critical' value of this sensor. The unit will check the current reading against this value, and send an alert if it's configured. Unless specified, the default value is used."
            ::= { temperatureArrayEntry 12 }

         temperatureArrayRearm OBJECT-TYPE
            SYNTAX  INTEGER
            ACCESS  read-write
            STATUS  mandatory
            DESCRIPTION
            "This value tells how many degrees the sensor has to reach beyond the threshold value, before changing to a new status. Useful to prevent the quick fluctuation of readings."
            ::= { temperatureArrayEntry 13 }

         temperatureArrayDelayError OBJECT-TYPE
            SYNTAX  INTEGER
            ACCESS  read-write
            STATUS  mandatory
            DESCRIPTION
            "The time in seconds (continuous time) that the sensor has to be in 'Error' status before its status is changed."
            ::= { temperatureArrayEntry 14 }

         temperatureArrayDelayNormal OBJECT-TYPE
            SYNTAX  INTEGER
            ACCESS  read-write
            STATUS  mandatory
            DESCRIPTION
            "The time in seconds (continuous time) that the sensor has to be in 'Normal' status before its status is changed."
            ::= { temperatureArrayEntry 15 }

         temperatureArrayDelayLowCritical OBJECT-TYPE
            SYNTAX  INTEGER
            ACCESS  read-write
            STATUS  mandatory
            DESCRIPTION
            "The time in seconds (continuous time) that the sensor has to be in 'Low Critical' status before its status is changed."
            ::= { temperatureArrayEntry 16 }

         temperatureArrayDelayLowWarning OBJECT-TYPE
            SYNTAX  INTEGER
            ACCESS  read-write
            STATUS  mandatory
            DESCRIPTION
            "The time in seconds (continuous time) that the sensor has to be in 'Low Warning' status before its status is changed."
            ::= { temperatureArrayEntry 17 }

         temperatureArrayDelayHighWarning OBJECT-TYPE
            SYNTAX  INTEGER
            ACCESS  read-write
            STATUS  mandatory
            DESCRIPTION
            "The time in seconds (continuous time) that the sensor has to be in 'High Warning' status before its status is changed."
            ::= { temperatureArrayEntry 18 }

         temperatureArrayDelayHighCritical OBJECT-TYPE
            SYNTAX  INTEGER
            ACCESS  read-write
            STATUS  mandatory
            DESCRIPTION
            "The time in seconds (continuous time) that the sensor has to be in 'High Critical' status before its status is changed."
            ::= { temperatureArrayEntry 19 }

         temperatureArrayRaw OBJECT-TYPE
            SYNTAX  INTEGER
            ACCESS  read-only
            STATUS  mandatory
            DESCRIPTION
            "The sensor's unformatted (raw) value that is being read directly from sensor, before it is converted to the preferred value."
            ::= { temperatureArrayEntry 20 }

         temperatureArrayOffset OBJECT-TYPE
            SYNTAX  INTEGER
            ACCESS  read-write
            STATUS  mandatory
            DESCRIPTION
            "The offset value for this sensor. It's used to adjust the reading value in case the reading is incorrect."
            ::= { temperatureArrayEntry 21 }

         temperatureArrayPort OBJECT-TYPE
            SYNTAX  INTEGER
            ACCESS  read-only
            STATUS  mandatory
            DESCRIPTION
            "The device's sensor port number, where this sensor is plugged in to."
            ::= { temperatureArrayEntry 35 }

         temperatureArraySubPort OBJECT-TYPE
            SYNTAX  INTEGER
            ACCESS  read-only
            STATUS  mandatory
            DESCRIPTION
            "The logical port number of this sensor in the array, or in a set of sensors. For Temperature Sensor, it's for the array of Temperature Sensors and Dual Sensors.  For example x.1, x.2, x.3 ..."
            ::= { temperatureArrayEntry 36 }

         temperatureArrayDisplayStyle OBJECT-TYPE
            SYNTAX  INTEGER {
               basic(0),
               gauge(1)
            }
            ACCESS  read-write
            STATUS  mandatory
            DESCRIPTION
            "The sensor's Display Style for the Web UI, to display the reading as a gauge or bar. 0 = bar style, 1 = gauge style."
            ::= { temperatureArrayEntry 45 }

         temperatureArrayHighCriticalDescription OBJECT-TYPE
            SYNTAX  DisplayString
            ACCESS  read-write
            STATUS  mandatory
            DESCRIPTION
            "The user specified 'High Critical' status description of this sensor. Unless specified, the default value is used."
            ::= { temperatureArrayEntry 46 }

         temperatureArrayLowCriticalDescription OBJECT-TYPE
            SYNTAX  DisplayString
            ACCESS  read-write
            STATUS  mandatory
            DESCRIPTION
            "The user specified 'Low Critical' status description of this sensor. Unless specified, the default value is used."
            ::= { temperatureArrayEntry 47 }

         temperatureArraySensorNormalDescription OBJECT-TYPE
            SYNTAX  DisplayString
            ACCESS  read-write
            STATUS  mandatory
            DESCRIPTION
            "The user specified 'Normal' status description of this sensor. Unless specified, the default value is used."
            ::= { temperatureArrayEntry 48 }

         temperatureArrayLowWarningDescription OBJECT-TYPE
            SYNTAX  DisplayString
            ACCESS  read-write
            STATUS  mandatory
            DESCRIPTION
            "The user specified 'Low Warning' status description of this sensor. Unless specified, the default value is used."
            ::= { temperatureArrayEntry 49 }

         temperatureArrayHighWarningDescription OBJECT-TYPE
            SYNTAX  DisplayString
            ACCESS  read-write
            STATUS  mandatory
            DESCRIPTION
            "The user specified 'High Warning' status description of this sensor. Unless specified, the default value is used."
            ::= { temperatureArrayEntry 50 }

         temperatureArraySensorErrorDescription OBJECT-TYPE
            SYNTAX  DisplayString
            ACCESS  read-write
            STATUS  mandatory
            DESCRIPTION
            "The user specified 'Sensor Error' status description of this sensor. Unless specified, the default value is used."
            ::= { temperatureArrayEntry 51 }

         temperatureArrayHighCriticalColor OBJECT-TYPE
            SYNTAX  INTEGER
            ACCESS  read-write
            STATUS  mandatory
            DESCRIPTION
            "The user specified 'High Critical' status field color. The unit will show this color on its web interface and in DCIM. Unless specified, the default value is used."
            ::= { temperatureArrayEntry 54 }

         temperatureArrayLowCriticalColor OBJECT-TYPE
            SYNTAX  INTEGER
            ACCESS  read-write
            STATUS  mandatory
            DESCRIPTION
            "The user specified 'Low Critical' status field color. The unit will show this color on its web interface and in DCIM. Unless specified, the default value is used."
            ::= { temperatureArrayEntry 55 }

         temperatureArraySensorNormalColor OBJECT-TYPE
            SYNTAX  INTEGER
            ACCESS  read-write
            STATUS  mandatory
            DESCRIPTION
            "The user specified 'Normal' status field color. The unit will show this color on its web interface and in DCIM. Unless specified, the default value is used."
            ::= { temperatureArrayEntry 56 }

         temperatureArrayLowWarningColor OBJECT-TYPE
            SYNTAX  INTEGER
            ACCESS  read-write
            STATUS  mandatory
            DESCRIPTION
            "The user specified 'Low Warning' status field color. The unit will show this color on its web interface and in DCIM. Unless specified, the default value is used."
            ::= { temperatureArrayEntry 57 }

         temperatureArrayHighWarningColor OBJECT-TYPE
            SYNTAX  INTEGER
            ACCESS  read-write
            STATUS  mandatory
            DESCRIPTION
            "The user specified 'High Warning' status field color. The unit will show this color on its web interface and in DCIM. Unless specified, the default value is used."
            ::= { temperatureArrayEntry 58 }

         temperatureArraySensorErrorColor OBJECT-TYPE
            SYNTAX  INTEGER
            ACCESS  read-write
            STATUS  mandatory
            DESCRIPTION
            "The user specified 'Sensor Error' status field color. The unit will show this color on its web interface and in DCIM. Unless specified, the default value is used."
            ::= { temperatureArrayEntry 59 }

         temperatureArrayAcknowledge OBJECT-TYPE
            SYNTAX  INTEGER {
               not-acked(0),
               acked(1),
               ack(2)
            }
            ACCESS  read-write
            STATUS  mandatory
            DESCRIPTION
            "The acknowledge status for the current status of the sensor: 0 = the status has been changed and waiting to be acknowledged, 1 = status is normal or have been already acknowledged, 2 = acknowledge the current status (this status is write-only)"
            ::= { temperatureArrayEntry 70 }

         temperatureArraySerialNumber OBJECT-TYPE
            SYNTAX  DisplayString
            ACCESS  read-write
            STATUS  mandatory
            DESCRIPTION
            "The serial number of temperature sensor, used to indicate which sensor it is in an array. It matches the MAC ID of the sensor for a DCT sensor array."
            ::= { temperatureArrayEntry 71 }

         temperatureArrayId OBJECT-TYPE
            SYNTAX  INTEGER
            ACCESS  read-only
            STATUS  mandatory
            DESCRIPTION
            "The Sensor ID of this sensor, used to identify which sensor it is in the system configuration."
            ::= { temperatureArrayEntry 1000 }

--/* End of temperatureArrayTable */

-- TRAP Definitions

   spNormalStatus TRAP-TYPE
      ENTERPRISE sensorProbe
      DESCRIPTION
         "sensorProbe status is Normal"
      --#TYPE "sensorProbe Normal Status"
      --#SEVERITY INFORMATIONAL
      ::= 1

   spWarningStatus TRAP-TYPE
      ENTERPRISE sensorProbe
      DESCRIPTION
         "sensorProbe status went to Warning"
      --#TYPE "sensorProbe Warning Status"
      --#SEVERITY MINOR
      ::= 2

   spCriticalStatus TRAP-TYPE
      ENTERPRISE sensorProbe
      DESCRIPTION
         "sensorProbe status went to Critical"
      --#TYPE "sensorProbe Critical Status"
      --#SEVERITY MAJOR
      ::= 3

   spDownStatus TRAP-TYPE
      ENTERPRISE sensorProbe
      DESCRIPTION
         "sensorProbe status went to Disabled"
      --#TYPE "sensorProbe Down Status"
      --#SEVERITY MINOR
      ::= 4

   spKeepAliveTrap TRAP-TYPE
      ENTERPRISE sensorProbe
      DESCRIPTION
         "sensorProbe send keep alive trap."
      --#SEVERITY  INFORMATIONAL
      ::= 5

   spUnknownStatus TRAP-TYPE
      ENTERPRISE sensorProbe
      DESCRIPTION
         "sensorProbe status went to Unknown"
      --#TYPE "sensorProbe Unknown Status"
      --#SEVERITY INFORMATIONAL
      ::= 7      

-- sensorProbeTrapType = generalTypeTrap(2)

   spTemperatureStatus TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 10

   spTemperatureArray1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 11

   spTemperatureArray2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 12

   spTemperatureArray3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 13

   spTemperatureArray4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 14

   spTemperatureArray5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 15

   spTemperatureArray6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 16

   spTemperatureArray7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 17

   spTemperatureArray8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 18

   spAnalogueStatus TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 20

   spSwitchStatus TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 30

   spIRMSStatus TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 40

   spVRMSStatus TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 50

   spWattStatus TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 60

   spRelayArray1Status TRAP-TYPE
      ENTERPRISE sensorProbe
      VARIABLES
         { spSensorStatus, spSensorValue, spSensorLevelExceeded, 
         spSensorIndex, spSensorName, spSensorDescription }
      DESCRIPTION
         "RelayArray1 sensor trap"
      --#SEVERITY  MAJOR
      ::= 71

   spRelayArray2Status TRAP-TYPE
      ENTERPRISE sensorProbe
      VARIABLES
         { spSensorStatus, spSensorValue, spSensorLevelExceeded, 
         spSensorIndex, spSensorName, spSensorDescription }
      DESCRIPTION
         "RelayArray2 sensor trap"
      --#SEVERITY  MAJOR
      ::= 72

   spRelayArray3Status TRAP-TYPE
      ENTERPRISE sensorProbe
      VARIABLES
         { spSensorStatus, spSensorValue, spSensorLevelExceeded, 
         spSensorIndex, spSensorName, spSensorDescription }
      DESCRIPTION
         "RelayArray3 sensor trap"
      --#SEVERITY  MAJOR
      ::= 73

   spRelayArray4Status TRAP-TYPE
      ENTERPRISE sensorProbe
      VARIABLES
         { spSensorStatus, spSensorValue, spSensorLevelExceeded, 
         spSensorIndex, spSensorName, spSensorDescription }
      DESCRIPTION
         "RelayArray4 sensor trap"
      --#SEVERITY  MAJOR
      ::= 74

   spRelayArray5Status TRAP-TYPE
      ENTERPRISE sensorProbe
      VARIABLES
         { spSensorStatus, spSensorValue, spSensorLevelExceeded, 
         spSensorIndex, spSensorName, spSensorDescription }
      DESCRIPTION
         "RelayArray5 sensor trap"
      --#SEVERITY  MAJOR
      ::= 75

   spRelayArray6Status TRAP-TYPE
      ENTERPRISE sensorProbe
      VARIABLES
         { spSensorStatus, spSensorValue, spSensorLevelExceeded, 
         spSensorIndex, spSensorName, spSensorDescription }
      DESCRIPTION
         "RelayArray6 sensor trap"
      --#SEVERITY  MAJOR
      ::= 77

   spRelayArray8Status TRAP-TYPE
      ENTERPRISE sensorProbe
      VARIABLES
         { spSensorStatus, spSensorValue, spSensorLevelExceeded, 
         spSensorIndex, spSensorName, spSensorDescription }
      DESCRIPTION
         "RelayArray8 sensor trap"
      --#SEVERITY  MAJOR
      ::= 78

   spVirtualStatus TRAP-TYPE
      ENTERPRISE sensorProbe
      VARIABLES
         { spSensorStatus, spSensorValue, spSensorLevelExceeded, 
         spSensorIndex, spSensorName, spSensorDescription }
      DESCRIPTION
         "Virtual sensor trap"
      --#SEVERITY  MAJOR
      ::= 80

-- sensorProbeTrapType = statusTypeTraps(4)

   spSenUnknownStatus TRAP-TYPE
      ENTERPRISE sensorProbe
      VARIABLES
         { spSensorStatus, spSensorValue, spSensorLevelExceeded, 
         spSensorIndex, spSensorName, spSensorDescription }
      DESCRIPTION
         "sensorProbe sensor status went to Unknown"
      --#TYPE "sensorProbe Unknown Status"
      --#SUMMARY "%s(%s) Status is now %d on port %d."
      --#ARGUMENTS {4,5,1,3}
      --#SEVERITY MAJOR
      --#TIMEINDEX 4
      ::= 51

   spSenNormalStatus TRAP-TYPE
      ENTERPRISE sensorProbe
      VARIABLES
         { spSensorStatus, spSensorValue, spSensorLevelExceeded, 
         spSensorIndex, spSensorName, spSensorDescription }
      DESCRIPTION
         "sensorProbe sensor status is Normal"
      --#TYPE "sensorProbe Normal Status"
      --#SUMMARY "%s(%s) Status is now %d on port %d."
      --#ARGUMENTS {4,5,1,3}
      --#SEVERITY INFORMATIONAL
      --#TIMEINDEX 4
      ::= 52

   spSenWarningStatus TRAP-TYPE
      ENTERPRISE sensorProbe
      VARIABLES
         { spSensorStatus, spSensorValue, spSensorLevelExceeded, 
         spSensorIndex, spSensorName, spSensorDescription }
      DESCRIPTION
         "sensorProbe sensor status went to Warning"
      --#TYPE "sensorProbe Warning Status"
      --#SUMMARY "%s(%s) Status is now %d on port %d."
      --#ARGUMENTS {4,5,1,3}
      --#SEVERITY MINOR
      --#TIMEINDEX 4
      ::= 53

   spSenCriticalStatus TRAP-TYPE
      ENTERPRISE sensorProbe
      VARIABLES
         { spSensorStatus, spSensorValue, spSensorLevelExceeded, 
         spSensorIndex, spSensorName, spSensorDescription }
      DESCRIPTION
         "sensorProbe sensor status went to Critical"
      --#TYPE "sensorProbe Critical Status"
      --#SUMMARY "%s(%s) Status is now %d on port %d."
      --#ARGUMENTS {4,5,1,3}
      --#SEVERITY MAJOR
      --#TIMEINDEX 4
      ::= 54

   spSenDownStatus TRAP-TYPE
      ENTERPRISE sensorProbe
      VARIABLES
         { spSensorStatus, spSensorValue, spSensorLevelExceeded, 
         spSensorIndex, spSensorName, spSensorDescription }
      DESCRIPTION
         "sensorProbe sensor status went to Disabled"
      --#TYPE "sensorProbe Down Status"
      --#SUMMARY "%s(%s) Status is now %d on port %d."
      --#ARGUMENTS {4,5,1,3}
      --#SEVERITY INFORMATIONAL
      --#TIMEINDEX 4
      ::= 55

-- sensorProbeTrapType = specificTypeTrap(1)

   spTemperature1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 101

   spTemperature2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 102

   spTemperature3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 103

   spTemperature4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 104

   spTemperature5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 105

   spTemperature6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 106

   spTemperature7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 107

   spTemperature8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 108



   spTemperatureArray1-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 111

   spTemperatureArray1-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 112

   spTemperatureArray1-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 113

   spTemperatureArray1-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 114

   spTemperatureArray1-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 115

   spTemperatureArray1-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 116

   spTemperatureArray1-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 117

   spTemperatureArray1-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 118



   spTemperatureArray2-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 121

   spTemperatureArray2-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 122

   spTemperatureArray2-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 123

   spTemperatureArray2-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 124

   spTemperatureArray2-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 125

   spTemperatureArray2-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 126

   spTemperatureArray2-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 127

   spTemperatureArray2-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 128



   spTemperatureArray3-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 131

   spTemperatureArray3-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 132

   spTemperatureArray3-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 133

   spTemperatureArray3-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 134

   spTemperatureArray3-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 135

   spTemperatureArray3-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 136

   spTemperatureArray3-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 137

   spTemperatureArray3-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 138



   spTemperatureArray4-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 141

   spTemperatureArray4-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 142

   spTemperatureArray4-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 143

   spTemperatureArray4-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 144

   spTemperatureArray4-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 145

   spTemperatureArray4-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 146

   spTemperatureArray4-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 147

   spTemperatureArray4-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 148



   spTemperatureArray5-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 151

   spTemperatureArray5-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 152

   spTemperatureArray5-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 153

   spTemperatureArray5-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 154

   spTemperatureArray5-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 155

   spTemperatureArray5-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 156

   spTemperatureArray5-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 157

   spTemperatureArray5-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 158



   spTemperatureArray6-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 161

   spTemperatureArray6-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 162

   spTemperatureArray6-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 163

   spTemperatureArray6-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 164

   spTemperatureArray6-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 165

   spTemperatureArray6-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 166

   spTemperatureArray6-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 167

   spTemperatureArray6-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 168



   spTemperatureArray7-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 171

   spTemperatureArray7-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 172

   spTemperatureArray7-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 173

   spTemperatureArray7-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 174

   spTemperatureArray7-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 175

   spTemperatureArray7-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 176

   spTemperatureArray7-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 177

   spTemperatureArray7-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 178



   spTemperatureArray8-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 181

   spTemperatureArray8-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 182

   spTemperatureArray8-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 183

   spTemperatureArray8-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 184

   spTemperatureArray8-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 185

   spTemperatureArray8-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 186

   spTemperatureArray8-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 187

   spTemperatureArray8-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 188



   spAnalogue1Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 201

   spAnalogue2Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 202

   spAnalogue3Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 203

   spAnalogue4Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 204

   spAnalogue5Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 205

   spAnalogue6Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 206

   spAnalogue7Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 207

   spAnalogue8Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 208



   spSwitch1Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 301

   spSwitch2Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 302

   spSwitch3Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 303

   spSwitch4Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 304

   spSwitch5Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 305

   spSwitch6Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 306

   spSwitch7Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 307

   spSwitch8Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 308

   spSwitch9Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 309

   spSwitch10Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 310

   spSwitch11Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 311

   spSwitch12Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 312

   spSwitch13Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 313

   spSwitch14Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 314

   spSwitch15Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 315

   spSwitch16Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 316

   spSwitch17Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 317

   spSwitch18Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 318

   spSwitch19Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 319

   spSwitch20Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 320

   spSwitch21Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 321

   spSwitch22Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 322

   spSwitch23Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 323

   spSwitch24Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 324

   spSwitch25Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 325

   spSwitch26Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 326

   spSwitch27Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 327

   spSwitch28Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 328

   spSwitch29Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 329

   spSwitch30Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 330

   spSwitch31Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 331

   spSwitch32Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 332

   spSwitch33Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 333

   spSwitch34Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 334

   spSwitch35Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 335

   spSwitch36Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 336

   spSwitch37Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 337

   spSwitch38Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 338

   spSwitch39Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 339

   spSwitch40Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 340

   spSwitch41Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 341

   spSwitch42Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 342

   spSwitch43Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 343

   spSwitch44Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 344

   spSwitch45Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 345

   spSwitch46Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 346

   spSwitch47Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 347

   spSwitch48Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 348

   spSwitch49Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 349

   spSwitch50Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 350

   spSwitch51Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 351

   spSwitch52Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 352

   spSwitch53Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 353

   spSwitch54Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 354

   spSwitch55Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 355

   spSwitch56Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 356

   spSwitch57Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 357

   spSwitch58Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 358

   spSwitch59Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 359

   spSwitch60Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 360

   spSwitch61Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 361

   spSwitch62Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 362

   spSwitch63Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 363

   spSwitch64Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 364

   spSwitch65Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 365

   spSwitch66Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 366

   spSwitch67Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 367

   spSwitch68Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 368

   spIRMS1Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 401

   spIRMS2Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 402

   spIRMS3Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 403

   spIRMS4Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 404

   spIRMS5Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 405

   spIRMS6Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 406

   spIRMS7Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 407

   spIRMS8Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 408

   spVRMS1Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 501

   spVRMS2Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 502

   spVRMS3Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 503

   spVRMS4Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 504

   spVRMS5Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 505

   spVRMS6Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 506

   spVRMS7Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 507

   spVRMS8Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 508

   spEnergy1Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 601

   spEnergy2Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 602

   spEnergy3Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 603

   spEnergy4Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 604

   spEnergy5Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 605

   spEnergy6Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 606

   spEnergy7Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 607

   spEnergy8Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 608

   spRelayArray1-1Status TRAP-TYPE
      ENTERPRISE sensorProbe
      VARIABLES
         { spSensorStatus, spSensorValue, spSensorLevelExceeded, 
         spSensorIndex, spSensorName, spSensorDescription }
      DESCRIPTION
         "RelayArray1.1 sensor trap"
      --#SEVERITY  MAJOR
      ::= 711

   spRelayArray1-2Status TRAP-TYPE
      ENTERPRISE sensorProbe
      VARIABLES
         { spSensorStatus, spSensorValue, spSensorLevelExceeded, 
         spSensorIndex, spSensorName, spSensorDescription }
      DESCRIPTION
         "RelayArray1.2 sensor trap"
      --#SEVERITY  MAJOR
      ::= 712

   spRelayArray1-3Status TRAP-TYPE
      ENTERPRISE sensorProbe
      VARIABLES
         { spSensorStatus, spSensorValue, spSensorLevelExceeded, 
         spSensorIndex, spSensorName, spSensorDescription }
      DESCRIPTION
         "RelayArray1.3 sensor trap"
      --#SEVERITY  MAJOR
      ::= 713

   spRelayArray1-4Status TRAP-TYPE
      ENTERPRISE sensorProbe
      VARIABLES
         { spSensorStatus, spSensorValue, spSensorLevelExceeded, 
         spSensorIndex, spSensorName, spSensorDescription }
      DESCRIPTION
         "RelayArray1.4 sensor trap"
      --#SEVERITY  MAJOR
      ::= 714

   spRelayArray1-5Status TRAP-TYPE
      ENTERPRISE sensorProbe
      VARIABLES
         { spSensorStatus, spSensorValue, spSensorLevelExceeded, 
         spSensorIndex, spSensorName, spSensorDescription }
      DESCRIPTION
         "RelayArray1.5 sensor trap"
      --#SEVERITY  MAJOR
      ::= 715

   spRelayArray1-6Status TRAP-TYPE
      ENTERPRISE sensorProbe
      VARIABLES
         { spSensorStatus, spSensorValue, spSensorLevelExceeded, 
         spSensorIndex, spSensorName, spSensorDescription }
      DESCRIPTION
         "RelayArray1.6 sensor trap"
      --#SEVERITY  MAJOR
      ::= 716

   spRelayArray1-7Status TRAP-TYPE
      ENTERPRISE sensorProbe
      VARIABLES
         { spSensorStatus, spSensorValue, spSensorLevelExceeded, 
         spSensorIndex, spSensorName, spSensorDescription }
      DESCRIPTION
         "RelayArray1.7 sensor trap"
      --#SEVERITY  MAJOR
      ::= 717

   spRelayArray1-8Status TRAP-TYPE
      ENTERPRISE sensorProbe
      VARIABLES
         { spSensorStatus, spSensorValue, spSensorLevelExceeded, 
         spSensorIndex, spSensorName, spSensorDescription }
      DESCRIPTION
         "RelayArray1.8 sensor trap"
      --#SEVERITY  MAJOR
      ::= 718

   spRelayArray2-1Status TRAP-TYPE
      ENTERPRISE sensorProbe
      VARIABLES
         { spSensorStatus, spSensorValue, spSensorLevelExceeded, 
         spSensorIndex, spSensorName, spSensorDescription }
      DESCRIPTION
         "RelayArray2.1 sensor trap"
      --#SEVERITY  MAJOR
      ::= 721

   spRelayArray2-2Status TRAP-TYPE
      ENTERPRISE sensorProbe
      VARIABLES
         { spSensorStatus, spSensorValue, spSensorLevelExceeded, 
         spSensorIndex, spSensorName, spSensorDescription }
      DESCRIPTION
         "RelayArray2.2 sensor trap"
      --#SEVERITY  MAJOR
      ::= 722

   spRelayArray2-3Status TRAP-TYPE
      ENTERPRISE sensorProbe
      VARIABLES
         { spSensorStatus, spSensorValue, spSensorLevelExceeded, 
         spSensorIndex, spSensorName, spSensorDescription }
      DESCRIPTION
         "RelayArray2.3 sensor trap"
      --#SEVERITY  MAJOR
      ::= 723

   spRelayArray2-4Status TRAP-TYPE
      ENTERPRISE sensorProbe
      VARIABLES
         { spSensorStatus, spSensorValue, spSensorLevelExceeded, 
         spSensorIndex, spSensorName, spSensorDescription }
      DESCRIPTION
         "RelayArray2.4 sensor trap"
      --#SEVERITY  MAJOR
      ::= 724

   spRelayArray2-5Status TRAP-TYPE
      ENTERPRISE sensorProbe
      VARIABLES
         { spSensorStatus, spSensorValue, spSensorLevelExceeded, 
         spSensorIndex, spSensorName, spSensorDescription }
      DESCRIPTION
         "RelayArray2.5 sensor trap"
      --#SEVERITY  MAJOR
      ::= 725

   spRelayArray2-6Status TRAP-TYPE
      ENTERPRISE sensorProbe
      VARIABLES
         { spSensorStatus, spSensorValue, spSensorLevelExceeded, 
         spSensorIndex, spSensorName, spSensorDescription }
      DESCRIPTION
         "RelayArray2.6 sensor trap"
      --#SEVERITY  MAJOR
      ::= 726

   spRelayArray2-7Status TRAP-TYPE
      ENTERPRISE sensorProbe
      VARIABLES
         { spSensorStatus, spSensorValue, spSensorLevelExceeded, 
         spSensorIndex, spSensorName, spSensorDescription }
      DESCRIPTION
         "RelayArray2.7 sensor trap"
      --#SEVERITY  MAJOR
      ::= 727

   spRelayArray2-8Status TRAP-TYPE
      ENTERPRISE sensorProbe
      VARIABLES
         { spSensorStatus, spSensorValue, spSensorLevelExceeded, 
         spSensorIndex, spSensorName, spSensorDescription }
      DESCRIPTION
         "RelayArray2.8 sensor trap"
      --#SEVERITY  MAJOR
      ::= 728

   spRelayArray3-1Status TRAP-TYPE
      ENTERPRISE sensorProbe
      VARIABLES
         { spSensorStatus, spSensorValue, spSensorLevelExceeded, 
         spSensorIndex, spSensorName, spSensorDescription }
      DESCRIPTION
         "RelayArray3.1 sensor trap"
      --#SEVERITY  MAJOR
      ::= 731

   spRelayArray3-2Status TRAP-TYPE
      ENTERPRISE sensorProbe
      VARIABLES
         { spSensorStatus, spSensorValue, spSensorLevelExceeded, 
         spSensorIndex, spSensorName, spSensorDescription }
      DESCRIPTION
         "RelayArray3.2 sensor trap"
      --#SEVERITY  MAJOR
      ::= 732

   spRelayArray3-3Status TRAP-TYPE
      ENTERPRISE sensorProbe
      VARIABLES
         { spSensorStatus, spSensorValue, spSensorLevelExceeded, 
         spSensorIndex, spSensorName, spSensorDescription }
      DESCRIPTION
         "RelayArray3.3 sensor trap"
      --#SEVERITY  MAJOR
      ::= 733

   spRelayArray3-4Status TRAP-TYPE
      ENTERPRISE sensorProbe
      VARIABLES
         { spSensorStatus, spSensorValue, spSensorLevelExceeded, 
         spSensorIndex, spSensorName, spSensorDescription }
      DESCRIPTION
         "RelayArray3.4 sensor trap"
      --#SEVERITY  MAJOR
      ::= 734

   spRelayArray3-5Status TRAP-TYPE
      ENTERPRISE sensorProbe
      VARIABLES
         { spSensorStatus, spSensorValue, spSensorLevelExceeded, 
         spSensorIndex, spSensorName, spSensorDescription }
      DESCRIPTION
         "RelayArray3.5 sensor trap"
      --#SEVERITY  MAJOR
      ::= 735

   spRelayArray3-6Status TRAP-TYPE
      ENTERPRISE sensorProbe
      VARIABLES
         { spSensorStatus, spSensorValue, spSensorLevelExceeded, 
         spSensorIndex, spSensorName, spSensorDescription }
      DESCRIPTION
         "RelayArray3.6 sensor trap"
      --#SEVERITY  MAJOR
      ::= 736

   spRelayArray3-7Status TRAP-TYPE
      ENTERPRISE sensorProbe
      VARIABLES
         { spSensorStatus, spSensorValue, spSensorLevelExceeded, 
         spSensorIndex, spSensorName, spSensorDescription }
      DESCRIPTION
         "RelayArray3.7 sensor trap"
      --#SEVERITY  MAJOR
      ::= 737

   spRelayArray3-8Status TRAP-TYPE
      ENTERPRISE sensorProbe
      VARIABLES
         { spSensorStatus, spSensorValue, spSensorLevelExceeded, 
         spSensorIndex, spSensorName, spSensorDescription }
      DESCRIPTION
         "RelayArray3.8 sensor trap"
      --#SEVERITY  MAJOR
      ::= 738

   spRelayArray4-1Status TRAP-TYPE
      ENTERPRISE sensorProbe
      VARIABLES
         { spSensorStatus, spSensorValue, spSensorLevelExceeded, 
         spSensorIndex, spSensorName, spSensorDescription }
      DESCRIPTION
         "RelayArray4.1 sensor trap"
      --#SEVERITY  MAJOR
      ::= 741

   spRelayArray4-2Status TRAP-TYPE
      ENTERPRISE sensorProbe
      VARIABLES
         { spSensorStatus, spSensorValue, spSensorLevelExceeded, 
         spSensorIndex, spSensorName, spSensorDescription }
      DESCRIPTION
         "RelayArray4.2 sensor trap"
      --#SEVERITY  MAJOR
      ::= 742

   spRelayArray4-3Status TRAP-TYPE
      ENTERPRISE sensorProbe
      VARIABLES
         { spSensorStatus, spSensorValue, spSensorLevelExceeded, 
         spSensorIndex, spSensorName, spSensorDescription }
      DESCRIPTION
         "RelayArray4.3 sensor trap"
      --#SEVERITY  MAJOR
      ::= 743

   spRelayArray4-4Status TRAP-TYPE
      ENTERPRISE sensorProbe
      VARIABLES
         { spSensorStatus, spSensorValue, spSensorLevelExceeded, 
         spSensorIndex, spSensorName, spSensorDescription }
      DESCRIPTION
         "RelayArray4.4 sensor trap"
      --#SEVERITY  MAJOR
      ::= 744

   spRelayArray4-5Status TRAP-TYPE
      ENTERPRISE sensorProbe
      VARIABLES
         { spSensorStatus, spSensorValue, spSensorLevelExceeded, 
         spSensorIndex, spSensorName, spSensorDescription }
      DESCRIPTION
         "RelayArray4.5 sensor trap"
      --#SEVERITY  MAJOR
      ::= 745

   spRelayArray4-6Status TRAP-TYPE
      ENTERPRISE sensorProbe
      VARIABLES
         { spSensorStatus, spSensorValue, spSensorLevelExceeded, 
         spSensorIndex, spSensorName, spSensorDescription }
      DESCRIPTION
         "RelayArray4.6 sensor trap"
      --#SEVERITY  MAJOR
      ::= 746

   spRelayArray4-7Status TRAP-TYPE
      ENTERPRISE sensorProbe
      VARIABLES
         { spSensorStatus, spSensorValue, spSensorLevelExceeded, 
         spSensorIndex, spSensorName, spSensorDescription }
      DESCRIPTION
         "RelayArray4.7 sensor trap"
      --#SEVERITY  MAJOR
      ::= 747

   spRelayArray4-8Status TRAP-TYPE
      ENTERPRISE sensorProbe
      VARIABLES
         { spSensorStatus, spSensorValue, spSensorLevelExceeded, 
         spSensorIndex, spSensorName, spSensorDescription }
      DESCRIPTION
         "RelayArray4.8 sensor trap"
      --#SEVERITY  MAJOR
      ::= 748

   spRelayArray5-1Status TRAP-TYPE
      ENTERPRISE sensorProbe
      VARIABLES
         { spSensorStatus, spSensorValue, spSensorLevelExceeded, 
         spSensorIndex, spSensorName, spSensorDescription }
      DESCRIPTION
         "RelayArray5.1 sensor trap"
      --#SEVERITY  MAJOR
      ::= 751

   spRelayArray5-2Status TRAP-TYPE
      ENTERPRISE sensorProbe
      VARIABLES
         { spSensorStatus, spSensorValue, spSensorLevelExceeded, 
         spSensorIndex, spSensorName, spSensorDescription }
      DESCRIPTION
         "RelayArray5.2 sensor trap"
      --#SEVERITY  MAJOR
      ::= 752

   spRelayArray5-3Status TRAP-TYPE
      ENTERPRISE sensorProbe
      VARIABLES
         { spSensorStatus, spSensorValue, spSensorLevelExceeded, 
         spSensorIndex, spSensorName, spSensorDescription }
      DESCRIPTION
         "RelayArray5.3 sensor trap"
      --#SEVERITY  MAJOR
      ::= 753

   spRelayArray5-4Status TRAP-TYPE
      ENTERPRISE sensorProbe
      VARIABLES
         { spSensorStatus, spSensorValue, spSensorLevelExceeded, 
         spSensorIndex, spSensorName, spSensorDescription }
      DESCRIPTION
         "RelayArray5.4 sensor trap"
      --#SEVERITY  MAJOR
      ::= 754

   spRelayArray5-5Status TRAP-TYPE
      ENTERPRISE sensorProbe
      VARIABLES
         { spSensorStatus, spSensorValue, spSensorLevelExceeded, 
         spSensorIndex, spSensorName, spSensorDescription }
      DESCRIPTION
         "RelayArray5.5 sensor trap"
      --#SEVERITY  MAJOR
      ::= 755

   spRelayArray5-6Status TRAP-TYPE
      ENTERPRISE sensorProbe
      VARIABLES
         { spSensorStatus, spSensorValue, spSensorLevelExceeded, 
         spSensorIndex, spSensorName, spSensorDescription }
      DESCRIPTION
         "RelayArray5.6 sensor trap"
      --#SEVERITY  MAJOR
      ::= 756

   spRelayArray5-7Status TRAP-TYPE
      ENTERPRISE sensorProbe
      VARIABLES
         { spSensorStatus, spSensorValue, spSensorLevelExceeded, 
         spSensorIndex, spSensorName, spSensorDescription }
      DESCRIPTION
         "RelayArray5.7 sensor trap"
      --#SEVERITY  MAJOR
      ::= 757

   spRelayArray5-8Status TRAP-TYPE
      ENTERPRISE sensorProbe
      VARIABLES
         { spSensorStatus, spSensorValue, spSensorLevelExceeded, 
         spSensorIndex, spSensorName, spSensorDescription }
      DESCRIPTION
         "RelayArray5.8 sensor trap"
      --#SEVERITY  MAJOR
      ::= 758

   spRelayArray6-1Status TRAP-TYPE
      ENTERPRISE sensorProbe
      VARIABLES
         { spSensorStatus, spSensorValue, spSensorLevelExceeded, 
         spSensorIndex, spSensorName, spSensorDescription }
      DESCRIPTION
         "RelayArray6.1 sensor trap"
      --#SEVERITY  MAJOR
      ::= 761

   spRelayArray6-2Status TRAP-TYPE
      ENTERPRISE sensorProbe
      VARIABLES
         { spSensorStatus, spSensorValue, spSensorLevelExceeded, 
         spSensorIndex, spSensorName, spSensorDescription }
      DESCRIPTION
         "RelayArray6.2 sensor trap"
      --#SEVERITY  MAJOR
      ::= 762

   spRelayArray6-3Status TRAP-TYPE
      ENTERPRISE sensorProbe
      VARIABLES
         { spSensorStatus, spSensorValue, spSensorLevelExceeded, 
         spSensorIndex, spSensorName, spSensorDescription }
      DESCRIPTION
         "RelayArray6.3 sensor trap"
      --#SEVERITY  MAJOR
      ::= 763

   spRelayArray6-4Status TRAP-TYPE
      ENTERPRISE sensorProbe
      VARIABLES
         { spSensorStatus, spSensorValue, spSensorLevelExceeded, 
         spSensorIndex, spSensorName, spSensorDescription }
      DESCRIPTION
         "RelayArray6.4 sensor trap"
      --#SEVERITY  MAJOR
      ::= 764

   spRelayArray6-5Status TRAP-TYPE
      ENTERPRISE sensorProbe
      VARIABLES
         { spSensorStatus, spSensorValue, spSensorLevelExceeded, 
         spSensorIndex, spSensorName, spSensorDescription }
      DESCRIPTION
         "RelayArray6.5 sensor trap"
      --#SEVERITY  MAJOR
      ::= 765

   spRelayArray6-6Status TRAP-TYPE
      ENTERPRISE sensorProbe
      VARIABLES
         { spSensorStatus, spSensorValue, spSensorLevelExceeded, 
         spSensorIndex, spSensorName, spSensorDescription }
      DESCRIPTION
         "RelayArray6.6 sensor trap"
      --#SEVERITY  MAJOR
      ::= 766

   spRelayArray6-7Status TRAP-TYPE
      ENTERPRISE sensorProbe
      VARIABLES
         { spSensorStatus, spSensorValue, spSensorLevelExceeded, 
         spSensorIndex, spSensorName, spSensorDescription }
      DESCRIPTION
         "RelayArray6.7 sensor trap"
      --#SEVERITY  MAJOR
      ::= 767

   spRelayArray6-8Status TRAP-TYPE
      ENTERPRISE sensorProbe
      VARIABLES
         { spSensorStatus, spSensorValue, spSensorLevelExceeded, 
         spSensorIndex, spSensorName, spSensorDescription }
      DESCRIPTION
         "RelayArray6.8 sensor trap"
      --#SEVERITY  MAJOR
      ::= 768

   spRelayArray7-1Status TRAP-TYPE
      ENTERPRISE sensorProbe
      VARIABLES
         { spSensorStatus, spSensorValue, spSensorLevelExceeded, 
         spSensorIndex, spSensorName, spSensorDescription }
      DESCRIPTION
         "RelayArray7.1 sensor trap"
      --#SEVERITY  MAJOR
      ::= 771

   spRelayArray7-2Status TRAP-TYPE
      ENTERPRISE sensorProbe
      VARIABLES
         { spSensorStatus, spSensorValue, spSensorLevelExceeded, 
         spSensorIndex, spSensorName, spSensorDescription }
      DESCRIPTION
         "RelayArray7.2 sensor trap"
      --#SEVERITY  MAJOR
      ::= 772

   spRelayArray7-3Status TRAP-TYPE
      ENTERPRISE sensorProbe
      VARIABLES
         { spSensorStatus, spSensorValue, spSensorLevelExceeded, 
         spSensorIndex, spSensorName, spSensorDescription }
      DESCRIPTION
         "RelayArray7.3 sensor trap"
      --#SEVERITY  MAJOR
      ::= 773

   spRelayArray7-4Status TRAP-TYPE
      ENTERPRISE sensorProbe
      VARIABLES
         { spSensorStatus, spSensorValue, spSensorLevelExceeded, 
         spSensorIndex, spSensorName, spSensorDescription }
      DESCRIPTION
         "RelayArray7.4 sensor trap"
      --#SEVERITY  MAJOR
      ::= 774

   spRelayArray7-5Status TRAP-TYPE
      ENTERPRISE sensorProbe
      VARIABLES
         { spSensorStatus, spSensorValue, spSensorLevelExceeded, 
         spSensorIndex, spSensorName, spSensorDescription }
      DESCRIPTION
         "RelayArray7.5 sensor trap"
      --#SEVERITY  MAJOR
      ::= 775

   spRelayArray7-6Status TRAP-TYPE
      ENTERPRISE sensorProbe
      VARIABLES
         { spSensorStatus, spSensorValue, spSensorLevelExceeded, 
         spSensorIndex, spSensorName, spSensorDescription }
      DESCRIPTION
         "RelayArray7.6 sensor trap"
      --#SEVERITY  MAJOR
      ::= 776

   spRelayArray7-7Status TRAP-TYPE
      ENTERPRISE sensorProbe
      VARIABLES
         { spSensorStatus, spSensorValue, spSensorLevelExceeded, 
         spSensorIndex, spSensorName, spSensorDescription }
      DESCRIPTION
         "RelayArray7.7 sensor trap"
      --#SEVERITY  MAJOR
      ::= 777

   spRelayArray7-8Status TRAP-TYPE
      ENTERPRISE sensorProbe
      VARIABLES
         { spSensorStatus, spSensorValue, spSensorLevelExceeded, 
         spSensorIndex, spSensorName, spSensorDescription }
      DESCRIPTION
         "RelayArray7.8 sensor trap"
      --#SEVERITY  MAJOR
      ::= 778

   spRelayArray8-1Status TRAP-TYPE
      ENTERPRISE sensorProbe
      VARIABLES
         { spSensorStatus, spSensorValue, spSensorLevelExceeded, 
         spSensorIndex, spSensorName, spSensorDescription }
      DESCRIPTION
         "RelayArray8.1 sensor trap"
      --#SEVERITY  MAJOR
      ::= 781

   spRelayArray8-2Status TRAP-TYPE
      ENTERPRISE sensorProbe
      VARIABLES
         { spSensorStatus, spSensorValue, spSensorLevelExceeded, 
         spSensorIndex, spSensorName, spSensorDescription }
      DESCRIPTION
         "RelayArray8.2 sensor trap"
      --#SEVERITY  MAJOR
      ::= 782

   spRelayArray8-3Status TRAP-TYPE
      ENTERPRISE sensorProbe
      VARIABLES
         { spSensorStatus, spSensorValue, spSensorLevelExceeded, 
         spSensorIndex, spSensorName, spSensorDescription }
      DESCRIPTION
         "RelayArray8.3 sensor trap"
      --#SEVERITY  MAJOR
      ::= 783

   spRelayArray8-4Status TRAP-TYPE
      ENTERPRISE sensorProbe
      VARIABLES
         { spSensorStatus, spSensorValue, spSensorLevelExceeded, 
         spSensorIndex, spSensorName, spSensorDescription }
      DESCRIPTION
         "RelayArray8.4 sensor trap"
      --#SEVERITY  MAJOR
      ::= 784

   spRelayArray8-5Status TRAP-TYPE
      ENTERPRISE sensorProbe
      VARIABLES
         { spSensorStatus, spSensorValue, spSensorLevelExceeded, 
         spSensorIndex, spSensorName, spSensorDescription }
      DESCRIPTION
         "RelayArray8.5 sensor trap"
      --#SEVERITY  MAJOR
      ::= 785

   spRelayArray8-6Status TRAP-TYPE
      ENTERPRISE sensorProbe
      VARIABLES
         { spSensorStatus, spSensorValue, spSensorLevelExceeded, 
         spSensorIndex, spSensorName, spSensorDescription }
      DESCRIPTION
         "RelayArray8.6 sensor trap"
      --#SEVERITY  MAJOR
      ::= 786

   spRelayArray8-7Status TRAP-TYPE
      ENTERPRISE sensorProbe
      VARIABLES
         { spSensorStatus, spSensorValue, spSensorLevelExceeded, 
         spSensorIndex, spSensorName, spSensorDescription }
      DESCRIPTION
         "RelayArray8.7 sensor trap"
      --#SEVERITY  MAJOR
      ::= 787

   spRelayArray8-8Status TRAP-TYPE
      ENTERPRISE sensorProbe
      VARIABLES
         { spSensorStatus, spSensorValue, spSensorLevelExceeded, 
         spSensorIndex, spSensorName, spSensorDescription }
      DESCRIPTION
         "RelayArray8.8 sensor trap"
      --#SEVERITY  MAJOR
      ::= 788

   spVirtual1Status TRAP-TYPE
      ENTERPRISE sensorProbe
      VARIABLES
         { spSensorStatus, spSensorValue, spSensorLevelExceeded, 
         spSensorIndex, spSensorName, spSensorDescription }
      DESCRIPTION
         "Virtual1 sensor trap"
      --#SEVERITY  MAJOR
      ::= 801

   spVirtual2Status TRAP-TYPE
      ENTERPRISE sensorProbe
      VARIABLES
         { spSensorStatus, spSensorValue, spSensorLevelExceeded, 
         spSensorIndex, spSensorName, spSensorDescription }
      DESCRIPTION
         "Virtual2 sensor trap"
      --#SEVERITY  MAJOR
      ::= 802

   spVirtual3Status TRAP-TYPE
      ENTERPRISE sensorProbe
      VARIABLES
         { spSensorStatus, spSensorValue, spSensorLevelExceeded, 
         spSensorIndex, spSensorName, spSensorDescription }
      DESCRIPTION
         "Virtual3 sensor trap"
      --#SEVERITY  MAJOR
      ::= 803

   spVirtual4Status TRAP-TYPE
      ENTERPRISE sensorProbe
      VARIABLES
         { spSensorStatus, spSensorValue, spSensorLevelExceeded, 
         spSensorIndex, spSensorName, spSensorDescription }
      DESCRIPTION
         "Virtual4 sensor trap"
      --#SEVERITY  MAJOR
      ::= 804

   spVirtual5Status TRAP-TYPE
      ENTERPRISE sensorProbe
      VARIABLES
         { spSensorStatus, spSensorValue, spSensorLevelExceeded, 
         spSensorIndex, spSensorName, spSensorDescription }
      DESCRIPTION
         "Virtual5 sensor trap"
      --#SEVERITY  MAJOR
      ::= 805

   spVirtual6Status TRAP-TYPE
      ENTERPRISE sensorProbe
      VARIABLES
         { spSensorStatus, spSensorValue, spSensorLevelExceeded, 
         spSensorIndex, spSensorName, spSensorDescription }
      DESCRIPTION
         "Virtual6 sensor trap"
      --#SEVERITY  MAJOR
      ::= 806

   spVirtual7Status TRAP-TYPE
      ENTERPRISE sensorProbe
      VARIABLES
         { spSensorStatus, spSensorValue, spSensorLevelExceeded, 
         spSensorIndex, spSensorName, spSensorDescription }
      DESCRIPTION
         "Virtual7 sensor trap"
      --#SEVERITY  MAJOR
      ::= 807

   spVirtual8Status TRAP-TYPE
      ENTERPRISE sensorProbe
      VARIABLES
         { spSensorStatus, spSensorValue, spSensorLevelExceeded, 
         spSensorIndex, spSensorName, spSensorDescription }
      DESCRIPTION
         "Virtual8 sensor trap"
      --#SEVERITY  MAJOR
      ::= 808

   spVirtual9Status TRAP-TYPE
      ENTERPRISE sensorProbe
      VARIABLES
         { spSensorStatus, spSensorValue, spSensorLevelExceeded, 
         spSensorIndex, spSensorName, spSensorDescription }
      DESCRIPTION
         "Virtual9 sensor trap"
      --#SEVERITY  MAJOR
      ::= 809

   spVirtual10Status TRAP-TYPE
      ENTERPRISE sensorProbe
      VARIABLES
         { spSensorStatus, spSensorValue, spSensorLevelExceeded, 
         spSensorIndex, spSensorName, spSensorDescription }
      DESCRIPTION
         "Virtual10 sensor trap"
      --#SEVERITY  MAJOR
      ::= 810

   spVirtual11Status TRAP-TYPE
      ENTERPRISE sensorProbe
      VARIABLES
         { spSensorStatus, spSensorValue, spSensorLevelExceeded, 
         spSensorIndex, spSensorName, spSensorDescription }
      DESCRIPTION
         "Virtual11 sensor trap"
      --#SEVERITY  MAJOR
      ::= 811

   spVirtual12Status TRAP-TYPE
      ENTERPRISE sensorProbe
      VARIABLES
         { spSensorStatus, spSensorValue, spSensorLevelExceeded, 
         spSensorIndex, spSensorName, spSensorDescription }
      DESCRIPTION
         "Virtual12 sensor trap"
      --#SEVERITY  MAJOR
      ::= 812

   spVirtual13Status TRAP-TYPE
      ENTERPRISE sensorProbe
      VARIABLES
         { spSensorStatus, spSensorValue, spSensorLevelExceeded, 
         spSensorIndex, spSensorName, spSensorDescription }
      DESCRIPTION
         "Virtual13 sensor trap"
      --#SEVERITY  MAJOR
      ::= 813

   spVirtual14Status TRAP-TYPE
      ENTERPRISE sensorProbe
      VARIABLES
         { spSensorStatus, spSensorValue, spSensorLevelExceeded, 
         spSensorIndex, spSensorName, spSensorDescription }
      DESCRIPTION
         "Virtual14 sensor trap"
      --#SEVERITY  MAJOR
      ::= 814

   spVirtual15Status TRAP-TYPE
      ENTERPRISE sensorProbe
      VARIABLES
         { spSensorStatus, spSensorValue, spSensorLevelExceeded, 
         spSensorIndex, spSensorName, spSensorDescription }
      DESCRIPTION
         "Virtual15 sensor trap"
      --#SEVERITY  MAJOR
      ::= 815

   spVirtual16Status TRAP-TYPE
      ENTERPRISE sensorProbe
      VARIABLES
         { spSensorStatus, spSensorValue, spSensorLevelExceeded, 
         spSensorIndex, spSensorName, spSensorDescription }
      DESCRIPTION
         "Virtual16 sensor trap"
      --#SEVERITY  MAJOR
      ::= 816

   spVirtual17Status TRAP-TYPE
      ENTERPRISE sensorProbe
      VARIABLES
         { spSensorStatus, spSensorValue, spSensorLevelExceeded, 
         spSensorIndex, spSensorName, spSensorDescription }
      DESCRIPTION
         "Virtual17 sensor trap"
      --#SEVERITY  MAJOR
      ::= 817

   spVirtual18Status TRAP-TYPE
      ENTERPRISE sensorProbe
      VARIABLES
         { spSensorStatus, spSensorValue, spSensorLevelExceeded, 
         spSensorIndex, spSensorName, spSensorDescription }
      DESCRIPTION
         "Virtual18 sensor trap"
      --#SEVERITY  MAJOR
      ::= 818

   spVirtual19Status TRAP-TYPE
      ENTERPRISE sensorProbe
      VARIABLES
         { spSensorStatus, spSensorValue, spSensorLevelExceeded, 
         spSensorIndex, spSensorName, spSensorDescription }
      DESCRIPTION
         "Virtual19 sensor trap"
      --#SEVERITY  MAJOR
      ::= 819

   spVirtual20Status TRAP-TYPE
      ENTERPRISE sensorProbe
      VARIABLES
         { spSensorStatus, spSensorValue, spSensorLevelExceeded, 
         spSensorIndex, spSensorName, spSensorDescription }
      DESCRIPTION
         "Virtual20 sensor trap"
      --#SEVERITY  MAJOR
      ::= 820

   spCustomStatus TRAP-TYPE
      ENTERPRISE sensorProbe
      VARIABLES
         { spSensorStatus, spSensorValue, spSensorLevelExceeded, 
         spSensorIndex, spSensorName, spSensorDescription,
    spSensorType, spSensorStatusName, spSensorSubIndex,
    spBoardIndex, spBoardDescription, spEventTimeStamp,
    spEventClassNumber, spEventClassName }
      DESCRIPTION
         "Custom sensor trap"
      --#SEVERITY  MAJOR
      ::= 1000

END
