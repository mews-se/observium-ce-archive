-- Copyright (C) 2008-2016 Aricent. All Rights Reserved

-- ECFM-Y1731 Proprietary MIB Definition 

-- This MIB contains tables used to configure a switch running 
-- ECFM-Y1731 in addition to the standard 802.1ag MIB and 
-- ECFM Proprietary MIB.
 
   ARICENT-ECFM-Y1731-MI-MIB DEFINITIONS ::= BEGIN 
 
   IMPORTS 
      MODULE-IDENTITY, 
      OBJECT-TYPE,  
      NOTIFICATION-TYPE,
      enterprises, 
      Integer32, 
      Unsigned32                         FROM SNMPv2-SMI 
      TEXTUAL-CONVENTION, 
      TruthValue, DisplayString,
      TimeInterval, TimeStamp,
      MacAddress, RowStatus, RowPointer  FROM SNMPv2-TC
      InterfaceIndex                     FROM IF-MIB
      Dot1agCfmMepId,
      Dot1agCfmMDLevelOrNone, 
      Dot1agCfmMepIdOrZero               FROM IEEE8021-CFM-MIB
      VlanId                             FROM Q-BRIDGE-MIB
      ;
      fsMIY1731MIB MODULE-IDENTITY 
         LAST-UPDATED "201209050000Z" 
         ORGANIZATION "ARICENT COMMUNICATIONS SOFTWARE" 
         CONTACT-INFO "support@aricent.com" 
         DESCRIPTION 
              "The Proprietary MIB for ECFM-Y1731 module with multiple
              instance capability"
         REVISION "201209050000Z" 
         DESCRIPTION 
              "The Proprietary MIB for ECFM-Y1731 module with multiple
              instance capability"
      ::=  { enterprises aricent-communication-holding-ltd(29601) iss(2) 7 }
 
 
fsMIY1731Notifications      OBJECT IDENTIFIER ::= { fsMIY1731MIB 0 }
fsMIY1731MIBObjects         OBJECT IDENTIFIER ::= { fsMIY1731MIB 1 }

-- ******************************************************************
-- Groups in the ECFM-Y1731 MIB Module
-- ******************************************************************

fsMIY1731System            OBJECT IDENTIFIER ::= { fsMIY1731MIBObjects 1 }
fsMIY1731Context           OBJECT IDENTIFIER ::= { fsMIY1731MIBObjects 2 }
      
-- ******************************************************************
-- Textual conventions
-- ******************************************************************

FsY1731CcmApplication ::= TEXTUAL-CONVENTION
    STATUS      current
    DESCRIPTION
       "This object specifies an enumerated value indicates the ETH-CC role to be or currently being 
        performed.

        ccFaultManagement(0)        Indicates ETH-CC is used for Fault Management.
        ccPerformanceMonitoring(1)  Indicates ETH-CC is used for Performance 
                                        Monitoring.
        ccProtectionSwitching(2)    Indicates ETH-CC is used for Protection 
                                    Switching
      "
    SYNTAX      INTEGER {
                  ccFaultManagement         (0),
                  ccPerformanceMonitoring   (1),
                  ccProtectionSwitching     (2)
                }

FsY1731TestTlvPatternType ::= TEXTUAL-CONVENTION
    STATUS      current
    DESCRIPTION
       "This object specifies the Test pattern for Test TLV to be 
        included in LBM or TST message.

        patternNullSignalWithoutCRC32(0) Pattern contains null signal without 
                                         any CRC.
        patternNullSignalWithCRC32(1)    Pattern contains null signal with CRC.
        patternPRBSWithoutCRC32(2)       Pattern contains pseudo random bit 
                                         sequence 2^-31-1 without any CRC.
        patternPRBSWithCRC32(3)          Pattern contains pseudo random bit 
                                         sequence 2^-31-1 with CRC.
      "
    SYNTAX      INTEGER {
                  patternNullSignalWithoutCRC32  (0),
                  patternNullSignalWithCRC32     (1),
                  patternPRBSWithoutCRC32        (2),
                  patternPRBSWithCRC32           (3)
                }

FsY1731DestType ::= TEXTUAL-CONVENTION
    STATUS      current
    DESCRIPTION
       "This object specifies the type of 
       transaction, unicast ,through MEPID or  multicast. 

        unicast(0)         Indicates the operation is to be unicast.
        mepid(1)           Indicates that MEPID of the target MEP is used for
                           operation.
        multicast(2)       Indicate the operation is Multicast .
        mipid(3)           Indicates that MIP info of the target is used for 
                           operation only in MPLS-TP networks (Currently not
                           applicable for Ethernet).
      "
    SYNTAX      INTEGER {
                  unicast                     (0),
                  mepid                       (1),
                  multicast                   (2),
                  mipid                       (3)
                }
                
FsY1731TransmitStatus ::= TEXTUAL-CONVENTION
    STATUS      current
    DESCRIPTION
       "This object specifies an enumerated value indicates whether particular transmission can be 
       initiated.

        ready(0)       Indicates transmission can be initiated.
        notReady(1)    Indicates transmission can not be initiated.
        start(2)       To initiate the transmission .
        stop(3)        To stop the transmission .

      "
    SYNTAX      INTEGER {
                  ready                   (0),
                  notReady                (1),
                  start                   (2),
                  stop                    (3) 
                }

FsY1731TransmitLbmTlvTypeOrNone ::= TEXTUAL-CONVENTION
    STATUS      current
    DESCRIPTION
       "This object specifies an enumerated value indicates which TLV is to be included in the LBM.

        none(0)               Indicates No TLV is included in the LBM.
        dataTlv (1)           Indicates Data TLV is included in the LBM.
        testTlv (2)           Indicates Test TLV is included in the LBM.
      "
    SYNTAX      INTEGER {
                  none                   (0),
                  dataTlv                (1),
                  testTlv                (2)
                }

FsY1731LbrErrType ::= TEXTUAL-CONVENTION
    STATUS      current
    DESCRIPTION
       "This object specifies an enumerated value indicates the received loopback reply error type.
        none                    (0)       Indicates that no error was
                                          encountered in the received LBR.
        BadMacServiceDataUnit   (1)       Indicates bad/corrupt mac service data unit
        Crc32CheckFailure       (2)       Indicates CRC32 checksum failure
      "
    SYNTAX      INTEGER {
                  none                   (0),
                  badMacServiceDataUnit  (1),
                  crc32CheckFailure      (2)
                }

FsY1731LmmInterval ::= TEXTUAL-CONVENTION
    STATUS      current
    DESCRIPTION
       "This object specifies the interval at which LMMs are sent by a MEP.
        The possible values are:
        
        interval100ms(1)   LMMs are sent every 100 milliseconds.
        interval1s(2)      LMMs are sent every second.
        interval10s(3)     LMMs are sent every 10 seconds.
        interval1min(4)    LMMs are sent every minute.
        interval10min(5)   LMMs are sent every 10 minutes.

       "
    SYNTAX      INTEGER {
                  interval100ms     (1),
                  interval1s        (2),
                  interval10s       (3),
                  interval1min      (4),
                  interval10min     (5)
                }

FsY1731TimeIntervalType ::= TEXTUAL-CONVENTION
    STATUS      current
    DESCRIPTION
       "This object specifies the units of interval at which LBM or TSTs are sent by a MEP.
        The possible values are:
        
        microseconds(1)   units for LBMs or TSTs transmission interval are 
                          microseconds.
        milliseconds(2)   units for LBMs or TSTs transmission interval are 
                          milliseconds.
        seconds(3)        units for LBM or TST transmission interval are 
                          seconds.

       "
    SYNTAX      INTEGER {
                  microseconds  (1),
                  milliseconds  (2),
                  seconds       (3)
                }


FsY1731AisLckInterval ::= TEXTUAL-CONVENTION
    STATUS      current
    DESCRIPTION
       "This object specifies the interval at which AIS or LCK(s) are sent by a MEP.
        The possible values are:
        
        interval1s(1)       AIS or LCK(s) are sent every second.
        interval1min(2)     AIS or LCK(s) are sent every minute.
        
        Note: enumerations start at one to match the 'AIS/LCK Interval
              field' protocol field.
       "
    SYNTAX      INTEGER {
                  interval1s        (1),
                  interval1min      (2)
                }

FsY1731Traps ::= TEXTUAL-CONVENTION
    STATUS      current
    DESCRIPTION
       "This object specifies the notifications to be provided to Management entity.
        Multiple notifications can be enabled at the same time. Notifications 
        are:
        none(0)				 Dummy Bit
        bTrapTstReceivedWithError(1)     The MEP has received a TST PDU with bad 
                                         mac service data unit or invalid CRC32 
                                         checksum.
        bTrapFrameLoss(2)                The calculated frame loss value is greater
                                         than the configured frame loss threshold
                                         value.
        bTrapFrameDelay(3)               The calculated frame delay value is greater
                                         than the configured frame delay threshold
                                         value.
        bTrapDefRdiCondition(4)          The MEP has encountered remote MEP defect
                                         condition.
        bTrapDefLossOfContinuity(5)      The MEP has encountered loss of continuity
                                         defect condition.
        bTrapDefUnexpectedPeriod(6)      The MEP has encountered unexpected period
                                         defect condition.
        bTrapDefUnexpectedMep(7)         The MEP has encountered unexpected MEP
                                         defect condition.
        bTrapDefMisMerge(8)              The MEP has encountered mismerge defect 
                                         condition.
        bTrapDefUnexpectedMegLevel(9)    The MEP has encountered unexpected MEG level 
                                         defect condition.
        bTrapDefLocalLinkFailure(10)     The MEP has encountered local link failure 
                                         defect condition.
        bTrapDefInternalHWFailure(11)    The MEP has encountered internal hardware 
                                         failure defect condition.
        bTrapDefInternalSWFailure(12)    The MEP has encountered internal software 
                                         failure defect condition.
        bTrapDefAisCondition(13)         The MEP has encountered alarm indication 
                                         defect condition.
        bTrapDefLckCondition(14)         The MEP has encountered locked defect 
                                         condition. "
    SYNTAX      BITS{
			none (0),
                        bTrapTstReceivedWithError (1),
                        bTrapFrameLoss (2),
                        bTrapFrameDelay (3),
                        bTrapDefRdiCondition (4),
                        bTrapDefLossOfContinuity (5),
                        bTrapDefUnexpectedPeriod (6),
                        bTrapDefUnexpectedMep (7),
                        bTrapDefMisMerge (8),
                        bTrapDefUnexpectedMegLevel (9),
                        bTrapDefLocalLinkFailure (10),
                        bTrapDefInternalHWFailure (11),
                        bTrapDefInternalSWFailure (12),
                        bTrapDefAisCondition (13),
                        bTrapDefLckCondition (14)
                     }

FsY1731MepDefects ::= TEXTUAL-CONVENTION
    STATUS      current
    DESCRIPTION
       "This object specifies a MEP to detect and report a number of defects, 
        and multiple defects can be present at the same time.
        These defects conditions are:
	none (0)			 Dummy Bit
        bDefRdiCondition (1)             The MEP has encountered remote MEP defect
                                         condition.
        bDefLossOfContinuity (2)         The MEP has encountered loss of continuity
                                         defect condition.
        bDefUnexpectedPeriod (3)         The MEP has encountered unexpected period
                                         defect condition.
        bDefUnexpectedMep (4)            The MEP has encountered unexpected MEP defect
                                         condition.
        bDefMisMerge (5)                 The MEP has encountered mismerge defect
                                         condition.
        bDefUnexpectedMegLevel (6)       The MEP has encountered unexpected MEG level
                                         defect condition.
        bDefLocalLinkFailure (7)         The MEP has encountered local link failure
                                         defect condition.
        bDefInternalHWFailure (8)        The MEP has encountered internal hardware
                                         failure defect condition.
        bDefInternalSWFailure (9)        The MEP has encountered internal software
                                         failure defect condition.
        bDefAisCondition(10)             The MEP has encountered alarm indication defect
                                         condition.
        bDefLckCondition(11)             The MEP has encountered locked defect
                                         condition. "
    SYNTAX      BITS{
			none (0),
                        bDefRdiCondition (1),
                        bDefLossOfContinuity (2),
                        bDefUnexpectedPeriod (3),
                        bDefUnexpectedMep (4),
                        bDefMisMerge (5),
                        bDefUnexpectedMegLevel (6),
                        bDefLocalLinkFailure (7),
                        bDefInternalHWFailure (8),
                        bDefInternalSWFailure (9),
                        bDefAisCondition (10),
                        bDefLckCondition (11)
                    }

FsY1731ErrorLogType ::= TEXTUAL-CONVENTION
    STATUS      current
    DESCRIPTION
       "This object specifies a MEP to detect and report a number of defects.
       
        logRdiConditionEntry(1)          The MEP has encountered remote MEP defect 
                                         condition entry.
                                         
        logLossOfContinuityEntry(2)      The MEP has encountered loss of continuity 
                                         defect condition  entry.
                                         
        logUnexpectedPeriodEntry(3)      The MEP has encountered unexpected period 
                                         defect condition  entry.
                                         
        logUnexpectedMepEntry(4)         The MEP has encountered unexpected MEP 
                                         defect condition entry.
                                         
        logMisMergeEntry(5)              The MEP has encountered mismerge defect 
                                         condition entry.
                                         
        logUnexpectedMegLevelEntry(6)    The MEP has encountered unexpected MEG 
                                         level defect condition entry.
                                         
        logLocalLinkFailureEntry(7)      The MEP has encountered local link failure 
                                         defect condition entry.
                                         
        logInternalHWFailureEntry(8)     The MEP has encountered internal hardware
                                         failure defect condition entry.
                                         
        logInternalSWFailureEntry(9)     The MEP has encountered internal software 
                                         failure defect condition entry.
                                         
        logAisConditonEntry(10)          The MEP has encountered alarm indication 
                                         defect condition entry.
                                         
        logLckConditionEntry(11)         The MEP has encountered locked defect 
                                         condition entry.
                                         
        logRdiConditionExit(12)          The MEP has encountered remote MEP defect 
                                         condition exit.
                                         
        logLossOfContinuityExit(13)      The MEP has encountered loss of continuity 
                                         defect condition  exit.
                                         
        logUnexpectedPeriodExit(14)      The MEP has encountered unexpected period 
                                         defect condition  exit.
                                         
        logUnexpectedMepExit(15)         The MEP has encountered unexpected MEP 
                                         defect condition exit.
                                         
        logMisMergeExit(16)              The MEP has encountered mismerge defect 
                                         condition exit.
                                         
        logUnexpectedMegLevelExit(17)    The MEP has encountered unexpected MEG level
                                         defect condition exit.
                                         
        logLocalLinkFailureExit(18)      The MEP has encountered local link failure 
                                         defect condition exit.
                                         
        logInternalHWFailureExit(19)     The MEP has encountered internal hardware 
                                         failure defect condition exit.
                                         
        logInternalSWFailureExit(20)     The MEP has encountered internal software 
                                         failure defect condition exit.
                                         
        logAisConditonExit(21)           The MEP has encountered alarm indication 
                                         defect condition exit.
                                         
        logLckConditionExit(22)          The MEP has encountered locked defect 
                                         condition exit."
    SYNTAX      INTEGER{

          logRdiConditionEntry(1),
          logLossOfContinuityEntry(2),
          logUnexpectedPeriodEntry(3),
          logUnexpectedMepEntry(4),
          logMisMergeEntry(5),
          logUnexpectedMegLevelEntry(6),
          logLocalLinkFailureEntry(7),
          logInternalHWFailureEntry(8),
          logInternalSWFailureEntry(9),
          logAisConditonEntry(10),
          logLckConditionEntry(11),
          logRdiConditionExit(12),
          logLossOfContinuityExit(13),
          logUnexpectedPeriodExit(14),
          logUnexpectedMepExit(15),
          logMisMergeExit(16),
          logUnexpectedMegLevelExit(17),
          logLocalLinkFailureExit(18),
          logInternalHWFailureExit(19),
          logInternalSWFailureExit(20),
          logAisConditonExit(21),
          logLckConditionExit(22)
                    }

FsY1731TimeRepresentation ::= TEXTUAL-CONVENTION
    DISPLAY-HINT "4d:4d"
    STATUS      current
    DESCRIPTION
       "This object specifies the time stamp.
        
        field  octets  contents                range
        -----  ------  --------                -----
        1      1-4     seconds                 0..4294967295
        2      5-8     nanoseconds             0..0..4294967295
       "

    SYNTAX     OCTET STRING (SIZE (8))

FsY1731EnabledStatus ::= TEXTUAL-CONVENTION 
    STATUS      current 
    DESCRIPTION 
        "This object specifies a simple status value." 
    SYNTAX      INTEGER { enabled(1), disabled(2) }

FsY1731AvailabilityInterval ::= TEXTUAL-CONVENTION
    STATUS      current
    DESCRIPTION
       "This object specifies the interval at which Availability Measurement
        is carried out by sendiong LMM.
        The possible values are:
        
        interval100ms(1)   Availability Measurement is carried out at every 100 milliseconds.
        interval1s(2)      Availability Measurement is carried out at every second.
        interval10s(3)     Availability Measurement is carried out at every 10 seconds.
        interval1min(4)    Availability Measurement is carried out at every minute.
        interval10min(5)   Availability Measurement is carried out at every 10 minutes.
        interval10min(6)   Availability Measurement is carried out at every 30 hour.
        interval10min(7)   Availability Measurement is carried out at every 1 hour.

       "
    SYNTAX      INTEGER {
                  interval100ms     (1),
                  interval1s        (2),
                  interval10s       (3),
                  interval1min      (4),
                  interval10min     (5),
                  interval30min     (6),
                  interval1hour     (7)
                }

FsY1731AvailabilityType ::= TEXTUAL-CONVENTION
    STATUS      current
    DESCRIPTION
       "This object specifies the type of availability measurement to be carried out
        The valid values are:

        Static (1)   Static Availability Measurement will be carried out.
        Sliding(2)   Sliding Availability Measurement will be carried out.
       "
    SYNTAX      INTEGER {
                  defStatic     (1),
                  defSliding    (2)
                }

-- *******************************************************************
-- The Context level object. This group will contain all the
-- MIB objects needed to access and modify per context  objects.
-- *******************************************************************

fsMIY1731ContextTable OBJECT-TYPE
    SYNTAX      SEQUENCE OF FsMIY1731ContextEntry
    MAX-ACCESS  not-accessible
    STATUS      current
    DESCRIPTION
      "This object specifies the List of per virtual context ECFM-Y1731 Module Parameters."
    ::= { fsMIY1731Context 1 }

fsMIY1731ContextEntry OBJECT-TYPE
    SYNTAX      FsMIY1731ContextEntry
    MAX-ACCESS  not-accessible
    STATUS      current
    DESCRIPTION
      "This object specifies the Per virtual context ECFM-Y1731 module parmaters."
    INDEX { fsMIY1731ContextId }
    ::= { fsMIY1731ContextTable 1 }

FsMIY1731ContextEntry ::= SEQUENCE {
      fsMIY1731ContextId                 Unsigned32,
      fsMIY1731ContextName               DisplayString,
      fsMIY1731FrameLossBufferClear      TruthValue,
      fsMIY1731FrameDelayBufferClear     TruthValue,
      fsMIY1731LbrCacheClear             TruthValue,
      fsMIY1731ErrorLogClear             TruthValue,
      fsMIY1731FrameLossBufferSize       Integer32,
      fsMIY1731FrameDelayBufferSize      Integer32,
      fsMIY1731LbrCacheSize              Integer32,
      fsMIY1731LbrCacheHoldTime          Integer32,
      fsMIY1731TrapControl               FsY1731Traps,
      fsMIY1731ErrorLogStatus            FsY1731EnabledStatus,
      fsMIY1731ErrorLogSize              Integer32,
      fsMIY1731OperStatus                FsY1731EnabledStatus,
      fsMIY1731LbrCacheStatus            INTEGER
      }

fsMIY1731ContextId OBJECT-TYPE
     SYNTAX      Unsigned32
     MAX-ACCESS  not-accessible
     STATUS      current
     DESCRIPTION
       "This object specifies the virtual context in the system.
       "
    ::= { fsMIY1731ContextEntry 1 }

fsMIY1731ContextName OBJECT-TYPE
     SYNTAX      DisplayString (SIZE (1..32))
     MAX-ACCESS  read-only
     STATUS      current
     DESCRIPTION
        "This object specifies the Name of the virtual context.
        "
     ::= { fsMIY1731ContextEntry 2 }


fsMIY1731FrameLossBufferClear OBJECT-TYPE 
     SYNTAX      TruthValue
     MAX-ACCESS  read-write
     STATUS      current 
     DESCRIPTION 
        "This object specifies the Trigger to remove the contents of Buffer maintained for storing
         frame-loss measured at various times.
         
         Note: Get operation value should be ignored.
        "
     ::= { fsMIY1731ContextEntry 3 } 

fsMIY1731FrameDelayBufferClear OBJECT-TYPE 
     SYNTAX      TruthValue
     MAX-ACCESS  read-write
     STATUS      current 
     DESCRIPTION 
        "This object specifies the Trigger to remove the contents of Buffer maintained for storing
         frame-delay measured at various times.
         
         Note: Get operation value should be ignored.
         "
     ::= { fsMIY1731ContextEntry 4 } 

fsMIY1731LbrCacheClear OBJECT-TYPE 
     SYNTAX      TruthValue
     MAX-ACCESS  read-write
     STATUS      current 
     DESCRIPTION 
        "This object specifies the Trigger to remove the contents of loopback cache  maintained for 
         storing loop back replies.
         
         Note: Get operation value should be ignored.
         "
     ::= { fsMIY1731ContextEntry 5 }
    
fsMIY1731ErrorLogClear OBJECT-TYPE 
     SYNTAX      TruthValue
     MAX-ACCESS  read-write
     STATUS      current 
     DESCRIPTION 
        "This object specifies the Trigger to remove the contents of continuity check error log  
         maintained to store continuity check errors detected by MEP.
         
         Note: Get operation value should be ignored.
         "
     ::= { fsMIY1731ContextEntry 6 }
    
fsMIY1731FrameLossBufferSize OBJECT-TYPE 
     SYNTAX      Integer32(1..4096)
     MAX-ACCESS  read-write
     STATUS      current 
     DESCRIPTION 
        "This object specifies the Maximum size (in entries) of the Frame Loss Buffer.
        "
     DEFVAL  { 1024 }
     ::= { fsMIY1731ContextEntry 7 } 

fsMIY1731FrameDelayBufferSize OBJECT-TYPE 
     SYNTAX      Integer32(1..4096)
     MAX-ACCESS  read-write
     STATUS      current 
     DESCRIPTION 
        "This object specifies the Maximum number of entries for the Frame Delay Buffer
        "
     DEFVAL  { 1024 }
     ::= { fsMIY1731ContextEntry 8 }
     
fsMIY1731LbrCacheSize OBJECT-TYPE 
     SYNTAX      Integer32(1..4096)
     MAX-ACCESS  read-write
     STATUS      current 
     DESCRIPTION 
        "This object specifies the Maximum number of entries for the loopback replies (LBR) Cache
        "
     DEFVAL  { 1024 }
     ::= { fsMIY1731ContextEntry 9 }
     
fsMIY1731LbrCacheHoldTime OBJECT-TYPE 
     SYNTAX      Integer32(1..2880)
     MAX-ACCESS  read-write
     STATUS      current 
     DESCRIPTION 
        "This object specifies the Time (in minutes) for which loopback replies (LBR) cache table 
         entries are retained.
        "
     DEFVAL  { 1440 }
     ::= { fsMIY1731ContextEntry 10 } 

fsMIY1731TrapControl OBJECT-TYPE 
     SYNTAX      FsY1731Traps
     MAX-ACCESS  read-write
     STATUS      current 
     DESCRIPTION 
        "This object specifies a vector of Boolean notification types, used to enable or disable the 
         Y1731 notification types:
                bTrapBadPduReceived
                bTrapFrameLoss
                bTrapFrameDelay
                bTrapDefRdiCondition
                bTrapDefLossOfContinuity
                bTrapDefUnexpectedPeriod
                bTrapDefUnexpectedMep
                bTrapDefMisMerge
                bTrapDefUnexpectedMegLevel
                bTrapDefLocalLinkFailure
                bTrapDefInternalHWFailure
                bTrapDefInternalSWFailure
                bTrapDefAisCondition
                bTrapDefLckCondition"
     ::= { fsMIY1731ContextEntry 11 } 

fsMIY1731ErrorLogStatus OBJECT-TYPE 
     SYNTAX      FsY1731EnabledStatus 
     MAX-ACCESS  read-write
     STATUS      current 
     DESCRIPTION 
        "This object specifies the administrative status of Error Log.
        
         This enables or disables the logging of errors or defects
         detected by MEP.
        "
     DEFVAL  { enabled }
     ::= { fsMIY1731ContextEntry 12 } 

fsMIY1731ErrorLogSize OBJECT-TYPE 
     SYNTAX      Integer32(1..4096)
     MAX-ACCESS  read-write
     STATUS      current 
     DESCRIPTION 
        "This object specifies the Maximum number of entries for the Error Log,
         only if fsMIY1731ErrorLogStatus is enabled.
        "
     DEFVAL  { 1024 }
     ::= { fsMIY1731ContextEntry 13 }

fsMIY1731OperStatus OBJECT-TYPE 
     SYNTAX      FsY1731EnabledStatus 
     MAX-ACCESS  read-write
     STATUS      current 
     DESCRIPTION 
        "This object specifies the administrative module status of Ethernet Y1731 functionality 
         in CFM module. This enables or disables Y1731 in the system. 
         
         A value of 'enabled' (1) indicates that Y1731 is enabled in the 
         device. A value of 'disabled' (2) indicates that Y1731 is disabled
         in the device. 
         Functionalities of ECFM would be according to Y1731 if Y1731 is
         enabled.
         
         Note: The ECFM Module must be enabled for Y1731 to enable or disable.
         "
     DEFVAL  { disabled }
     ::= { fsMIY1731ContextEntry 14 } 
     
fsMIY1731LbrCacheStatus OBJECT-TYPE 
     SYNTAX      INTEGER  { enabled(1), disabled(2) }
     MAX-ACCESS  read-write
     STATUS      current 
     DESCRIPTION 
        "This object specifies the administrative status of LBR cache.
         This enables or disables caching of LBRs 
         "
     DEFVAL  { enabled }
     ::= { fsMIY1731ContextEntry 15 }


-- ******************************************************************
-- The Maintenance Entity Group Managed Object.  This group contains all  
-- the MIB objects used to maintain Maintenance Entities.
-- ******************************************************************

-- ******************************************************************
-- The Maintenance Entity Group (MEG) Table
-- ******************************************************************
    
fsMIY1731MegTable OBJECT-TYPE
    SYNTAX      SEQUENCE OF FsMIY1731MegEntry
    MAX-ACCESS  not-accessible
    STATUS      current
    DESCRIPTION
       "This object specifies the Maintenance Entity Group table. Each row in the table
        represents a different Maintenance Entity Group.

        A Maintenance Entity Group is described in ITU-T Recommendation 
        Y.1731 as the one which includes different MEs that satisfy the 
        following conditions:
        - MEs in a MEG exist in the same administrative boundary; and
        - MEs in a MEG have the same MEG Level; and
        - MEs in a MEG belong to the same point-to-point ETH connection or 
          multipoint ETH connectivity.
       "
    ::= { fsMIY1731Context 2 }

fsMIY1731MegEntry OBJECT-TYPE
    SYNTAX      FsMIY1731MegEntry
    MAX-ACCESS  not-accessible
    STATUS      current
    DESCRIPTION
       "This object specifies the Maintenance Entity Group table entry. This entry is not lost
        upon reboot. It is backed up by stable storage.
       "
    INDEX { fsMIY1731ContextId,
            fsMIY1731MegIndex }
    ::= { fsMIY1731MegTable 1 }

FsMIY1731MegEntry ::= SEQUENCE {
      fsMIY1731MegIndex                 Unsigned32,
      fsMIY1731MegClientMEGLevel        Dot1agCfmMDLevelOrNone,
      fsMIY1731MegVlanPriority          Integer32,
      fsMIY1731MegDropEnable            TruthValue,
      fsMIY1731MegRowStatus             RowStatus 
      }

fsMIY1731MegIndex OBJECT-TYPE
    SYNTAX      Unsigned32(1..4294967295)
    MAX-ACCESS  not-accessible
    STATUS      current
    DESCRIPTION
       "This object specifies the index to the Maintenance Entity Group table.
       "
    ::= { fsMIY1731MegEntry 1 }

fsMIY1731MegClientMEGLevel OBJECT-TYPE
    SYNTAX      Dot1agCfmMDLevelOrNone
    MAX-ACCESS  read-write
    STATUS      current
    DESCRIPTION
       "This object specifies the MEG Level at which the most immediate client layer MEPs or MIPs 
        exist.
        The value (-1) is reserved to indicate that no client MEG level has 
        been configured.
       "
    DEFVAL { -1 }
    ::= { fsMIY1731MegEntry 2 }

fsMIY1731MegVlanPriority OBJECT-TYPE
    SYNTAX      Integer32(0..7)
    MAX-ACCESS  read-write
    STATUS      current
    DESCRIPTION
       "This object specifies the Priority. 3 bit value to be used in the VLAN tag, if present
        in the transmitted frame.
        Applicable to all ECFM-Y1731 frames transmitted by the MEPs of the MEG
        until user explicitly configures particular frame's priority.
       "
    DEFVAL { 7 }
    ::= { fsMIY1731MegEntry 3 }

fsMIY1731MegDropEnable OBJECT-TYPE
    SYNTAX      TruthValue
    MAX-ACCESS  read-write
    STATUS      current
    DESCRIPTION
       "This object specifies the Drop Enable bit value to be used in the VLAN tag, if present in the 
        transmitted CFM frame.
        Applicable to all ECFM-Y1731 frames transmitted by the MEPs of the MEG
        until user explicitly configures particular frame's drop enable 
        parameter.
       "
    DEFVAL { false }
    ::= { fsMIY1731MegEntry 4 }

fsMIY1731MegRowStatus OBJECT-TYPE
    SYNTAX      RowStatus
    MAX-ACCESS  read-write
    STATUS      current
    DESCRIPTION
       "This object specifies the status of MEG row.
        The writable columns in a row can not be changed if the row
        is active. All columns must have a valid value before a row
        can be activated, possible values are row status active and
        row status not active.
       "
    ::= { fsMIY1731MegEntry 5 }

-- ******************************************************************
-- The Maintenance Entity Object. This group contains all the
-- MIB objects used to maintain Maintenance Entities in the MIB.
-- ******************************************************************

-- ******************************************************************
-- The Maintenance Entity (ME) Table
-- ******************************************************************

fsMIY1731MeTable OBJECT-TYPE
    SYNTAX      SEQUENCE OF FsMIY1731MeEntry
    MAX-ACCESS  not-accessible
    STATUS      current
    DESCRIPTION
       "This object specifies the Maintenance Entity table.  Each row in the table represents 
        an ME.  An ME represents a relationship between two MEPs, each 
        configured with a single service instance.

        Configuring a Maintenance Entity Group End Point (MEP) at each 
        of the DSAPs creates a Maintenance Entity (ME) to monitor
        that connectionless connectivity. The ITU-Carrier Code (ICC) and 
        Unique MEGID Code (UMC) form the Maintenance Entity Group Identifier 
        (MEGID) that is carried in CFM Messages to identify incorrect 
        connectivity among Service Instances.  A small integer, the 
        Maintenance Entity Group End Point Identifier (MEPID), identifies 
        each MEP among those configured on a single ME.

        This table uses two indices, first index is the index of the
        Maintenance Entity Group table.

        The writable objects in this table need to be persistent
        upon reboot or restart of a device.
       "
    ::= { fsMIY1731Context 3 }

fsMIY1731MeEntry OBJECT-TYPE
    SYNTAX      FsMIY1731MeEntry
    MAX-ACCESS  not-accessible
    STATUS      current
    DESCRIPTION
       "This object specifies the ME table entry."
    INDEX { fsMIY1731ContextId,
            fsMIY1731MegIndex, 
            fsMIY1731MeIndex }
    ::= { fsMIY1731MeTable 1 }

FsMIY1731MeEntry ::= SEQUENCE {
      fsMIY1731MeIndex                     Unsigned32,
      fsMIY1731MeCciEnabled                TruthValue,
      fsMIY1731MeCcmApplication            FsY1731CcmApplication,
      fsMIY1731MeMegIdIcc                  OCTET STRING,
      fsMIY1731MeMegIdUmc                  OCTET STRING,
      fsMIY1731MeRowStatus                 RowStatus
    }

fsMIY1731MeIndex OBJECT-TYPE
   SYNTAX      Unsigned32(1..4294967295)
   MAX-ACCESS  not-accessible
   STATUS      current
   DESCRIPTION
   "This object specifies the Index of the ME table.
   "
   ::= { fsMIY1731MeEntry 1 }

fsMIY1731MeCciEnabled OBJECT-TYPE
    SYNTAX      TruthValue
    MAX-ACCESS  read-write
    STATUS      current
    DESCRIPTION
       "This object specifies the If set to true, all MEPs in the ME will generate CCM messages.
       "
    DEFVAL { false }
    ::= { fsMIY1731MeEntry 2 }

fsMIY1731MeCcmApplication OBJECT-TYPE
    SYNTAX      FsY1731CcmApplication
    MAX-ACCESS  read-write
    STATUS      current
    DESCRIPTION
       "This object specifies an enumerated value indicating the ETH-CC Role.
        Note: Performance Monitoring is applicable only for point-to-point 
        Maintenance Entity (ME). 
       "
    DEFVAL { ccFaultManagement }
    ::= { fsMIY1731MeEntry 3 }

fsMIY1731MeMegIdIcc OBJECT-TYPE
    SYNTAX      OCTET STRING (SIZE(0..6))
    MAX-ACCESS  read-write
    STATUS      current
    DESCRIPTION
       "This object specifies the Unique code assigned to Network Operator or Service Provider maintained
       by ITU-T Telecommunication Standardization Bureau.

       The ITU Carrier Code used to form MEGID.

       This object contains non-null ICC value if
       it is configured by the user, otherwise null
       ICC value with octet size 0 should be
       assigned.
       "
    ::= { fsMIY1731MeEntry 4 }

fsMIY1731MeMegIdUmc OBJECT-TYPE
    SYNTAX      OCTET STRING (SIZE(0..6))
    MAX-ACCESS  read-write
    STATUS      current
    DESCRIPTION
       "This object specifies the Unique code assigned by Network Operator or Service Provider 
       and is appended to fsMIY1731MeMegIdIcc to form the MEGID 

       The unique MEGID Code used to form MEGID.

       This object contains non-null UMC value if
       it is configured by the user, otherwise null
       UMC value with octet size 0 should be
       assigned.
       "
    ::= { fsMIY1731MeEntry 5 }

fsMIY1731MeRowStatus OBJECT-TYPE
    SYNTAX      RowStatus
    MAX-ACCESS  read-write
    STATUS      current
    DESCRIPTION
       "This object specifies the status of ME row.

        The writable columns in a row can not be changed if the row
        is active. All columns must have a valid value before a row
        can be activated, possible values are row status active and
        row status not active.
       "
    ::= { fsMIY1731MeEntry 6 }

-- ******************************************************************
-- The MEP Object.  This object represents a Maintenance Entity Group
-- End Point as described in ITU-T Y.1731 document.
-- ******************************************************************

-- ******************************************************************
-- The MEP Table
-- ******************************************************************

fsMIY1731MepTable OBJECT-TYPE
    SYNTAX      SEQUENCE OF FsMIY1731MepEntry
    MAX-ACCESS  not-accessible
    STATUS      current
    DESCRIPTION
       "This object specifies the Maintenance Entity Group End Point (MEP) table.

        Each row in the table represents a different MEP. A MEP is
        an actively managed CFM entity, associated with a specific
        DSAP of a Service Instance, which can generate and receive
        CFM PDUs and track any responses.  It is an end point of a
        single Maintenance Entity.

        This table uses three indices. The first two indices are the
        indices of the Maintenance Entity Group (MEG) and Maintenance 
        Entity (ME) tables, the reason being that a MEP is always 
        related to an ME and MEG.

        The MEP table stores all the managed objects for sending
        LBM, LTM, AIS and LCK. This table also stores all the managed
        objects required for monitoring the performance.

        The objects which are used to initiate a transaction are to
        be set only when the row-status of the table is active.
        'fsMIY1731MepTransmit' naming convention is used to isolate 
        these objects from the others.
       "
    ::= { fsMIY1731Context 4 }

fsMIY1731MepEntry OBJECT-TYPE
    SYNTAX      FsMIY1731MepEntry
    MAX-ACCESS  not-accessible
    STATUS      current
    DESCRIPTION
       "This object specifies the MEP table entry"
    INDEX { fsMIY1731ContextId,
            fsMIY1731MegIndex,
            fsMIY1731MeIndex,
            fsMIY1731MepIdentifier
          }
    ::= { fsMIY1731MepTable 1 }
FsMIY1731MepEntry ::= SEQUENCE {
        fsMIY1731MepIdentifier                     Dot1agCfmMepId,
        fsMIY1731MepOutOfService                   TruthValue,
        fsMIY1731MepRdiCapability                  FsY1731EnabledStatus,
        fsMIY1731MepRdiPeriod                      Unsigned32,
        fsMIY1731MepCcmDropEnable                  TruthValue,
        fsMIY1731MepCcmPriority                    Integer32,
        fsMIY1731MepMulticastLbmRecvCapability     FsY1731EnabledStatus,
        fsMIY1731MepLoopbackCapability             FsY1731EnabledStatus,
        fsMIY1731MepLbmCurrentTransId              Unsigned32,
        fsMIY1731MepTransmitLbmStatus              FsY1731TransmitStatus,
        fsMIY1731MepTransmitLbmResultOK            TruthValue,
        fsMIY1731MepTransmitLbmDestMacAddress      MacAddress,
        fsMIY1731MepTransmitLbmDestMepId           Dot1agCfmMepIdOrZero, 
        fsMIY1731MepTransmitLbmDestType            FsY1731DestType,
        fsMIY1731MepTransmitLbmMessages            Integer32,
        fsMIY1731MepTransmitLbmInterval            Unsigned32,
        fsMIY1731MepTransmitLbmIntervalType        FsY1731TimeIntervalType,
        fsMIY1731MepTransmitLbmDeadline            Unsigned32,
        fsMIY1731MepTransmitLbmDropEnable          TruthValue,
        fsMIY1731MepTransmitLbmPriority            Integer32,
        fsMIY1731MepTransmitLbmVariableBytes       TruthValue,
        fsMIY1731MepTransmitLbmTlvType             FsY1731TransmitLbmTlvTypeOrNone,
        fsMIY1731MepTransmitLbmDataPattern         OCTET STRING,
        fsMIY1731MepTransmitLbmDataPatternSize     Unsigned32,
        fsMIY1731MepTransmitLbmTestPatternType     FsY1731TestTlvPatternType,
        fsMIY1731MepTransmitLbmTestPatternSize     Unsigned32,
        fsMIY1731MepTransmitLbmSeqNumber           Unsigned32,
        fsMIY1731MepBitErroredLbrIn                Unsigned32,
        fsMIY1731MepTransmitLtmStatus              Integer32,
        fsMIY1731MepTransmitLtmResultOK            TruthValue,
        fsMIY1731MepTransmitLtmFlags               BITS,
        fsMIY1731MepTransmitLtmTargetMacAddress    MacAddress,
        fsMIY1731MepTransmitLtmTargetMepId         Dot1agCfmMepIdOrZero,
        fsMIY1731MepTransmitLtmTargetIsMepId       TruthValue,
        fsMIY1731MepTransmitLtmTtl                 Unsigned32,
        fsMIY1731MepTransmitLtmDropEnable          TruthValue,
        fsMIY1731MepTransmitLtmPriority            Integer32,
        fsMIY1731MepTransmitLtmSeqNumber           Unsigned32,
        fsMIY1731MepTransmitLtmTimeout             TimeInterval,
        fsMIY1731MepMulticastTstRecvCapability     FsY1731EnabledStatus,
        fsMIY1731MepTransmitTstPatternType         FsY1731TestTlvPatternType,
        fsMIY1731MepTransmitTstVariableBytes       TruthValue,
        fsMIY1731MepTransmitTstPatternSize         Unsigned32,
        fsMIY1731MepTransmitTstDestType            FsY1731DestType,
        fsMIY1731MepTransmitTstDestMacAddress      MacAddress,
        fsMIY1731MepTransmitTstDestMepId           Dot1agCfmMepIdOrZero,
        fsMIY1731MepTransmitTstSeqNumber           Unsigned32,
        fsMIY1731MepTransmitTstPriority            Integer32,
        fsMIY1731MepTransmitTstDropEnable          TruthValue,
        fsMIY1731MepTransmitTstMessages            Integer32,
        fsMIY1731MepTransmitTstStatus              FsY1731TransmitStatus,
        fsMIY1731MepTransmitTstResultOK            TruthValue,
        fsMIY1731MepTransmitTstInterval            Unsigned32,
        fsMIY1731MepTransmitTstIntervalType        FsY1731TimeIntervalType,
        fsMIY1731MepTransmitTstDeadline            Unsigned32,
        fsMIY1731MepBitErroredTstIn                Unsigned32,
        fsMIY1731MepValidTstIn                     Unsigned32,
        fsMIY1731MepTstOut                         Unsigned32,
        fsMIY1731MepTransmitLmmStatus              FsY1731TransmitStatus,
        fsMIY1731MepTransmitLmmResultOK            TruthValue,
        fsMIY1731MepTransmitLmmInterval            FsY1731LmmInterval,
        fsMIY1731MepTransmitLmmDeadline            Unsigned32,
        fsMIY1731MepTransmitLmmDropEnable          TruthValue,
        fsMIY1731MepTransmitLmmPriority            Integer32,
        fsMIY1731MepTransmitLmmDestMacAddress      MacAddress,
        fsMIY1731MepTransmitLmmDestMepId           Dot1agCfmMepIdOrZero,
        fsMIY1731MepTransmitLmmDestIsMepId         TruthValue,
        fsMIY1731MepTransmitLmmMessages            Integer32,
        fsMIY1731MepTxFCf                          Unsigned32,
        fsMIY1731MepRxFCb                          Unsigned32,
        fsMIY1731MepTxFCb                          Unsigned32,
        fsMIY1731MepNearEndFrameLossThreshold      Unsigned32,
        fsMIY1731MepFarEndFrameLossThreshold       Unsigned32,
        fsMIY1731MepTransmitDmStatus               FsY1731TransmitStatus,
        fsMIY1731MepTransmitDmResultOK             TruthValue,
        fsMIY1731MepTransmitDmType                 INTEGER,
        fsMIY1731MepTransmitDmInterval             TimeInterval,
        fsMIY1731MepTransmitDmMessages             Integer32,
        fsMIY1731MepTransmitDmmDropEnable          TruthValue,
        fsMIY1731MepTransmit1DmDropEnable          TruthValue,
        fsMIY1731MepTransmitDmmPriority            Integer32,
        fsMIY1731MepTransmit1DmPriority            Integer32,
        fsMIY1731MepTransmitDmDestMacAddress       MacAddress,
        fsMIY1731MepTransmitDmDestMepId            Dot1agCfmMepIdOrZero,
        fsMIY1731MepTransmitDmDestIsMepId          TruthValue,
        fsMIY1731MepTransmitDmDeadline             Unsigned32,
        fsMIY1731MepDmrOptionalFields              TruthValue,
        fsMIY1731Mep1DmRecvCapability              INTEGER,
        fsMIY1731MepFrameDelayThreshold            Unsigned32,
        fsMIY1731MepAisCapability                  FsY1731EnabledStatus,
        fsMIY1731MepAisCondition                   TruthValue,
        fsMIY1731MepAisInterval                    FsY1731AisLckInterval,
        fsMIY1731MepAisPeriod                      Unsigned32,
        fsMIY1731MepAisPriority                    Integer32,
        fsMIY1731MepAisDropEnable                  TruthValue,
        fsMIY1731MepAisDestIsMulticast             TruthValue,
        fsMIY1731MepAisClientMacAddress            MacAddress,
        fsMIY1731MepLckDestIsMulticast             TruthValue,
        fsMIY1731MepLckClientMacAddress            MacAddress,
        fsMIY1731MepLckCondition                   TruthValue,
        fsMIY1731MepLckInterval                    FsY1731AisLckInterval,
        fsMIY1731MepLckPeriod                      Unsigned32,
        fsMIY1731MepLckPriority                    Unsigned32,
        fsMIY1731MepLckDropEnable                  TruthValue,
        fsMIY1731MepLckDelay                       TimeInterval,  
        fsMIY1731MepDefectConditions               FsY1731MepDefects,
        fsMIY1731MepUnicastCcmMacAddress           MacAddress,
        fsMIY1731MepRowStatus                      RowStatus,
        fsMIY1731MepRxFCf                          Unsigned32,
        fsMIY1731Mep1DmTransInterval               TimeInterval, 
        fsMIY1731MepTransmitThDestMacAddress       MacAddress,
        fsMIY1731MepTransmitThDestMepId            Dot1agCfmMepIdOrZero,
        fsMIY1731MepTransmitThDestIsMepId          TruthValue,
        fsMIY1731MepTransmitThMessages             Integer32,
        fsMIY1731MepTransmitThPps                  Unsigned32,
        fsMIY1731MepTransmitThDeadline             Unsigned32,
        fsMIY1731MepTransmitThType                 INTEGER,
        fsMIY1731MepTransmitThStatus               FsY1731TransmitStatus,
        fsMIY1731MepTransmitThFrameSize            Unsigned32,
        fsMIY1731MepTransmitThBurstMessages        Integer32,
        fsMIY1731MepTransmitThBurstDeadline        Unsigned32,
        fsMIY1731MepTransmitThBurstType            INTEGER,
        fsMIY1731MepTransmitThTestPatternType      FsY1731TestTlvPatternType,
        fsMIY1731MepThVerifiedBps                  Unsigned32,
        fsMIY1731MepThUnVerifiedBps                Unsigned32,
        fsMIY1731MepTransmitLbmMode                INTEGER,
        fsMIY1731MepLbmOut                         Unsigned32,
        fsMIY1731MepTransmitLbmTimeout             TimeInterval,
        fsMIY1731MepTstCapability                  FsY1731EnabledStatus,
        fsMIY1731MepTransmitThResultOK             TruthValue,
        fsMIY1731MepThVerifiedFrameSize            Unsigned32,
        fsMIY1731MepAisOffload                     INTEGER,
        fsMIY1731MepLbmTTL                         Unsigned32,
        fsMIY1731MepLbmIcc                         DisplayString,
        fsMIY1731MepLbmNodeId                      Unsigned32,
        fsMIY1731MepLbmIfNum                       Unsigned32,
        fsMIY1731MepLoopbackStatus                 TruthValue
        }

fsMIY1731MepIdentifier OBJECT-TYPE
    SYNTAX      Dot1agCfmMepId
    MAX-ACCESS  not-accessible
    STATUS      current
    DESCRIPTION
       "This object specifies the Integer that is unique among all the MEPs in the same ME.
        Other definition is: a small integer, unique over a given
        Maintenance Entity, identifying a specific Maintenance
        Entity Group End Point.

        MEP Identifier is also known as the MEPID.
       "
    ::= { fsMIY1731MepEntry 1 }

fsMIY1731MepOutOfService OBJECT-TYPE
    SYNTAX      TruthValue
    MAX-ACCESS  read-write
    STATUS      current
    DESCRIPTION
       "This object specifies a Boolean indicating the administrative service that is being or to be 
        performed.
        true indicates operation needs to be performed Out-of-service 
        and false indicates operation needs to be performed In-service.
       "
    DEFVAL { false }
    ::= { fsMIY1731MepEntry 2 }

fsMIY1731MepRdiCapability OBJECT-TYPE
    SYNTAX      FsY1731EnabledStatus 
    MAX-ACCESS  read-write
    STATUS      current
    DESCRIPTION
       "This object specifies the administrative status of  RDI Transmission capability.
        This enables or disables the transmission of RDI bit in the CCM PDU by
        the MEP.
        If fsMIY1731MepRdiPeriod is provided then it will be enabled for that
        period only.
       "
    DEFVAL { enabled }
    ::= { fsMIY1731MepEntry 3 }

fsMIY1731MepRdiPeriod OBJECT-TYPE
    SYNTAX      Unsigned32(0..172800)
    MAX-ACCESS  read-write
    STATUS      current
    DESCRIPTION
       "This object specifies the Time (in seconds) for which RDI Capability (fsMIY1731MepRdiCapability)
       is enabled.
       "
    ::= { fsMIY1731MepEntry 4 }

fsMIY1731MepCcmDropEnable OBJECT-TYPE
    SYNTAX      TruthValue
    MAX-ACCESS  read-write
    STATUS      current
    DESCRIPTION
       "This object specifies the Drop Enable bit value to be used in the VLAN tag, if present in the 
        transmitted CCM frame.
       "
    DEFVAL { false }
    ::= { fsMIY1731MepEntry 5 }

fsMIY1731MepCcmPriority OBJECT-TYPE
    SYNTAX      Integer32(0..7)
    MAX-ACCESS  read-write
    STATUS      current
    DESCRIPTION
       "This object is used to configure CCM Priority for the Ethernet 
        and the MPLS-TP (LSP/PW) based MEPs.

        For Ethernet: 
            The Priority is a 3-bit priority value to be used in the VLAN tag,
            if present in the transmitted CCM frame. The default value is 7.

        For MPLS-TP (LSP/PW): 
            This indicates the 3-bit EXP value that needs to be used in the 
            MPLS header of CCM frame.
            The default EXP value is 7. The range is (0..7).
            Note: Diff-serv based EXP field mapping is not supported.
       "
    DEFVAL { 7 }
    ::= { fsMIY1731MepEntry 6 }

fsMIY1731MepMulticastLbmRecvCapability OBJECT-TYPE
    SYNTAX      FsY1731EnabledStatus 
    MAX-ACCESS  read-write
    STATUS      current
    DESCRIPTION
       "This object specifies the administrative status of Multicast LBM frame reception. This enables 
        or disables the capability of MEP to process the multicast LBM.
        
        A value of 'enabled' (1) indicates to accept and process multicast LBM.
        A value of 'disabled' (2) indicates not to process the multicast LBM.
       "
   DEFVAL { disabled }
    ::= { fsMIY1731MepEntry 7 }

fsMIY1731MepLoopbackCapability OBJECT-TYPE
    SYNTAX      FsY1731EnabledStatus
    MAX-ACCESS  read-write
    STATUS      current
    DESCRIPTION
       "This object specifies the administrative status of  Loopback (ping) capability.
        This enables or disables capability of MEP to initiate and process 
        Loopback (ping) operation. 
        A value of 'enabled' (1) indicates to initiate as well as process LBM.
        A value of 'disabled' (2) indicates not to initiate as well as  process
        the LBM.
       "
   DEFVAL { enabled }
   ::= { fsMIY1731MepEntry 8 }

fsMIY1731MepLbmCurrentTransId OBJECT-TYPE
    SYNTAX      Unsigned32(0..4294967295)
    MAX-ACCESS  read-only
    STATUS      current
    DESCRIPTION
       "This object specifies the current LBM Transaction.
       "
    ::= { fsMIY1731MepEntry 9 }

fsMIY1731MepTransmitLbmStatus OBJECT-TYPE
    SYNTAX      FsY1731TransmitStatus
    MAX-ACCESS  read-write
    STATUS      current
    DESCRIPTION
       "This object specifies an Enumerated value set to 'start' to initiate LBM transmission 
        and 'stop' to stop LBM transmission.
        'ready' and 'notReady' indicates whether LBM can be initiated or not.

        Note: User can not set to 'ready' or 'notReady'.
       "
    DEFVAL { ready }
    ::= { fsMIY1731MepEntry 10 }

fsMIY1731MepTransmitLbmResultOK OBJECT-TYPE
    SYNTAX      TruthValue
    MAX-ACCESS  read-only
    STATUS      current
    DESCRIPTION
       "This object specifies the result of LBM transaction, 
        - true       The Loopback Message(s) will be
                     (or has been) sent.
        - false      The Loopback Message(s) will not
                     be sent.
       "
     DEFVAL { true }
    ::= { fsMIY1731MepEntry 11 }

fsMIY1731MepTransmitLbmDestMacAddress OBJECT-TYPE
    SYNTAX      MacAddress
    MAX-ACCESS  read-write
    STATUS      current
    DESCRIPTION
       "This object specifies the Target MAC Address Field to be transmitted: A unicast
        destination MAC address.
        This address will be used if the value of the column
        fsMIY1731MepTransmitLbmDestType is 'Unicast'
       "
    ::= { fsMIY1731MepEntry 12 }

fsMIY1731MepTransmitLbmDestMepId OBJECT-TYPE
    SYNTAX      Dot1agCfmMepIdOrZero
    MAX-ACCESS  read-write
    STATUS      current
    DESCRIPTION
       "This object specifies the Maintenance association End Point Identifier of another
        MEP in the same Maintenance Entity to which the LBM is
        to be sent.
        This address will be used if the value of the column
        fsMIY1731MepTransmitLbmDestType is for 'MepID'.
       "
    ::= { fsMIY1731MepEntry 13 }

fsMIY1731MepTransmitLbmDestType OBJECT-TYPE
    SYNTAX     FsY1731DestType 
    MAX-ACCESS  read-write
    STATUS      current
    DESCRIPTION
       "This object specifies the Lbm Destination Type i.e. Unicast, MepID, Multicast
        or MipId(MIP Id applicable only for MPLS-TP network).
       "
    ::= { fsMIY1731MepEntry 14 }

fsMIY1731MepTransmitLbmMessages OBJECT-TYPE
    SYNTAX      Integer32 (0..8192)
    MAX-ACCESS  read-write
    STATUS      current
    DESCRIPTION
       "This object specifies the number of Loopback messages to be transmitted."
    ::= { fsMIY1731MepEntry 15 }

fsMIY1731MepTransmitLbmInterval OBJECT-TYPE
    SYNTAX      Unsigned32 (1..1000) 
    MAX-ACCESS  read-write
    STATUS      current
    DESCRIPTION
       "This object specifies the Interval between two successive LBM transmissions to be used by the 
        MEP.
        fsMIY1731MepTransmitLbmIntervalType are used as units for this object.
        
        Ranges applicable for allowed units are:
        10-1000 for microseconds 
        1-1000  for millseconds 
        1-600   for seconds 
       "
    DEFVAL { 1 }
    ::= { fsMIY1731MepEntry 16 }

fsMIY1731MepTransmitLbmIntervalType OBJECT-TYPE
    SYNTAX      FsY1731TimeIntervalType 
    MAX-ACCESS  read-write
    STATUS      current
    DESCRIPTION
     "This object specifies the Units of fsMIY1731MepTransmitLbmInterval to be used by the
      MEP for LBM transmission.
      "
    DEFVAL { seconds }
    ::= { fsMIY1731MepEntry 17 }

fsMIY1731MepTransmitLbmDeadline OBJECT-TYPE
    SYNTAX      Unsigned32(0..172800)
    MAX-ACCESS  read-write
    STATUS      current
    DESCRIPTION
       "This object Specifies a timeout, in seconds, before loopback (ping) exits.
        Loopback (ping) exits, if configured number of messages
        fsMIY1731MepTransmitLbmMessages are sent before timeout.
       "
    ::= { fsMIY1731MepEntry 18 }

fsMIY1731MepTransmitLbmDropEnable OBJECT-TYPE
    SYNTAX      TruthValue
    MAX-ACCESS  read-write
    STATUS      current
    DESCRIPTION
       "This object specifies the Drop Enable bit value to be used in the VLAN tag, if present
        in the transmitted LBM frame.
       "
    DEFVAL { true }
    ::= { fsMIY1731MepEntry 19 }

fsMIY1731MepTransmitLbmPriority OBJECT-TYPE
    SYNTAX      Integer32(0..7)
    MAX-ACCESS  read-write
    STATUS      current
    DESCRIPTION
       "This object is used to configure LBM Priority for the Ethernet 
        and the MPLS-TP (LSP/PW) based MEPs.

        For Ethernet: 
            The Priority is a 3-bit priority value to be used in the VLAN tag,
            if present in the transmitted LBM frame. The default value is 7.

        For MPLS-TP (LSP/PW): 
            This indicates the 3-bit EXP value that needs to be used in the 
            MPLS header of LBM frame.
            The default EXP value is 7. The range is (0..7).
            Note: Diff-serv based EXP field mapping is not supported.
       "
    DEFVAL { 7 }
    ::= { fsMIY1731MepEntry 20 }

fsMIY1731MepTransmitLbmVariableBytes OBJECT-TYPE
    SYNTAX      TruthValue
    MAX-ACCESS  read-write
    STATUS      current
    DESCRIPTION
       "This object specifies  a varying number of data bytes is to be transmitted in the 
        LBM.
        'true' indicates that LBMs to be transmitted are with varying bytes 
         of data and 'false' indicates that LBM(s)to be transmitted is of 
         the same size.
       "
    DEFVAL { false }
    ::= { fsMIY1731MepEntry 21 }

fsMIY1731MepTransmitLbmTlvType OBJECT-TYPE
    SYNTAX      FsY1731TransmitLbmTlvTypeOrNone
    MAX-ACCESS  read-write
    STATUS      current
    DESCRIPTION
       "This object specifies  the type of the TLV to be included in the LBM frame, if 
        required to be send.
       "
    DEFVAL { none }
    ::= { fsMIY1731MepEntry 22 }


fsMIY1731MepTransmitLbmDataPattern OBJECT-TYPE
    SYNTAX      OCTET STRING(SIZE(0..8970))
    MAX-ACCESS  read-write
    STATUS      current
    DESCRIPTION
       "This object specifies an arbitrary amount of data to be included in the Data TLV,
        if the Data TLV is selected to be sent, determined by the
        fsMIY1731MepTransmitLbmTlvType.

        Size of data value sent in LBM is determined by the
        fsMIY1731MepTransmitLbmDataPatternSize.

        Default value of Data Pattern is all 1 Sequence.
       "
    ::= { fsMIY1731MepEntry 23 }
   
fsMIY1731MepTransmitLbmDataPatternSize OBJECT-TYPE
    SYNTAX      Unsigned32(0..8970)
    MAX-ACCESS  read-write
    STATUS      current
    DESCRIPTION
       "This object specifies the size (bytes) of the
       pattern(fsMIY1731MepTransmitLbmDataPatterm) 
       to be included in the Data TLV, if the Data TLV is to be included in the
       LBM.
        fsMIY1731MepTransmitLbmDataPattern should be of zero length if this object
        is zero. 
       Maximum frame size supported by ECFM is 9K,
       following is the calculation for the maximum size of data-tlv supported
       by ECFM :
       18 bytes - Ethernet Header
       4  bytes - CFM Header
       4  bytes - Transaction-Id
       1  byte  - End Tlv
       3  bytes - Data Tlv Over Head

       9000 - 30  = 8970 bytes
       "
    DEFVAL { 34 }
    ::= { fsMIY1731MepEntry 24 }

fsMIY1731MepTransmitLbmTestPatternType OBJECT-TYPE
    SYNTAX      FsY1731TestTlvPatternType
    MAX-ACCESS  read-write
    STATUS      current
    DESCRIPTION
       "This object specifies the type of pattern to be included in the test TLV of the LBM, 
        if the Test TLV is selected to be sent.
       "
    DEFVAL { patternPRBSWithoutCRC32 }
    ::= { fsMIY1731MepEntry 25 }

fsMIY1731MepTransmitLbmTestPatternSize OBJECT-TYPE
    SYNTAX      Unsigned32(0..8969)
    MAX-ACCESS  read-write
    STATUS      current
    DESCRIPTION
       "This object specifies the size of the pattern to be included in the Test TLV,
        if the Test TLV is selected to be sent.
        
       Maximum frame size supported by ECFM is 9K,
       following is the calculation for the maximum size of test-tlv supported
       by ECFM :
       18 bytes - Ethernet Header
       4  bytes - CFM Header
       4  bytes - Transaction-Id
       1  byte  - End Tlv
       4  bytes - Test Tlv Over Head
       
       9000 - 31  = 8969 bytes
       "
    DEFVAL { 33 } 
    ::= { fsMIY1731MepEntry 26 }

fsMIY1731MepTransmitLbmSeqNumber OBJECT-TYPE
    SYNTAX      Unsigned32
    MAX-ACCESS  read-only
    STATUS      current
    DESCRIPTION
       "This object specifies the sequence number to be transmitted in the next LBM.
       "
    ::= { fsMIY1731MepEntry 27 }

fsMIY1731MepBitErroredLbrIn OBJECT-TYPE
    SYNTAX      Unsigned32
    MAX-ACCESS  read-write
    STATUS      current
    DESCRIPTION
       "This object specifies the number of bit-errored LBRs received.
        LBR with different pattern as of Test TLV in the sent LBM is considered
        as bit-errored LBR
       "
    ::= { fsMIY1731MepEntry 28 }

fsMIY1731MepTransmitLtmStatus OBJECT-TYPE
   SYNTAX      INTEGER {
                  ready                   (0),
                  notReady                (1),
                  transmit                (2)
                }

   MAX-ACCESS  read-write
   STATUS      current
   DESCRIPTION
      "This object specifies a Enumerated value set to 'transmit' to initiate LTM transmission. 
       'ready' and 'notReady' indicates whether LTM can be initiated or not.

       Note: User can not set to 'ready' or 'notReady'.
      "
   DEFVAL { ready }
   ::= { fsMIY1731MepEntry 29 }

fsMIY1731MepTransmitLtmResultOK OBJECT-TYPE
   SYNTAX      TruthValue
   MAX-ACCESS  read-only
   STATUS      current
   DESCRIPTION
       "This object specifies the result of the operation:
        - true    The Linktrace Message will be (or has been) sent.
        - false   The Linktrace Message will not be sent
        "
   DEFVAL { true }
   ::= { fsMIY1731MepEntry 30 }

fsMIY1731MepTransmitLtmFlags OBJECT-TYPE
    SYNTAX      BITS {
                  useHWonly   (0)
                }
    MAX-ACCESS  read-write
    STATUS      current
    DESCRIPTION
       "This object specifies the flags field for LTMs transmitted by the MEP. Indicates that only MAC
       address learned in bridge's forwarding tables is to be used to forward
       the LTM to the next hop."
       
    DEFVAL {{ useHWonly }}
    ::= { fsMIY1731MepEntry 31 }

fsMIY1731MepTransmitLtmTargetMacAddress OBJECT-TYPE
    SYNTAX      MacAddress
    MAX-ACCESS  read-write
    STATUS      current
    DESCRIPTION
       "This object specifies the Target MAC Address Field to be transmitted: A unicast
        destination MAC address.
        This address will be used if the value of the column
        fsMIY1731MepTransmitLtmTargetIsMepId is 'false'.
       "
    ::= { fsMIY1731MepEntry 32 }

fsMIY1731MepTransmitLtmTargetMepId OBJECT-TYPE
    SYNTAX      Dot1agCfmMepIdOrZero
    MAX-ACCESS  read-write
    STATUS      current
    DESCRIPTION
       "This object specifies an indication of the Target MAC Address Field to be
        transmitted:
        The Maintenance association End Point Identifier of
        another MEP in the same Maintenance Association
        This address will be used if the value of the column
        fsMIY1731MepTransmitLtmTargetIsMepId is 'true'.
       "
    ::= { fsMIY1731MepEntry 33 }

fsMIY1731MepTransmitLtmTargetIsMepId OBJECT-TYPE
    SYNTAX      TruthValue
    MAX-ACCESS  read-write
    STATUS      current
    DESCRIPTION
       "This object specifies True indicates that MEPID of the target MEP is used for
        Linktrace transmission.
        False indicates that unicast destination MAC address of the
        target MEP is used for Loopback transmission.
       "
    ::= { fsMIY1731MepEntry 34 }

fsMIY1731MepTransmitLtmTtl OBJECT-TYPE
    SYNTAX      Unsigned32 (0..255)
    MAX-ACCESS  read-write
    STATUS      current
    DESCRIPTION
       "This object specifies the LTM TTL field. Default value, if not specified, is 64.
        The TTL field indicates the number of hops remaining to the
        LTM.  Decremented by 1 by each entity that handles the LTM.
        The value received in the LTM is returned
        in the LTR.  If 0 on input, the LTM is not transmitted to the
        next hop.
       "
    DEFVAL {64}
    ::= { fsMIY1731MepEntry 35 }

fsMIY1731MepTransmitLtmDropEnable OBJECT-TYPE
    SYNTAX      TruthValue
    MAX-ACCESS  read-write
    STATUS      current
    DESCRIPTION
       "This object specifies the Drop Enable bit value to be used in the VLAN tag, if present in the 
        transmitted LTM frame.
       "
    DEFVAL { false }
    ::= { fsMIY1731MepEntry 36 }

fsMIY1731MepTransmitLtmPriority OBJECT-TYPE
    SYNTAX      Integer32(0..7)
    MAX-ACCESS  read-write
    STATUS      current
    DESCRIPTION
       "This object specifies the Priority. 3 bit value to be used in the VLAN tag, if present
        in the transmitted LTM frame.
       "
    DEFVAL { 7 }
    ::= { fsMIY1731MepEntry 37 }

fsMIY1731MepTransmitLtmSeqNumber OBJECT-TYPE
    SYNTAX      Unsigned32
    MAX-ACCESS  read-only
    STATUS      current
    DESCRIPTION
       "This object specifies the sequence number to be transmitted in next LBM.
       "
    ::= { fsMIY1731MepEntry 38 }

fsMIY1731MepTransmitLtmTimeout OBJECT-TYPE
    SYNTAX      TimeInterval(1..1000)
    MAX-ACCESS  read-write
    STATUS      current
    DESCRIPTION
       "This object specifies the Time for all the replies (LTR) of a LTM to be received by
        the MEP.No reply (LTR) would be entertained thereafter (timeout).
       "
    DEFVAL { 500 }
    ::= { fsMIY1731MepEntry 39 }

fsMIY1731MepMulticastTstRecvCapability OBJECT-TYPE
    SYNTAX      FsY1731EnabledStatus
    MAX-ACCESS  read-write
    STATUS      current
    DESCRIPTION
       "This object specifies the administrative status of multicast TST frame reception. This 
        enables or disables the capability of MEP to process the multicast TST.
        A value of 'enabled' (1) indicates to accept and process multicast TST. 
        A value of 'disabled' (2) indicates not to process the multicast TST.
       "
    DEFVAL { disabled }
    ::= { fsMIY1731MepEntry 40 }

fsMIY1731MepTransmitTstPatternType OBJECT-TYPE
    SYNTAX      FsY1731TestTlvPatternType
    MAX-ACCESS  read-write
    STATUS      current
    DESCRIPTION
       "This object specifies the type of the pattern to be included in the test TLV of TST
       frame.
       "
    DEFVAL { patternPRBSWithoutCRC32 }
    ::= { fsMIY1731MepEntry 41 }

fsMIY1731MepTransmitTstVariableBytes OBJECT-TYPE
    SYNTAX      TruthValue
    MAX-ACCESS  read-write
    STATUS      current
    DESCRIPTION
       "This object specifies a varying number of data bytes to send in the TST.
        True indicates that TSTs are to be send with varying bytes of data and
        False indicates that TST(s) are send with same number of bytes of data.
       "
    DEFVAL { false }
    ::= { fsMIY1731MepEntry 42 }

fsMIY1731MepTransmitTstPatternSize OBJECT-TYPE
    SYNTAX      Unsigned32(0..8969)
    MAX-ACCESS  read-write
    STATUS      current
    DESCRIPTION
       "This object specifies the size of the pattern to be included in the Test TLV of 
        the TST message.
       
        Maximum frame size supported by ECFM is 9K,
        following is the calculation for the maximum size of test-tlv supported
        by ECFM :
        18 bytes - Ethernet Header
        4  bytes - CFM Header
        4  bytes - Transaction-Id
        1  byte  - End Tlv
        4  bytes - Data Tlv Over Head
       
        9000 - 31  = 8969 bytes
       "
    DEFVAL { 33 }
    ::= { fsMIY1731MepEntry 43 }

fsMIY1731MepTransmitTstDestType OBJECT-TYPE
    SYNTAX      FsY1731DestType 
    MAX-ACCESS  read-write
    STATUS      current
    DESCRIPTION
       "This object specifies the TST Destination Types (unicast,MEPID,Multicast)
       "
    ::= { fsMIY1731MepEntry 44 }

fsMIY1731MepTransmitTstDestMacAddress OBJECT-TYPE
    SYNTAX      MacAddress
    MAX-ACCESS  read-write
    STATUS      current
    DESCRIPTION
       "This object specifies the Target MAC Address Field to be transmitted: A unicast
        destination MAC address.  
        This address will be used if the value of the column
        fsMIY1731MepTransmitTstDestType is 'Unicast'
       "
    ::= { fsMIY1731MepEntry 45 }

fsMIY1731MepTransmitTstDestMepId OBJECT-TYPE
    SYNTAX      Dot1agCfmMepIdOrZero
    MAX-ACCESS  read-write
    STATUS      current
    DESCRIPTION
       "This object specifies the Maintenance Entity Group End Point Identifier of another
        MEP in the same Maintenance Association to which the TST is
        to be sent.
        This address will be used if the value of the column
        fsMIY1731MepTransmitTstDestType is for 'MepID'.
       "
    ::= { fsMIY1731MepEntry 46 }

fsMIY1731MepTransmitTstSeqNumber OBJECT-TYPE
   SYNTAX      Unsigned32
   MAX-ACCESS  read-only
   STATUS      current
   DESCRIPTION
      "This object specifies the Sequence number to be sent in the TST message.
      "
   ::= { fsMIY1731MepEntry 47 }

fsMIY1731MepTransmitTstPriority OBJECT-TYPE
    SYNTAX      Integer32(0..7)
    MAX-ACCESS  read-write
    STATUS      current
    DESCRIPTION
       "This object specifies the Priority. 3 bit value to be used in the VLAN tag, if present
        in the transmitted TST frame.
       "
    DEFVAL { 7 }
    ::= { fsMIY1731MepEntry 48 }

fsMIY1731MepTransmitTstDropEnable OBJECT-TYPE
    SYNTAX      TruthValue
    MAX-ACCESS  read-write
    STATUS      current
    DESCRIPTION
       "This object specifies the Drop Enable bit value to be used in the VLAN tag, if present
        in the transmitted TST frame.
       "
    DEFVAL { false }
    ::= { fsMIY1731MepEntry 49 }

fsMIY1731MepTransmitTstMessages OBJECT-TYPE
    SYNTAX      Integer32(0..8192)
    MAX-ACCESS  read-write
    STATUS      current
    DESCRIPTION
       "This object specifies the number of Test messages to be transmitted.
       "
    ::= { fsMIY1731MepEntry 50 }
    
fsMIY1731MepTransmitTstStatus OBJECT-TYPE
    SYNTAX      FsY1731TransmitStatus
    MAX-ACCESS  read-write
    STATUS      current
    DESCRIPTION
       "This object specifies an Enumerated value set to 'start' to initiate TST transmission 
        and 'stop' to stop TST transmission.
        'ready' and 'notReady' indicates whether TST can be initiated or not.

        Note: User can not set to 'ready' or 'notReady'.
       "
    DEFVAL { ready }
    ::= { fsMIY1731MepEntry 51 }

fsMIY1731MepTransmitTstResultOK OBJECT-TYPE
    SYNTAX      TruthValue
    MAX-ACCESS  read-only
    STATUS      current
    DESCRIPTION
       "This object specifies the result of the operation:

        - true       The Test Message(s) will be
                     (or has been) sent.
        - false      The Test Message(s) will not
                     be sent.
       "
    DEFVAL { true }
    ::= { fsMIY1731MepEntry 52 }

fsMIY1731MepTransmitTstInterval OBJECT-TYPE
    SYNTAX      Unsigned32(1..1000)
    MAX-ACCESS  read-write
    STATUS      current
    DESCRIPTION
       "This object specifies the Interval between two successive TST transmissions to be used by the 
        MEP.
        fsMIY1731MepTransmitTstIntervalType is used as units for this object.
        
        Ranges applicable for allowed units are:
        10-1000 for microseconds 
        1-1000  for millseconds 
        1-600   for seconds 
       "
    DEFVAL { 1 }
    ::= { fsMIY1731MepEntry 53 }

fsMIY1731MepTransmitTstIntervalType OBJECT-TYPE
    SYNTAX      FsY1731TimeIntervalType
    MAX-ACCESS  read-write
    STATUS      current
    DESCRIPTION
       "This object specifies the Units of fsMIY1731MepTransmitTstInterval to be used by the 
        MEP for TSTs transmission.
       "
    DEFVAL { seconds }
    ::= { fsMIY1731MepEntry 54 }


fsMIY1731MepTransmitTstDeadline OBJECT-TYPE
    SYNTAX      Unsigned32(0..172800)
    MAX-ACCESS  read-write
    STATUS      current
    DESCRIPTION
       "This object specifies the Specify a timeout(in seconds), before test exits. Test exits, if 
       configured number of messages are sent before timeout.
       "
    ::= { fsMIY1731MepEntry 55 }

fsMIY1731MepBitErroredTstIn OBJECT-TYPE
    SYNTAX      Unsigned32
    MAX-ACCESS  read-write
    STATUS      current
    DESCRIPTION
       "This object specifies the number of bit-errored TST messages received.
        Reception of invalid TST message is considered as bit-errored TST
        messages.
       "
    ::= { fsMIY1731MepEntry 56 }

fsMIY1731MepValidTstIn OBJECT-TYPE
    SYNTAX      Unsigned32
    MAX-ACCESS  read-write
    STATUS      current
    DESCRIPTION
       "This object specifies the Number of valid TST messages received.
       "
    ::= { fsMIY1731MepEntry 57 }

fsMIY1731MepTstOut OBJECT-TYPE
   SYNTAX      Unsigned32
   MAX-ACCESS  read-write
   STATUS      current
   DESCRIPTION
      "This object specifies the Number of TST messages transmitted.
      "
   ::= { fsMIY1731MepEntry 58 }

fsMIY1731MepTransmitLmmStatus OBJECT-TYPE
   SYNTAX       FsY1731TransmitStatus
   MAX-ACCESS   read-write
   STATUS       current
   DESCRIPTION
       "This object specifies an Enumerated value set to 'start' to initiate LM transmission 
        and 'stop' to stop LM transmission.
        'ready' and 'notReady' indicates whether LM can be initiated or not.

        Note: User can not set to 'ready' or 'notReady'.
       "
   DEFVAL { ready }
    ::= { fsMIY1731MepEntry 59 }

fsMIY1731MepTransmitLmmResultOK OBJECT-TYPE
    SYNTAX      TruthValue
    MAX-ACCESS  read-only
    STATUS      current
    DESCRIPTION
       "This object specifies the result of the operation:

        - true    The Loss measurement Message (LMM) will be (or has been) sent.

        - false   The Loss measurement Message (LMM) will not be sent.
       "
    DEFVAL { true }
    ::= { fsMIY1731MepEntry 60 }

fsMIY1731MepTransmitLmmInterval OBJECT-TYPE
    SYNTAX      FsY1731LmmInterval
    MAX-ACCESS  read-write
    STATUS      current
    DESCRIPTION
       "This object specifies the Interval between two successive LMM transmissions to be used by the MEP.
       "
    DEFVAL { interval100ms }
    ::= { fsMIY1731MepEntry 61 }

fsMIY1731MepTransmitLmmDeadline OBJECT-TYPE
    SYNTAX      Unsigned32(0..172800)
    MAX-ACCESS  read-write
    STATUS      current
    DESCRIPTION
       "This object specifies a  timeout, in seconds, before loss measurement exits.
        Loss Measurement exits, if configured number of messages are sent 
        before timeout.
       "
    ::= { fsMIY1731MepEntry 62 }

fsMIY1731MepTransmitLmmDropEnable OBJECT-TYPE
    SYNTAX      TruthValue
    MAX-ACCESS  read-write
    STATUS      current
    DESCRIPTION
       "This object specifies the Drop Enable bit value to be used in the VLAN tag, if present
        in the transmitted LMM frame.
       "
    DEFVAL { false }
    ::= { fsMIY1731MepEntry 63 }

fsMIY1731MepTransmitLmmPriority OBJECT-TYPE
    SYNTAX      Integer32(0..7)
    MAX-ACCESS  read-write
    STATUS      current
    DESCRIPTION
       "This object specifies the Priority. 3 bit value to be used in the VLAN tag, if present
        in the transmitted LMM frame.
       "
   DEFVAL { 7 }
    ::= { fsMIY1731MepEntry 64 }

fsMIY1731MepTransmitLmmDestMacAddress OBJECT-TYPE
    SYNTAX      MacAddress
    MAX-ACCESS  read-write
    STATUS      current
    DESCRIPTION
       "This object specifies the Target MAC Address Field to be transmitted: A unicast
        destination MAC address to be used for LMM.
       "
    ::= { fsMIY1731MepEntry 65 }

fsMIY1731MepTransmitLmmDestMepId OBJECT-TYPE
    SYNTAX      Dot1agCfmMepIdOrZero
    MAX-ACCESS  read-write
    STATUS      current
    DESCRIPTION
       "This object specifies an indication of the Target MAC Address Field to be
        transmitted:
        The Maintenance association End Point Identifier of
        another MEP in the same Maintenance Association
        This address will be used if the value of the column
        fsMIY1731MepTransmitLmmDestIsMepId is 'true'.
       "
    ::= { fsMIY1731MepEntry 66 }

fsMIY1731MepTransmitLmmDestIsMepId OBJECT-TYPE
    SYNTAX      TruthValue
    MAX-ACCESS  read-write
    STATUS      current
    DESCRIPTION
       "This object specifies the True indicates that MEPID of the target MEP is used for
        LM frame transmission.
        False indicates that unicast destination MAC address of the
        target MEP is used for Frame Loss Measurement transmission.
       "
    ::= { fsMIY1731MepEntry 67 }

fsMIY1731MepTransmitLmmMessages OBJECT-TYPE
    SYNTAX      Integer32(0..8192)
    MAX-ACCESS  read-write
    STATUS      current
    DESCRIPTION
       "This object specifies the number of LMM messages to be transmitted.
       "
    ::= { fsMIY1731MepEntry 68 }

fsMIY1731MepTxFCf OBJECT-TYPE
    SYNTAX      Unsigned32
    MAX-ACCESS  read-only
    STATUS      current
    DESCRIPTION
       "This object specifies the counter of in-profile data frames transmitted towards its 
        peer MEP transmitted in the last CCM or LMM.
       "
    ::= { fsMIY1731MepEntry 69 }

fsMIY1731MepRxFCb OBJECT-TYPE
    SYNTAX      Unsigned32
    MAX-ACCESS  read-only
    STATUS      current
    DESCRIPTION
       "This object specifies the counter of in-profile data frames received from its peer MEP at the
        time of receiving the last CCM frame.
       "
    ::= { fsMIY1731MepEntry 70 }

fsMIY1731MepTxFCb OBJECT-TYPE
    SYNTAX      Unsigned32
    MAX-ACCESS  read-only
    STATUS      current
    DESCRIPTION
       "This object specifies the value of fsMIY1731MepTxFCf field in the last CCM or LMR frame 
        received from its peer MEP.
       "
    ::= { fsMIY1731MepEntry 71 }

fsMIY1731MepNearEndFrameLossThreshold OBJECT-TYPE
    SYNTAX      Unsigned32
    MAX-ACCESS  read-write
    STATUS      current
    DESCRIPTION
       "This object specifies the Threshold value for the near-end frame loss.
        Notification is sent to Management Application if calculated near-end 
        frame loss exceeds configured threshold.
       "
    ::= { fsMIY1731MepEntry 72 }

fsMIY1731MepFarEndFrameLossThreshold OBJECT-TYPE
    SYNTAX      Unsigned32
    MAX-ACCESS  read-write
    STATUS      current
    DESCRIPTION
       "This object specifies the Threshold value for the far-end frame loss.
        Notification is sent to Management Application if calculated far-end 
        frame loss exceeds configured threshold.
       "
    ::= { fsMIY1731MepEntry 73 }
   
fsMIY1731MepTransmitDmStatus OBJECT-TYPE
   SYNTAX       FsY1731TransmitStatus
   MAX-ACCESS   read-write
   STATUS       current
   DESCRIPTION
       "This object specifies an Enumerated value set to 'start' to initiate 1DM or DMM transmission 
        and 'stop' to stop 1DM or DMM transmission.
        'ready' and 'notReady' indicates whether 1DM or DMM can be initiated 
         or not.

        Note: User can not set to 'ready' or 'notReady'.
       "
   DEFVAL { ready }
    ::= { fsMIY1731MepEntry 74 }

fsMIY1731MepTransmitDmResultOK OBJECT-TYPE
    SYNTAX      TruthValue
    MAX-ACCESS  read-only
    STATUS      current
    DESCRIPTION
       "This object specifies the Indicates the result of the operation:

        - true    The Delay measurement Message (1DM or DMM) will be 
                  (or has been) sent.
        - false   The Delay measurement Message (1DM  or DMM) will not be sent.
       "
    DEFVAL { true }
    ::= { fsMIY1731MepEntry 75 }

fsMIY1731MepTransmitDmType OBJECT-TYPE
    SYNTAX      INTEGER { oneWay(1), twoWay(2) }
    MAX-ACCESS  read-write
    STATUS      current
    DESCRIPTION
       "This object specifies the Type of delay measurement to be initiated:
        
        - oneWay(1)   Measurement (by 1DM) is calculated at destination end.
        - twoWay(2)   Measurement (by DMM-DMR) is calculated at initiation end.
       "
    DEFVAL { 2 }
    ::= { fsMIY1731MepEntry 76 }

fsMIY1731MepTransmitDmInterval OBJECT-TYPE
    SYNTAX      TimeInterval(1..1000)
    MAX-ACCESS  read-write
    STATUS      current
    DESCRIPTION
       "This object specifies the Interval between two successive DM messages 
        (1DM or DMM) transmissions to be used by the MEP.
       "
    DEFVAL { 100 }
    ::= { fsMIY1731MepEntry 77 }

fsMIY1731MepTransmitDmMessages  OBJECT-TYPE
    SYNTAX      Integer32(0..8192)
    MAX-ACCESS  read-write
    STATUS      current
    DESCRIPTION
       "This object specifies the number of DM (1DM or DMM) messages to be transmitted.
       "
    ::= { fsMIY1731MepEntry 78 }

fsMIY1731MepTransmitDmmDropEnable OBJECT-TYPE
    SYNTAX      TruthValue
    MAX-ACCESS  read-write
    STATUS      current
    DESCRIPTION
       "This object specifies the Drop Enable bit value to be used in the VLAN tag, if present
        in the transmitted DMM frame.
       "
    DEFVAL { false }
    ::= { fsMIY1731MepEntry 79 }

fsMIY1731MepTransmit1DmDropEnable OBJECT-TYPE
    SYNTAX      TruthValue
    MAX-ACCESS  read-write
    STATUS      current
    DESCRIPTION
       "This object specifies the Drop Enable bit value to be used in the VLAN tag, if present
        in the transmitted 1DM frame.
       "
    DEFVAL { false }
    ::= { fsMIY1731MepEntry 80 }

fsMIY1731MepTransmitDmmPriority OBJECT-TYPE
    SYNTAX      Integer32(0..7)
    MAX-ACCESS  read-write
    STATUS      current
    DESCRIPTION
       "This object specifies the Priority. 3 bit value to be used in the VLAN tag, if present
        in the transmitted DMM frame.
       "
   DEFVAL { 7 }
    ::= { fsMIY1731MepEntry 81 }

fsMIY1731MepTransmit1DmPriority OBJECT-TYPE
    SYNTAX      Integer32(0..7)
    MAX-ACCESS  read-write
    STATUS      current
    DESCRIPTION
       "This object specifies the Priority. 3 bit value to be used in the VLAN tag, if present
        in the transmitted 1DM frame.
       "
   DEFVAL { 7 }
    ::= { fsMIY1731MepEntry 82 }

fsMIY1731MepTransmitDmDestMacAddress OBJECT-TYPE
    SYNTAX      MacAddress
    MAX-ACCESS  read-write
    STATUS      current
    DESCRIPTION
       "This object specifies the Target MAC Address Field to be transmitted: A unicast
        destination MAC address to be used for 1DM or DMM.
       "
    ::= { fsMIY1731MepEntry 83 }

fsMIY1731MepTransmitDmDestMepId OBJECT-TYPE
    SYNTAX      Dot1agCfmMepIdOrZero
    MAX-ACCESS  read-write
    STATUS      current
    DESCRIPTION
       "This object specifies an indication of the Target MAC Address Field to be
        transmitted:
        The Maintenance association End Point Identifier of
        another MEP in the same Maintenance Association
        This address will be used if the value of the column
        fsMIY1731MepTransmitDmDestIsMepId is 'true'.
       "
    ::= { fsMIY1731MepEntry 84 }

fsMIY1731MepTransmitDmDestIsMepId OBJECT-TYPE
    SYNTAX      TruthValue
    MAX-ACCESS  read-write
    STATUS      current
    DESCRIPTION
       "This object when True indicates that MEPID of the target MEP is used for
        Delay frame transmission.

        False indicates that unicast destination MAC address of the
        target MEP is used for Delay frame transmission.
       "
    ::= { fsMIY1731MepEntry 85 }

fsMIY1731MepTransmitDmDeadline OBJECT-TYPE
    SYNTAX      Unsigned32(0..172800)
    MAX-ACCESS  read-write
    STATUS      current
    DESCRIPTION
       "This object specifies a timeout, in seconds, before Delay Measurement operation exits.
        Delay Measurement operation exits, if configured number of messages are 
        sent before timeout.
       "
    ::= { fsMIY1731MepEntry 86 }

fsMIY1731MepDmrOptionalFields OBJECT-TYPE
    SYNTAX      TruthValue
    MAX-ACCESS  read-write
    STATUS      current
    DESCRIPTION
       "This object specifies whether to include optional fields in the DMR Frame or not.
        True indicates optional fields are to be included and False indicates 
        optional fields are not included.

        Optional fields are included to include the processing time at peer MEP.
       "
    DEFVAL { false }
    ::= { fsMIY1731MepEntry 87 }

fsMIY1731Mep1DmRecvCapability OBJECT-TYPE
    SYNTAX      INTEGER { enabled(1), disabled(2) }
    MAX-ACCESS  read-write
    STATUS      current
    DESCRIPTION
       "This object specifies the administrative status of 1DM Frame reception. This enables 
        or disables the capability of MEP to process the 1DM Frames. 
        A value of 'enabled' (1) indicates to accept and process 1DM Frames.
        A value of 'disabled' (2) indicates not to process the 1DM Frames.
       "
    DEFVAL { enabled }
    ::= { fsMIY1731MepEntry 88 }

fsMIY1731MepFrameDelayThreshold OBJECT-TYPE
    SYNTAX      Unsigned32 
    MAX-ACCESS  read-write
    STATUS      current
    DESCRIPTION
       "This object specifies the Threshold (in microseconds) for the Frame delay.
        Notification is sent to Management application if calculated frame delay 
        exceeds configured threshold.
       "
    DEFVAL { 200 }
    ::= { fsMIY1731MepEntry 89 }

fsMIY1731MepAisCapability OBJECT-TYPE
    SYNTAX      FsY1731EnabledStatus 
    MAX-ACCESS  read-write
    STATUS      current
    DESCRIPTION
       "This object specifies the administrative status of  AIS capability.This enables or disables 
        transmission of AIS frames.  
        
        A value of 'enabled' (1) indicates AIS frames will be transmitted when 
        MEP is in AIS/LCK condition determined by fsMIY1731MepAisCondition and
        fsMIY1731MepLckCondition objects respectively or dot1agCfmMepDefects
        shows any defect. 
        A value of 'disabled' (2) indicates AIS frames will not be transmitted.
       
        If fsMIY1731MepAisPeriod is provided then it will be enabled for that
        period only.
        fsMIY1731MepAisClientMacAddress in needs to be configured incase user
        needs to send AIS frame(s) as unicast or fsMIY1731MegClientMEGLevel
        in case of AIS frames needs to be sent as multicast in prior to
        enabling of fsMIY1731MepAisCapability.
       "
 
    DEFVAL { disabled }
    ::= { fsMIY1731MepEntry 90 }

fsMIY1731MepAisCondition OBJECT-TYPE
    SYNTAX      TruthValue
    MAX-ACCESS  read-only
    STATUS      current
    DESCRIPTION
       "This object specifies the MEP is in AIS condition.
        AIS condition occurs when it receives an AIS frame.
       "
    DEFVAL { false }
    ::= { fsMIY1731MepEntry 91 }

fsMIY1731MepAisInterval OBJECT-TYPE
    SYNTAX      FsY1731AisLckInterval
    MAX-ACCESS  read-write
    STATUS      current
    DESCRIPTION
       "This object specifies the Interval between two successive AIS transmissions.
       "
    DEFVAL { interval1s }
    ::= { fsMIY1731MepEntry 92 }

fsMIY1731MepAisPeriod OBJECT-TYPE
    SYNTAX      Unsigned32(0..172800)
    MAX-ACCESS  read-write
    STATUS      current
    DESCRIPTION
       "This object specifies the Time (in seconds) for which AIS Capability (fsMIY1731MepAisCapability)
       is enabled.
       "
    ::= { fsMIY1731MepEntry 93 }

fsMIY1731MepAisPriority OBJECT-TYPE
    SYNTAX      Integer32(0..7)
    MAX-ACCESS  read-write
    STATUS      current
    DESCRIPTION
       "This object is used for configuring AIS Priority for the Ethernet 
        and the MPLS-TP (LSP/PW) based MEPs.

        For Ethernet: 
            The Priority is a 3-bit priority value to be used in the VLAN tag,
            if present in the transmitted AIS frame. The default value is 7.

        For MPLS-TP (LSP/PW): 
            This indicates the 3-bit EXP value that needs to be used in the 
            MPLS header of AIS frame.
            The default EXP value is 7. The range is (0..7).
            Note: Diff-serv based EXP field mapping is not supported.
       "
   DEFVAL { 7 }
    ::= { fsMIY1731MepEntry 94 }

fsMIY1731MepAisDropEnable OBJECT-TYPE
    SYNTAX      TruthValue
    MAX-ACCESS  read-write
    STATUS      current
    DESCRIPTION
       "This object specifies the Drop Enable bit value to be used in the VLAN tag, if present
        in the transmitted AIS frame.
       "
    DEFVAL { false }
    ::= { fsMIY1731MepEntry 95 }

fsMIY1731MepAisDestIsMulticast OBJECT-TYPE
    SYNTAX      TruthValue
    MAX-ACCESS  read-write
    STATUS      current
    DESCRIPTION
       "This object specifies an Enumerated value set to indicate the type of AIS transmission,
       unicast or multicast. 
       'true' indicates that AIS(s) are to be transmitted as multicast,
       'false' indicates that AIS(s) are to be transmitted as unicast.
       "
    ::= { fsMIY1731MepEntry 96 }

fsMIY1731MepAisClientMacAddress OBJECT-TYPE
    SYNTAX      MacAddress
    MAX-ACCESS  read-write
    STATUS      current
    DESCRIPTION
       "This object specifies a unicast destination MAC address of the Client MEP to which AIS frame
        is to send.

        This object is not supported on MEPs created over MPLS-TP networks, as 
        these networks do not operate based on MAC Address.
       "
    ::= { fsMIY1731MepEntry 97 }

fsMIY1731MepLckDestIsMulticast OBJECT-TYPE
    SYNTAX      TruthValue
    MAX-ACCESS  read-write
    STATUS      current
    DESCRIPTION
       "This object specifies an Enumerated value set to indicate the type of LCK transmission, 
       unicast or multicast.
       'true' indicates that LCK signals are to be transmitted as multicast,
       'false' indicates that LCK signals are to be transmitted as unicast.
       "
    ::= { fsMIY1731MepEntry 98 }

fsMIY1731MepLckClientMacAddress OBJECT-TYPE
    SYNTAX      MacAddress
    MAX-ACCESS  read-write
    STATUS      current
    DESCRIPTION
       "This object specifies a unicast destination MAC address of the Client MEP to which AIS frame
        is to send.
       "
    ::= { fsMIY1731MepEntry 99 }

fsMIY1731MepLckCondition OBJECT-TYPE
    SYNTAX      TruthValue
    MAX-ACCESS  read-only
    STATUS      current
    DESCRIPTION
       "This object specifies if MEP is in LCK condition.
        LCK condition occurs when it receives a LCK frame.
       "
    DEFVAL { false }
    ::= { fsMIY1731MepEntry 100 }

fsMIY1731MepLckInterval OBJECT-TYPE
    SYNTAX      FsY1731AisLckInterval
    MAX-ACCESS  read-write
    STATUS      current
    DESCRIPTION
       "This object specifies the Interval between two successive LCK transmissions to be 
        used by the MEP.
       "
    DEFVAL { interval1s }
    ::= { fsMIY1731MepEntry 101 }

fsMIY1731MepLckPeriod OBJECT-TYPE
    SYNTAX      Unsigned32(0..172800)
    MAX-ACCESS  read-write
    STATUS      current
    DESCRIPTION
       "This object specifies the Time period (in seconds) for which LCK messages are to be 
        transmitted.
       "
    ::= { fsMIY1731MepEntry 102 }

fsMIY1731MepLckPriority OBJECT-TYPE
    SYNTAX      Unsigned32(0..7)
    MAX-ACCESS  read-write
    STATUS      current
    DESCRIPTION
       "This object specifies the Priority. 3 bit value to be used in the VLAN tag, if present
        in the transmitted LCK frame.
       "
   DEFVAL { 7 }
    ::= { fsMIY1731MepEntry 103 }

fsMIY1731MepLckDropEnable OBJECT-TYPE
    SYNTAX      TruthValue
    MAX-ACCESS  read-write
    STATUS      current
    DESCRIPTION
       "This object specifies the Drop Enable bit value to be used in the VLAN tag, if present
        in the transmitted LCK frame.
       "
    DEFVAL { false }
    ::= { fsMIY1731MepEntry 104 }

fsMIY1731MepLckDelay OBJECT-TYPE
    SYNTAX      TimeInterval(1..10)
    MAX-ACCESS  read-write
    STATUS      current
    DESCRIPTION
       "This object specifies When a MEP is set as locked (for out-of-service operations), data traffic through 
        that MEP will be blocked after this delay.
       "
    DEFVAL { 1 }
    ::= { fsMIY1731MepEntry 105 }


fsMIY1731MepDefectConditions OBJECT-TYPE
    SYNTAX      FsY1731MepDefects 
    MAX-ACCESS  read-only
    STATUS      current
    DESCRIPTION
       "This object specifies a vector of Boolean indicates the defect conditions.
       "
    ::= { fsMIY1731MepEntry 106 }

fsMIY1731MepUnicastCcmMacAddress OBJECT-TYPE
    SYNTAX      MacAddress
    MAX-ACCESS  read-write
    STATUS      current
    DESCRIPTION
       "This object specifies the Unicast MacAddress used for performance monitoring through Continuity 
        Check Messages.

        Continuity Check Messages are to be transmitted as multicast frames 
        incase this object contains NULL value.

        This object is not supported on MEPs created over MPLS-TP networks, as 
        these networks do not operate based on MAC Address.
       " 
    ::= { fsMIY1731MepEntry 107 }

fsMIY1731MepRowStatus OBJECT-TYPE
    SYNTAX      RowStatus
    MAX-ACCESS  read-write
    STATUS      current
    DESCRIPTION
       "This object specifies the status of MEP row.

        The writable columns in a row can not be changed if the row
        is active. All columns must have a valid value before a row
        can be activated, possible values are row status active and
        row status not active.
       "
   ::= { fsMIY1731MepEntry 108 }

fsMIY1731MepRxFCf OBJECT-TYPE
    SYNTAX      Unsigned32
    MAX-ACCESS  read-only
    STATUS      current
    DESCRIPTION
       "This object specifies the value of fsMIY1731MepRxFCf field is the value of in-profile data frames 
        received from its peer MEP.
       "
    ::= { fsMIY1731MepEntry 109 }

fsMIY1731Mep1DmTransInterval OBJECT-TYPE
    SYNTAX      TimeInterval(0..1500)
    MAX-ACCESS  read-write
    STATUS      current
    DESCRIPTION
       "This object specifies the Time interval (in 0.01 seconds) between two successive One-way DM Transactions
        and is used to carry out Delay Variation Measurement for
        1DM transactions.
        The value '0' indicates One-way Delay Variation measurement cannot take place.
        The value should be greater than the DM Interval.
       "
    DEFVAL { 0 }
    ::= { fsMIY1731MepEntry 110 }

fsMIY1731MepTransmitThDestMacAddress OBJECT-TYPE
    SYNTAX      MacAddress
    MAX-ACCESS  read-write
    STATUS      current
    DESCRIPTION
       "This object specifies the the Target MAC Address Field to be transmitted: A unicast
        destination MAC address to be used for Throughput Measurement.
       "
    ::= { fsMIY1731MepEntry 111 }

fsMIY1731MepTransmitThDestMepId OBJECT-TYPE
    SYNTAX      Dot1agCfmMepIdOrZero
    MAX-ACCESS  read-write
    STATUS      current
    DESCRIPTION
       "This object specifies an indication of the Target MAC Address Field to be
        transmitted:
        The Maintenance association End Point Identifier of
        another MEP in the same Maintenance Association
        This address will be used if the value of the column
        fsMIY1731MepTransmitThDestIsMepId is 'true'.
       "
    ::= { fsMIY1731MepEntry 112 }

fsMIY1731MepTransmitThDestIsMepId OBJECT-TYPE
    SYNTAX      TruthValue
    MAX-ACCESS  read-write
    STATUS      current
    DESCRIPTION
       "This object when True indicates that MEPID of the target MEP is used for
       Throughput Measurement.
        False indicates that unicast destination MAC address of the
        target MEP is used for Throughput Measurement.
       "
    ::= { fsMIY1731MepEntry 113 }

fsMIY1731MepTransmitThMessages  OBJECT-TYPE
    SYNTAX      Integer32(0..8192)
    MAX-ACCESS  read-write
    STATUS      current
    DESCRIPTION
       "This object specifies the number of Throughput messages (LBM / TST) to be transmitted.
       "
    ::= { fsMIY1731MepEntry 114 }

fsMIY1731MepTransmitThPps OBJECT-TYPE
    SYNTAX      Unsigned32 (1..100000)
    MAX-ACCESS  read-write
    STATUS      current
    DESCRIPTION
       "This object specifies the number of Throughput messages being transmitted in a second.
        It is used to calculate the time interval between two successive 
        message transmission. It's default value is 100 packets per sec.
       "
    DEFVAL {100}
    ::= { fsMIY1731MepEntry 115 }

fsMIY1731MepTransmitThDeadline OBJECT-TYPE
    SYNTAX      Unsigned32(0..172800)
    MAX-ACCESS  read-write
    STATUS      current
    DESCRIPTION
       "This object specifies a timeout, in seconds, before Throughput Measurement operation exits.
        Throughput Measurement operation exits, if configured number of messages are 
        sent before timeout.
       "
    ::= { fsMIY1731MepEntry 116 }

fsMIY1731MepTransmitThType OBJECT-TYPE
    SYNTAX      INTEGER { oneWay(1), twoWay(2) }
    MAX-ACCESS  read-write
    STATUS      current
    DESCRIPTION
       "This object specifies the Type of Throughput measurement to be initiated:
        
        - oneWay(1)   Measurement (by TST) is calculated at initiation end with
          the use of VSM PDUs.
        - twoWay(2)   Measurement (by LBM-LBR) is calculated at initiation end.
       "
    DEFVAL { 2 }
    ::= { fsMIY1731MepEntry 117 }

fsMIY1731MepTransmitThStatus OBJECT-TYPE
    SYNTAX      FsY1731TransmitStatus
    MAX-ACCESS  read-write
    STATUS      current
    DESCRIPTION
       "This object specifies an Enumerated value set to 'start' to initiate Throughput transaction 
        and 'stop' to stop Throughput transaction.
        'ready' and 'notReady' indicates whether Throughput transaction can be initiated or not.

        Note: User can not set to 'ready' or 'notReady'.
       "
    DEFVAL { ready }
    ::= { fsMIY1731MepEntry 118 }

fsMIY1731MepTransmitThFrameSize OBJECT-TYPE
    SYNTAX      Unsigned32 (64..1522)
    MAX-ACCESS  read-write
    STATUS      current
    DESCRIPTION
       "The object specifies the initial total packet size configured by the user
       including the Test TLV of the (LBM / TST) message.
       
        As the Frame Size value is varied to calculate the maximum Throughput 
        this value represents the unverifed Frame Size with which last
        throughput value is calculated or to be calculated.
       "
    DEFVAL { 1500 }
    ::= { fsMIY1731MepEntry 119 }

fsMIY1731MepTransmitThBurstMessages  OBJECT-TYPE
    SYNTAX      Integer32(0..8192)
    MAX-ACCESS  read-write
    STATUS      current
    DESCRIPTION
       "This object specifies the number of Throughput messages (LBM / TST) to be transmitted in a
       burst.
       "
    DEFVAL { 10 }
    ::= { fsMIY1731MepEntry 120 }

fsMIY1731MepTransmitThBurstDeadline OBJECT-TYPE
    SYNTAX      Unsigned32(0..172800000)
    MAX-ACCESS  read-write
    STATUS      current
    DESCRIPTION
       "This object specifies the time period, in milliseconds, for which a burst exists (LB Burst
       / TST Burst ).
       "
    DEFVAL { 100 }
    ::= { fsMIY1731MepEntry 121 }

fsMIY1731MepTransmitThBurstType OBJECT-TYPE
    SYNTAX      INTEGER { burstMessages(1), burstDeadline(2) }
    MAX-ACCESS  read-write
    STATUS      current
    DESCRIPTION
       "This object specifies the Throughput Burst can be initiated as:
        
        - burstMessages(1)   Number of Throughput messages (LBM / TST) to be
          transmitted in a burst.

        - burstDeadline(2)   Timeout, in seconds, before single Throughput Burst
          (LB Burst / TST Burst ) exits.
       "
    DEFVAL { 2 }
    ::= { fsMIY1731MepEntry 122 }

fsMIY1731MepTransmitThTestPatternType OBJECT-TYPE
    SYNTAX      FsY1731TestTlvPatternType
    MAX-ACCESS  read-write
    STATUS      current
    DESCRIPTION
       "This object specifies the type of the pattern to be included in the test TLV of
        Throughput frame(LBM/TST PDU) .
        TestTlvPattern Types can be:
        patternNullSignalWithoutCRC32(0) Pattern contains null signal without 
                                         any CRC.
        patternNullSignalWithCRC32(1)    Pattern contains null signal with CRC.
        patternPRBSWithoutCRC32(2)       Pattern contains pseudo random bit 
                                         sequence 2^-31-1 without any CRC.
        patternPRBSWithCRC32(3)          Pattern contains pseudo random bit 
                                         sequence 2^-31-1 with CRC.

       "
    DEFVAL { patternNullSignalWithoutCRC32 }
    ::= { fsMIY1731MepEntry 123 }

fsMIY1731MepThVerifiedBps OBJECT-TYPE
    SYNTAX      Unsigned32
    MAX-ACCESS  read-only
    STATUS      current
    DESCRIPTION
       "This object specifies the verified throughput value.
       "
    ::= { fsMIY1731MepEntry 124 }

fsMIY1731MepThUnVerifiedBps OBJECT-TYPE
    SYNTAX      Unsigned32
    MAX-ACCESS  read-only
    STATUS      current
    DESCRIPTION
       "This object specifies the throughput value under verification. This is the 
       throughput value for which verification is still to be performed.
       "
    ::= { fsMIY1731MepEntry 125 }

fsMIY1731MepTransmitLbmMode OBJECT-TYPE
    SYNTAX      INTEGER { burst(1), requestResponse(2) }
    MAX-ACCESS  read-write
    STATUS      current
    DESCRIPTION
       "This object specifies the LBMs which can be initiated as:
        
        - burst(1)   Lbms are initiated without waiting for the reception of 
          LBR PDUs.

        - requestResponse(2)   After initiating the Lbm wait for the
          reception of Lbr or the timeout before sending the next Lbm.
       "
    DEFVAL { 2 }
    ::= { fsMIY1731MepEntry 126 }

fsMIY1731MepLbmOut OBJECT-TYPE
   SYNTAX      Unsigned32
   MAX-ACCESS  read-write
   STATUS      current
   DESCRIPTION
      "This object specifies the Number of LBM messages transmitted.
      "
   ::= { fsMIY1731MepEntry 127 }

fsMIY1731MepTransmitLbmTimeout OBJECT-TYPE
    SYNTAX      TimeInterval(1..1000)
    MAX-ACCESS  read-write
    STATUS      current
    DESCRIPTION
       "This object specifies the Time for all the replies (LBR) of LBMs to be received by
        the MEP.No reply (LBR) would be entertained thereafter (timeout).
       "
    DEFVAL { 500 }
    ::= { fsMIY1731MepEntry 128 }

fsMIY1731MepTstCapability OBJECT-TYPE
    SYNTAX      FsY1731EnabledStatus
    MAX-ACCESS  read-write
    STATUS      current
    DESCRIPTION
       "This object specifies the administrative status of Tst capability.
        This enables or disables capability of MEP to initiate and process 
        Tst operation. 
        A value of 'enabled' (1) indicates to initiate as well as process TST.
        A value of 'disabled' (2) indicates not to initiate as well as process
        the TST.
       "
    DEFVAL { enabled }
    ::= { fsMIY1731MepEntry 129 }

fsMIY1731MepTransmitThResultOK OBJECT-TYPE
    SYNTAX      TruthValue
    MAX-ACCESS  read-only
    STATUS      current
    DESCRIPTION
       "This object specifies the result of Th transaction, 
        - true       The TH Message(s) will be
                     (or has been) sent.
        - false      The TH Message(s) will not
                     be sent due to some internal problem.
       "
    DEFVAL { true }
    ::= { fsMIY1731MepEntry 130 }

fsMIY1731MepThVerifiedFrameSize OBJECT-TYPE
    SYNTAX      Unsigned32 (0..9000)
    MAX-ACCESS  read-only
    STATUS      current
    DESCRIPTION
       "This object specifies the Frame Size with which verified Throughput is achieved
       "
    DEFVAL { 0 }
    ::= { fsMIY1731MepEntry 131 }

fsMIY1731MepAisOffload OBJECT-TYPE
    SYNTAX      INTEGER  { enabled(1), disabled(2) }
    MAX-ACCESS  read-create
    STATUS      current
    DESCRIPTION
       "This object specifies the administrative MEP AIS Offloading status. 
        When value 'enabled' (1) is set, the AIS Offloading is enabled for the 
        MEP. When value 'disabled' (2) is set, the AIS Offloading will be 
        disabled for the MEP. By Default AIS Offloading is disabled.
       "
    DEFVAL { disabled }
    ::= { fsMIY1731MepEntry 132 }

fsMIY1731MepLbmTTL  OBJECT-TYPE
    SYNTAX           Unsigned32(1..255)
    MAX-ACCESS       read-write 
    STATUS           current
    DESCRIPTION      
       "This object specifies the time-to-live(TTL) value to be used in the 
        MPLS outer label header when loopback connectivity verification (ping) 
        or diagnostic tests has to be performed to a MEP/MIP in the MPLS-TP 
        network.

        By default TTL value will be 255.

        If the user sets a particular value, then that TTL will be set and 
        carried in LBM packets.
  
        When performing loopback connectivity verification (ping) or diagnostic 
        tests to a MIP, this object MUST be set to an appropriate TTL value 
        needed to reach the MIP.

        For MIP, this must be configured in conjunction with 
        fsMIY1731MepTransmitLbmDestType as mipid(3), fsMIY1731MepLbmIcc,
        fsMIY1731MepLbmNodeId, fsMIY1731MepLbmIfNum.

        For MEP, this must be configured in conjunction with 
        fsMIY1731MepTransmitLbmDestType as mepid(1) and 
        fsMIY1731MepTransmitLbmDestMepId.
       "
    DEFVAL { 255 }
    ::= { fsMIY1731MepEntry 133 }

fsMIY1731MepLbmIcc OBJECT-TYPE
    SYNTAX         DisplayString (SIZE (0..6))
    MAX-ACCESS     read-write
    STATUS         current
    DESCRIPTION
       "This object specifies the ICC(ITU Carrier Code) of the MIP node in ICC 
        based MPLS-TP network for which loopback connectivity verification
        (ping) or diagnostic tests has to be initiated. 

        The ICC code consists of 1-6 characters with alphabetic
	or numberic characters.

        This must be configured in conjunction with 
        fsMIY1731MepTransmitLbmDestType as mipid(3), 
        fsMIY1731MepLbmNodeId, fsMIY1731MepLbmIfNum. fsMIY1731MepLbmTTL.
        
        This object must be set ONLY to perform loopback connectivity
        verification or diagnostic tests to a MIP (and not for remote MEP) in 
        the MPLS-TP network.
       "
        
    ::= { fsMIY1731MepEntry 134 }

fsMIY1731MepLbmNodeId OBJECT-TYPE
    SYNTAX             Unsigned32
    MAX-ACCESS         read-write 
    STATUS             current
    DESCRIPTION    
       "This object specifies the Node Id of the specific MIP node in MPLS-TP 
        network for which loopback connectivity verification(ping) or diagnostic
        tests has to be initiated.

        This must be interpreted in conjunction with the fsMIY1731MepLbmIcc 
        object. 

        This must be configured in conjunction with 
        fsMIY1731MepTransmitLbmDestType as mipid(3), 
        fsMIY1731MepLbmIcc, fsMIY1731MepLbmIfNum. fsMIY1731MepLbmTTL.

        This object must be set ONLY to perform loopback connectivity
        verification or diagnostic tests to a MIP (and not for remote MEP) in 
        the MPLS-TP network.
       "
    ::= { fsMIY1731MepEntry 135 }

fsMIY1731MepLbmIfNum OBJECT-TYPE
    SYNTAX            Unsigned32
    MAX-ACCESS        read-write 
    STATUS            current
    DESCRIPTION    
       "This object specifies the Interface Number of the specific MIP node in 
        MPLS-TP network for which loopback connectivity verification(ping) or 
        diagnostic tests has to be initiated.

        Per Interface MIP is identified by configuring the non-zero If-Num 
        of the Access Point towards the server layer.

        Per Node MIP is identified by configuring a value of zero to this 
        object.

        This must be interpreted in conjunction with the fsMIY1731MepLbmIcc 
        and fsMIY1731MepLbmNodeId objects. 

        This must be configured in conjunction with 
        fsMIY1731MepTransmitLbmDestType as mipid(3), 
        fsMIY1731MepLbmIcc, fsMIY1731MepLbmNodeId. fsMIY1731MepLbmTTL.

        This object must be set ONLY to perform loopback connectivity
        verification or diagnostic tests to a MIP (and not for remote MEP) in 
        the MPLS-TP network.
       "
    ::= { fsMIY1731MepEntry 136 }

fsMIY1731MepLoopbackStatus OBJECT-TYPE
    SYNTAX      TruthValue
    MAX-ACCESS  read-write
    STATUS      current
    DESCRIPTION
       "This object specifies the loopback status of the MEP. This object used
       in Y1564/RFC2544 to put the remote end in loopback mode for looping
       back all the data packets.
       "
    DEFVAL { false }
    ::= { fsMIY1731MepEntry 137 }

-- ---------------------------------------------------------------------------- 
-- The MEP Table - End
-- ---------------------------------------------------------------------------- 
-- ******************************************************************
-- The Error Log Table
-- ******************************************************************
fsMIY1731ErrorLogTable OBJECT-TYPE
    SYNTAX      SEQUENCE OF FsMIY1731ErrorLogEntry
    MAX-ACCESS  not-accessible
    STATUS      current
    DESCRIPTION
       "This object specifies the Error Log table.
       Size of this table is defined by the object fsMIY1731ErrorLogSize.
       If the addition of an error entry would exceed the 
       resources allocated to table, then the oldest entries in the table are 
       deleted until sufficient resources are available to hold the new
       error entry.
       
       Each row in the table represents error or defect
       detected by a specific MEP.
       This table uses three indices. The first four are the indices of MEP
       table the reason being that a error or defect can only
       be detected by MEP.
       
       SNMP SMI does not allow to state in a MIB that an object in
       a table is an array.  The solution is to take the index (or
       indices) of the first table and add one or more indices.
       "
    ::= { fsMIY1731Context 5 }

fsMIY1731ErrorLogEntry OBJECT-TYPE
    SYNTAX      FsMIY1731ErrorLogEntry
    MAX-ACCESS  not-accessible
    STATUS      current
    DESCRIPTION
       "This object specifies the Error Log Table."
    INDEX { fsMIY1731ContextId,
            fsMIY1731MegIndex,
            fsMIY1731MeIndex,
            fsMIY1731MepIdentifier,
            fsMIY1731ErrorLogSeqNumber
          }
    ::= { fsMIY1731ErrorLogTable 1 }

FsMIY1731ErrorLogEntry ::= SEQUENCE {
      fsMIY1731ErrorLogSeqNumber           Unsigned32,
      fsMIY1731ErrorLogTimeStamp           TimeStamp,
      fsMIY1731ErrorLogType                FsY1731ErrorLogType,
      fsMIY1731ErrorLogRMepIdentifier      Dot1agCfmMepIdOrZero
    }

fsMIY1731ErrorLogSeqNumber OBJECT-TYPE
    SYNTAX      Unsigned32(0..4294967295)
    MAX-ACCESS  not-accessible
    STATUS      current
    DESCRIPTION
       "This object specifies the Locally maintained sequence number of Error Log Entries"
    ::= { fsMIY1731ErrorLogEntry 1 }

fsMIY1731ErrorLogTimeStamp OBJECT-TYPE
    SYNTAX      TimeStamp
    MAX-ACCESS  read-only
    STATUS      current
    DESCRIPTION
       "This object specifies the time at which error or defect is 
       detected by a MEP.
       "
    ::= { fsMIY1731ErrorLogEntry 2 }

fsMIY1731ErrorLogType OBJECT-TYPE
    SYNTAX      FsY1731ErrorLogType 
    MAX-ACCESS  read-only
    STATUS      current
    DESCRIPTION
       "This object specifies the type of error or defect detected by MEP.
        Type of errors/defects are:
        bDefRdiCondition,
        bDefLossOfContinuity,
        bDefUnexpectedPeriod,
        bDefUnexpectedMep,
        bDefMisMerge,
        bDefUnexpectedMegLevel,
        bDefLocalLinkFailure,
        bDefInternalHWFailure,
        bDefInternalSWFailure,
        bDefAisCondition,
        bDefLckCondition 
       "
    ::= { fsMIY1731ErrorLogEntry 3 }

fsMIY1731ErrorLogRMepIdentifier OBJECT-TYPE
    SYNTAX      Dot1agCfmMepIdOrZero
    MAX-ACCESS  read-only
    STATUS      current
    DESCRIPTION
       "This object specifies the specific remote MEP due to which defect is detected.
        Zero indicates that no remote MEP contributes for the occurence of 
        defect.
       "
    ::= { fsMIY1731ErrorLogEntry 4 }


-- ******************************************************************
-- The Linktrace Reply Table
-- ******************************************************************

fsMIY1731LtrTable OBJECT-TYPE
    SYNTAX      SEQUENCE OF FsMIY1731LtrEntry
    MAX-ACCESS  not-accessible
    STATUS      current
    DESCRIPTION
       "This object specifies the table which extends the MEP table and contains a list of
        Linktrace replies received by a specific MEP in response to
        a linktrace message.

        SNMP SMI does not allow to state in a MIB that an object in
        a table is an array.  The solution is to take the index (or
        indices) of the first table and add one or more indices.
       "
    ::= { fsMIY1731Context 6 }

fsMIY1731LtrEntry OBJECT-TYPE
    SYNTAX      FsMIY1731LtrEntry
    MAX-ACCESS  not-accessible
    STATUS      current
    DESCRIPTION
       "This object specifies the Linktrace Reply table entry."
    INDEX { fsMIY1731ContextId,
            fsMIY1731MegIndex,
            fsMIY1731MeIndex,
            fsMIY1731MepIdentifier,
            fsMIY1731LtrSeqNumber,
            fsMIY1731LtrReceiveOrder
          }
    ::= { fsMIY1731LtrTable 1 }

FsMIY1731LtrEntry ::= SEQUENCE {
      fsMIY1731LtrSeqNumber              Unsigned32,
      fsMIY1731LtrReceiveOrder           Unsigned32,
      fsMIY1731LtrReceiveTime            TimeInterval
    }

fsMIY1731LtrSeqNumber OBJECT-TYPE
    SYNTAX      Unsigned32(0..4294967295)
    MAX-ACCESS  not-accessible
    STATUS      current
    DESCRIPTION
       "This object specifies the Transaction identifier/Sequence number returned by a previous
        transmit linktrace message command, indicating which LTM's
        response is going to be returned.
       "
    ::= { fsMIY1731LtrEntry 1}

fsMIY1731LtrReceiveOrder OBJECT-TYPE
    SYNTAX      Unsigned32(1..4294967295)
    MAX-ACCESS  not-accessible
    STATUS      current
    DESCRIPTION
       "This object specifies an index to distinguish among multiple LTRs with the same LTR
        Transaction Identifier field value. fsMIY1731LtrReceiveOrder
        are assigned sequentially from 1, in the order that the
        Linktrace Initiator received the LTRs.
       "
    ::= { fsMIY1731LtrEntry 2 }

fsMIY1731LtrReceiveTime OBJECT-TYPE
    SYNTAX      TimeInterval
    MAX-ACCESS  read-only
    STATUS      current
    DESCRIPTION
       "This object specifies the time taken to receive a LTR in response to a transmitted 
        LTM.
       "
    ::= { fsMIY1731LtrEntry 3}

-- ******************************************************************
-- The Loopback Message Table
-- ******************************************************************
fsMIY1731LbmTable OBJECT-TYPE
    SYNTAX      SEQUENCE OF FsMIY1731LbmEntry
    MAX-ACCESS  not-accessible
    STATUS      current
    DESCRIPTION
       "This object specifies the table which extends the MEP table and contains information of
        Loopback messages sent by a specific MEP.

        SNMP SMI does not allow to state in a MIB that an object in
        a table is an array.  The solution is to take the index (or
        indices) of the first table and add one or more indices.
       "
    ::= { fsMIY1731Context 7 }

fsMIY1731LbmEntry OBJECT-TYPE
    SYNTAX      FsMIY1731LbmEntry
    MAX-ACCESS  not-accessible
    STATUS      current
    DESCRIPTION
       "This object specifies the Loopback Message table entry."
    INDEX { fsMIY1731ContextId,
            fsMIY1731MegIndex,
            fsMIY1731MeIndex,
            fsMIY1731MepIdentifier,
            fsMIY1731LbmTransId,
            fsMIY1731LbmSeqNumber
          }
    ::= { fsMIY1731LbmTable 1 }

FsMIY1731LbmEntry ::= SEQUENCE {
      fsMIY1731LbmTransId                Unsigned32,
      fsMIY1731LbmSeqNumber              Unsigned32,
      fsMIY1731LbmBytesSent              Unsigned32,
      fsMIY1731LbmTargetMacAddress       MacAddress,
      fsMIY1731LbmUnexptedLbrIn          Unsigned32,
      fsMIY1731LbmDuplicatedLbrIn        Unsigned32,
      fsMIY1731LbmNumOfResponders        Unsigned32,
      fsMIY1731LbmDestType               FsY1731DestType,
      fsMIY1731LbmDestMepId              Dot1agCfmMepIdOrZero,
      fsMIY1731LbmIcc                    DisplayString,
      fsMIY1731LbmNodeId                 Unsigned32,
      fsMIY1731LbmIfNum                  Unsigned32, 
      fsMIY1731LbmTTL                    Unsigned32
    }

fsMIY1731LbmTransId OBJECT-TYPE
    SYNTAX      Unsigned32 (1..4294967295)
    MAX-ACCESS  not-accessible
    STATUS      current
    DESCRIPTION
       "This object specifies the Transaction Identifier identifies a loopback or ping (LBM)transaction.
       "
    ::= { fsMIY1731LbmEntry 1}

fsMIY1731LbmSeqNumber OBJECT-TYPE
    SYNTAX      Unsigned32 (0..4294967295)
    MAX-ACCESS  not-accessible
    STATUS      current
    DESCRIPTION
       "This object specifies the Sequence number returned by a previous transmit loopback message, 
       indicating which LBM's response is going to be returned.
       "
    ::= { fsMIY1731LbmEntry 2}

fsMIY1731LbmBytesSent OBJECT-TYPE
    SYNTAX      Unsigned32
    MAX-ACCESS  read-only
    STATUS      current
    DESCRIPTION
       "This object specifies the size (in bytes) of the LBM transmitted.
       "
    ::= { fsMIY1731LbmEntry 3 }

fsMIY1731LbmTargetMacAddress OBJECT-TYPE
    SYNTAX      MacAddress
    MAX-ACCESS  read-only
    STATUS      current
    DESCRIPTION
       "This object specifies the Mac Address of the target MP (MEP or MIP) to which LBM has been sent.
        For multicast LBM this object should not be considered.
       "
    ::= { fsMIY1731LbmEntry 4}

fsMIY1731LbmUnexptedLbrIn OBJECT-TYPE
    SYNTAX      Unsigned32
    MAX-ACCESS  read-only
    STATUS      current
    DESCRIPTION
       "This object specifies the Number of unexpected Lbrs Received.
       "
    ::= { fsMIY1731LbmEntry 5 }

fsMIY1731LbmDuplicatedLbrIn OBJECT-TYPE
    SYNTAX      Unsigned32
    MAX-ACCESS  read-only
    STATUS      current
    DESCRIPTION
       "This object specifies the Number of Duplicated Lbrs Received.
       "
    ::= { fsMIY1731LbmEntry 6 }

fsMIY1731LbmNumOfResponders OBJECT-TYPE
    SYNTAX      Unsigned32
    MAX-ACCESS  read-only
    STATUS      current
    DESCRIPTION
       "This object specifies the Number of Responders which have sent the reply (LBR)
        for the initiated LBM.
       "
    ::= { fsMIY1731LbmEntry 7 }

fsMIY1731LbmDestType  OBJECT-TYPE
    SYNTAX      FsY1731DestType
    MAX-ACCESS  read-only
    STATUS      current
    DESCRIPTION
       "This object specifies the type (i.e. Unicast, MepID, Multicast
        or MipId(MIP Id applicable only for MPLS-TP network)) of the 
        destination for which LBM was sent. 
       "
::= { fsMIY1731LbmEntry 8 } 

fsMIY1731LbmDestMepId OBJECT-TYPE
    SYNTAX      Dot1agCfmMepIdOrZero
    MAX-ACCESS  read-only
    STATUS      current
    DESCRIPTION
       "This object specifies the Target MEP ID to which LBM was sent.
       "
::= { fsMIY1731LbmEntry 9 } 

fsMIY1731LbmIcc  OBJECT-TYPE
    SYNTAX       DisplayString
    MAX-ACCESS   read-only
    STATUS       current
    DESCRIPTION
       "This object specifies the ICC of the MIP node in ICC
        based MPLS-TP network for which LBM was sent.
       "
::= { fsMIY1731LbmEntry 10 } 

fsMIY1731LbmNodeId  OBJECT-TYPE
    SYNTAX          Unsigned32
    MAX-ACCESS      read-only
    STATUS          current
    DESCRIPTION
       "This object specifies the Node Id of the specific MIP node in MPLS-TP
        network for which LBM was sent.
       "
::= { fsMIY1731LbmEntry 11 } 

fsMIY1731LbmIfNum  OBJECT-TYPE
    SYNTAX         Unsigned32
    MAX-ACCESS     read-only
    STATUS         current
    DESCRIPTION
       "This object specifies the Interface Number of the specific MIP node in
        MPLS-TP network for which LBM was sent. 
       "
::= { fsMIY1731LbmEntry 12 } 

fsMIY1731LbmTTL  OBJECT-TYPE
    SYNTAX       Unsigned32
    MAX-ACCESS   read-only
    STATUS       current
    DESCRIPTION
       "This object specifies the time-to-live(TTL) value used in the  
        MPLS outer label header in the LBM which was sent. 
       " 
::= { fsMIY1731LbmEntry 13 } 


-- ******************************************************************
-- The Loopback Reply Table
-- ******************************************************************
fsMIY1731LbrTable OBJECT-TYPE
    SYNTAX      SEQUENCE OF FsMIY1731LbrEntry
    MAX-ACCESS  not-accessible
    STATUS      current
    DESCRIPTION
       "This object specifies the table which extends the MEP table and contains a list of
        Loopback replies received by a specific MEP in response to
        a loopback message.

        Size of this table is defined by the object fsMIY1731LbrCacheSize.
        If the addition of a loopback reply entry would exceed the 
        resources allocated to table, then the oldest entries in the table are 
        deleted until sufficient resources are available to hold the new
        loopback reply entry.

        SNMP SMI does not allow to state in a MIB that an object in
        a table is an array.  The solution is to take the index (or
        indices) of the first table and add one or more indices.
       "
    ::= { fsMIY1731Context 8 }

fsMIY1731LbrEntry OBJECT-TYPE
    SYNTAX      FsMIY1731LbrEntry
    MAX-ACCESS  not-accessible
    STATUS      current
    DESCRIPTION
       "This object specifies the Loopback Reply table entry."
    INDEX { fsMIY1731ContextId,
            fsMIY1731MegIndex,
            fsMIY1731MeIndex,
            fsMIY1731MepIdentifier,
            fsMIY1731LbmTransId,
            fsMIY1731LbrSeqNumber,
            fsMIY1731LbrReceiveOrder
          }
    ::= { fsMIY1731LbrTable 1 }

FsMIY1731LbrEntry ::= SEQUENCE {
      fsMIY1731LbrSeqNumber              Unsigned32,
      fsMIY1731LbrReceiveOrder           Unsigned32,
      fsMIY1731LbrResponderMacAddress    MacAddress,
      fsMIY1731LbrReceiveTime            TimeInterval,
      fsMIY1731LbrErrorType              FsY1731LbrErrType,
      fsMIY1731LbrDestType               FsY1731DestType,
      fsMIY1731LbrDestMepId              Dot1agCfmMepIdOrZero,
      fsMIY1731LbrICC                    DisplayString,
      fsMIY1731LbrNodeId                 Unsigned32,
      fsMIY1731LbrIfNum                  Unsigned32 
    }

fsMIY1731LbrSeqNumber OBJECT-TYPE
    SYNTAX      Unsigned32 (0..4294967295)
    MAX-ACCESS  not-accessible
    STATUS      current
    DESCRIPTION
       "This object specifies the Sequence number received in the Loopback reply.
       "
    ::= { fsMIY1731LbrEntry 1}

fsMIY1731LbrReceiveOrder OBJECT-TYPE
    SYNTAX      Unsigned32(1..4294967295)
    MAX-ACCESS  not-accessible
    STATUS      current
    DESCRIPTION
       "This object specifies the Order in which LBRs are received for a same Sequence Number field
        value. 
       "
    ::= { fsMIY1731LbrEntry 2 }

fsMIY1731LbrResponderMacAddress OBJECT-TYPE
    SYNTAX      MacAddress
    MAX-ACCESS  read-only
    STATUS      current
    DESCRIPTION
       "This object specifies the Mac Address of the MP which has sent the response for the 
        LBM.
       "
    ::= { fsMIY1731LbrEntry 3}

fsMIY1731LbrReceiveTime OBJECT-TYPE
    SYNTAX      TimeInterval
    MAX-ACCESS  read-only
    STATUS      current
    DESCRIPTION
       "This object specifies the Time taken to receive a LBR in response to the 
        transmitted LBM.
       "
    ::= { fsMIY1731LbrEntry 4}

fsMIY1731LbrErrorType OBJECT-TYPE
    SYNTAX     FsY1731LbrErrType 
    MAX-ACCESS  read-only
    STATUS      current
    DESCRIPTION
       "This object specifies that received loobback reply is errored one.
        bit 0 indicates bad MSDU (when data in the LBR does not match what was
        sent in the LBM)
        bit 1 indicates bit errored LBR (LBR is with bit errors)
       "
    ::= { fsMIY1731LbrEntry 5 }

fsMIY1731LbrDestType  OBJECT-TYPE
    SYNTAX      FsY1731DestType
    MAX-ACCESS  read-only
    STATUS      current
    DESCRIPTION
       "This object specifies the Type ((i.e. Unicast, MepID, Multicast
        or MipId(MIP Id applicable only for MPLS-TP network)) of the 
        destination from which LBR was received.
       "
::= { fsMIY1731LbrEntry 6 }

fsMIY1731LbrDestMepId OBJECT-TYPE
    SYNTAX      Dot1agCfmMepIdOrZero
    MAX-ACCESS  read-only
    STATUS      current
    DESCRIPTION
       "This object specifies the MEP which has sent the response for the LBM.
       "
::= { fsMIY1731LbrEntry 7 }

fsMIY1731LbrICC  OBJECT-TYPE
    SYNTAX       DisplayString
    MAX-ACCESS   read-only
    STATUS       current
    DESCRIPTION
       "This object specifies the ICC of the MIP node in ICC
        based MPLS-TP network from which LBR was received.
       "
::= { fsMIY1731LbrEntry 8 }

fsMIY1731LbrNodeId  OBJECT-TYPE
    SYNTAX          Unsigned32
    MAX-ACCESS      read-only
    STATUS          current
    DESCRIPTION
       "This object specifies the Node Id of the specific MIP node in MPLS-TP
        network from which LBR was received.
       "
::= { fsMIY1731LbrEntry 9 }

fsMIY1731LbrIfNum  OBJECT-TYPE
    SYNTAX         Unsigned32
    MAX-ACCESS     read-only
    STATUS         current
    DESCRIPTION
       "This object specifies the Interface Number of the specific MIP node in
        MPLS-TP network from which LBR was received.
        "
::= { fsMIY1731LbrEntry 10 }

-- ******************************************************************
-- The Loopback Statistics Table
-- ******************************************************************

fsMIY1731LbStatsTable OBJECT-TYPE
    SYNTAX      SEQUENCE OF FsMIY1731LbStatsEntry
    MAX-ACCESS  not-accessible
    STATUS      current
    DESCRIPTION
       "This object specifies the table which extends the MEP table and contains output of loopback 
       or ping transaction. 
       Output includes number of replies recieved, time taken for a reply to
       come.

       SNMP SMI does not allow to state in a MIB that an object in
       a table is an array.  The solution is to take the index (or
       indices) of the first table and add one or more indices.
       "
    ::= { fsMIY1731Context 9 }

fsMIY1731LbStatsEntry OBJECT-TYPE
    SYNTAX      FsMIY1731LbStatsEntry
    MAX-ACCESS  not-accessible
    STATUS      current
    DESCRIPTION
       "This object specifies the Loopback Statistics table entry."
    INDEX { fsMIY1731ContextId,
            fsMIY1731MegIndex,
            fsMIY1731MeIndex,
            fsMIY1731MepIdentifier,
            fsMIY1731LbmTransId
          }
    ::= { fsMIY1731LbStatsTable 1 }

FsMIY1731LbStatsEntry ::= SEQUENCE {
      fsMIY1731LbStatsLbmOut                Unsigned32,
      fsMIY1731LbStatsLbrIn                 Unsigned32,
      fsMIY1731LbStatsLbrTimeAverage        TimeInterval,
      fsMIY1731LbStatsLbrTimeMin            TimeInterval,
      fsMIY1731LbStatsLbrTimeMax            TimeInterval,
      fsMIY1731LbStatsTotalResponders       Unsigned32,
      fsMIY1731LbStatsAvgLbrsPerResponder   Unsigned32            
    }

fsMIY1731LbStatsLbmOut OBJECT-TYPE
    SYNTAX      Unsigned32
    MAX-ACCESS  read-only
    STATUS      current
    DESCRIPTION
       "This object specifies the Number of LBMs sent in a loopback or ping transaction.
       "
    ::= { fsMIY1731LbStatsEntry 1}

fsMIY1731LbStatsLbrIn OBJECT-TYPE
    SYNTAX      Unsigned32
    MAX-ACCESS  read-only
    STATUS      current
    DESCRIPTION
       "This object specifies the Number of replies (LBR) received in a loopback or ping transaction.
       "
    ::= { fsMIY1731LbStatsEntry 2 }

fsMIY1731LbStatsLbrTimeAverage OBJECT-TYPE
    SYNTAX      TimeInterval
    MAX-ACCESS  read-only
    STATUS      current
    DESCRIPTION
       "This object specifies the Average time taken to receive the replies (LBR) for the current 
        loopback or ping transaction.
       "
    ::= { fsMIY1731LbStatsEntry 3 }

fsMIY1731LbStatsLbrTimeMin OBJECT-TYPE
    SYNTAX      TimeInterval
    MAX-ACCESS  read-only
    STATUS      current
    DESCRIPTION
       "This object specifies the Minimum time taken to receive the replies (LBR) for the
       current loopback or ping transaction.
       "
    ::= { fsMIY1731LbStatsEntry 4 }

fsMIY1731LbStatsLbrTimeMax OBJECT-TYPE
    SYNTAX      TimeInterval
    MAX-ACCESS  read-only
    STATUS      current
    DESCRIPTION
       "This object specifies the Maximum time taken to receive the replies (LBR) for the current 
        loopback or ping transaction.
       "
    ::= { fsMIY1731LbStatsEntry 5 }

fsMIY1731LbStatsTotalResponders OBJECT-TYPE
    SYNTAX      Unsigned32
    MAX-ACCESS  read-only
    STATUS      current
    DESCRIPTION
       "This object specifies the Total Number of Responders which have sent the reply
        (LBR) for the initiated LBM.
       "
    ::= { fsMIY1731LbStatsEntry 6 }

fsMIY1731LbStatsAvgLbrsPerResponder OBJECT-TYPE
    SYNTAX      Unsigned32
    MAX-ACCESS  read-only
    STATUS      current
    DESCRIPTION
    "This object specifies the Average Number of LBR(s) received per Responder.
    "
    ::= { fsMIY1731LbStatsEntry 7 }

-- ******************************************************************
-- The Frame Delay Buffer Table
-- ******************************************************************

fsMIY1731FdTable OBJECT-TYPE
    SYNTAX      SEQUENCE OF FsMIY1731FdEntry
    MAX-ACCESS  not-accessible
    STATUS      current
    DESCRIPTION
       "This object specifies the table which extends the MEP table and contains a list of
        information about the Frame Delay measured at various times by a 
        MEP.
        Size of this table is defined by the object
        fsMIY1731FrameDelayBufferSize. If the addition of a frame delay entry 
        would exceed the resources allocated to table, then the oldest entries 
        in the table are deleted until sufficient resources are available to 
        hold the new frame delay entry.

        Delay Measured can be of one-way or two-way.
        
       "
    ::= { fsMIY1731Context 10 }

fsMIY1731FdEntry OBJECT-TYPE
    SYNTAX      FsMIY1731FdEntry
    MAX-ACCESS  not-accessible
    STATUS      current
    DESCRIPTION
       "This object specifies the Frame delay buffer table entry."
    INDEX { fsMIY1731ContextId,
            fsMIY1731MegIndex,
            fsMIY1731MeIndex,
            fsMIY1731MepIdentifier,
            fsMIY1731FdTransId,
            fsMIY1731FdSeqNumber        
          }
    ::= { fsMIY1731FdTable 1 }

FsMIY1731FdEntry ::= SEQUENCE {
      fsMIY1731FdTransId                      Unsigned32,
      fsMIY1731FdSeqNumber                    Unsigned32,
      fsMIY1731FdTxTimeStampf                 FsY1731TimeRepresentation,
      fsMIY1731FdMeasurementTimeStamp         TimeStamp,
      fsMIY1731FdPeerMepMacAddress            MacAddress,
      fsMIY1731FdIfIndex                      InterfaceIndex,
      fsMIY1731FdDelayValue                   FsY1731TimeRepresentation,
      fsMIY1731FdIFDV                         FsY1731TimeRepresentation,
      fsMIY1731FdFDV                          FsY1731TimeRepresentation,
      fsMIY1731FdMeasurementType              INTEGER
    }

fsMIY1731FdTransId OBJECT-TYPE
    SYNTAX      Unsigned32 (1..4294967295)
    MAX-ACCESS  not-accessible
    STATUS      current
    DESCRIPTION
       "This object specifies a delay measurement transaction.
       "
    ::= { fsMIY1731FdEntry 1 }

fsMIY1731FdSeqNumber OBJECT-TYPE
    SYNTAX      Unsigned32 (0..4294967295)
    MAX-ACCESS  not-accessible
    STATUS      current
    DESCRIPTION
       "This object specifies the Locally maintained sequence number of FD Entries"
    ::= { fsMIY1731FdEntry 2}

fsMIY1731FdTxTimeStampf OBJECT-TYPE
    SYNTAX      FsY1731TimeRepresentation
    MAX-ACCESS  read-only
    STATUS      current
    DESCRIPTION
       "This object specifies the TxTimeStampf value sent in a Delay measurement message (DMM).
        or received in 1DM frame.
       "
    ::= { fsMIY1731FdEntry 3 }

fsMIY1731FdMeasurementTimeStamp OBJECT-TYPE
    SYNTAX      TimeStamp 
    MAX-ACCESS  read-only
    STATUS      current
    DESCRIPTION
       "This object specifies the Time at which measurement takes place.
       "
    ::= { fsMIY1731FdEntry 4}

fsMIY1731FdPeerMepMacAddress OBJECT-TYPE
    SYNTAX      MacAddress
    MAX-ACCESS  read-only
    STATUS      current
    DESCRIPTION
       "This object specifies the Mac Address of the peer MEP to which DM message(s) 
        is sent.
       "
    ::= { fsMIY1731FdEntry 5 }

fsMIY1731FdIfIndex OBJECT-TYPE
    SYNTAX      InterfaceIndex
    MAX-ACCESS  read-only
    STATUS      current
    DESCRIPTION
       "This object specifie the interface index of the interface either a
        bridge port, or an aggregated IEEE 802.1 link within a bridge port, 
        to which the MEP at which measurement takes place is attached.
       "
    ::= { fsMIY1731FdEntry 6 }

fsMIY1731FdDelayValue OBJECT-TYPE
    SYNTAX      FsY1731TimeRepresentation
    MAX-ACCESS  read-only
    STATUS      current
    DESCRIPTION
       "This object specifies the measured frame delay value.
       "
    ::= { fsMIY1731FdEntry 7 }

fsMIY1731FdIFDV OBJECT-TYPE
    SYNTAX      FsY1731TimeRepresentation
    MAX-ACCESS  read-only
    STATUS      current
    DESCRIPTION
       "This object specifies the Inter frame delay variation, (IFDV), calculated with respect to 
        current transaction.
       "
    ::= { fsMIY1731FdEntry 8 }

fsMIY1731FdFDV OBJECT-TYPE
    SYNTAX      FsY1731TimeRepresentation
    MAX-ACCESS  read-only
    STATUS      current
    DESCRIPTION
       "This object specifies the Frame delay variation, (IFDV), calculated with respect to current 
        transaction.
       "
    ::= { fsMIY1731FdEntry 9 }

fsMIY1731FdMeasurementType OBJECT-TYPE
    SYNTAX      INTEGER { oneWay(1), twoWay(2) } 
    MAX-ACCESS  read-only
    STATUS      current
    DESCRIPTION
       "This object specifies the Type of the frame-delay measurement (oneWay or twoWay).
       "
    ::= { fsMIY1731FdEntry 10 }


-- ******************************************************************
-- The Frame Delay Statistics Table
-- ******************************************************************

fsMIY1731FdStatsTable OBJECT-TYPE
    SYNTAX      SEQUENCE OF FsMIY1731FdStatsEntry
    MAX-ACCESS  not-accessible
    STATUS      current
    DESCRIPTION
       "This object specifies the table which extends the MEP table and contains output of one-way and 
        two-way delay measurement transaction. 
       "
    ::= { fsMIY1731Context 11 }

fsMIY1731FdStatsEntry OBJECT-TYPE
    SYNTAX      FsMIY1731FdStatsEntry
    MAX-ACCESS  not-accessible
    STATUS      current
    DESCRIPTION
       "This object specifies the Delay Statistics table entry."
    INDEX { fsMIY1731ContextId,
            fsMIY1731MegIndex,
            fsMIY1731MeIndex,
            fsMIY1731MepIdentifier,
            fsMIY1731FdTransId
          }
    ::= { fsMIY1731FdStatsTable 1 }

FsMIY1731FdStatsEntry ::= SEQUENCE {
      fsMIY1731FdStatsTimeStamp             TimeStamp,
      fsMIY1731FdStatsDmmOut                Unsigned32,
      fsMIY1731FdStatsDmrIn                 Unsigned32,
      fsMIY1731FdStatsDelayAverage          FsY1731TimeRepresentation,
      fsMIY1731FdStatsFDVAverage            FsY1731TimeRepresentation,
      fsMIY1731FdStatsIFDVAverage           FsY1731TimeRepresentation,
      fsMIY1731FdStatsDelayMin              FsY1731TimeRepresentation, 
      fsMIY1731FdStatsDelayMax              FsY1731TimeRepresentation
    }

fsMIY1731FdStatsTimeStamp OBJECT-TYPE
    SYNTAX      TimeStamp
    MAX-ACCESS  read-only
    STATUS      current
    DESCRIPTION
       "This object specifies the Time stamp at which one-way or two-way delay measurement (DMM) is
        initiated.
       "
    ::= { fsMIY1731FdStatsEntry 1 }

fsMIY1731FdStatsDmmOut OBJECT-TYPE
    SYNTAX      Unsigned32
    MAX-ACCESS  read-only
    STATUS      current
    DESCRIPTION
       "This object specifies the Number of DMMs sent for a two-way delay measurement
        transaction.
       "
    ::= { fsMIY1731FdStatsEntry 2 }

fsMIY1731FdStatsDmrIn OBJECT-TYPE
    SYNTAX      Unsigned32
    MAX-ACCESS  read-only
    STATUS      current
    DESCRIPTION
       "This object specifies the Number of requests received for a one-way or responses received for
       two-way delay measurement transaction.
       "
    ::= { fsMIY1731FdStatsEntry 3 }

fsMIY1731FdStatsDelayAverage OBJECT-TYPE
    SYNTAX      FsY1731TimeRepresentation
    MAX-ACCESS  read-only
    STATUS      current
    DESCRIPTION
       "This object specifies the Average delay measured for a one-way or two-way delay measurement
        transaction.
       "
    ::= { fsMIY1731FdStatsEntry 4 }

fsMIY1731FdStatsFDVAverage OBJECT-TYPE
    SYNTAX      FsY1731TimeRepresentation
    MAX-ACCESS  read-only
    STATUS      current
    DESCRIPTION
       "This object specifies the Frame Delay Variation (FDV) average calculated for a 
       delay measurement transaction.
       "
    ::= { fsMIY1731FdStatsEntry 5 }

fsMIY1731FdStatsIFDVAverage OBJECT-TYPE
    SYNTAX      FsY1731TimeRepresentation
    MAX-ACCESS  read-only
    STATUS      current
    DESCRIPTION
       "This object specifies the Inter Frame Delay Variation (IFDV) average calculated for 
       delay measurement transaction.
       "
    ::= { fsMIY1731FdStatsEntry 6 }

fsMIY1731FdStatsDelayMin OBJECT-TYPE
    SYNTAX      FsY1731TimeRepresentation
    MAX-ACCESS  read-only
    STATUS      current
    DESCRIPTION
       "This object specifies the minimum value of frame-delay.
       "
    ::= { fsMIY1731FdStatsEntry 7 }

fsMIY1731FdStatsDelayMax OBJECT-TYPE
    SYNTAX      FsY1731TimeRepresentation
    MAX-ACCESS  read-only
    STATUS      current
    DESCRIPTION
       "This object specifies the maximum value of frame-delay.
       "
    ::= { fsMIY1731FdStatsEntry 8 }

-- ******************************************************************
-- The Frame Loss Buffer Table
-- ******************************************************************

fsMIY1731FlTable OBJECT-TYPE
    SYNTAX      SEQUENCE OF FsMIY1731FlEntry
    MAX-ACCESS  not-accessible
    STATUS      current
    DESCRIPTION
       "This object specifies the table which extends the MEP table and contains a information about
        the Frame-loss measured at various times by a MEP. 
        
        Size of this table is defined by the object
        fsMIY1731FrameLossBufferSize. If the addition of a frame loss entry 
        would exceed the resources allocated to table, then the oldest entries 
        in the table are deleted until sufficient resources are available to 
        hold the new frame loss entry.
       "
    ::= { fsMIY1731Context 12 }

fsMIY1731FlEntry OBJECT-TYPE
    SYNTAX      FsMIY1731FlEntry
    MAX-ACCESS  not-accessible
    STATUS      current
    DESCRIPTION
       "This object specifies the Frame Loss Statistics table entry."
    INDEX { fsMIY1731ContextId,
            fsMIY1731MegIndex,
            fsMIY1731MeIndex,
            fsMIY1731MepIdentifier,
            fsMIY1731FlTransId,
            fsMIY1731FlSeqNumber
          }
    ::= { fsMIY1731FlTable 1 }

FsMIY1731FlEntry ::= SEQUENCE {
      fsMIY1731FlTransId                  Unsigned32,
      fsMIY1731FlSeqNumber                Unsigned32,
      fsMIY1731FlMeasurementTimeStamp     TimeStamp,
      fsMIY1731FlPeerMepMacAddress        MacAddress,
      fsMIY1731FlIfIndex                  InterfaceIndex,
      fsMIY1731FlFarEndLoss               Unsigned32,
      fsMIY1731FlNearEndLoss              Unsigned32,
      fsMIY1731FlMeasurementTime          TimeInterval
    }

fsMIY1731FlTransId OBJECT-TYPE
    SYNTAX      Unsigned32 (1..4294967295)
    MAX-ACCESS  not-accessible
    STATUS      current
    DESCRIPTION
       "This object specifies the Identifies a loss measurement transaction.
       "
    ::= { fsMIY1731FlEntry 1 }

fsMIY1731FlSeqNumber OBJECT-TYPE
    SYNTAX      Unsigned32 (1..4294967295)
    MAX-ACCESS  not-accessible
    STATUS      current
    DESCRIPTION
       "This object specifies the Locally maintained sequence number of Frame Loss Entries"
    ::= { fsMIY1731FlEntry 2 }

fsMIY1731FlMeasurementTimeStamp OBJECT-TYPE
    SYNTAX      TimeStamp
    MAX-ACCESS  read-only
    STATUS      current
    DESCRIPTION
       "This object specifies the Time at which frame-loss is actually measured.
       "
    ::= { fsMIY1731FlEntry 3 }

fsMIY1731FlPeerMepMacAddress OBJECT-TYPE
    SYNTAX      MacAddress
    MAX-ACCESS  read-only
    STATUS      current
    DESCRIPTION
       "This object specifies the Mac Address of the peer MEP to which loss measurement 
        message(s) is sent.
       "
    ::= { fsMIY1731FlEntry 4 }

fsMIY1731FlIfIndex OBJECT-TYPE
    SYNTAX      InterfaceIndex
    MAX-ACCESS  read-only
    STATUS      current
    DESCRIPTION
       "This object specifies the interface index of the interface either a
        bridge port, or an aggregated IEEE 802.1 link within a bridge port, 
        to which the MEP at which measurement takes place is attached.
       "
    ::= { fsMIY1731FlEntry 5 }

fsMIY1731FlFarEndLoss OBJECT-TYPE
    SYNTAX      Unsigned32 (0..4294967295)
    MAX-ACCESS  read-only
    STATUS      current
    DESCRIPTION
       "This object specifies the far-end frame-loss value.
       "
    ::= { fsMIY1731FlEntry 6 }

fsMIY1731FlNearEndLoss OBJECT-TYPE
    SYNTAX      Unsigned32 (0..4294967295)
    MAX-ACCESS  read-only
    STATUS      current
    DESCRIPTION
       "This object specifies the near-end frame-loss value.
       "
    ::= { fsMIY1731FlEntry 7 }

fsMIY1731FlMeasurementTime OBJECT-TYPE
    SYNTAX      TimeInterval
    MAX-ACCESS  read-only
    STATUS      current
    DESCRIPTION
       "This object specifies the Time taken to measure frame-loss.
       "
    ::= { fsMIY1731FlEntry 8 }

-- ******************************************************************
-- The Frame Loss Statistics Table
-- ******************************************************************

fsMIY1731FlStatsTable OBJECT-TYPE
    SYNTAX      SEQUENCE OF FsMIY1731FlStatsEntry
    MAX-ACCESS  not-accessible
    STATUS      current
    DESCRIPTION
       "This object specifies the table which extends the MEP table and contains output of 
        frame-loss measurement transaction. 
       "
    ::= { fsMIY1731Context 13 }

fsMIY1731FlStatsEntry OBJECT-TYPE
    SYNTAX      FsMIY1731FlStatsEntry
    MAX-ACCESS  not-accessible
    STATUS      current
    DESCRIPTION
       "This object specifies the Frame Loss Statistics table entry."
    INDEX { fsMIY1731ContextId,
            fsMIY1731MegIndex,
            fsMIY1731MeIndex,
            fsMIY1731MepIdentifier,
            fsMIY1731FlTransId
          }
    ::= { fsMIY1731FlStatsTable 1 }

FsMIY1731FlStatsEntry ::= SEQUENCE {
      fsMIY1731FlStatsTimeStamp             TimeStamp,
      fsMIY1731FlStatsMessagesOut           Unsigned32,
      fsMIY1731FlStatsMessagesIn            Unsigned32,
      fsMIY1731FlStatsFarEndLossAverage     Unsigned32,
      fsMIY1731FlStatsNearEndLossAverage    Unsigned32,
      fsMIY1731FlStatsMeasurementType       INTEGER,
      fsMIY1731FlStatsFarEndLossMin         Unsigned32, 
      fsMIY1731FlStatsFarEndLossMax         Unsigned32,
      fsMIY1731FlStatsNearEndLossMin        Unsigned32,
      fsMIY1731FlStatsNearEndLossMax        Unsigned32
    }

fsMIY1731FlStatsTimeStamp OBJECT-TYPE
    SYNTAX      TimeStamp
    MAX-ACCESS  read-only
    STATUS      current
    DESCRIPTION
       "This object specifies the Time stamp at which frame-loss measurement transaction is initiated.
       "
    ::= { fsMIY1731FlStatsEntry 1 }

fsMIY1731FlStatsMessagesOut OBJECT-TYPE
    SYNTAX      Unsigned32 (1..4294967295)
    MAX-ACCESS  read-only
    STATUS      current
    DESCRIPTION
       "This object specifies the Number of frames with ETH-LM information sent for a transaction.
       "
    ::= { fsMIY1731FlStatsEntry 2 }

fsMIY1731FlStatsMessagesIn OBJECT-TYPE
    SYNTAX      Unsigned32 
    MAX-ACCESS  read-only
    STATUS      current
    DESCRIPTION
       "This object specifies the Number of frames with ETH-LM information received for a  
       transaction.
       "
    ::= { fsMIY1731FlStatsEntry 3 }

fsMIY1731FlStatsFarEndLossAverage OBJECT-TYPE
    SYNTAX      Unsigned32
    MAX-ACCESS  read-only
    STATUS      current
    DESCRIPTION
       "This object specifies the Average of the far-end frame-loss measured for a transaction.
       "
    ::= { fsMIY1731FlStatsEntry 4 }

fsMIY1731FlStatsNearEndLossAverage OBJECT-TYPE
    SYNTAX      Unsigned32
    MAX-ACCESS  read-only
    STATUS      current
    DESCRIPTION
       "This object specifies the Average of the near-end frame-loss measured for a transaction.
       "
    ::= { fsMIY1731FlStatsEntry 5 }

fsMIY1731FlStatsMeasurementType OBJECT-TYPE
    SYNTAX      INTEGER { singleEnded(1), dualEnded(2) }
    MAX-ACCESS  read-only
    STATUS      current
    DESCRIPTION
       "This object specifies the Type of the frame-loss measurement (Single-ended or Dual-ended) done.
       "
    ::= { fsMIY1731FlStatsEntry 6 }

fsMIY1731FlStatsFarEndLossMin OBJECT-TYPE
    SYNTAX      Unsigned32 
    MAX-ACCESS  read-only
    STATUS      current
    DESCRIPTION
       "This object specifies the minimum value of far-end frame-loss.
       "
    ::= { fsMIY1731FlStatsEntry 7 }

fsMIY1731FlStatsFarEndLossMax OBJECT-TYPE
    SYNTAX      Unsigned32 
    MAX-ACCESS  read-only
    STATUS      current
    DESCRIPTION
       "This object specifies the maxmium value of far-end frame-loss.
       "
    ::= { fsMIY1731FlStatsEntry 8 }

fsMIY1731FlStatsNearEndLossMin OBJECT-TYPE
    SYNTAX      Unsigned32 
    MAX-ACCESS  read-only
    STATUS      current
    DESCRIPTION
       "This object specifies the minimum value of near-end frame-loss.
       "
    ::= { fsMIY1731FlStatsEntry 9 }

fsMIY1731FlStatsNearEndLossMax OBJECT-TYPE
    SYNTAX      Unsigned32 
    MAX-ACCESS  read-only
    STATUS      current
    DESCRIPTION
       "This object specifies the maxmium value of near-end frame-loss.
       "
    ::= { fsMIY1731FlStatsEntry 10 }

-- ************************************************************************
-- The Remote Maintenance End Point Table for Y.1731 based MPLS-TP networks
-- ************************************************************************

fsMIY1731MplstpExtRemoteMepTable OBJECT-TYPE
    SYNTAX      SEQUENCE OF FsMIY1731MplstpExtRemoteMepEntry
    MAX-ACCESS  not-accessible
    STATUS      current
    DESCRIPTION
       "This object specifies the Remote Maintenance End Point table for the Y.1731 extensions
        over MPLS-TP networks. 
        Each row in the table realizes an ME for the MPLS-TP networks using
        the local and remote MEP identifiers which are indices to the table. 
        This table is mainly used to associate a specific LSP/PW to an ME.

        This table uses five indices, first index provides the virtual context 
        identifier in which this entry resides. The second index is the index 
        to the MEG table identifying the specific MD/Level. Third index is the 
        index to ME table identifying the specific MEG. The fourth index is 
        the Local MEP Indentifier. The fifth index is the remote MEP Identifier.

        The writable objects in this table need to be persistent upon reboot 
        or restart of a device."

    REFERENCE
       "MPLS-TP OAM based on Y.1731, draft-bhh-mpls-tp-oam-y1731-06.txt."
    ::= { fsMIY1731Context 14 }

fsMIY1731MplstpExtRemoteMepEntry OBJECT-TYPE
    SYNTAX      FsMIY1731MplstpExtRemoteMepEntry
    MAX-ACCESS  not-accessible
    STATUS      current
    DESCRIPTION
       "This object specifies an instance of the Remote Maintenenace End Point table entry used in
        Y.1731 based MPLS-TP networks."
    INDEX { fsMIY1731ContextId,
            fsMIY1731MegIndex,
            fsMIY1731MeIndex,
            fsMIY1731MepIdentifier,
            fsMIY1731MplstpExtRMepIdentifier
          }
    ::= { fsMIY1731MplstpExtRemoteMepTable 1 }

FsMIY1731MplstpExtRemoteMepEntry ::= SEQUENCE {
      fsMIY1731MplstpExtRMepIdentifier            Dot1agCfmMepId,
      fsMIY1731MplstpExtRMepServicePointer        RowPointer,
      fsMIY1731MplstpExtRMepRowStatus             RowStatus
}

fsMIY1731MplstpExtRMepIdentifier OBJECT-TYPE
    SYNTAX      Dot1agCfmMepId
    MAX-ACCESS  not-accessible
    STATUS      current
    DESCRIPTION
       "This object specifies the Maintenance End Point Identifier of a Remote MEP associated with the 
        Local-MEP(fsMIY1731MepIdentifier) which together constitutes an ME.
       "
    ::= { fsMIY1731MplstpExtRemoteMepEntry  1 }

fsMIY1731MplstpExtRMepServicePointer OBJECT-TYPE
    SYNTAX      RowPointer
    MAX-ACCESS  read-create
    STATUS      current
    DESCRIPTION
       "This object specifies the MPLS Transport path which represents the ME. 

        This object may point to an entry in the mplsTunnelTable, if the value 
        of the object fsMIEcfmExtMaPrimarySelectorType in fsMIEcfmExtMaTable is 
        mplsTunnelLsp. 

        Otherwise this object may point to an entry in the pwTable, if the value
        of the object fsMIEcfmExtMaPrimarySelectorType in fsMIEcfmExtMaTable is
        mplsPseudoWire.
       "
    ::= { fsMIY1731MplstpExtRemoteMepEntry  2 }

fsMIY1731MplstpExtRMepRowStatus OBJECT-TYPE
    SYNTAX      RowStatus
    MAX-ACCESS  read-create
    STATUS      current
    DESCRIPTION
       "This object specifies the status of the row.

        The writable columns in a row can not be changed if the row
        is active. All columns must have a valid value before a row
        can be activated.
       "
    ::= { fsMIY1731MplstpExtRemoteMepEntry 3 }


-- *******************************************************************
-- ECFM-Y1731 Per Context Statistics Table
-- *******************************************************************

fsMIY1731StatsTable OBJECT-TYPE
    SYNTAX        SEQUENCE OF FsMIY1731StatsEntry
    MAX-ACCESS    not-accessible
    STATUS        current
    DESCRIPTION
       "This object specifies the List of per virtual context ECFM-Y1731 Module Statistics."
    ::= { fsMIY1731Context 15 }

fsMIY1731StatsEntry OBJECT-TYPE
    SYNTAX       FsMIY1731StatsEntry
    MAX-ACCESS   not-accessible
    STATUS       current
    DESCRIPTION
       "This object specifies the Per virtual context ECFM-Y1731 Module Statistics." 
    INDEX { fsMIY1731ContextId }
    ::= { fsMIY1731StatsTable 1 }

FsMIY1731StatsEntry ::= SEQUENCE {
       fsMIY1731AisOut       Unsigned32,
       fsMIY1731AisIn        Unsigned32,
       fsMIY1731LckOut       Unsigned32,
       fsMIY1731LckIn        Unsigned32,
       fsMIY1731TstOut       Unsigned32,
       fsMIY1731TstIn        Unsigned32,
       fsMIY1731LmmOut       Unsigned32,
       fsMIY1731LmmIn        Unsigned32,
       fsMIY1731LmrOut       Unsigned32,
       fsMIY1731LmrIn        Unsigned32,
       fsMIY17311DmOut       Unsigned32,
       fsMIY17311DmIn        Unsigned32,
       fsMIY1731DmmOut       Unsigned32,
       fsMIY1731DmmIn        Unsigned32,
       fsMIY1731DmrOut       Unsigned32,
       fsMIY1731DmrIn        Unsigned32,
       fsMIY1731ApsOut       Unsigned32,
       fsMIY1731ApsIn        Unsigned32,
       fsMIY1731MccOut       Unsigned32,
       fsMIY1731MccIn        Unsigned32,
       fsMIY1731VsmOut       Unsigned32,
       fsMIY1731VsmIn        Unsigned32,
       fsMIY1731VsrOut       Unsigned32,
       fsMIY1731VsrIn        Unsigned32,
       fsMIY1731ExmOut       Unsigned32,
       fsMIY1731ExmIn        Unsigned32,
       fsMIY1731ExrOut       Unsigned32,
       fsMIY1731ExrIn        Unsigned32,
       fsMIY1731TxFailOpcode Unsigned32
}

fsMIY1731AisOut OBJECT-TYPE
    SYNTAX      Unsigned32
    MAX-ACCESS  read-write
    STATUS      current
    DESCRIPTION
       "This object specifies the Number of AIS PDUs transmitted.
       "
    ::= { fsMIY1731StatsEntry 1 }
 
fsMIY1731AisIn OBJECT-TYPE
    SYNTAX      Unsigned32
    MAX-ACCESS  read-write
    STATUS      current
    DESCRIPTION
       "This object specifies the Number of AIS PDUs received.
       "
    ::= { fsMIY1731StatsEntry 2 }

fsMIY1731LckOut OBJECT-TYPE
    SYNTAX      Unsigned32
    MAX-ACCESS  read-write
    STATUS      current
    DESCRIPTION
       "This object specifies the Number of LCK PDUs transmitted.
       "
    ::= { fsMIY1731StatsEntry 3 }
 
fsMIY1731LckIn OBJECT-TYPE
    SYNTAX      Unsigned32
    MAX-ACCESS  read-write
    STATUS      current
    DESCRIPTION
       "This object specifies the Number of LCK PDUs received.
       "
    ::= { fsMIY1731StatsEntry 4 }

fsMIY1731TstOut OBJECT-TYPE
    SYNTAX      Unsigned32
    MAX-ACCESS  read-write
    STATUS      current
    DESCRIPTION
       "This object specifies the Number of TST PDUs transmitted.
       "
    ::= { fsMIY1731StatsEntry 5 }
 
fsMIY1731TstIn OBJECT-TYPE
    SYNTAX      Unsigned32
    MAX-ACCESS  read-write
    STATUS      current
    DESCRIPTION
       "This object specifies the Number of TST PDUs received.
       "
    ::= { fsMIY1731StatsEntry 6 }

fsMIY1731LmmOut OBJECT-TYPE
    SYNTAX      Unsigned32
    MAX-ACCESS  read-write
    STATUS      current
    DESCRIPTION
       "This object specifies the Number of LMM PDUs transmitted.
       "
    ::= { fsMIY1731StatsEntry 7 }
 
fsMIY1731LmmIn OBJECT-TYPE
    SYNTAX      Unsigned32
    MAX-ACCESS  read-write
    STATUS      current
    DESCRIPTION
       "This object specifies the Number of LMM PDUs received.
       "
    ::= { fsMIY1731StatsEntry 8 } 

fsMIY1731LmrOut OBJECT-TYPE
    SYNTAX      Unsigned32
    MAX-ACCESS  read-write
    STATUS      current
    DESCRIPTION
       "This object specifies the Number of LMR PDUs transmitted.
       "
    ::= { fsMIY1731StatsEntry 9 }
 
fsMIY1731LmrIn OBJECT-TYPE
    SYNTAX      Unsigned32
    MAX-ACCESS  read-write
    STATUS      current
    DESCRIPTION
       "This object specifies the Number of LMR PDUs received.
       "
    ::= { fsMIY1731StatsEntry 10 } 

fsMIY17311DmOut OBJECT-TYPE
    SYNTAX      Unsigned32
    MAX-ACCESS  read-write
    STATUS      current
    DESCRIPTION
       "This object specifies the Number of 1DM PDUs transmitted.
       "
    ::= { fsMIY1731StatsEntry 11 }
 
fsMIY17311DmIn OBJECT-TYPE
    SYNTAX      Unsigned32
    MAX-ACCESS  read-write
    STATUS      current
    DESCRIPTION
       "This object specifies the Number of 1DM PDUs received.
       "
    ::= { fsMIY1731StatsEntry 12 } 

fsMIY1731DmmOut OBJECT-TYPE
    SYNTAX      Unsigned32
    MAX-ACCESS  read-write
    STATUS      current
    DESCRIPTION
       "This object specifies the Number of DMM PDUs transmitted.
       "
    ::= { fsMIY1731StatsEntry 13 }
 
fsMIY1731DmmIn OBJECT-TYPE
    SYNTAX      Unsigned32
    MAX-ACCESS  read-write
    STATUS      current
    DESCRIPTION
       "This object specifies the Number of DMM PDUs received.
       "
    ::= { fsMIY1731StatsEntry 14 } 

fsMIY1731DmrOut OBJECT-TYPE
    SYNTAX      Unsigned32
    MAX-ACCESS  read-write
    STATUS      current
    DESCRIPTION
       "This object specifies the Number of DMR PDUs transmitted.
       "
    ::= { fsMIY1731StatsEntry 15 }
 
fsMIY1731DmrIn OBJECT-TYPE
    SYNTAX      Unsigned32
    MAX-ACCESS  read-write
    STATUS      current
    DESCRIPTION
       "This object specifies the Number of DMR PDUs received.
       "
    ::= { fsMIY1731StatsEntry 16 } 

fsMIY1731ApsOut OBJECT-TYPE
    SYNTAX      Unsigned32
    MAX-ACCESS  read-write
    STATUS      current
    DESCRIPTION
       "This object specifies the Number of APS PDUs transmitted.
       "
    ::= { fsMIY1731StatsEntry 17 }
 
fsMIY1731ApsIn OBJECT-TYPE
    SYNTAX      Unsigned32
    MAX-ACCESS  read-write
    STATUS      current
    DESCRIPTION
       "This object specifies the Number of APS PDUs received.
       "
    ::= { fsMIY1731StatsEntry 18 } 

fsMIY1731MccOut OBJECT-TYPE
    SYNTAX      Unsigned32
    MAX-ACCESS  read-write
    STATUS      current
    DESCRIPTION
       "This object specifies the Number of MCC PDUs transmitted.
       "
    ::= { fsMIY1731StatsEntry 19 }
 
fsMIY1731MccIn OBJECT-TYPE
    SYNTAX      Unsigned32
    MAX-ACCESS  read-write
    STATUS      current
    DESCRIPTION
       "This object specifies the Number of MCC PDUs received.
       "
    ::= { fsMIY1731StatsEntry 20 } 

fsMIY1731VsmOut OBJECT-TYPE
    SYNTAX      Unsigned32
    MAX-ACCESS  read-write
    STATUS      current
    DESCRIPTION
       "This object specifies the Number of VSM PDUs transmitted.
       "
    ::= { fsMIY1731StatsEntry 21 } 

fsMIY1731VsmIn OBJECT-TYPE
    SYNTAX      Unsigned32
    MAX-ACCESS  read-write
    STATUS      current
    DESCRIPTION
       "This object specifies the Number of VSM PDUs received.
       "
    ::= { fsMIY1731StatsEntry 22 } 

fsMIY1731VsrOut OBJECT-TYPE
    SYNTAX      Unsigned32
    MAX-ACCESS  read-write
    STATUS      current
    DESCRIPTION
       "This object specifies the Number of VSR PDUs transmitted.
       "
    ::= { fsMIY1731StatsEntry 23 } 

fsMIY1731VsrIn OBJECT-TYPE
    SYNTAX      Unsigned32
    MAX-ACCESS  read-write
    STATUS      current
    DESCRIPTION
       "This object specifies the Number of VSR PDUs received.
       "
    ::= { fsMIY1731StatsEntry 24 } 

fsMIY1731ExmOut OBJECT-TYPE
    SYNTAX      Unsigned32
    MAX-ACCESS  read-write
    STATUS      current
    DESCRIPTION
       "This object specifies the Number of EXM PDUs transmitted.
       "
    ::= { fsMIY1731StatsEntry 25 } 

fsMIY1731ExmIn OBJECT-TYPE
    SYNTAX      Unsigned32
    MAX-ACCESS  read-write
    STATUS      current
    DESCRIPTION
       "This object specifies the Number of EXM PDUs received.
       "
    ::= { fsMIY1731StatsEntry 26 }

fsMIY1731ExrOut OBJECT-TYPE
    SYNTAX      Unsigned32
    MAX-ACCESS  read-write
    STATUS      current
    DESCRIPTION
       "This object specifies the Number of EXR PDUs transmitted.
       "
    ::= { fsMIY1731StatsEntry 27 }

fsMIY1731ExrIn OBJECT-TYPE
    SYNTAX      Unsigned32
    MAX-ACCESS  read-write
    STATUS      current
    DESCRIPTION
       "This object specifies the Number of EXR PDUs received.
       "
    ::= { fsMIY1731StatsEntry 28 }

fsMIY1731TxFailOpcode OBJECT-TYPE
    SYNTAX      Unsigned32
    MAX-ACCESS  read-only
    STATUS      current
    DESCRIPTION
       "This object specifies the Opcode value of Last Tx Failure CFM PDU.
        When CFM PDU is not transmitted from system due to system failure then 
        CFM PDU Tx failure trap is generated and the trap contains this value.
       "
    ::= { fsMIY1731StatsEntry 29 }


-- ******************************************************************
-- The Port Table
-- ******************************************************************

fsMIY1731PortTable OBJECT-TYPE
    SYNTAX        SEQUENCE OF FsMIY1731PortEntry
    MAX-ACCESS    not-accessible
    STATUS        current
    DESCRIPTION
    "This object specifies ECFM information specific to interface.
    "
    ::= { fsMIY1731System 1 }

fsMIY1731PortEntry OBJECT-TYPE
    SYNTAX       FsMIY1731PortEntry
    MAX-ACCESS   not-accessible
    STATUS       current
    DESCRIPTION
    "This object specifies Each entry in this table is for each interface present in the system.
      This table is indexed by the fsMIY1731PortIfIndex
    "
    INDEX { fsMIY1731PortIfIndex }
    ::= { fsMIY1731PortTable 1 }

FsMIY1731PortEntry ::= SEQUENCE {
       fsMIY1731PortIfIndex      InterfaceIndex,
       fsMIY1731PortAisOut       Unsigned32,
       fsMIY1731PortAisIn        Unsigned32,
       fsMIY1731PortLckOut       Unsigned32,
       fsMIY1731PortLckIn        Unsigned32,
       fsMIY1731PortTstOut       Unsigned32,
       fsMIY1731PortTstIn        Unsigned32,
       fsMIY1731PortLmmOut       Unsigned32,
       fsMIY1731PortLmmIn        Unsigned32,
       fsMIY1731PortLmrOut       Unsigned32,
       fsMIY1731PortLmrIn        Unsigned32,
       fsMIY1731Port1DmOut       Unsigned32,
       fsMIY1731Port1DmIn        Unsigned32,
       fsMIY1731PortDmmOut       Unsigned32,
       fsMIY1731PortDmmIn        Unsigned32,
       fsMIY1731PortDmrOut       Unsigned32,
       fsMIY1731PortDmrIn        Unsigned32,
       fsMIY1731PortApsOut       Unsigned32,
       fsMIY1731PortApsIn        Unsigned32,
       fsMIY1731PortMccOut       Unsigned32,
       fsMIY1731PortMccIn        Unsigned32,
       fsMIY1731PortVsmOut       Unsigned32,
       fsMIY1731PortVsmIn        Unsigned32,
       fsMIY1731PortVsrOut       Unsigned32,
       fsMIY1731PortVsrIn        Unsigned32,
       fsMIY1731PortExmOut       Unsigned32,
       fsMIY1731PortExmIn        Unsigned32,
       fsMIY1731PortExrOut       Unsigned32,
       fsMIY1731PortExrIn        Unsigned32,
       fsMIY1731PortOperStatus   FsY1731EnabledStatus,
       fsMIY1731LastTxFailOpcode Unsigned32    
}

fsMIY1731PortIfIndex OBJECT-TYPE
    SYNTAX        InterfaceIndex
    MAX-ACCESS    not-accessible
    STATUS        current
    DESCRIPTION
       "This object specifies the interface index of the interface either a
        bridge port, or an aggregated IEEE 802.1 link within a bridge
        port.
       "
    ::= { fsMIY1731PortEntry 1 }
 
fsMIY1731PortAisOut OBJECT-TYPE
    SYNTAX      Unsigned32
    MAX-ACCESS  read-write
    STATUS      current
    DESCRIPTION
       "This object specifies the Number of AIS PDUs transmitted by this interface.
       "
    ::= { fsMIY1731PortEntry 2 }
 
fsMIY1731PortAisIn OBJECT-TYPE
    SYNTAX      Unsigned32
    MAX-ACCESS  read-write
    STATUS      current
    DESCRIPTION
       "This object specifies the Number of AIS PDUs received by this interface.
       "
    ::= { fsMIY1731PortEntry 3 }

fsMIY1731PortLckOut OBJECT-TYPE
    SYNTAX      Unsigned32
    MAX-ACCESS  read-write
    STATUS      current
    DESCRIPTION
       "This object specifies the Number of LCK PDUs transmitted by this interface.
       "
    ::= { fsMIY1731PortEntry 4 }
 
fsMIY1731PortLckIn OBJECT-TYPE
    SYNTAX      Unsigned32
    MAX-ACCESS  read-write
    STATUS      current
    DESCRIPTION
       "This object specifies the Number of LCK PDUs received by this interface.
       "
    ::= { fsMIY1731PortEntry 5 }

fsMIY1731PortTstOut OBJECT-TYPE
    SYNTAX      Unsigned32
    MAX-ACCESS  read-write
    STATUS      current
    DESCRIPTION
       "This object specifies the Number of TST PDUs transmitted by this interface.
       "
    ::= { fsMIY1731PortEntry 6 }
 
fsMIY1731PortTstIn OBJECT-TYPE
    SYNTAX      Unsigned32
    MAX-ACCESS  read-write
    STATUS      current
    DESCRIPTION
       "This object specifies the Number of TST PDUs received by this interface.
       "
    ::= { fsMIY1731PortEntry 7 } 

fsMIY1731PortLmmOut OBJECT-TYPE
    SYNTAX      Unsigned32
    MAX-ACCESS  read-write
    STATUS      current
    DESCRIPTION
       "This object specifies the Number of LMM PDUs transmitted by this interface.
       "
    ::= { fsMIY1731PortEntry 8 }
 
fsMIY1731PortLmmIn OBJECT-TYPE
    SYNTAX      Unsigned32
    MAX-ACCESS  read-write
    STATUS      current
    DESCRIPTION
       "This object specifies the Number of LMM PDUs received by this interface.
       "
    ::= { fsMIY1731PortEntry 9 } 

fsMIY1731PortLmrOut OBJECT-TYPE
    SYNTAX      Unsigned32
    MAX-ACCESS  read-write
    STATUS      current
    DESCRIPTION
       "This object specifies the Number of LMR PDUs transmitted by this interface.
       "
    ::= { fsMIY1731PortEntry 10 }
 
fsMIY1731PortLmrIn OBJECT-TYPE
    SYNTAX      Unsigned32
    MAX-ACCESS  read-write
    STATUS      current
    DESCRIPTION
       "This object specifies the Number of LMR PDUs received by this interface.
       "
    ::= { fsMIY1731PortEntry 11 } 

fsMIY1731Port1DmOut OBJECT-TYPE
    SYNTAX      Unsigned32
    MAX-ACCESS  read-write
    STATUS      current
    DESCRIPTION
       "This object specifies the Number of 1DM PDUs transmitted by this interface.
       "
    ::= { fsMIY1731PortEntry 12 }
 
fsMIY1731Port1DmIn OBJECT-TYPE
    SYNTAX      Unsigned32
    MAX-ACCESS  read-write
    STATUS      current
    DESCRIPTION
       "This object specifies the Number of 1DM PDUs received by this interface.
       "
    ::= { fsMIY1731PortEntry 13 } 

fsMIY1731PortDmmOut OBJECT-TYPE
    SYNTAX      Unsigned32
    MAX-ACCESS  read-write
    STATUS      current
    DESCRIPTION
       "This object specifies the Number of DMM PDUs transmitted by this interface.
       "
    ::= { fsMIY1731PortEntry 14 }
 
fsMIY1731PortDmmIn OBJECT-TYPE
    SYNTAX      Unsigned32
    MAX-ACCESS  read-write
    STATUS      current
    DESCRIPTION
       "This object specifies the Number of DMM PDUs received by this interface.
       "
    ::= { fsMIY1731PortEntry 15 } 

fsMIY1731PortDmrOut OBJECT-TYPE
    SYNTAX      Unsigned32
    MAX-ACCESS  read-write
    STATUS      current
    DESCRIPTION
       "This object specifies the Number of DMR PDUs transmitted by this interface.
       "
    ::= { fsMIY1731PortEntry 16 }
 
fsMIY1731PortDmrIn OBJECT-TYPE
    SYNTAX      Unsigned32
    MAX-ACCESS  read-write
    STATUS      current
    DESCRIPTION
       "This object specifies the Number of DMR PDUs received by this interface.
       "
    ::= { fsMIY1731PortEntry 17 } 

fsMIY1731PortApsOut OBJECT-TYPE
    SYNTAX      Unsigned32
    MAX-ACCESS  read-write
    STATUS      current
    DESCRIPTION
       "This object specifies the Number of APS PDUs transmitted by this interface.
       "
    ::= { fsMIY1731PortEntry 18 }
 
fsMIY1731PortApsIn OBJECT-TYPE
    SYNTAX      Unsigned32
    MAX-ACCESS  read-write
    STATUS      current
    DESCRIPTION
       "This object specifies the Number of APS PDUs received by this interface.
       "
    ::= { fsMIY1731PortEntry 19 } 

fsMIY1731PortMccOut OBJECT-TYPE
    SYNTAX      Unsigned32
    MAX-ACCESS  read-write
    STATUS      current
    DESCRIPTION
       "This object specifies the Number of MCC PDUs transmitted by this interface.
       "
    ::= { fsMIY1731PortEntry 20 }
 
fsMIY1731PortMccIn OBJECT-TYPE
    SYNTAX      Unsigned32
    MAX-ACCESS  read-write
    STATUS      current
    DESCRIPTION
       "This object specifies the Number of MCC PDUs received by this interface.
       "
    ::= { fsMIY1731PortEntry 21 } 

fsMIY1731PortVsmOut OBJECT-TYPE
    SYNTAX      Unsigned32
    MAX-ACCESS  read-write
    STATUS      current
    DESCRIPTION
       "This object specifies the Number of VSM PDUs transmitted by this interface.
       "
    ::= { fsMIY1731PortEntry 22 } 

fsMIY1731PortVsmIn OBJECT-TYPE
    SYNTAX      Unsigned32
    MAX-ACCESS  read-write
    STATUS      current
    DESCRIPTION
       "This object specifies the Number of VSM PDUs received by this interface.
       "
    ::= { fsMIY1731PortEntry 23 } 

fsMIY1731PortVsrOut OBJECT-TYPE
    SYNTAX      Unsigned32
    MAX-ACCESS  read-write
    STATUS      current
    DESCRIPTION
       "This object specifies the Number of VSR PDUs transmitted by this interface.
       "
    ::= { fsMIY1731PortEntry 24 } 

fsMIY1731PortVsrIn OBJECT-TYPE
    SYNTAX      Unsigned32
    MAX-ACCESS  read-write
    STATUS      current
    DESCRIPTION
       "This object specifies the Number of VSR PDUs received by this interface.
       "
    ::= { fsMIY1731PortEntry 25 } 

fsMIY1731PortExmOut OBJECT-TYPE
    SYNTAX      Unsigned32
    MAX-ACCESS  read-write
    STATUS      current
    DESCRIPTION
       "This object specifies the Number of EXM PDUs transmitted by this interface.
       "
    ::= { fsMIY1731PortEntry 26 } 

fsMIY1731PortExmIn OBJECT-TYPE
    SYNTAX      Unsigned32
    MAX-ACCESS  read-write
    STATUS      current
    DESCRIPTION
       "This object specifies the Number of EXM PDUs received by this interface.
       "
    ::= { fsMIY1731PortEntry 27 } 

fsMIY1731PortExrOut OBJECT-TYPE
    SYNTAX      Unsigned32
    MAX-ACCESS  read-write
    STATUS      current
    DESCRIPTION
       "This object specifies the Number of EXR PDUs transmitted by this interface.
       "
    ::= { fsMIY1731PortEntry 28 } 

fsMIY1731PortExrIn OBJECT-TYPE
    SYNTAX      Unsigned32
    MAX-ACCESS  read-write
    STATUS      current
    DESCRIPTION
       "This object specifies the Number of EXR PDUs received by this interface.
       "
    ::= { fsMIY1731PortEntry 29 } 

fsMIY1731PortOperStatus OBJECT-TYPE
   SYNTAX      FsY1731EnabledStatus 
   MAX-ACCESS  read-write
   STATUS      current
   DESCRIPTION
      "This object specifies the administrative module status of Ethernet Y1731
       functionality. This enables or disables Y1731 in the system.
       If set to enable, enables the Y1731 for a particular port. 
       Otherwise, disables Y1731 for a particular port.
       Note: The ECFM Module must be enabled for Y1731 to enable or disable."
   DEFVAL { disabled }
   ::= { fsMIY1731PortEntry 30 }

fsMIY1731LastTxFailOpcode OBJECT-TYPE
    SYNTAX      Unsigned32
    MAX-ACCESS  read-only
    STATUS      current
    DESCRIPTION
       "This object specifies the Opcode value of Last Tx Failure CFM PDU.
        When CFM PDU is not transmitted from system due to system failure then 
        CFM PDU Tx failure trap will generate & which contain this value.
       "
    ::= { fsMIY1731PortEntry 31 }

-- ******************************************************************
--                 MEP AVilability Table  
-- ******************************************************************

fsMIY1731MepAvailabilityTable OBJECT-TYPE
    SYNTAX      SEQUENCE OF FsMIY1731MepAvailabilityEntry
    MAX-ACCESS  not-accessible
    STATUS      current
    DESCRIPTION
       "This object specifies the Maintenance Entity Group End Point (MEP) Availability 
        table.

        Each row in the table is associated with a different MEP. 

        This table uses three indices. The first two indices are the
        indices of the Maintenance Entity Group (MEG) and Maintenance 
        Entity (ME) tables, the reason being that a MEP is always 
        related to an ME and MEG.

        The MEP table stores all the managed objects for availability
        measurement.

        The objects which are used to initiate a transaction are to
        be set only when the row-status of the table is active.
        'fsMIY1731MepTransmit' naming convention is used to isolate 
        these objects from the others.
       "
    ::= { fsMIY1731Context 16 }

fsMIY1731MepAvailabilityEntry OBJECT-TYPE
    SYNTAX      FsMIY1731MepAvailabilityEntry
    MAX-ACCESS  not-accessible
    STATUS      current
    DESCRIPTION
       "This object specifies the MEP Availability table entry"
    INDEX { fsMIY1731ContextId,
            fsMIY1731MegIndex,
            fsMIY1731MeIndex,
            fsMIY1731MepIdentifier
          }
    ::= { fsMIY1731MepAvailabilityTable 1 }

FsMIY1731MepAvailabilityEntry ::= SEQUENCE {
        fsMIY1731MepAvailabilityStatus                    FsY1731TransmitStatus,
        fsMIY1731MepAvailabilityResultOK                  TruthValue, 
        fsMIY1731MepAvailabilityInterval                  FsY1731AvailabilityInterval,
        fsMIY1731MepAvailabilityDeadline                  Unsigned32,
        fsMIY1731MepAvailabilityLowerThreshold            OCTET STRING,
        fsMIY1731MepAvailabilityUpperThreshold            OCTET STRING,
        fsMIY1731MepAvailabilityModestAreaIsAvailable     TruthValue,
        fsMIY1731MepAvailabilityWindowSize                Unsigned32,
        fsMIY1731MepAvailabilityDestMacAddress            MacAddress,
        fsMIY1731MepAvailabilityDestMepId                 Dot1agCfmMepIdOrZero,
        fsMIY1731MepAvailabilityDestIsMepId               TruthValue,
        fsMIY1731MepAvailabilityType                      FsY1731AvailabilityType,
        fsMIY1731MepAvailabilitySchldDownInitTime         Unsigned32,
        fsMIY1731MepAvailabilitySchldDownEndTime          Unsigned32,
        fsMIY1731MepAvailabilityPriority                  Unsigned32,
        fsMIY1731MepAvailabilityDropEnable                TruthValue,
        fsMIY1731MepAvailabilityPercentage                OCTET STRING,
        fsMIY1731MepAvailabilityRowStatus                 RowStatus
        }

fsMIY1731MepAvailabilityStatus OBJECT-TYPE
   SYNTAX       FsY1731TransmitStatus
   MAX-ACCESS   read-write
   STATUS       current
   DESCRIPTION
       "This object specifies an Enumerated value set to 'start' to initiate Avilability Measurement 
        and 'stop' to stop Availability Measurement.
        'ready' and 'notReady' indicates whether Availability Measurement
        can be initiated or not.

        Note: User can not set to 'ready' or 'notReady'.
       "
   DEFVAL { ready }
    ::= { fsMIY1731MepAvailabilityEntry 1 }

fsMIY1731MepAvailabilityResultOK OBJECT-TYPE
    SYNTAX      TruthValue
    MAX-ACCESS  read-only
    STATUS      current
    DESCRIPTION
       "This object specifies the result of the operation:

        - true    Initiating Availability measurement by sending
                  LM Message (LMM) is successful.

        - false   Initiating Availability measurement has failed 
                  as failure encountered in sending LM Message (LMM).
       "
    DEFVAL { true }
    ::= { fsMIY1731MepAvailabilityEntry 2 }

fsMIY1731MepAvailabilityInterval OBJECT-TYPE
    SYNTAX      FsY1731AvailabilityInterval 
    MAX-ACCESS  read-write
    STATUS      current
    DESCRIPTION
       "This object specifies a time interval much smaller than Deadline, 
        Interval between two successive LMM transmissions to be used by the MEP
        for calculating Availability. 
       "
    DEFVAL { interval100ms }
    ::= { fsMIY1731MepAvailabilityEntry 3 }

fsMIY1731MepAvailabilityDeadline OBJECT-TYPE
    SYNTAX      Unsigned32
    MAX-ACCESS  read-write
    STATUS      current
    DESCRIPTION
       "This object specifies a  timeout, in seconds, the Time interval to conduct 
        the availability functionality
       "
    ::= { fsMIY1731MepAvailabilityEntry 4 }

fsMIY1731MepAvailabilityLowerThreshold OBJECT-TYPE
    SYNTAX      OCTET STRING (SIZE(1..6))
    MAX-ACCESS  read-write
    STATUS      current
    DESCRIPTION
       "This object specifies the Availability frame loss ratio threshold, the lower threshold used to define 
        an interval as available. If far-end loss ratio is lesser than 
        configured lower threshold, that interval will be declared as available.
        AvailabilityLowerThreshold can be equal to AvailabilityUpperThreshold.
        Example: 50%    should be given as 35:30:2e:30:30
                 39.61% should be given as 33:39:2e:36:31
       "
    ::= { fsMIY1731MepAvailabilityEntry 5 }

fsMIY1731MepAvailabilityUpperThreshold OBJECT-TYPE
    SYNTAX      OCTET STRING (SIZE(1..6))
    MAX-ACCESS  read-write
    STATUS      current
    DESCRIPTION
       "This object specifies the Unavailability frame loss ratio threshold, the upper threshold to define
        an interval as unavailable. If far-end loss ratio is greater than 
        configured upper threshold, that interval will be declared as unavailable.
        Example: 50%    should be given as 35:30:2e:30:30
                 39.61% should be given as 33:39:2e:36:31
       "
    ::= { fsMIY1731MepAvailabilityEntry 6 }

fsMIY1731MepAvailabilityModestAreaIsAvailable OBJECT-TYPE
    SYNTAX      TruthValue
    MAX-ACCESS  read-write
    STATUS      current
    DESCRIPTION
       "This object specifies whether the area between upper and lower 
        threshold is referred as available or unavailable.

       True -  If Calculated Frame loss ration falls 
               between upper and lower threshold, 
               it will be declared as Available.

       False - If Calculated Frame loss ration falls 
               between upper and lower threshold, 
               it will be declared as Unavailable.
       "
    ::= { fsMIY1731MepAvailabilityEntry 7 }

fsMIY1731MepAvailabilityWindowSize OBJECT-TYPE
    SYNTAX      Unsigned32
    MAX-ACCESS  read-write
    STATUS      current
    DESCRIPTION
       "This object specifies the Number of consecutive small time intervals for assessing availability 
       "
    ::= { fsMIY1731MepAvailabilityEntry 8 }

fsMIY1731MepAvailabilityDestMacAddress OBJECT-TYPE
    SYNTAX      MacAddress
    MAX-ACCESS  read-write
    STATUS      current
    DESCRIPTION
       "This object specifies the Target MAC Address Field to be transmitted: A unicast
        destination MAC address to be used for Availability Measurement.
       "
    ::= { fsMIY1731MepAvailabilityEntry 9 }

fsMIY1731MepAvailabilityDestMepId OBJECT-TYPE
    SYNTAX      Dot1agCfmMepIdOrZero
    MAX-ACCESS  read-write
    STATUS      current
    DESCRIPTION
       "This object specifies an indication of the Target MAC Address Field to be
        transmitted:
        The Maintenance association End Point Identifier of
        another MEP in the same Maintenance Association
        This address will be used if the value of the column
        fsMIY1731MepAvailabilityDestIsMepId is 'true'.
       "
    ::= { fsMIY1731MepAvailabilityEntry 10 }

fsMIY1731MepAvailabilityDestIsMepId OBJECT-TYPE
    SYNTAX      TruthValue
    MAX-ACCESS  read-write
    STATUS      current
    DESCRIPTION
       "This object when True indicates that MEPID of the target MEP is used for
        LMM transmission during Availability Measurement.
        False indicates that unicast destination MAC address of the
        target MEP is used for LMM transmission during Availability 
        Measurement.
       "
    ::= { fsMIY1731MepAvailabilityEntry 11 }

fsMIY1731MepAvailabilityType OBJECT-TYPE
    SYNTAX      FsY1731AvailabilityType
    MAX-ACCESS  read-write
    STATUS      current
    DESCRIPTION
       "This object specifies the defStatic indicates that the algorithm for Availability Measurement
        is static window algorithm. The availability measurement will be 
        conducted as per MEF 10.2 
        (Section 6.9.7. Availability Performance for a Point-to-Point EVC)

        defSliding indicates that the algorithm for Availability Measurement
        is sliding window algorithm. The availability measurement will be
        conducted as per ITU-T Y.1563 
        ( Section 9 Ethernet service availability )
       "
    DEFVAL { defStatic }
    ::= { fsMIY1731MepAvailabilityEntry 12 }

fsMIY1731MepAvailabilitySchldDownInitTime OBJECT-TYPE
    SYNTAX      Unsigned32
    MAX-ACCESS  read-write
    STATUS      current
    DESCRIPTION
       "This object specifies the Time when Scheduled down time is initiated, denotes the beginning of 
        time interval agreed upon by both the Subscriber and Service Provider 
        during which a service may be disabled by the Service Provider.
        Init Time should be defined with reference to zero and dealine.
       "
    ::= { fsMIY1731MepAvailabilityEntry 13 }

fsMIY1731MepAvailabilitySchldDownEndTime OBJECT-TYPE 
    SYNTAX      Unsigned32
    MAX-ACCESS  read-write
    STATUS      current
    DESCRIPTION
       "This object specifies the Time when Scheduled down time is ending, denotes the ending of
        time interval agreed upon by both the Subscriber and Service Provider
        during which a service may be disabled by the Service Provider.
        End Time should be defined with reference to zero and dealine.
       "
    ::= { fsMIY1731MepAvailabilityEntry 14 }

fsMIY1731MepAvailabilityPriority OBJECT-TYPE
    SYNTAX      Unsigned32(0..7)
    MAX-ACCESS  read-write
    STATUS      current
    DESCRIPTION
       "This object specifies the Priority. 3 bit value to be used in the VLAN tag, if present
        in the transmitted LMM frame.
       "
   DEFVAL { 7 }
    ::= { fsMIY1731MepAvailabilityEntry 15 }

fsMIY1731MepAvailabilityDropEnable OBJECT-TYPE
    SYNTAX      TruthValue
    MAX-ACCESS  read-write
    STATUS      current
    DESCRIPTION
       "This object specifies the Drop Enable bit value to be used in the VLAN tag, if present
        in the transmitted LMM frame.
       "
    DEFVAL { false }
    ::= { fsMIY1731MepAvailabilityEntry 16 }

fsMIY1731MepAvailabilityPercentage OBJECT-TYPE 
    SYNTAX      OCTET STRING (SIZE(1..6))
    MAX-ACCESS  read-only
    STATUS      current
    DESCRIPTION
       "This object specifies the percentage of Availability

         If fsMIY1731MepAvailabilityType is selected as defStatic,
         this object contains the Availability Performance metric 
         as defined in MEF 10.2 
         (Section 6.9.7. Availability Performance for a Point-to-Point EVC)

         If fsMIY1731MepAvailabilityType is selected as defSliding,
         this object contains Percent Ethernet service availability
         as defined in ITU-T Y.1563 
         ( Section 9 Ethernet service availability )
         Example: 50%    will be given as 35:30:2e:30:30
                  39.61% will be given as 33:39:2e:36:31
       "
    ::= { fsMIY1731MepAvailabilityEntry 17 }

fsMIY1731MepAvailabilityRowStatus OBJECT-TYPE
    SYNTAX      RowStatus
    MAX-ACCESS  read-write
    STATUS      current
    DESCRIPTION
       "This object specifies the status of MEP Availability Table row.

        The writable columns in a row can not be changed if the row
        is active. All columns must have a valid value before a row
        can be activated, possible values are row status active and
        row status not active.
       "
   ::= { fsMIY1731MepAvailabilityEntry 18 }

-- ******************************************************************
--                 MEP AVilability Table ENDS 
-- ******************************************************************

-- ******************************************************************
-- NOTIFICATIONS (TRAPS)
-- These notifications will be sent to the management entity
-- whenever a MEP loses/restores contact with one or more other MEPs.
-- ******************************************************************
fsMIY1731FrameLossTrap NOTIFICATION-TYPE
    OBJECTS     { fsMIY1731ContextName,
                  fsMIY1731FlMeasurementTimeStamp,
                  fsMIY1731FlStatsMeasurementType,
                  fsMIY1731FlFarEndLoss,
                  fsMIY1731FlNearEndLoss
                }
    STATUS      current
    DESCRIPTION
       "This object specifies the MEP that can measure frame-loss. A notification
        is sent to the management entity with the OID
        of the MEP that has measured frame-loss exceeded thresholds.

        To warn the system administrator of the problem, 
        as controlled by the MEP

        If measured frame-loss exceeds threshold is raised after a notification
        has been sent, another notification is issued.

        The management entity receiving the notification can identify
        the system from the network source address of the
        notification, and can identify the MEP reporting the frame-loss
        by the indices in the OID of the each element of trap
        variable except fsMIY1731ContextName in the notification:

           fsMIY1731MegIndex - Also the index of the MEP's
                              Maintenance Entity Group table entry
                              (fsMIY1731MegTable).
           fsMIY1731MeIndex - Also an index (with the MEG table index)
                              of the MEP's Maintenance Entity
                              table entry (fsMIY1731MeTable).
           fsMIY1731MepIdentifier - MEP Identifier and final index
                              into the MEP table (fsMIY1731MepTable).
       "
    ::= { fsMIY1731Notifications 1 }

fsMIY1731DefectConditionTrap NOTIFICATION-TYPE
    OBJECTS     { fsMIY1731ContextName,
                  fsMIY1731ErrorLogType
                }
    STATUS      current
    DESCRIPTION
        "This object specifies the a MEP having a persistent defect condition. A notification
        (fault alarm) is sent to the management entity with the OID
        of the MEP that has detected the fault.

        Whenever a MEP has a persistent defect,
        it may or may not generate a Fault Alarm to warn the system
        administrator of the problem.

        If a defect is raised after a Fault
        Alarm has been issued, another Fault Alarm is issued.

        The management entity receiving the notification can identify
        the system from the network source address of the
        notification, and can identify the MEP reporting the defect
        by the indices in the OID of the fsMIY1731ErrorLogType
        variable in the notification:

           fsMIY1731MegIndex - Also the index of the MEP's
                              Maintenance Entity Group table entry
                              (fsMIY1731MegTable).
           fsMIY1731MeIndex - Also an index (with the MEG table index)
                              of the MEP's Maintenance Entity
                              table entry (fsMIY1731MeTable).
           fsMIY1731MepIdentifier - MEP Identifier and final index
                              into the MEP table (fsMIY1731MepTable)
       "
 
    ::= { fsMIY1731Notifications 2 }

fsMIY1731TstRecivedWithErrorTrap NOTIFICATION-TYPE
     OBJECTS     { fsMIY1731ContextName,
                   fsMIY1731MepBitErroredTstIn
                 }
    STATUS      current
    DESCRIPTION
       "This object specifies the MEP that has received a TST PDU and the validation criteria has failed 
        A notification is sent to the management entity with the OID
        of the MEP that has received the TST PDU.

        If a invalid TST PDU is received after a notification
        has been sent, another notification is issued.

        The management entity receiving the notification can identify
        the system from the network source address of the
        notification, and can identify the MEP reporting the invalid TST PDU
        by the indices in the OID of the each element of trap
        variable except fsMIY1731ContextName in the notification:

           fsMIY1731MegIndex - Also the index of the MEP's
                              Maintenance Entity Group entry
                              (fsMIY1731MegTable).
           fsMIY1731MeIndex - Also an index (with the MEG table index)
                              of the MEP's Maintenance Entity
                              table entry (fsMIY1731MeTable).
           fsMIY1731MepIdentifier - MEP Identifier and final index
                              into the MEP table (fsMIY1731MepTable).
       "
 
    ::= { fsMIY1731Notifications 3 }

fsMIY1731FrameDelayTrap NOTIFICATION-TYPE
    OBJECTS     { fsMIY1731ContextName,
                  fsMIY1731FdMeasurementTimeStamp,
                  fsMIY1731FdMeasurementType,
                  fsMIY1731FdDelayValue
                }
    STATUS      current
    DESCRIPTION
        "This object specifies the MEP that can measure iframe-delay. A notification
        is sent to the management entity with the OID
        of the MEP that has measured frame-delay exceeded threshold.

        To warn the system administrator of the problem, 
        as controlled by the MEP

        If measured frame-delay exceeds threshold is raised after a notification
        has been sent, another notification is issued.

        The management entity receiving the notification can identify
        the system from the network source address of the
        notification, and can identify the MEP reporting the frame-delay
        by the indices in the OID of the each element of trap
        variable except fsMIY1731ContextName in the notification:

           fsMIY1731MegIndex - Also the index of the MEP's
                              Maintenance Entity Group entry
                              (fsMIY1731MegTable).
           fsMIY1731MeIndex - Also an index (with the MEG table index)
                              of the MEP's Maintenance Entity
                              table entry (fsMIY1731MeTable).
           fsMIY1731MepIdentifier - MEP Identifier and final index
                              into the MEP table (fsMIY1731MepTable).
       "
 
    ::= { fsMIY1731Notifications 4 }

fsMIY1731TxFailTrap NOTIFICATION-TYPE
    OBJECTS     { 
                  fsMIY1731LastTxFailOpcode
                }
    STATUS      current
    DESCRIPTION
        "This object is used to warn the system administrator when there is CFM Tx Failure occurred.

        The management entity receiving the notification can identify
        the system from the network source address of the
        notification, and can identify the Port Number & Opcode value 
        in the OID Port Number will be appended with the Opcode OID:

           fsMIY1731LastTxFailOpcode - Last Tx Failure CFM PDU Opcode Value. 
       "
 
    ::= { fsMIY1731Notifications 5 }


-- ******************************************************************
-- The Loopback Managed Object.  This group contains all the MIB  
-- objects used to maintain Loopback status Entities.
-- ******************************************************************

-- ******************************************************************
-- The Loopback Table
-- ******************************************************************
    
fsMIY1731LoopbackTable OBJECT-TYPE
    SYNTAX      SEQUENCE OF FsMIY1731LoopbackEntry
    MAX-ACCESS  not-accessible
    STATUS      current
    DESCRIPTION
       "This object specifies the table which contains controls for the loopback state of the
        remote MEP as well as indicates the status of the loopback
        function. 
       "
    ::= { fsMIY1731Context 17 }

fsMIY1731LoopbackEntry OBJECT-TYPE
    SYNTAX      FsMIY1731LoopbackEntry
    MAX-ACCESS  not-accessible
    STATUS      current
    DESCRIPTION
       "This object specifies an entry in the table, containing information on the loopback
       status for a single Ethernet service interface. Entries in the
       table are automatically created whenever the local entity
       supports loopback capabilities.  The loopback status on the
       interface can be determined from the fsMIY1731LoopbackStatus
       object.
       "
    INDEX { fsMIY1731ContextId,
            fsMIY1731LoopbackIndex }
    ::= { fsMIY1731LoopbackTable 1 }

FsMIY1731LoopbackEntry ::= SEQUENCE {
      fsMIY1731LoopbackIndex            VlanId,
      fsMIY1731LoopbackStatus           INTEGER
      }

fsMIY1731LoopbackIndex OBJECT-TYPE
    SYNTAX      VlanId
    MAX-ACCESS  not-accessible
    STATUS      current
    DESCRIPTION
       "This object specifies the service provider VLAN (S-VLAN) if value is
        less than 4094. If the value is greater than 4094 this object
        indicates VFI.
       "
    ::= { fsMIY1731LoopbackEntry 1 }

fsMIY1731LoopbackStatus OBJECT-TYPE
    SYNTAX      INTEGER { enabled(1), disabled(2) }
    MAX-ACCESS  read-write
    STATUS      current
    DESCRIPTION
       "This object specifies the loopback status of the LoopbackIndex. 
       "
    DEFVAL { disabled }
    ::= { fsMIY1731LoopbackEntry 2 }

END
