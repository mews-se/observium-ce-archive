-- Copyright (C) 2006-2012 Aricent Group . All Rights Reserved

--    IPv6 Proprietary MIB Definition

ARICENT-IPV6-MIB DEFINITIONS ::= BEGIN 
 

   IMPORTS
      MODULE-IDENTITY, OBJECT-TYPE, Counter32,
      enterprises, Integer32,
      Unsigned32,TimeTicks                           FROM SNMPv2-SMI
      RowStatus,TruthValue, DisplayString, 
      TEXTUAL-CONVENTION                             FROM SNMPv2-TC
      InetZoneIndex,InetScopeType                    FROM INET-ADDRESS-MIB
      InterfaceIndex                                 FROM IF-MIB; 

      futureipv6 MODULE-IDENTITY
         LAST-UPDATED "202407250000Z"
         ORGANIZATION "ARICENT COMMUNICATIONS SOFTWARE"
         CONTACT-INFO "support@aricent.com"

         DESCRIPTION
            " The MIB module for IPv6. "

         REVISION "202407250000Z"
         DESCRIPTION
            "Updated fsipv6RouteProtocol enumerations
            to match implementation. Added kernel route type 
            for routes insalled by the kernel and sent to iss."

         REVISION "202201260000Z"
         DESCRIPTION
            "Updated fsipv6PingOperStatus enumerations
            to match implementation. Added limited 
            continuous ping support for Web usage."

         REVISION "201209050000Z"
         DESCRIPTION
            "The revised version of the MIB for IPv6
            release 1.1.0.0. "

         REVISION "199912171330Z"
         DESCRIPTION
            "The first version of the MIB for IPv6
            release 1.0.0.0. "
      ::=  { enterprises futuresoftware (2076) 28 }

--  FSR-MIB (private mib definition)

-- futuresoftware  OBJECT IDENTIFIER ::= { enterprises 2076 }
	 
-- futureipv6  OBJECT IDENTIFIER ::= { futuresoftware 28 }		
	
-- -------------------------------------------------------------
-- Textual Conventions
-- -------------------------------------------------------------

InterfaceList ::= TEXTUAL-CONVENTION
    STATUS      current
    DESCRIPTION
        "Each octet within this value specifies a set of eight
        interfaces, with the first octet specifying router-ports 1 through
        8, the second octet specifying router-ports 9 through 16, etc.
        Within each octet, the most significant bit represents the lowest 
        numbered router-port or L3 interface, and the least significant bit
        represents the highest numbered port.  Thus, each L3 interface
        of the switch is represented by a single bit within the
        value of this object.  If that bit has a value of '1',
        then that L3 interface is included in the set of interfaces; the interface 
        is not included if its bit has a value of '0'."
    SYNTAX      OCTET STRING

Ipv6Address ::= TEXTUAL-CONVENTION
    DISPLAY-HINT "2x:"
    STATUS       current
    DESCRIPTION
       "This data type is used to model IPv6 addresses.
        This is a binary string of 16 octets in network
         byte-order."
    SYNTAX       OCTET STRING (SIZE (16))

	
fsipv6  OBJECT IDENTIFIER ::= { futureipv6 1 }

fsipv6Icmp OBJECT IDENTIFIER ::= { futureipv6 2 }

fsipv6Udp OBJECT IDENTIFIER ::= { futureipv6 3 }

fsipv6Tunnel OBJECT IDENTIFIER ::= {futureipv6 5 }

fsipv6Route OBJECT IDENTIFIER ::= {futureipv6 6 }

-- the IPv6 general group
-- fsipv6 GROUP

fsipv6Scalars  OBJECT IDENTIFIER ::= { fsipv6 1 }
fsipv6Tables  OBJECT IDENTIFIER ::= { fsipv6 2 }
fsipv6Test   OBJECT IDENTIFIER ::= { fsipv6 3 }
fsipv6RaRDNSSTable   OBJECT IDENTIFIER ::= { fsipv6 4 }

-- fsipv6Scalars BEGIN

          fsipv6NdCacheMaxRetries OBJECT-TYPE
              SYNTAX   Integer32 (1..10)
              MAX-ACCESS   read-write
              STATUS   current
              DESCRIPTION
                 "This object specifies the maximum number of retries
                  that can be attempted upon resolving the 'physical'
                  address of an IPv6 address during address resolution
                  or unreachability detection."
              DEFVAL { 3 }
              ::= { fsipv6Scalars 1 }

         fsipv6PmtuConfigStatus OBJECT-TYPE
             SYNTAX  INTEGER {
                      enable(1),
                      disable(2)
                    }
             MAX-ACCESS     read-write
             STATUS     current
             DESCRIPTION
               "Flag to enable or disable Path MTU Discovery for the node."
             DEFVAL  { enable }
             ::= { fsipv6Scalars 2 }

         fsipv6PmtuTimeOutInterval OBJECT-TYPE
             SYNTAX Unsigned32 
             MAX-ACCESS  read-write
             STATUS  current
             DESCRIPTION
                "The time in minutes after which the path MTU entry times out."
             DEFVAL { 60 }
             ::= { fsipv6Scalars 3 }
         
         -- IPv6 Jumbograms Scalars

         fsipv6JumboEnable OBJECT-TYPE
             SYNTAX  INTEGER {
                      enable(1),
                      disable(2)
                    }
             MAX-ACCESS     read-write
             STATUS     current
             DESCRIPTION
               "Flag to enable or disable IPv6 Jumbogram facility for the node."
             DEFVAL  { enable }
             ::= { fsipv6Scalars 4 }


         fsipv6NumOfSendJumbo OBJECT-TYPE
             SYNTAX  Integer32 
             MAX-ACCESS  read-only
             STATUS  current
             DESCRIPTION
                "Number of IPv6 Jumbograms sent from the node."
             ::= { fsipv6Scalars 5 }
	
         fsipv6NumOfRecvJumbo OBJECT-TYPE
             SYNTAX  Integer32 
             MAX-ACCESS  read-only
             STATUS  current
             DESCRIPTION
                "Number of IPv6 Jumbograms received."
             ::= { fsipv6Scalars 6 }

         fsipv6ErrJumbo OBJECT-TYPE
             SYNTAX  Integer32 
             MAX-ACCESS  read-only
             STATUS  current
             DESCRIPTION
                "Number of IPv6 Error Jumbograms received or transmitted."
             ::= { fsipv6Scalars 7 }

         fsipv6GlobalDebug OBJECT-TYPE
              SYNTAX  Unsigned32
              MAX-ACCESS read-write
              STATUS  current
              DESCRIPTION
                   "Enables the tracing in the selected submodule in IP6. A 32 bit
              integer is used to store the Tracing level in the specified module.
              Different Tracing Levels -
                 BIT 0 - Initialisation and Shutdown Trace.
                 BIT 1 - Management trace.
                 BIT 2 - Data path trace.
                 BIT 3 - Control Plane trace.
                 BIT 4 - Packet Dump.
                 BIT 5 - OS Resource trace.
                 BIT 6 - All Failure trace (All failures including Packet Validation)
                 BIT 7 - Buffer Trace.

              Different submodule Tracing -
                 BIT 24 - Tracing in IP6 module.
                 BIT 25  - Tracing in ICMP6 submodule.
                 BIT 26 - Tracing in ND6 submodule.
                 BIT 27 - Tracing in UDP6 submodule.
                 BIT 29 - Tracing in PING6 submodule.
 
              The remaining bits are unused.The combination of levels and submodules
              are allowed i.e. Tracing can be allowed at all failure and data path
              level in All submodules by setting the BIT appropriately.
              For Example, setting the debug value to 00000001000000000000000001000000 
              will enable all failure trace prints in IP6 module."
             ::= {  fsipv6Scalars 8  }

-- sizing wanted scalars - begin

-- These Values would come into effect, if only the router is rebooted
-- after the configuration.  The value of all the objects range from 1
-- to configured value, if the Minumum value is not specified in the
-- 'DESCRIPTION' part.

              fsipv6MaxRouteEntries OBJECT-TYPE
              SYNTAX  Unsigned32 
              MAX-ACCESS read-write 
              STATUS  current
              DESCRIPTION
                "Maximum Number of Route Entries that could be configured in
              the system. Minumum value is 5."
              ::= { fsipv6Scalars 9 }

              fsipv6MaxLogicalIfaces OBJECT-TYPE
              SYNTAX  Unsigned32 
              MAX-ACCESS read-write 
              STATUS  current
              DESCRIPTION
                "Maximum Number of configurable Logical IPv6 Interfaces" 
              ::= { fsipv6Scalars 10 }

              fsipv6MaxTunnelIfaces OBJECT-TYPE
              SYNTAX  Unsigned32
              MAX-ACCESS read-write
              STATUS  current
              DESCRIPTION
                "Maximum Number of configurable Tunnel Interfaces"
              ::= { fsipv6Scalars 11 }

              fsipv6MaxAddresses OBJECT-TYPE
              SYNTAX  Unsigned32 
              MAX-ACCESS read-write 
              STATUS  current
              DESCRIPTION
                 "Maximum Number of Configurable IPv6 Interfaces."
              ::= { fsipv6Scalars 12 }

              fsipv6MaxFragReasmEntries OBJECT-TYPE
              SYNTAX Unsigned32  
              MAX-ACCESS read-write 
              STATUS  current
              DESCRIPTION
                 "This object could be used for 2 purpose. 
                  1. Maximum Number of IP6 datagrams awaiting reassembly.
                  2. Maximum Number of fragments that could be allowed in
                     a single reassembly list."
              ::= { fsipv6Scalars 13 }

              fsipv6Nd6MaxCacheEntries OBJECT-TYPE
              SYNTAX Unsigned32  
              MAX-ACCESS read-write 
              STATUS  current
              DESCRIPTION
                 "Maximum Number of ND Cache Entries."
              ::= { fsipv6Scalars 14 }

              fsipv6PmtuMaxDest OBJECT-TYPE
              SYNTAX Unsigned32  
              MAX-ACCESS read-write 
              STATUS  current
              DESCRIPTION
                 "Maximum Number of PMTU Table Entries"
              ::= { fsipv6Scalars 15 }

-- sizing wanted scalars - end

              fsipv6RFC5095Compatibility OBJECT-TYPE
              SYNTAX     INTEGER {
                            enabled(1),
                            disabled(2)
                        }
              MAX-ACCESS read-write 
              STATUS  current
              DESCRIPTION
                 "When the IPv6 node is configured to be RFC5095 compatible, 
                  then it should treat Type 0 Routing Header as invalid 
                  routing header type."
              DEFVAL  {enabled}
              ::= { fsipv6Scalars 16 }

              fsipv6RFC5942Compatibility OBJECT-TYPE
              SYNTAX     INTEGER {
                            enabled(1),
                            disabled(2)
                        }
              MAX-ACCESS read-write 
              STATUS  current
              DESCRIPTION
                 "When the IPv6 node is configured to be RFC5942, ISS compatible
                  with RFC 5942 and prefix can be configured as on-link and off-link."
              DEFVAL  {disabled}
              ::= { fsipv6Scalars 17 }

-- Scalar objects for SeND
 
              fsipv6SENDSecLevel OBJECT-TYPE
              SYNTAX Integer32 (0..1)
              MAX-ACCESS read-write
              STATUS  current
              DESCRIPTION
                 "This Object specifies the sec level value for CGA generation in Secure Neighbor Discovery.
                  Note: For Sec values greater than zero, the above algorithm does not guaranty to terminate 
                  after a certain number of iterations (RFC 3972 Section 4)"
              ::= { fsipv6Scalars 18 }
         

              fsipv6SENDNbrSecLevel OBJECT-TYPE
              SYNTAX Integer32 (0..7)
              MAX-ACCESS read-write
              STATUS  current
              DESCRIPTION
                 "This object specifies the sec level that are accepted from neighbors in Secure Neighbor
                  Discovery.
                  Note: CGA verification should be able to process all security parameter values, since 
                  verification procedure is relatively faster compared to CGA Generation (RFC 3972 Section 5)."
              ::= { fsipv6Scalars 19 }

              fsipv6SENDAuthType OBJECT-TYPE
              SYNTAX INTEGER {
                        cga (0),
                        ta (1),
                        cgaandta (2),
                        cgaorta (3)
              }
              MAX-ACCESS read-write
              STATUS  current
              DESCRIPTION
                 "This object specifies the authorisation type to be used. The options include; 
                  0 indicates only CGA authorisation is required. 
                  1 indicates only CA authorisation is required. 
                  2 indicates both CGA and CA authorisation is required.
                  3 indicates CGA authorisation or CA authorisation is required."
              ::= { fsipv6Scalars 20 }
            
              fsipv6SENDMinBits OBJECT-TYPE
              SYNTAX INTEGER {
                        key512 (512),
                        key1024 (1024)
              }
              MAX-ACCESS read-write
              STATUS  current
              DESCRIPTION
                 "This object specifies the minimum acceptable key length.
                  Note: Only 512 and 1024 bits key support available in ISS"
              DEFVAL  { key1024 }
              ::= { fsipv6Scalars 21 }

              fsipv6SENDSecDAD OBJECT-TYPE  
              SYNTAX INTEGER {
                        enabled (1),
                        disabled (2)
              }
              MAX-ACCESS read-write
              STATUS  current
              DESCRIPTION
                 "In mixed mode Secure Neighbour Discovery, when enabled it indicates secured advertisements
                  are only accepted for first tentative address. When disabled it indicates unsecured 
                  advertisements are accepted for first tentative address and for second and third
                  tentative addresses only secured messages are accepted
                  Note: Although collision count is a 8-bit value, DAD is performed only thrice in 
                        compliance to RFC3971"
              DEFVAL  { 2 }
              ::= { fsipv6Scalars 22 }

              fsipv6SENDPrefixChk OBJECT-TYPE
              SYNTAX INTEGER {
                        enabled (1),
                        disabled (2)
              }
              MAX-ACCESS read-write
              STATUS  current
              DESCRIPTION
                 "This object specifies the prefix and range check status. In Secure Neighbor Discovery When 
                  enabled it indicates prefix and range checks are relaxed in host. When disabled it 
                  indicates prefix and range checks are performed in host to verify that prefix advertised 
                  by router are in the range that it is certified to advertise"
              DEFVAL  { 2 }
              ::= { fsipv6Scalars 23 }

              fsipv6ECMPPRTTimer OBJECT-TYPE
              SYNTAX     Integer32
              MAX-ACCESS read-write
              STATUS  current
              DESCRIPTION
                 "Timer value for ECMP PRT."
              DEFVAL  {60}
              ::= { fsipv6Scalars 24 }

              fsipv6NdCacheTimeout OBJECT-TYPE
              SYNTAX Integer32 (30..86400)
              MAX-ACCESS read-write
              STATUS current
              DESCRIPTION
                 "Time after which the entry in cache is deleted."
              DEFVAL { 30 }
              ::= { fsipv6Scalars 25 }

              
-- fsipv6Scalars END

-- fsipv6Tables BEGIN
         -- IPv6 Interface Table

         -- The IPv6 Interface table defines the logical interfaces on which
         -- IPv6 protocol is running. These include LAN interfaces, Point-to-
         -- Point interfaces, IPv6 over IPv4 Tunnel interfaces and NBMA
         -- interfaces.

         -- Entries of this table are created/deleted from SNMP.


         fsipv6IfTable OBJECT-TYPE
             SYNTAX      SEQUENCE OF Fsipv6IfEntry
             MAX-ACCESS      not-accessible
             STATUS      current
             DESCRIPTION
               "The IPv6 Interface table contains information on the 
               entity's internetwork-layer interfaces on which IPv6.
               protocol is enabled. An IPv6 interface constitutes a logical 
               network layer attachment to the layer immediately below
               IPv6. These include LAN interfaces, Point-to-Point interfaces, 
               NBMA interfaces and IPv6 over IPv4 Tunnel interfaces."
             ::= { fsipv6Tables 1 }


         fsipv6IfEntry OBJECT-TYPE
             SYNTAX     Fsipv6IfEntry
             MAX-ACCESS     not-accessible
             STATUS     current
             DESCRIPTION
               "An interface entry containing objects about a particular 
               IPv6 interface. The entry is created or deleted from SNMP."
             INDEX   { fsipv6IfIndex }
             ::= { fsipv6IfTable 1 }


         Fsipv6IfEntry ::= SEQUENCE {
                 fsipv6IfIndex
                     InterfaceIndex,
                 fsipv6IfType   
                     INTEGER,
                 fsipv6IfPortNum
                     Integer32,
                 fsipv6IfCircuitNum
                     Integer32,
                 fsipv6IfToken    
                     OCTET STRING,
                 fsipv6IfAdminStatus
                     INTEGER,
                 fsipv6IfOperStatus
                     INTEGER,
                 fsipv6IfRouterAdvStatus
                     INTEGER,
                 fsipv6IfRouterAdvFlags
                     INTEGER,
                 fsipv6IfHopLimit
                     Integer32,
                 fsipv6IfDefRouterTime
                     Integer32,
                 fsipv6IfReachableTime
                     Integer32,
                 fsipv6IfRetransmitTime
                     Integer32,
                 fsipv6IfDelayProbeTime
                     Integer32,
                 fsipv6IfPrefixAdvStatus
                     INTEGER,
                 fsipv6IfMinRouterAdvTime
                     Integer32,
                 fsipv6IfMaxRouterAdvTime
                     Integer32,
                 fsipv6IfDADRetries
                     Integer32,
                 fsipv6IfForwarding
                     INTEGER,
                 fsipv6IfRoutingStatus
                     INTEGER,
                 fsipv6IfIcmpErrInterval
                     Integer32,
                 fsipv6IfIcmpTokenBucketSize
                     Integer32,
                 fsipv6IfDestUnreachableMsg
                     INTEGER,
                 fsipv6IfUnnumAssocIPIf
                     InterfaceIndex,
                 fsipv6IfRedirectMsg
		     INTEGER, 
                 fsipv6IfAdvSrcLLAdr
                     INTEGER,
                 fsipv6IfAdvIntOpt
                     INTEGER,
                 fsipv6IfNDProxyAdminStatus
                     INTEGER,
                 fsipv6IfNDProxyMode
                     INTEGER,
                 fsipv6IfNDProxyOperStatus
                     INTEGER,
                 fsipv6IfNDProxyUpStream
                     TruthValue,
                 fsipv6IfSENDSecStatus
                     INTEGER,
                 fsipv6IfSENDDeltaTimestamp
                     Unsigned32,
                 fsipv6IfSENDFuzzTimestamp
                     Unsigned32,
                 fsipv6IfSENDDriftTimestamp
                     Unsigned32,
	         fsipv6IfDefRoutePreference
		     INTEGER
         }


         fsipv6IfIndex OBJECT-TYPE
             SYNTAX     InterfaceIndex
             MAX-ACCESS   not-accessible
             STATUS     current
             DESCRIPTION
               "A unique value identifying the particular IPv6 
               interface."
             ::= { fsipv6IfEntry 1 }


         fsipv6IfType OBJECT-TYPE
             SYNTAX     INTEGER {
                            ethernetcsmacd(6),
                            ppp(23),
                            softwareLoopback(24),
                            framerelay(32),
                            tunnel(131),
                            l3ipvlan(136) 
                        }
             MAX-ACCESS     read-only
             STATUS     current
             DESCRIPTION
               "The type of interface immediately `below' the network layer 
               in the protocol stack."
             ::= { fsipv6IfEntry 2 }


         fsipv6IfPortNum OBJECT-TYPE
             SYNTAX     Integer32 (1..255)
             MAX-ACCESS     read-only
             STATUS    current
             DESCRIPTION
               "This object identifies the 'interface' over which this
               network interface operates and is dependent on the value of
               fsipv6IfType. This object reflects the ifindex value of
               ifTable."
             ::= { fsipv6IfEntry 3 }


         fsipv6IfCircuitNum OBJECT-TYPE
             SYNTAX     Integer32
             MAX-ACCESS     read-only
             STATUS     current
             DESCRIPTION
               "This object identifies the circuit over which this network
               interface operates and is dependent on the value of
               fsipv6IfType. If the data-link layer is Ethernet, PPP or
               IPv4 Tunnel, this object can have only value of zero. If the
               data-link layer is Frame Relay, this object requires a non-zero
               value which will identify the Frame Relay virtual circuit."
             ::= { fsipv6IfEntry 4 }


         fsipv6IfToken OBJECT-TYPE
             SYNTAX     OCTET STRING (SIZE (1..8))
             MAX-ACCESS     read-write
             STATUS     current
             DESCRIPTION
               "The address token for this interface that is (at least) 
               unique on the link this interface is attached to. This token
               can be specified only if the fsipv6IfType is frame-relay(32). For
               other interface types, the interface token is autoconfigured
               according to the rules of the link type this interface is
               attached to. This address token is combined with the prefix
               'fe80' to form a link-local IPv6 address on this interface."
             ::= { fsipv6IfEntry 5 }


         fsipv6IfAdminStatus OBJECT-TYPE
             SYNTAX     INTEGER {
                            up(1),
                            down(2)
                        }
             MAX-ACCESS     read-write
             STATUS     current
             DESCRIPTION
              "Indicates whether IPv6 is enabled/disabled on this interface.
               When lower layer indicates the creation of the interface, an
               entry will be create in IPv6 interfac table with
               fsipv6IfAdminStatus in down(2) state. Either on setting this
               object as up(1) or configuring any IPv6 address over this
               interface, will set the fsipv6IfAdminStatus to up(1) state.
               If this object is set to down(2), and if no IPv6 address is
               configured for this interface, fsipv6IfAdminStatus goes
               down(2). Else the Status remains up(1), as long as the
               IPv6 address are present. Once these addresses are removed,
               the status goes to down(2)."
             ::= { fsipv6IfEntry 6 }


         fsipv6IfOperStatus OBJECT-TYPE
             SYNTAX     INTEGER {
                            up(1),
                            down(2),
                            stale(3)
                        }
             MAX-ACCESS     read-only
             STATUS     current
             DESCRIPTION
               "The operational state of interface. It is up(1) if the
                fsipv6IfAdminStatus is 'up' and the layer below the network
                layer is also operational. Otherwise it is down(2)."
             ::= { fsipv6IfEntry 7 }

         fsipv6IfRouterAdvStatus OBJECT-TYPE
            SYNTAX  INTEGER {
                     enabled(1),
                     disabled(2)
                 }
             MAX-ACCESS     read-write
             STATUS     current
             DESCRIPTION
              "The router advertisement status on this interface. When
               the object is set to enabled(1), router advertisements can be
               allowed on the IPv6 interface. Otherwise, router advertisements
               are not allowed."
             DEFVAL  { disabled}
             ::= { fsipv6IfEntry 8 }


         fsipv6IfRouterAdvFlags OBJECT-TYPE
            SYNTAX  INTEGER {
                       mbit(1),
                       obit(2),
                       nombit(3),
                       noobit(4),
                       mobits(5),
                       none(6)
                    }
             MAX-ACCESS     read-write
             STATUS     current
             DESCRIPTION
              "This object specifies the bits to be set in the router
               advertisements sent by this entity on this interface.
               M-bit set in the router advertisement indicates hosts
               to configure an address by stateful protocol means. O-bit
               set in the router advertisement indicates hosts to configure
               other non-address information by stateful means."
             DEFVAL  { none }
             ::= { fsipv6IfEntry 9 }


         fsipv6IfHopLimit OBJECT-TYPE
             SYNTAX     Integer32 (1..255)
             MAX-ACCESS     read-write
             STATUS     current
             DESCRIPTION
              "The Hop Limit value to be placed in the router advertisements
               sent on this IPv6 interface."
             DEFVAL  { 64 }
             ::= { fsipv6IfEntry 10 }


         fsipv6IfDefRouterTime OBJECT-TYPE
             SYNTAX     Integer32
             MAX-ACCESS     read-write
             STATUS     current
             DESCRIPTION
              "The default router time to be indicated in the router 
               advertisements sent on this IPv6 interface. This defines the
               time in seconds for which this entity acts as the default
               router for all all hosts on the interface. A value of 0 
               indicates that the entity is not a default router.
               The value can be configured in the range between 
               fsipv6IfMaxRouterAdvTime and 9000 seconds."
             DEFVAL  { 0 }
             ::= { fsipv6IfEntry 11 }


         fsipv6IfReachableTime OBJECT-TYPE
             SYNTAX     Integer32 (0..3600)
             MAX-ACCESS     read-write
             STATUS     current
             DESCRIPTION
              "The reachable time to be indicated in the router
               advertisements sent on this IPv6 interface and also used by
               this entity. This defines the time in seconds that a neighboring
               node is considered to be reachable after having received the 
               reachability confirmation from that node."
             DEFVAL  { 30 }
             ::= { fsipv6IfEntry 12 }


         fsipv6IfRetransmitTime OBJECT-TYPE
             SYNTAX     Integer32 (1..3600)
             MAX-ACCESS     read-write
             STATUS     current
             DESCRIPTION
              "The retransmit time to be indicated in the router 
               advertisements sent on this IPv6 interface and also used by
               this entity. This defines the time in seconds between 
               retransmitted Neighbor Solicitations and is used during
               address resolution, unreachability detection and
               duplicate address detection."
             DEFVAL  { 1 }
             ::= { fsipv6IfEntry 13 }


         fsipv6IfDelayProbeTime OBJECT-TYPE
             SYNTAX     Integer32 (0..10)
             MAX-ACCESS     read-write
             STATUS     current
             DESCRIPTION
               "The time in seconds to delay before starting unreachability
               probing of neighbor entries which are stale."
             DEFVAL  { 5 }
             ::= { fsipv6IfEntry 14 }


         fsipv6IfPrefixAdvStatus OBJECT-TYPE
            SYNTAX  INTEGER {
                      enabled(1),
                      disabled(2)
                    }
             MAX-ACCESS     read-write
             STATUS     current
             DESCRIPTION
              "The prefix advertisement status on this IPv6 interface. 
               Object value enabled(1) allows the configured prefixes to 
               be advertised in router advertisements. Otherwise, the prefixes
               are not sent in router advertisements."
             DEFVAL  { enabled }
             ::= { fsipv6IfEntry 15 }


          fsipv6IfMinRouterAdvTime OBJECT-TYPE
              SYNTAX   Integer32
              MAX-ACCESS   read-write
              STATUS   current
              DESCRIPTION
                "The minimum time in seconds allowed between sending 
                 unsolicited router advertisements.The default value is
                 one-third the default value of fsipv6IfMaxRouterAdvTime.
                 The value can be configured in the range between 3 seconds
                 and three-fourth of fsipv6IfMaxRouterAdvTime."
             DEFVAL  { 198 }
             ::= { fsipv6IfEntry 16 }


          fsipv6IfMaxRouterAdvTime OBJECT-TYPE
              SYNTAX   Integer32 (4..1800)
              MAX-ACCESS   read-write
              STATUS   current
              DESCRIPTION
                 "The maximum time in seconds between sending unsolicited 
                  router advertisements. Router advertisements are sent
                  periodically at a random interval between the values
                  specified by fsipv6IfMinRouterAdvTime and
                  fsipv6IfMaxRouterAdvTime."
             DEFVAL  { 600 }
             ::= { fsipv6IfEntry 17 }


          fsipv6IfDADRetries OBJECT-TYPE
              SYNTAX   Integer32 (0..10)
              MAX-ACCESS   read-write
              STATUS   current
              DESCRIPTION
                  "The maximum number of neighbor solicitations sent for
                   the purpose of duplicate address detection on a tentative 
                   address."
             DEFVAL  { 1 }
             ::= { fsipv6IfEntry 18 }

          fsipv6IfForwarding OBJECT-TYPE
              SYNTAX  INTEGER {
                      enabled(1),
                      disabled(2)
                    }
              MAX-ACCESS     read-write
              STATUS     current
              DESCRIPTION
                  "This MIB object is used to configure IPv6 routing and forwarding
                   on this interface. The default value is set to enabled."
              DEFVAL  { 1 }
             ::= { fsipv6IfEntry 19 }

          fsipv6IfRoutingStatus OBJECT-TYPE
              SYNTAX  INTEGER {
                      enabled(1),
                      disabled(2)
                    }
              MAX-ACCESS     read-only
              STATUS     current
              DESCRIPTION
                  "This MIB object indicates the current routing status
                   on this interface. This is based on the global IPv6
                   forwarding status of the mib object 'ipv6Forwarding'.
                   If 'ipv6Forwarding' is set to disabled, the routing
                   status is set to disabled on all the interfaces.
                   If 'ipv6Forwarding' is set to enabled, the value 
                   taken by this MIB objet is same as 'fsipv6IfForwarding'"
             ::= { fsipv6IfEntry 20 }

          fsipv6IfIcmpErrInterval OBJECT-TYPE
              SYNTAX   Integer32 (0..65535)
              UNITS       "milliseconds"
              MAX-ACCESS     read-write
              STATUS     current
              DESCRIPTION
                  "Time interval between tokens being added to the ICMPv6 token bucket."
              DEFVAL  { 100 }
              ::= { fsipv6IfEntry 21 }

           fsipv6IfIcmpTokenBucketSize OBJECT-TYPE
              SYNTAX  Integer32 (0..200)
              MAX-ACCESS     read-write
              STATUS     current
              DESCRIPTION
                  "Maximum number of tokens stored in the ICMPv6 bucket"
              DEFVAL  { 10 }
              ::= { fsipv6IfEntry 22 }

         fsipv6IfDestUnreachableMsg OBJECT-TYPE
              SYNTAX  INTEGER {
                   enabled(1),
                   disabled(2)
              }
              MAX-ACCESS     read-write
              STATUS     current
              DESCRIPTION
                  "Indicates whether ICMPv6 destination unreachable messages are
                   enabled/disabled on this interface."
              DEFVAL  { enabled }
              ::= { fsipv6IfEntry 23 }

         fsipv6IfUnnumAssocIPIf OBJECT-TYPE
              SYNTAX            InterfaceIndex
              MAX-ACCESS        read-write
              STATUS            current
              DESCRIPTION
                 "This object stores the interface index of the interface associated
                  with the unnumbered interface. The source IPv6 addresses used over
                  the Unnumbered interface in relation to the destination IPv6
                  address are borrowed from the associated interface. When no 
                  unnumbered interface is associated to this interface the value of
                  this object should be 0."
              ::= { fsipv6IfEntry 24 }

         fsipv6IfRedirectMsg OBJECT-TYPE
              SYNTAX  INTEGER {
                   enabled(1),
                   disabled(2)
              }
              MAX-ACCESS     read-write
              STATUS     current
              DESCRIPTION
                  "Indicates whether ICMPv6 redirect  messages are
                   enabled/disabled on this interface."
              DEFVAL  { disabled }
              ::= { fsipv6IfEntry 25 }

         fsipv6IfAdvSrcLLAdr OBJECT-TYPE
              SYNTAX  INTEGER {
                   enabled(1),
                   disabled(2)
              }
              MAX-ACCESS     read-write
              STATUS     current
              DESCRIPTION
                  "Indicates whether source IPv6 advertisement Link Layer
                   address flag enabled/disabled on this interface for router advertisement."
              DEFVAL  { disabled }
              ::= { fsipv6IfEntry 26 }
        
         fsipv6IfAdvIntOpt OBJECT-TYPE
              SYNTAX  INTEGER {
                   enabled(1),
                   disabled(2)
              }
              MAX-ACCESS     read-write
              STATUS     current
              DESCRIPTION
                  "Indicates whether IPv6 advertisement Interval Option
                   flag enabled/disabled on this interface for router advetisement."
              DEFVAL  { disabled }
              ::= { fsipv6IfEntry 27 }

         fsipv6IfNDProxyAdminStatus OBJECT-TYPE
              SYNTAX  INTEGER {
                   enabled(1),
                   disabled(2)
              }
              MAX-ACCESS     read-write
              STATUS         current
              DESCRIPTION
                      "This object specifies the status of Neighbor
                       Discovery (ND) Proxy Feature on the interface."
              DEFVAL  { disabled }
              ::= { fsipv6IfEntry 28 }

         fsipv6IfNDProxyMode OBJECT-TYPE
              SYNTAX  INTEGER {
                   global(1),
                   local(2)
              }
              MAX-ACCESS     read-write
              STATUS         current
              DESCRIPTION
                      "This Object is used to enable or disable Neighbor
                       Discovery (ND) Proxy feature in local subnet. 
                       This object takes effect only when
                       ND Proxying is enabled on the interface.
                       When this object is set to local (2),
                       Router acts as ND proxy for target address which
                       is in the same subnet also. When this object is set to
                       global (1), Router does not act as ND proxy for target
                       address which is in same subnet."
              DEFVAL  { global }
              ::= { fsipv6IfEntry 29 }

         fsipv6IfNDProxyOperStatus OBJECT-TYPE
              SYNTAX  INTEGER {
                   enabled(1),
                   inprogress(2),
                   disabled(3)
              }
              MAX-ACCESS     read-only
              STATUS         current
              DESCRIPTION
                      "This object specifies the current operational status
                       of Neighbor Discovery (ND) Proxy on this interface. 
                       This object take effect only when ND Proxying is enabled
                       on the interface. When the operational status is disabled on
                       downstream interface to prevent loops, after 60 minute
                       timer-expiry, this object is set to inprogress(2).
                       This object is set as enabled(3), when 2 P-Bit Router
                       Advertisements are sent on this interface"
              DEFVAL  { disabled }
              ::= { fsipv6IfEntry 30 }

         fsipv6IfNDProxyUpStream OBJECT-TYPE
              SYNTAX  TruthValue
              MAX-ACCESS     read-write
              STATUS         current
              DESCRIPTION
                      "This object specifies whether the interface is an 
                       upstream or downstream Proxy interface. This object 
                       takes effect only when ND Proxying is enabled on the
                       interface. When set to true, the interface acts as an
                       Upstream interface and when set to false, it acts as a
                       downstream interface."
              DEFVAL  { false }
              ::= { fsipv6IfEntry 31 }

        fsipv6IfSENDSecStatus OBJECT-TYPE
             SYNTAX  INTEGER {
                   secured(1),
                   unsecured(2),
                   mixed(3)
              }
              MAX-ACCESS     read-write
              STATUS         current
              DESCRIPTION
                      "This object specifies the admin status of Secure Neighbor Discovery
                       feature in the interface.  The options include; 
                       1 enables SeND on the interface,
                       2 disables SeND on the interface,
                       3 enables mixed mode on the interface."
              DEFVAL  { unsecured }
              ::= { fsipv6IfEntry 32 }

        fsipv6IfSENDDeltaTimestamp OBJECT-TYPE
             SYNTAX  Unsigned32 (0..1000) 
              MAX-ACCESS     read-write
              STATUS         current
              DESCRIPTION
                      "This object specifies the Delta timestamp value for the interface"
              DEFVAL  { 300 }
              ::= { fsipv6IfEntry 33 }
   
        fsipv6IfSENDFuzzTimestamp OBJECT-TYPE
             SYNTAX  Unsigned32 (0..10000)
              MAX-ACCESS     read-write
              STATUS         current
              DESCRIPTION
                      "This object specifies the Fuzz timestamp value for the interface"
              DEFVAL  { 1 }
              ::= { fsipv6IfEntry 34 }
        
        fsipv6IfSENDDriftTimestamp OBJECT-TYPE
             SYNTAX  Unsigned32 (1..100)
              MAX-ACCESS     read-write
              STATUS         current
              DESCRIPTION
                      "This object specifies the Drift timestamp value for the interface"
              DEFVAL  { 1 }
              ::= { fsipv6IfEntry 35 }
        
        fsipv6IfDefRoutePreference OBJECT-TYPE
              SYNTAX   INTEGER {
                           low(0),
                           medium(1),
                           high(2)
                       }
              MAX-ACCESS   read-write
              STATUS   current
              DESCRIPTION
                      "This object specifies the default router preference value 
                       advertised through RA for the interface"
              DEFVAL  { medium }
              ::= { fsipv6IfEntry 36 }

         -- IPv6 Interface statistic table
         fsipv6IfStatsTable OBJECT-TYPE
             SYNTAX     SEQUENCE OF Fsipv6IfStatsEntry
             MAX-ACCESS     not-accessible
             STATUS     current
             DESCRIPTION
                 "IPv6 interface traffic statistics"
             ::= { fsipv6Tables 2 }


         fsipv6IfStatsEntry OBJECT-TYPE
             SYNTAX     Fsipv6IfStatsEntry
             MAX-ACCESS     not-accessible
             STATUS     current
             DESCRIPTION
                 "An interface statistics entry containing objects
                 at a particular IPv6 interface."
             INDEX   { fsipv6IfStatsIndex }
             ::= { fsipv6IfStatsTable 1 }


         Fsipv6IfStatsEntry ::= 
             SEQUENCE {
                 fsipv6IfStatsIndex
                     InterfaceIndex,
                 fsipv6IfStatsInReceives
                     Counter32,
                 fsipv6IfStatsInHdrErrors
                     Counter32,
                 fsipv6IfStatsTooBigErrors
                     Counter32,
                 fsipv6IfStatsInAddrErrors
                     Counter32,
                 fsipv6IfStatsForwDatagrams
                     Counter32,
                 fsipv6IfStatsInUnknownProtos
                     Counter32,
                 fsipv6IfStatsInDiscards
                     Counter32,
                 fsipv6IfStatsInDelivers
                     Counter32,
                 fsipv6IfStatsOutRequests
                     Counter32,
                 fsipv6IfStatsOutDiscards
                     Counter32,
                 fsipv6IfStatsOutNoRoutes
                     Counter32,
                 fsipv6IfStatsReasmReqds
                     Counter32,
                 fsipv6IfStatsReasmOKs
                     Counter32,
                 fsipv6IfStatsReasmFails
                     Counter32,
                 fsipv6IfStatsFragOKs
                     Counter32,
                 fsipv6IfStatsFragFails
                     Counter32,
                 fsipv6IfStatsFragCreates
                     Counter32,
                 fsipv6IfStatsInMcastPkts
                     Counter32,
                 fsipv6IfStatsOutMcastPkts
                     Counter32,
                 fsipv6IfStatsInTruncatedPkts
                     Counter32,
                 fsipv6IfStatsInRouterSols
                     Counter32,
                 fsipv6IfStatsInRouterAdvs
                     Counter32,
                 fsipv6IfStatsInNeighSols
                     Counter32,
                 fsipv6IfStatsInNeighAdvs
                     Counter32,
                 fsipv6IfStatsInRedirects
                     Counter32,
                 fsipv6IfStatsOutRouterSols
                     Counter32,
                 fsipv6IfStatsOutRouterAdvs
                     Counter32,
                 fsipv6IfStatsOutNeighSols
                     Counter32,
                 fsipv6IfStatsOutNeighAdvs
                     Counter32,
                 fsipv6IfStatsOutRedirects
                     Counter32,
                 fsipv6IfStatsLastRouterAdvTime
                     TimeTicks,
                 fsipv6IfStatsNextRouterAdvTime
                     TimeTicks,
                 fsipv6IfStatsIcmp6ErrRateLmtd
                     Counter32,
                 fsipv6IfStatsSENDDroppedPkts
                     Counter32,
                 fsipv6IfStatsSENDInvalidPkts
                     Counter32
             }


         fsipv6IfStatsIndex OBJECT-TYPE
             SYNTAX     InterfaceIndex
             MAX-ACCESS    not-accessible
             STATUS     current
             DESCRIPTION
                 "The index value which uniquely identifies the IPv6
                 interface for which this statistics are maintained.
                 The interface identified by a particular value of this 
                 index is the same interface as identified by the same 
                 value of fsipv6IfIndex."
             ::= { fsipv6IfStatsEntry 1 }


         fsipv6IfStatsInReceives OBJECT-TYPE
             SYNTAX      Counter32
             MAX-ACCESS      read-only
             STATUS      current
             DESCRIPTION
                "The total number of input datagrams received from
                interfaces, including those received in error."
             ::= { fsipv6IfStatsEntry 2 }


         fsipv6IfStatsInHdrErrors OBJECT-TYPE
             SYNTAX     Counter32
             MAX-ACCESS     read-only
             STATUS     current
             DESCRIPTION
                "The number of input datagrams discarded due to
                errors in their IPv6 headers, including version
                number mismatch, other format errors, hop count
                exceeded, errors discovered in processing their
                IPv6 options, etc."
             ::= { fsipv6IfStatsEntry 3 }


         fsipv6IfStatsTooBigErrors OBJECT-TYPE
             SYNTAX      Counter32
             MAX-ACCESS      read-only
             STATUS      current
             DESCRIPTION
               "The number of datagrams that could not be forwarded
                because their size exceeded the Path MTU"
             ::= { fsipv6IfStatsEntry 4 }


         fsipv6IfStatsInAddrErrors OBJECT-TYPE
             SYNTAX      Counter32
             MAX-ACCESS      read-only
             STATUS      current
             DESCRIPTION
                "The number of input datagrams discarded because
                the IPv6 address in their IPv6 header's destination
                field was not a valid address to be received at
                this entity.  This count includes invalid
                addresses (e.g., ::0) and unsupported addresses
                (e.g., addresses with unallocated prefixes).  For
                entities which are not IPv6 routers and therefore
                do not forward datagrams, this counter includes
                datagrams discarded because the destination address
                was not a local address."
             ::= { fsipv6IfStatsEntry 5 }


         fsipv6IfStatsForwDatagrams OBJECT-TYPE
             SYNTAX      Counter32
             MAX-ACCESS      read-only
             STATUS      current
             DESCRIPTION
                "The number of input datagrams for which this
                entity was not their final IPv6 destination, as a
                result of which an attempt was made to find a
                route to forward them to that final destination.
                In entities which do not act as IPv6 routers, this
                counter will include only those packets which were
                Source-Routed via this entity, and the Source-
                Route option processing was successful."
             ::= { fsipv6IfStatsEntry 6 }


         fsipv6IfStatsInUnknownProtos OBJECT-TYPE
             SYNTAX      Counter32
             MAX-ACCESS      read-only
             STATUS     current 
             DESCRIPTION
                "The number of locally-addressed datagrams
                received successfully but discarded because of an
                unknown or unsupported protocol."
             ::= { fsipv6IfStatsEntry 7 }


         fsipv6IfStatsInDiscards OBJECT-TYPE
             SYNTAX      Counter32
             MAX-ACCESS      read-only
             STATUS      current
             DESCRIPTION
                "The number of input IPv6 datagrams for which no
                problems were encountered to prevent their
                continued processing, but which were discarded
                (e.g., for lack of buffer space).  Note that this
                counter does not include any datagrams discarded
                while awaiting re-assembly."
             ::= { fsipv6IfStatsEntry 8 }


         fsipv6IfStatsInDelivers OBJECT-TYPE
             SYNTAX      Counter32
             MAX-ACCESS      read-only
             STATUS      current
             DESCRIPTION
              "The total number of input datagrams successfully
              delivered to IPv6 user-protocols (including ICMP)."
             ::= { fsipv6IfStatsEntry 9 }


         fsipv6IfStatsOutRequests OBJECT-TYPE
             SYNTAX      Counter32
             MAX-ACCESS      read-only
             STATUS      current
             DESCRIPTION
              "The total number of IPv6 datagrams which local IPv6
              user-protocols (including ICMP) supplied to IPv6 in
              requests for transmission.  Note that this counter
              does not include any datagrams counted in
              fsipv6IfStatsForwDatagrams."
             ::= { fsipv6IfStatsEntry 10 }


         fsipv6IfStatsOutDiscards OBJECT-TYPE
             SYNTAX      Counter32
             MAX-ACCESS      read-only
             STATUS      current
             DESCRIPTION
                 "The number of output IPv6 datagrams for which no
                 problem was encountered to prevent their
                 transmission to their destination, but which were
                 discarded (e.g., for lack of buffer space).  Note
                 that this counter would include datagrams counted
                 in fsipv6IfStatsForwDatagrams if any such packets
                 met this (discretionary) discard criterion."
             ::= { fsipv6IfStatsEntry 11 }


         fsipv6IfStatsOutNoRoutes OBJECT-TYPE
             SYNTAX      Counter32
             MAX-ACCESS      read-only
             STATUS      current
             DESCRIPTION
                "The number of IPv6 datagrams discarded because no
                 route could be found to transmit them to their
                 destination.  Note that this counter includes any
                 packets counted in fsipv6IfStatsForwDatagrams which
                 meet this `no-route' criterion.  Note that this
                 includes any datagarms which a host cannot route
                 because all of its default routers are down."
             ::= { fsipv6IfStatsEntry 12 }


         fsipv6IfStatsReasmReqds OBJECT-TYPE
             SYNTAX      Counter32
             MAX-ACCESS      read-only
             STATUS      current
             DESCRIPTION
                "The number of IPv6 fragments received which needed
                 to be reassembled at this entity."
             ::= { fsipv6IfStatsEntry 13 }


         fsipv6IfStatsReasmOKs OBJECT-TYPE
             SYNTAX      Counter32
             MAX-ACCESS      read-only
             STATUS      current
             DESCRIPTION
               "The number of IPv6 datagrams successfully
               reassembled."
             ::= { fsipv6IfStatsEntry 14 }


         fsipv6IfStatsReasmFails OBJECT-TYPE
             SYNTAX      Counter32
             MAX-ACCESS      read-only
             STATUS      current
             DESCRIPTION
                "The number of failures detected by the IPv6 re-
                assembly algorithm (for whatever reason: timed
                out, errors, etc).  Note that this is not
                necessarily a count of discarded IPv6 fragments
                since some algorithms (notably the algorithm in
                RFC 815) can lose track of the number of fragments
                by combining them as they are received."
             ::= { fsipv6IfStatsEntry 15 }


         fsipv6IfStatsFragOKs OBJECT-TYPE
             SYNTAX      Counter32
             MAX-ACCESS      read-only
             STATUS      current
             DESCRIPTION
                "The number of IPv6 datagrams that have been
                 successfully fragmented at this entity."
             ::= { fsipv6IfStatsEntry 16 }


         fsipv6IfStatsFragFails OBJECT-TYPE
             SYNTAX      Counter32
             MAX-ACCESS      read-only
             STATUS      current
             DESCRIPTION
                "The number of IPv6 datagrams that have been
                 discarded because they needed to be fragmented
                 at this entity but could not be."
             ::= { fsipv6IfStatsEntry 17 }


         fsipv6IfStatsFragCreates OBJECT-TYPE
             SYNTAX      Counter32
             MAX-ACCESS      read-only
             STATUS      current
             DESCRIPTION
                "The number of IPv6 datagram fragments that have
                 been generated as a result of fragmentation at
                 this entity."
             ::= { fsipv6IfStatsEntry 18 }


         fsipv6IfStatsInMcastPkts OBJECT-TYPE
             SYNTAX      Counter32
             MAX-ACCESS      read-only
             STATUS     current
             DESCRIPTION
                "The number of multicast packets received
                 by the interface"
             ::= { fsipv6IfStatsEntry 19 }


         fsipv6IfStatsOutMcastPkts OBJECT-TYPE
             SYNTAX      Counter32
             MAX-ACCESS      read-only
             STATUS      current
             DESCRIPTION
                "The number of multicast packets transmitted
                 by the interface"
             ::= { fsipv6IfStatsEntry 20 }


         fsipv6IfStatsInTruncatedPkts OBJECT-TYPE
             SYNTAX      Counter32
             MAX-ACCESS      read-only
             STATUS      current
             DESCRIPTION
                "The number of input datagrams discarded because
                 datagram frame didn't carry enough data"
             ::= { fsipv6IfStatsEntry 21 }


         fsipv6IfStatsInRouterSols OBJECT-TYPE
             SYNTAX     Counter32
             MAX-ACCESS     read-only
             STATUS     current
             DESCRIPTION
              "The number of ICMP Router Solicit messages
               received."
             ::= { fsipv6IfStatsEntry 22 }


         fsipv6IfStatsInRouterAdvs OBJECT-TYPE
             SYNTAX     Counter32
             MAX-ACCESS     read-only
             STATUS     current
             DESCRIPTION
              "The number of ICMP Router Advertisement messages
              received."
             ::= { fsipv6IfStatsEntry 23 }


         fsipv6IfStatsInNeighSols OBJECT-TYPE
             SYNTAX     Counter32
             MAX-ACCESS     read-only
             STATUS     current
             DESCRIPTION
              "The number of ICMP Neighbor Solicit messages
               received."
             ::= { fsipv6IfStatsEntry 24 }


         fsipv6IfStatsInNeighAdvs OBJECT-TYPE
             SYNTAX     Counter32
             MAX-ACCESS     read-only
             STATUS     current
             DESCRIPTION
              "The number of ICMP Neighbor Advertisement
              messages received."
             ::= { fsipv6IfStatsEntry 25 }

         fsipv6IfStatsInRedirects OBJECT-TYPE
             SYNTAX     Counter32
             MAX-ACCESS     read-only
             STATUS     current
             DESCRIPTION
              "The number of ICMP Redirect messages 
               received."
             ::= { fsipv6IfStatsEntry 26 }

         fsipv6IfStatsOutRouterSols OBJECT-TYPE
             SYNTAX     Counter32
             MAX-ACCESS     read-only
             STATUS     current
             DESCRIPTION
              "The number of ICMP Router Solicit messages
               sent."
             ::= { fsipv6IfStatsEntry 27 }


         fsipv6IfStatsOutRouterAdvs OBJECT-TYPE
             SYNTAX     Counter32
             MAX-ACCESS     read-only
             STATUS     current
             DESCRIPTION
              "The number of ICMP Router Advertisement messages
               sent."
             ::= { fsipv6IfStatsEntry 28 }


         fsipv6IfStatsOutNeighSols OBJECT-TYPE
             SYNTAX     Counter32
             MAX-ACCESS     read-only
             STATUS     current
             DESCRIPTION
              "The number of ICMP Neighbor Solicitation
               messages sent."
             ::= { fsipv6IfStatsEntry 29 }


         fsipv6IfStatsOutNeighAdvs OBJECT-TYPE
             SYNTAX     Counter32
             MAX-ACCESS     read-only
             STATUS     current
             DESCRIPTION
              "The number of ICMP Neighbor Advertisement
              messages sent."
             ::= { fsipv6IfStatsEntry 30 }


         fsipv6IfStatsOutRedirects OBJECT-TYPE
             SYNTAX     Counter32
             MAX-ACCESS     read-only
             STATUS     current
             DESCRIPTION
              "The number of Redirect messages sent."
             ::= { fsipv6IfStatsEntry 31 }


          fsipv6IfStatsLastRouterAdvTime OBJECT-TYPE
              SYNTAX   TimeTicks
              MAX-ACCESS   read-only
              STATUS   current
              DESCRIPTION
               "The time at which the last Periodic router advertisement
                was sent."
             ::= { fsipv6IfStatsEntry 32 }


          fsipv6IfStatsNextRouterAdvTime OBJECT-TYPE
              SYNTAX   TimeTicks
              MAX-ACCESS   read-only
              STATUS   current
              DESCRIPTION
               "The time at which the next Periodic router advertisement
                is scheduled to be sent."
             ::= { fsipv6IfStatsEntry 33 }


         fsipv6IfStatsIcmp6ErrRateLmtd OBJECT-TYPE
              SYNTAX     Counter32
              MAX-ACCESS     read-only
              STATUS     current
              DESCRIPTION
                   "No of rate limited ICMP6 error messages "
              ::= { fsipv6IfStatsEntry 34 }

         fsipv6IfStatsSENDDroppedPkts OBJECT-TYPE
              SYNTAX     Counter32
              MAX-ACCESS     read-only
              STATUS     current
              DESCRIPTION
                   "This object displays the number of unsecured packets received 
                    on a secured interface."
              ::= { fsipv6IfStatsEntry 35 }
         
         fsipv6IfStatsSENDInvalidPkts OBJECT-TYPE
              SYNTAX     Counter32
              MAX-ACCESS     read-only
              STATUS     current
              DESCRIPTION
                   "This object displays the number of packets dropped due to failed
                    in validation"
              ::= { fsipv6IfStatsEntry 36 }

          -- IPv6 Prefix Table
          
          -- The IPv6 Prefix table contains this entity's IPv6
          -- address prefix information that are advertised along
          -- with the route advertisement message.

          -- Entries are created/deleted from SNMP.

          fsipv6PrefixTable   OBJECT-TYPE
              SYNTAX   SEQUENCE OF Fsipv6PrefixEntry
              MAX-ACCESS   not-accessible
              STATUS   current
              DESCRIPTION
                 "The table containing entity's IPv6 address prefix information."
              ::= { fsipv6Tables 3 }

          fsipv6PrefixEntry   OBJECT-TYPE
              SYNTAX   Fsipv6PrefixEntry
              MAX-ACCESS   not-accessible
              STATUS   current
              DESCRIPTION
                 "The entry in the IPv6 Address Prefix Table which defines a
                  prefix to be advertised in the route advertisement message
                  send on an IPv6 interface."
              INDEX  {fsipv6PrefixIndex,
                      fsipv6PrefixAddress,
                      fsipv6PrefixAddrLen
                     }
              ::= { fsipv6PrefixTable 1 }

          Fsipv6PrefixEntry  ::=
              SEQUENCE {
                 fsipv6PrefixIndex
                     InterfaceIndex,
                 fsipv6PrefixAddress
                     OCTET STRING,
                 fsipv6PrefixAddrLen
                     Integer32,
                 fsipv6PrefixProfileIndex
                     Integer32,
                 fsipv6PrefixAdminStatus
                     RowStatus,
                 fsipv6SupportEmbeddedRp
                     TruthValue
              }

          fsipv6PrefixIndex OBJECT-TYPE
              SYNTAX   InterfaceIndex
              MAX-ACCESS  not-accessible
              STATUS   current
              DESCRIPTION
                 "The index value which uniquely identifies the IPv6
                 interface on which this IPv6 address prefix entry is
                 to be advertised. The interface identified by a
                 particular value of this index is the same interface
                 as identified by the same value of fsipv6IfIndex."
              ::= { fsipv6PrefixEntry 1 }


          fsipv6PrefixAddress OBJECT-TYPE
              SYNTAX   OCTET STRING (SIZE (16))
              MAX-ACCESS   not-accessible
              STATUS   current
              DESCRIPTION
                 "The IPv6 address prefix to which this entry's prefix
                  information pertains."
              ::= { fsipv6PrefixEntry 2 }


          fsipv6PrefixAddrLen OBJECT-TYPE
              SYNTAX   Integer32 (1..128)
              MAX-ACCESS  not-accessible
              STATUS   current
              DESCRIPTION
                 "The length of the prefix (in bits) associated with
                 the IPv6 address prefix of this entry."
              ::= { fsipv6PrefixEntry 3 }


          fsipv6PrefixProfileIndex OBJECT-TYPE
              SYNTAX   Integer32 (0..200)
              MAX-ACCESS   read-write
              STATUS   current
              DESCRIPTION
                "Indicates the index into the IPv6 Address Profile Table.
                 This entry of the IPv6 Address Profile table defines the
                 parameters for this prefix."
              DEFVAL { 0 }
              ::= { fsipv6PrefixEntry 4 }

          fsipv6PrefixAdminStatus OBJECT-TYPE
              SYNTAX            RowStatus
              MAX-ACCESS   read-create
              STATUS   current
              DESCRIPTION
                "Indicates the administrative status of the prefix.
                 CreateAndGo and NotInService are not supported."
              ::= { fsipv6PrefixEntry 5 }

         fsipv6SupportEmbeddedRp OBJECT-TYPE
   	     SYNTAX      TruthValue
             MAX-ACCESS     read-write
             STATUS     current
             DESCRIPTION
               "Flag to control the usage of associated IPv6 Prefix address
                as a valid embedded-RP prefix on specified interface"
             DEFVAL  {false}
             ::= { fsipv6PrefixEntry 6 }


          -- IPv6 Address Table
          
          -- The IPv6 address table contains this entity's IPv6
          -- addressing information.

          -- Entries are created/deleted from SNMP.


          fsipv6AddrTable   OBJECT-TYPE
              SYNTAX   SEQUENCE OF Fsipv6AddrEntry
              MAX-ACCESS   not-accessible
              STATUS   current
              DESCRIPTION
                 "The table containing entity's IPv6 addressing information."
              ::= { fsipv6Tables 4 }


          fsipv6AddrEntry   OBJECT-TYPE
              SYNTAX   Fsipv6AddrEntry
              MAX-ACCESS   not-accessible
              STATUS   current
              DESCRIPTION
                 "The entry in the IPv6 Address Table which defines a
                 unicast, anycast or link-local address on an IPv6 interface."
              INDEX  {fsipv6AddrIndex,
                      fsipv6AddrAddress,
                      fsipv6AddrPrefixLen
                     }
              ::= { fsipv6AddrTable 1 }


          Fsipv6AddrEntry  ::=
              SEQUENCE {
                 fsipv6AddrIndex
                     InterfaceIndex,
                 fsipv6AddrAddress
                     OCTET STRING,
                 fsipv6AddrPrefixLen
                     Integer32,
                 fsipv6AddrAdminStatus
                     RowStatus,
                 fsipv6AddrType
                     INTEGER,
                 fsipv6AddrProfIndex
                     Integer32,
                 fsipv6AddrOperStatus    
                     INTEGER,
                 fsipv6AddrScope
                     InetScopeType,
                 fsipv6AddrSENDCgaStatus
                     TruthValue,
                 fsipv6AddrSENDCgaModifier
                     OCTET STRING,
                 fsipv6AddrSENDCollisionCount
                     INTEGER
              }


          fsipv6AddrIndex OBJECT-TYPE
              SYNTAX   InterfaceIndex
              MAX-ACCESS  not-accessible
              STATUS   current
              DESCRIPTION
                 "The index value which uniquely identifies the IPv6
                 interface on which this IPv6 address entry exists.
                 The interface identified by a particular value of this 
                 index is the same interface as identified by the same 
                 value of fsipv6IfIndex."
              ::= { fsipv6AddrEntry 1 }


          fsipv6AddrAddress OBJECT-TYPE
              SYNTAX   OCTET STRING (SIZE (16))
              MAX-ACCESS   not-accessible
              STATUS   current
              DESCRIPTION
                 "The IPv6 address to which this entry's addressing
                  information pertains."
              ::= { fsipv6AddrEntry 2 }


          fsipv6AddrPrefixLen OBJECT-TYPE
              SYNTAX   Integer32 (0..128)
              MAX-ACCESS  not-accessible
              STATUS   current
              DESCRIPTION
                 "The length of the prefix (in bits) associated with
                 the IPv6 address of this entry. For a link-local address,
                 the prefix is always start with '0xfe80' and the prefix
                 length is 128 bits."
              ::= { fsipv6AddrEntry 3 }


          fsipv6AddrAdminStatus OBJECT-TYPE
              SYNTAX            RowStatus
              MAX-ACCESS   read-create
              STATUS   current
              DESCRIPTION
                "Indicates the desired status of the address. Also a creation
                 of an address can trigger IPv6 to be enabled over the
                 interface. Similarly deletion of all the address may trigger
                 IPv6 to be disabled on the interface. NotInService value is
                 not supported."
              ::= { fsipv6AddrEntry 4 }


          fsipv6AddrType OBJECT-TYPE
              SYNTAX   INTEGER {
                            unicast(1),
                            anycast(2),
                            linklocal(3)
                       }
              MAX-ACCESS   read-write
              STATUS   current
              DESCRIPTION
                "Indicates whether the address is a unicast, anycast or
                 link-local address. Syntactically there is no difference
                 between a unicast address and a anycast address while a
                 link-local address has the prefix '0xfe80'. This
                 object can be modified only if fsipv6AddrOperStatus is
                 down."
              ::= { fsipv6AddrEntry 5 }


          fsipv6AddrProfIndex OBJECT-TYPE
              SYNTAX   Integer32 (0..200)
              MAX-ACCESS   read-write
              STATUS   current
              DESCRIPTION
                "Indicates the index into the IPv6 Address Profile Table.
                 This entry of the IPv6 Address Profile table defines the
                 parameters for this address. For a link-local address,
                 this object always takes the value zero and cannot be
                 modified from SNMP."
              DEFVAL { 0 }
              ::= { fsipv6AddrEntry 6 }


          fsipv6AddrOperStatus OBJECT-TYPE
              SYNTAX   INTEGER {

                           tentative (1),    -- DAD resolution going
                                             -- on on the address

                           complete (2),     -- DAD completed on the address

                           down(3),          -- address is operationally
                                             -- down

                           failed(4)         -- DAD failed for the address

                       }
              MAX-ACCESS   read-only
              STATUS   current
              DESCRIPTION
                 "Indicates the operational status of the address. A
                 status of failed(4) indicates that a duplicate address has
                 been detected on this IPv6 interface. On interfaces on
                 which Duplicate Address Detection is not performed, this
                 object will take values only complete(2) and down(3)."
              ::= { fsipv6AddrEntry 7 }
          

          fsipv6AddrScope OBJECT-TYPE
              SYNTAX      InetScopeType
              MAX-ACCESS   read-only
              STATUS   current
              DESCRIPTION
                " Scope is a 4-bit value that describes the scope of
                  an IPV6 address.An unicast address can possibly have 2 
                  scopes (Linklocal and Global) only. A multicast address
                  can have a maximum of 11 scopes.The reserved scopes cannot be used by
                  the user/administrator.  Only unassigned multicast scoped can be configured 
                  and used in  a given IPv6 domain as per the need."
                   
                   ::= { fsipv6AddrEntry 8 }

          fsipv6AddrSENDCgaStatus OBJECT-TYPE
              SYNTAX TruthValue 
              MAX-ACCESS   read-write
              STATUS   current
              DESCRIPTION
                   "This object displays the CGA generation status.
                    When true, it indicates address is cryptographically generated address(CGA). 
	            When false, it indicates the address is not a cryptographically generated address (CGA)"
              DEFVAL { false }
                   ::= { fsipv6AddrEntry 9 }
          
          fsipv6AddrSENDCgaModifier OBJECT-TYPE
              SYNTAX OCTET STRING
              MAX-ACCESS   read-write
              STATUS   current
              DESCRIPTION
                   "This object stores the 128 bit modifier used for generating 
                    cryptographically generated address (CGA).
                    Note: This object is defined as read-write object to enable it to be saved 
                          and restored. Only read write objects are stored during MSR.(Mib Save 
                          and Restore). The mib value is not configurable by the user. "
                   ::= { fsipv6AddrEntry 10 }
          
          fsipv6AddrSENDCollisionCount OBJECT-TYPE
              SYNTAX Integer32
              MAX-ACCESS   read-write
              STATUS   current
              DESCRIPTION
                   "This object stores the collision count for Duplicate Address Detection (DAD).
                    Note: This object is defined as read-write object to enable it to be saved
                          and restored. Only read write objects are stored during MSR.(Mib Save
                          and Restore). The mib value is not configurable by the user. " 
                   ::= { fsipv6AddrEntry 11 } 
    

          -- IPv6 Address Profile Table
    
          -- This table contains parameters related to the advertisement of 
          -- address prefixes. Since the prefix advertisement is done only on 
          -- LAN interfaces, this information is kept separately from the IPv6 
          -- address table which contains addresses on all interfaces.

          -- Entries are created/deleted from SNMP except for the first profile
          -- entry which is autocreated and cannot be deleted.


          fsipv6AddrProfileTable   OBJECT-TYPE
              SYNTAX   SEQUENCE OF Fsipv6AddrProfileEntry
              MAX-ACCESS   not-accessible
              STATUS   current
              DESCRIPTION
                 "The table containing information for an address or set of
                 addresses of the entity."
              ::= { fsipv6Tables 5 }


          fsipv6AddrProfileEntry   OBJECT-TYPE
              SYNTAX   Fsipv6AddrProfileEntry
              MAX-ACCESS   not-accessible
              STATUS   current
              DESCRIPTION
                 "The entry in the IPv6 Address Profile Table which contains
                 parameters related to the advertisement of address prefixes.
                 One or more IPv6 addresses refer to this profile through the
                 object fsipv6AddrProfIndex in the fsipv6AddrTable. An entry of
                 this table other than the first entry is created/deleted 
                 from SNMP."
              INDEX  { fsipv6AddrProfileIndex }
              ::= { fsipv6AddrProfileTable 1 }


          Fsipv6AddrProfileEntry  ::=
              SEQUENCE {
                 fsipv6AddrProfileIndex
                     Unsigned32,
                 fsipv6AddrProfileStatus
                     INTEGER,
                 fsipv6AddrProfilePrefixAdvStatus
                     INTEGER,
                 fsipv6AddrProfileOnLinkAdvStatus
                     INTEGER,
                 fsipv6AddrProfileAutoConfAdvStatus
                     INTEGER,
                 fsipv6AddrProfilePreferredTime
                     Unsigned32,
                 fsipv6AddrProfileValidTime
                     Unsigned32,
                 fsipv6AddrProfileValidLifeTimeFlag
                     INTEGER,
                 fsipv6AddrProfilePreferredLifeTimeFlag
                     INTEGER
              }


          fsipv6AddrProfileIndex OBJECT-TYPE
              SYNTAX   Unsigned32 (0..200)
              MAX-ACCESS    not-accessible
              STATUS   current
              DESCRIPTION
                 "A unique value identifying the particular IPv6 Address
                  profile entry. This is referred by fsipv6AddrProfIndex of
                  IPv6 Address Table. The index 0 is created with default value
                  during system start-up and this entry is not configurable."
              ::= { fsipv6AddrProfileEntry 1 }


          fsipv6AddrProfileStatus OBJECT-TYPE
              SYNTAX   INTEGER {
                           valid (1),
                           invalid (2)
                       }
              MAX-ACCESS   read-write
              STATUS   current
              DESCRIPTION
                 "Indicates that the entry is valid or not. An entry other
                 than the first entry can be deleted by setting this object
                 to invalid(2)."
              ::= { fsipv6AddrProfileEntry 2 }


          fsipv6AddrProfilePrefixAdvStatus OBJECT-TYPE
              SYNTAX   INTEGER {
                           on(1),
                           off(2)
                       }
              MAX-ACCESS   read-write
              STATUS   current
              DESCRIPTION
                 "If this object has value on(1), the address prefixes
                 corresponding to those addresses which use this profile
                 will be advertised in router advertisements sent by this
                 entity. If it has value off(2), these address prefixes
                 will not be advertised."
              DEFVAL { on }
              ::= { fsipv6AddrProfileEntry 3 }


          fsipv6AddrProfileOnLinkAdvStatus OBJECT-TYPE
              SYNTAX   INTEGER {
                           on(1),
                           off(2)
                       }
              MAX-ACCESS   read-write
              STATUS   current
              DESCRIPTION
                 "If this object has value on(1), the address prefixes
                 corresponding to those addresses which use this profile
                 will be advertised with on-link flag set in the router 
                 advertisements sent by this entity. These prefixes can be
                 used for on-link determination by hosts which receive these
                 router advertisements. If the object has value off(2), 
                 these address prefixes will not not have the on-link flag
                 set if advertised."
              DEFVAL { on }
              ::= { fsipv6AddrProfileEntry 4 }


          fsipv6AddrProfileAutoConfAdvStatus OBJECT-TYPE
              SYNTAX   INTEGER {
                            on(1),
                            off(2)
                       }
              MAX-ACCESS   read-write
              STATUS   current
              DESCRIPTION
                 "If this object has value on(1), the address prefixes
                 corresponding to those addresses which use this profile
                 will be advertised with autonomous address configuration 
                 flag set in the router advertisements sent by this entity. 
                 These prefixes can be used for autonomous address 
                 configuration (i.e. can be used to form a local interface 
                 address) by hosts which receive these router advertisements. 
                 If the object has value off(2), these address prefixes will 
                 not not have the autonomous address configuration flag set 
                 if advertised."
              DEFVAL { on }
              ::= { fsipv6AddrProfileEntry 5 }


          fsipv6AddrProfilePreferredTime OBJECT-TYPE
              SYNTAX   Unsigned32 (0..4294967295)
              MAX-ACCESS   read-write
              STATUS   current
              DESCRIPTION
                 "This object specifies the preferred lifetime in seconds
                 for the address prefixes corresponding to those addresses 
                 which use this profile. This is sent in router advertisements
                 by this entity. A value of 4,294,967,295 represents
                 infinity.This value should be less than fsipv6AddrProfileValidTime"
              DEFVAL { 604800 }
              ::= { fsipv6AddrProfileEntry 6 }


          fsipv6AddrProfileValidTime OBJECT-TYPE
              SYNTAX   Unsigned32 (0..4294967295)
              MAX-ACCESS   read-write
              STATUS   current
              DESCRIPTION
                 "This object specifies the valid lifetime in seconds
                 for the address prefixes corresponding to those addresses 
                 which use this profile. This is sent in router advertisements
                 by this entity. A value of 4,294,967,295 represents
                 infinity."
              DEFVAL { 4294967295 }
              ::= { fsipv6AddrProfileEntry 7 }

         fsipv6AddrProfileValidLifeTimeFlag OBJECT-TYPE
              SYNTAX  INTEGER  {
                          fixed    (1),
                          variable (2)
			  }
             MAX-ACCESS  read-write
             STATUS  current
             DESCRIPTION
	            "By setting this flag to fixed (1),the router 
                     advertisement Valid life time value is set 
                     to fixed and by setting to variable(2), the 
                     router advertisement Valid life time value 
                     can decrease in real time. This flag will 
                     synchronise the router clocks."
              DEFVAL  { fixed }
              ::= { fsipv6AddrProfileEntry 8 }

         fsipv6AddrProfilePreferredLifeTimeFlag OBJECT-TYPE
              SYNTAX  INTEGER  {
                          fixed    (1),
                          variable (2)
			  }
             MAX-ACCESS  read-write
             STATUS  current
             DESCRIPTION
	            "By setting this flag to fixed (1),the router 
                     advertisement Preferred life time value is set 
                     to fixed and by setting to variable(2), the 
                     router advertisement preferred life time value 
                     can decrease in real time. This flag will 
                     synchronise the router clocks."
              DEFVAL  { fixed }
              ::= { fsipv6AddrProfileEntry 9 }


        -- Path MTU for IPv6
         
         fsipv6PmtuTable OBJECT-TYPE
             SYNTAX     SEQUENCE OF Fsipv6PmtuEntry
             MAX-ACCESS not-accessible
             STATUS     current
             DESCRIPTION
               "IPv6 Path MTU table. This table contains
               an entry for a specific path traversed by
               packets exchanged between the source and
               destination nodes."
             ::= { fsipv6Tables 6 }

         fsipv6PmtuEntry OBJECT-TYPE
             SYNTAX     Fsipv6PmtuEntry
             MAX-ACCESS not-accessible
             STATUS     current
             DESCRIPTION
                     "A Path MTU entry."
             INDEX   { fsipv6PmtuDest }
             ::= { fsipv6PmtuTable 1 }

         Fsipv6PmtuEntry ::= SEQUENCE {
                 fsipv6PmtuDest     OCTET STRING,
                 fsipv6Pmtu      Integer32,
                 fsipv6PmtuTimeStamp Integer32,
                 fsipv6PmtuAdminStatus INTEGER
             }

         fsipv6PmtuDest OBJECT-TYPE
             SYNTAX      OCTET STRING (SIZE (16))
             MAX-ACCESS  not-accessible
             STATUS     current
             DESCRIPTION
               "The destination IPv6 address of the packets
               to be exchanged."
             ::= { fsipv6PmtuEntry 1 }

         fsipv6Pmtu OBJECT-TYPE
             SYNTAX     Integer32(1280..65535)
             MAX-ACCESS read-write 
             STATUS     current
             DESCRIPTION
               "Indicates the path MTU value for the path."
             ::= { fsipv6PmtuEntry 2 }

         fsipv6PmtuTimeStamp   OBJECT-TYPE
             SYNTAX  Integer32 
             MAX-ACCESS  read-only
             STATUS  current
             DESCRIPTION
                "Indicates the entry created time in the PMTU table."
             ::= { fsipv6PmtuEntry 3 }


         fsipv6PmtuAdminStatus   OBJECT-TYPE
             SYNTAX  INTEGER{
				valid(1),
				invalid(2)
			} 
             MAX-ACCESS  read-write
             STATUS  current
             DESCRIPTION
                "The desired status of the PmtuTable. This variable
                 has to be made valid(1) for creating a entry in the PmtuTable.
                 If set to invalid(2), the entry is deleted."
             ::= { fsipv6PmtuEntry 4 }


         -- IPv6 Address Translation table for LAN interfaces

         -- The fsipv6NdLanCacheTable contain the Ipv6Address
         -- to `physical' address equivalences for on-link nodes
         -- on Ethernet. 
         -- Static entries can be created/deleted from SNMP. Dynamic
         -- entries get created for neighbors upon IPv6 packet forwarding.


         fsipv6NdLanCacheTable OBJECT-TYPE
             SYNTAX      SEQUENCE OF Fsipv6NdLanCacheEntry
             MAX-ACCESS      not-accessible
             STATUS      current
             DESCRIPTION
               "The IPv6 Address Translation table used for
               mapping from IPv6 addresses to physical addresses
               on Ethernet."
             ::= { fsipv6Tables 7 }


         fsipv6NdLanCacheEntry OBJECT-TYPE
             SYNTAX     Fsipv6NdLanCacheEntry
             MAX-ACCESS     not-accessible
             STATUS     current
             DESCRIPTION
               "Each entry contains one IPv6 address to `physical'
               address equivalence. Entries are created dynamically upon
               address resolution or statically from SNMP."
             INDEX   { fsipv6NdLanCacheIfIndex,
                       fsipv6NdLanCacheIPv6Addr }
             ::= { fsipv6NdLanCacheTable 1 }


         Fsipv6NdLanCacheEntry ::= 
             SEQUENCE {
                 fsipv6NdLanCacheIfIndex
                     InterfaceIndex,
                 fsipv6NdLanCacheIPv6Addr
                     OCTET STRING,
                 fsipv6NdLanCacheStatus
                     INTEGER,
                 fsipv6NdLanCachePhysAddr
                     OCTET STRING,
                 fsipv6NdLanCacheState
                     INTEGER,
                 fsipv6NdLanCacheUseTime
                     TimeTicks,
                 fsipv6NdLanCacheIsSecure
                     TruthValue
             }


          fsipv6NdLanCacheIfIndex OBJECT-TYPE
              SYNTAX   InterfaceIndex
              MAX-ACCESS    not-accessible
              STATUS   current
              DESCRIPTION
                "The index value which uniquely identifies the IPv6
                 interface on which this fsipv6NdLanCache entry exists.
                 The interface identified by a particular value of this
                 index is the same interface as identified by the same 
                 value of fsipv6IfIndex."
              ::= { fsipv6NdLanCacheEntry 1 }


         fsipv6NdLanCacheIPv6Addr OBJECT-TYPE
             SYNTAX     OCTET STRING (SIZE (16))
             MAX-ACCESS   not-accessible
             STATUS     current
             DESCRIPTION
               "The IPv6 Address corresponding to the `physical' address
                on Ethernet."
             ::= { fsipv6NdLanCacheEntry 2 }


         fsipv6NdLanCacheStatus OBJECT-TYPE
             SYNTAX     INTEGER  {
                          valid (1),
                          invalid(2)
                        }
             MAX-ACCESS     read-write
             STATUS     current
             DESCRIPTION
              "Setting this object to the value invalid(2)
               effects in invalidating the corresponding entry
               in the fsipv6NdLanCacheTable. Otherwise, the entry
               remains valid."
             DEFVAL  { valid }
             ::= { fsipv6NdLanCacheEntry 3 }


         fsipv6NdLanCachePhysAddr OBJECT-TYPE
             SYNTAX     OCTET STRING (SIZE (6))
             MAX-ACCESS     read-write
             STATUS     current
             DESCRIPTION
               "The `physical' address on Ethernet."
             ::= { fsipv6NdLanCacheEntry 4 }


         fsipv6NdLanCacheState OBJECT-TYPE
             SYNTAX     INTEGER {
                         static(1),    
                         reachable(2),
                         incomplete(3),
                         stale(4),
                         delay(5),
                         probe(6)
                        }
             MAX-ACCESS     read-only
             STATUS     current
             DESCRIPTION
              "The reachability state of NdLanCacheEntry. Upon creation of
               an entry from SNMP, this object takes the value as 'static'.
               Otherwise takes the value that correspond to the states of 
               dynamically created entries."
             ::= { fsipv6NdLanCacheEntry 5 }


          fsipv6NdLanCacheUseTime OBJECT-TYPE
              SYNTAX   TimeTicks
              MAX-ACCESS   read-only
              STATUS   current
              DESCRIPTION
               "The value of sysUpTime at the time the entry was consulted
                upon IPv6 packet forwarding."
              ::= { fsipv6NdLanCacheEntry 6 }

          fsipv6NdLanCacheIsSecure OBJECT-TYPE
              SYNTAX TruthValue 
              MAX-ACCESS   read-only
              STATUS   current
              DESCRIPTION
               "This object displays whether the neighbor is a secured neighbor or not.
                When true, it indicates that the neighbor is secured.
                When false, it indicates that the neighbor is unsecured."
              ::= { fsipv6NdLanCacheEntry 7 }
 

         -- IPv6 Address Translation table for NBMA interfaces

         -- The fsipv6NdWanCacheTable contain the Ipv6Address
         -- to `physical' address equivalences for on-link nodes
         -- on NBMA interfaces. The 'physical address' actually refers
         -- to the IPv6 interface on which the Ipv6Address is on-link.

         -- Static entries can be created/deleted from SNMP. Dynamic 
         -- entries get created for on-link nodes upon reception of 
         -- IPv6 packet.


         fsipv6NdWanCacheTable OBJECT-TYPE
             SYNTAX      SEQUENCE OF Fsipv6NdWanCacheEntry
             MAX-ACCESS      not-accessible
             STATUS      current
             DESCRIPTION
               "The IPv6 Address Translation table used for
               mapping from IPv6 addresses to physical addresses
               on NBMA interface. The 'physical address' actually refers
               to the IPv6 interface on which the Ipv6Address is on-link."
             ::= { fsipv6Tables 8 }


         fsipv6NdWanCacheEntry OBJECT-TYPE
             SYNTAX     Fsipv6NdWanCacheEntry
             MAX-ACCESS     not-accessible
             STATUS     current
             DESCRIPTION
               "Each entry contains one IPv6 address to `physical'
               address equivalence.  Entries are created dynamically upon
               reception of IPv6 packet from an on-link source or statically 
               from SNMP."
             INDEX   { fsipv6NdWanCacheIfIndex,
                       fsipv6NdWanCacheIPv6Addr }
             ::= { fsipv6NdWanCacheTable 1 }


         Fsipv6NdWanCacheEntry ::= 
             SEQUENCE {
                 fsipv6NdWanCacheIfIndex
                     InterfaceIndex,
                 fsipv6NdWanCacheIPv6Addr
                     OCTET STRING,
                 fsipv6NdWanCacheStatus
                     INTEGER,
                 fsipv6NdWanCacheState
                     INTEGER,
                 fsipv6NdWanCacheUseTime
                     TimeTicks
             }


          fsipv6NdWanCacheIfIndex OBJECT-TYPE
              SYNTAX   InterfaceIndex
              MAX-ACCESS  not-accessible
              STATUS   current
              DESCRIPTION
                "The index value which uniquely identifies the IPv6
                 interface on which this fsipv6NdWanCache entry exists.
                 The interface identified by a particular value of this 
                 index is the same interface as identified by the same 
                 value of fsipv6IfIndex."
              ::= { fsipv6NdWanCacheEntry 1 }


         fsipv6NdWanCacheIPv6Addr OBJECT-TYPE
             SYNTAX     OCTET STRING (SIZE (16))
             MAX-ACCESS   not-accessible  
             STATUS     current
             DESCRIPTION
                "The IPv6 Address of the on-link node on this NBMA interface."
             ::= { fsipv6NdWanCacheEntry 2 }


         fsipv6NdWanCacheStatus OBJECT-TYPE
             SYNTAX     INTEGER  {
                          valid (1),
                          invalid(2)
                        }
             MAX-ACCESS     read-write
             STATUS     current
             DESCRIPTION
              "Setting this object to the value 'invalid(2)'
              effects in invalidating the corresponding entry
              in the fsipv6NdWanCacheTable. Otherwise, the entry
              remains valid."
             DEFVAL  { valid }
             ::= { fsipv6NdWanCacheEntry 3 }


         fsipv6NdWanCacheState OBJECT-TYPE
             SYNTAX     INTEGER {
                          static(1),
                          reachable(2)
                        }
             MAX-ACCESS     read-only
             STATUS     current
             DESCRIPTION
                     "The reachability state of NdWanCacheEntry. 
                      Upon creation of an entry from SNMP, this object 
                      takes the value as 'static'. Otherwise takes the 
                      value as 'reachable' that corresponds to the state 
                      of dynamically created entries."
             ::= { fsipv6NdWanCacheEntry 4 }


          fsipv6NdWanCacheUseTime OBJECT-TYPE
              SYNTAX   TimeTicks
              MAX-ACCESS   read-only
              STATUS   current
              DESCRIPTION
                      "The value of sysUpTime at the time the entry
                       was consulted upon IPv6 packet forwarding."
             ::= { fsipv6NdWanCacheEntry 5 }



          -- The IPv6 Ping table

          -- This table is used to generate IPv6 Echo requests from this
          -- entity to destinations.

          -- Entries are created/deleted from SNMP.


          fsipv6PingTable     OBJECT-TYPE
              SYNTAX  SEQUENCE OF Fsipv6PingEntry
              MAX-ACCESS  not-accessible
              STATUS  current
              DESCRIPTION
                "This entity's IPv6 Ping Table."
              ::= { fsipv6Tables 12 }

          
          fsipv6PingEntry     OBJECT-TYPE
              SYNTAX  Fsipv6PingEntry
              MAX-ACCESS  not-accessible
              STATUS  current
              DESCRIPTION
                 "Contains the information about a particular IPv6 Ping 
                 operation. An entry is created/deleted from SNMP."
              INDEX   { fsipv6PingIndex } 
              ::= { fsipv6PingTable 1 }
          

          Fsipv6PingEntry     ::=     
               SEQUENCE { 
                  fsipv6PingIndex
                      Integer32,
                  fsipv6PingDest              
                      OCTET STRING,
                  fsipv6PingIfIndex              
                      InterfaceIndex,
                  fsipv6PingAdminStatus       
                      INTEGER,
                  fsipv6PingInterval          
                      Integer32,
                  fsipv6PingRcvTimeout        
                      Integer32,
                  fsipv6PingTries             
                      Integer32,
                  fsipv6PingSize              
                      Integer32,
                  fsipv6PingSentCount         
                      Integer32,
                  fsipv6PingAverageTime       
                      Integer32,
                  fsipv6PingMaxTime           
                      Integer32,
                  fsipv6PingMinTime           
                      Integer32,
                  fsipv6PingOperStatus        
                      INTEGER,
                  fsipv6PingSuccesses         
                      Counter32,
                  fsipv6PingPercentageLoss    
                      Integer32,
                  fsipv6PingData
                      OCTET STRING,
                  fsipv6PingSrcAddr
                      OCTET STRING, 
                  fsipv6PingZoneId
                      DisplayString, 
                  fsipv6PingDestAddrType
                      INTEGER,
                  fsipv6PingHostName
                      OCTET STRING,
                  fsipv6PingContInterval
                      Integer32
              }
          

          fsipv6PingIndex      OBJECT-TYPE
              SYNTAX  Integer32(0..5)
              MAX-ACCESS   not-accessible
              STATUS  current
              DESCRIPTION
                "A unique value identifying the particular IPv6 Ping entry."
              ::= { fsipv6PingEntry 1 }      

          
          fsipv6PingDest      OBJECT-TYPE
              SYNTAX  OCTET STRING (SIZE (16))
              MAX-ACCESS  read-write
              STATUS  current
              DESCRIPTION
                "The IPv6 address of the destination to be pinged. This
                 should be a unicast or link-local address"
              ::= { fsipv6PingEntry 2 }
          

          fsipv6PingIfIndex    OBJECT-TYPE
              SYNTAX   InterfaceIndex
              MAX-ACCESS   read-write
              STATUS   current
              DESCRIPTION
                "The index value which uniquely identifies the IPv6
                 interface on which this Ping is to be sent. The interface 
                 identified by a particular value of this index is the same 
                 interface as identified by the same value of fsipv6IfIndex.
                 The value of this object is needed when pinging to a
                 link-local destination, otherwise it is ignored."
              ::= { fsipv6PingEntry 3 }


          fsipv6PingAdminStatus       OBJECT-TYPE
              SYNTAX  INTEGER {
                          up(1),
                          down(2),
                          invalid(3),
                          create(4)
                      }
              MAX-ACCESS  read-write
              STATUS  current
              DESCRIPTION
                 "The desired status for the ping operation. This variable
                 has to be made up(1) for starting the ping operation.
                 If set to down(2), the ping is stopped but the statistics 
                 will still be available. The entry is created when this 
                 variable is set to create(4) and deleted on setting this
                 variable to invalid(3)."
              ::= { fsipv6PingEntry 4 }
          
          
          fsipv6PingInterval   OBJECT-TYPE
              SYNTAX  Integer32 (1..100)
              MAX-ACCESS  read-write
              STATUS  current
              DESCRIPTION
                 "The time interval in seconds between successive pings
                 sent to the destination."
              DEFVAL { 1 }
              ::= { fsipv6PingEntry 5 }
          

          fsipv6PingRcvTimeout   OBJECT-TYPE
              SYNTAX  Integer32 (0..100)
              MAX-ACCESS  read-write
              STATUS  current
              DESCRIPTION
                 "The time in seconds after which this entity times out
                 waiting for a particular ping response."
              DEFVAL { 5 }
              ::= { fsipv6PingEntry 6 }
          

          fsipv6PingTries     OBJECT-TYPE
              SYNTAX  Integer32 (1..1000)
              MAX-ACCESS  read-write
              STATUS  current
              DESCRIPTION
                 "The number of times the destination is to be pinged."
              DEFVAL { 5 }
              ::= { fsipv6PingEntry 7 }
          

          fsipv6PingSize      OBJECT-TYPE
              SYNTAX  Integer32  (32..2080)
              MAX-ACCESS  read-write
              STATUS  current
              DESCRIPTION
                 "The size of the data portion of the Ping packet."
              DEFVAL { 100 }
              ::= { fsipv6PingEntry 8 }
          

          fsipv6PingSentCount OBJECT-TYPE
              SYNTAX  Integer32
              MAX-ACCESS  read-only
              STATUS  current
              DESCRIPTION
                 "Total number of packets sent to destination."
              ::= { fsipv6PingEntry 9 }
          

          fsipv6PingAverageTime       OBJECT-TYPE
              SYNTAX  Integer32
              MAX-ACCESS  read-only
              STATUS  current
              DESCRIPTION
                 "The average value of the round trip time in seconds to this
                 destination."
              ::= { fsipv6PingEntry 10 }
          
          
          fsipv6PingMaxTime   OBJECT-TYPE
              SYNTAX  Integer32
              MAX-ACCESS  read-only
              STATUS  current
              DESCRIPTION
                 "The maximum value of the round trip time in seconds to this
                 destination."
              ::= { fsipv6PingEntry 11 }
          

          fsipv6PingMinTime   OBJECT-TYPE
              SYNTAX  Integer32
              MAX-ACCESS  read-only
              STATUS  current
              DESCRIPTION
                 "The minimum value of the round trip time in seconds to this
                 destination."
              ::= { fsipv6PingEntry 12 }
          

          fsipv6PingOperStatus        OBJECT-TYPE
              SYNTAX  INTEGER { 
                          notInitiated(1),
                          inProgress(2),
                          completed(3)
                      }
              MAX-ACCESS  read-only
              STATUS  current
              DESCRIPTION
                 "The current status of this ping operation."
              ::= { fsipv6PingEntry 13 }
          

          fsipv6PingSuccesses OBJECT-TYPE
              SYNTAX  Counter32
              MAX-ACCESS  read-only
              STATUS  current
              DESCRIPTION
                 "The number of ping responses received."
              ::= { fsipv6PingEntry 14 }
          

          fsipv6PingPercentageLoss OBJECT-TYPE
              SYNTAX  Integer32
              MAX-ACCESS  read-only
              STATUS  current
              DESCRIPTION
                 "Percentage of lost packets for which no responses were
                 received till timeout."
              ::= { fsipv6PingEntry 15 }


          fsipv6PingData      OBJECT-TYPE
              SYNTAX  OCTET STRING (SIZE (6))
              MAX-ACCESS  read-write
              STATUS  current
              DESCRIPTION
                "Data that should be sent in the Ping message"
              ::= { fsipv6PingEntry 16 }

          fsipv6PingSrcAddr      OBJECT-TYPE
              SYNTAX  OCTET STRING (SIZE (16))
              MAX-ACCESS  read-write
              STATUS  current
              DESCRIPTION
                "Source address to be used for the ping"
              ::= { fsipv6PingEntry 17 }

          fsipv6PingZoneId   OBJECT-TYPE
              SYNTAX      DisplayString
              MAX-ACCESS  read-write
              STATUS  current
              DESCRIPTION
                 "Zone-Id shoule be able to identify a particular zone 
                  of the address's scope. This Zone id applies 
                  to all kinds of unicast and multicast addresses of
                  non-global scope except the unspecified address.             
                  The zone-id is not supported for global address."
              REFERENCE "RFC4007"
              ::= { fsipv6PingEntry 18 }

          fsipv6PingDestAddrType      OBJECT-TYPE
              SYNTAX  INTEGER { 
                          other (0),
                          anycast (2)
                      }
              MAX-ACCESS  read-write
              STATUS  current
              DESCRIPTION
                 "The address type of the destination to be pinged.
                  other   - unicast or linklocal address
                  anycast - anycast address .An IPv6 packet cannot have anycast
                  address as source address. So fsipv6PingDestAddrType is used
                  to distinguish the anycast destination from other
                  types."
              DEFVAL { 0 }
              ::= { fsipv6PingEntry 19 }
         
         fsipv6PingHostName   OBJECT-TYPE
              SYNTAX      OCTET STRING (SIZE (0..255))
              MAX-ACCESS  read-write
              STATUS  current
              DESCRIPTION
                 "This object specifies the DNS host name 
                  used to send echo requests."
              ::= { fsipv6PingEntry 20 }

          fsipv6PingContInterval OBJECT-TYPE
              SYNTAX      Integer32 (0..3600)
              MAX-ACCESS  read-create
              STATUS      current
              DESCRIPTION
                 "Specifies the interval for continuous ping operations.
                 A value of 0 indicates that continuous ping generation 
                 is not enabled. Other values indicate that continuous 
                 ping is enabled and that a new ping attempt (based on 
                 other entry settings) will be initiated periodically 
                 per the current interval value."

              DEFVAL { 0 }
              ::= { fsipv6PingEntry 21 }
          
-- Supoort for Proxy ND - START

--fsipv6NDProxyTable BEGIN

          fsipv6NDProxyListTable  OBJECT-TYPE
             SYNTAX   SEQUENCE OF Fsipv6NDProxyListEntry
             MAX-ACCESS   not-accessible
             STATUS   current
             DESCRIPTION       
                 "Configurable list of IPv6 Addresses for which
                  Proxy Neighbor Discovery is desired."
             ::= { fsipv6Tables 13 }


          fsipv6NDProxyListEntry  OBJECT-TYPE
              SYNTAX  Fsipv6NDProxyListEntry
             MAX-ACCESS  not-accessible
              STATUS  current
              DESCRIPTION       
                 "An entry in the ND Proxy Table. Each 
                  entry specifies the IPv6 address for
                  which proxy feature is needed, and
                  the adminstatus for the row."
             INDEX   { fsipv6NdProxyAddr }
              ::= { fsipv6NDProxyListTable 1 }


          Fsipv6NDProxyListEntry ::= SEQUENCE {
               fsipv6NdProxyAddr 
                   OCTET STRING,
               fsipv6NdProxyAdminStatus
                   INTEGER
               }

          fsipv6NdProxyAddr  OBJECT-TYPE 
              SYNTAX  OCTET STRING (SIZE (16))
              MAX-ACCESS   not-accessible
              STATUS  current
              DESCRIPTION
                  "IPv6 address for Proxy ND."
              ::= { fsipv6NDProxyListEntry 1 }

          fsipv6NdProxyAdminStatus  OBJECT-TYPE 
              SYNTAX  INTEGER  {
                          create  	(1),
                          invalid   (2)
                      }
              MAX-ACCESS  read-write
              STATUS  current
              DESCRIPTION
                  "The desired state of the ND Proxy list entry. 
                   When set to create(4) the IPv6 interface is 
                   created and invalid(4) to delete the interface."
              ::= { fsipv6NDProxyListEntry 2 }


-- Supprot for Proxy ND - END

-- Support for Address Selection Policy Table -START

-- fsipv6AddrSelPolicyTable BEGIN

   
           fsipv6AddrSelPolicyTable  OBJECT-TYPE
             SYNTAX   SEQUENCE OF Fsipv6AddrSelPolicyEntry
             MAX-ACCESS   not-accessible
             STATUS   current
             DESCRIPTION
                 "This table is used for default address selection in IPv6. This table is used to configure the Precedence
                  and Label associated with a source/destination address. The Address Selection Policy Table
                  contains the following default entries -

                  Prefix        Precedence  Label
                  ::1/128               50     0
                  ::/0                  40     1
                  2002::/16             30     2
                  ::/96                 20     3
                  ::ffff:0:0/96         10     4
                  
                 A lookup of this table aids in selection of best source/destination address from amongst a candidate list.
                 "
             ::= { fsipv6Tables 14 }


            fsipv6AddrSelPolicyEntry OBJECT-TYPE
             SYNTAX Fsipv6AddrSelPolicyEntry
             MAX-ACCESS not-accessible
             STATUS current
             DESCRIPTION
                 "This table entry is used to configure the following parameters for an IPv6 source/destination address -
                  Prefix, PrefixLen,Ifindex,Preference,Label,Address Type,IsSelfAddress, IsAddressPublic,
                  IsAddressDeprecated, ReachabilityStatus, ConfigStatus and Rowstatus"
             INDEX {
              fsipv6AddrSelPolicyPrefix,
              fsipv6AddrSelPolicyPrefixLen,
              fsipv6AddrSelPolicyIfIndex
             }
              ::= { fsipv6AddrSelPolicyTable 1 }



            Fsipv6AddrSelPolicyEntry ::= SEQUENCE {
              fsipv6AddrSelPolicyPrefix   
                 OCTET STRING,
              fsipv6AddrSelPolicyPrefixLen     
                 Integer32,
              fsipv6AddrSelPolicyIfIndex
                 InterfaceIndex,
              fsipv6AddrSelPolicyScope  
                 Integer32,
              fsipv6AddrSelPolicyPrecedence    
                 Integer32,
              fsipv6AddrSelPolicyLabel     
                 Integer32,
              fsipv6AddrSelPolicyAddrType
                 INTEGER,
              fsipv6AddrSelPolicyIsPublicAddr      
                 INTEGER,
              fsipv6AddrSelPolicyIsSelfAddr         
                 INTEGER,
              fsipv6AddrSelPolicyReachabilityStatus    
                 INTEGER,
              fsipv6AddrSelPolicyConfigStatus           
                 INTEGER,
              fsipv6AddrSelPolicyRowStatus                
                 RowStatus
            }

            fsipv6AddrSelPolicyPrefix OBJECT-TYPE
               SYNTAX OCTET STRING (SIZE (16))
               MAX-ACCESS not-accessible
               STATUS current
               DESCRIPTION
                   "The IPv6 Address/Prefix for which the policy needs to be configured."
            ::= { fsipv6AddrSelPolicyEntry 1 }


            fsipv6AddrSelPolicyPrefixLen OBJECT-TYPE
               SYNTAX Integer32 (1..128)
               MAX-ACCESS not-accessible
               STATUS current
               DESCRIPTION
                  "The Prefix length associated with the IPV6 address identified by 'fsipv6AddrSelPolicyPrefix."
            ::= { fsipv6AddrSelPolicyEntry 2 }

             
            fsipv6AddrSelPolicyIfIndex OBJECT-TYPE
               SYNTAX InterfaceIndex
               MAX-ACCESS not-accessible
               STATUS current
               DESCRIPTION
                 "The index value that uniquely identifies the interface to
                 which this entry is applicable. A value of 0 indicates that the associated address is reachable 
                 via any interface."
             ::= { fsipv6AddrSelPolicyEntry 3 }

            fsipv6AddrSelPolicyScope OBJECT-TYPE
                SYNTAX   Integer32 (0..15)
                MAX-ACCESS read-only
                STATUS   current
                DESCRIPTION
                    " This MIB object identifies the scope of the IPv6 address. This can take the following values based on
                      whether the address is unicast/anycast or multicast.
                        0  reserved
                        1  Interface-Local scope
                        2  Link-Local scope
                        3  reserved
                        4  Admin-Local scope
                        5  Site-Local scope
                        6  (unassigned)
                        7  (unassigned)
                        8  Organization-Local scope
                        9  (unassigned)
                        10  (unassigned)
                        11  (unassigned)
                        12  (unassigned)
                        13  (unassigned)
                        14  Global scope
                        15  reserved

                   Link-local and global scopes are applicable for unicast/anycast addresses.

                   The following are valid multicast scopes -
                   Interface-Local scope spans only a single interface on a node
                   and is useful only for loopback transmission of multicast.

                   Link-Local is used for uniquely identifying interfaces within a single link.

                   Admin-Local scope is the smallest scope that must be
                   administratively configured, i.e., not automatically derived
                   from physical connectivity or other, non-multicast-related
                   configuration.

                   Site-Local scope is intended to span a single site.

                   Organization-Local scope is intended to span multiple sites
                   belonging to a single organization.

                   Global scope is used for uniquely identifying interfaces anywhere in the Internet
                   scopes labeled (unassigned) are available for administrators
                   to define additional multicast regions."

               ::= { fsipv6AddrSelPolicyEntry 4 }

               fsipv6AddrSelPolicyPrecedence OBJECT-TYPE
                 SYNTAX   Integer32 (1..128)
                 MAX-ACCESS  read-write
                 STATUS   current
                 DESCRIPTION
                        "The precedence value associated with the address in the policy table. This value is applicable for
                 destination addresses.Higher the value, higher the precedence."
               DEFVAL { 30 }
               ::= { fsipv6AddrSelPolicyEntry 5 }

               fsipv6AddrSelPolicyLabel OBJECT-TYPE
                 SYNTAX   Integer32 (0..255)
                 MAX-ACCESS  read-write
                 STATUS   current
                 DESCRIPTION
                      "The label value  associated with the address in the policy table."
               DEFVAL { 2 }
                ::= { fsipv6AddrSelPolicyEntry 6}

              fsipv6AddrSelPolicyAddrType OBJECT-TYPE
                SYNTAX   INTEGER {
                            unicast(1),
                            anycast(2),
                            multicast(3)
                       }
                MAX-ACCESS   read-write
                STATUS   current
                DESCRIPTION
                        "This MIB object is used to configure an address as unicast/anycast/multicast, provided the 
                         IPv6 address meets the validation criteria for the address type."  
              ::= { fsipv6AddrSelPolicyEntry 7 }

              fsipv6AddrSelPolicyIsPublicAddr OBJECT-TYPE
                 SYNTAX  INTEGER  {
                         true             (1),
                         false            (2)
                       }
                  MAX-ACCESS  read-only
                  STATUS  current
                  DESCRIPTION
                      " This MIB object indicates whether the address configured in the policy table is a private or public
                        address."
                  ::= { fsipv6AddrSelPolicyEntry 8 }

                fsipv6AddrSelPolicyIsSelfAddr OBJECT-TYPE
                   SYNTAX  INTEGER  {
                         true             (1),
                         false            (2)
                       }
                   MAX-ACCESS  read-only
                   STATUS  current
                   DESCRIPTION
                       "This MIB object indicates whether the given address is configured on the associated interface 
                        and represents a self-address. The associated MIB object fsipv6AddrSelPolicyIfIndex takes value true
                        if the associated IPv6 address is a self-node address.."
                    ::= { fsipv6AddrSelPolicyEntry 9 }

                 fsipv6AddrSelPolicyReachabilityStatus OBJECT-TYPE
                 SYNTAX  INTEGER  {
                          reachable        (1),
                          unreachable      (2)
                      }
                 MAX-ACCESS read-only
                 STATUS     current
                 DESCRIPTION
                      "This MIB object indicates whether the address configured in the Policy Table is reachable/unreachable
                      "
                 ::= { fsipv6AddrSelPolicyEntry 10 }

               fsipv6AddrSelPolicyConfigStatus OBJECT-TYPE
                SYNTAX  INTEGER  {
                          automatic      (1),
                          management     (2)
                      }
                MAX-ACCESS read-only
                STATUS     current
                DESCRIPTION
                  "This MIB object indicates whether the associated entry in the Policy table is created automatically or
                   via the administrator."
                 ::= { fsipv6AddrSelPolicyEntry 11 }

                 fsipv6AddrSelPolicyRowStatus OBJECT-TYPE
                 SYNTAX RowStatus
                 MAX-ACCESS read-create
                 STATUS current
                 DESCRIPTION
                   "Administrative Status of the policy table. This object is used
                    to create or delete the entry in the policy table. The following values 
                    are not supported for this MIB object - CREATE_AND_GO." 
                ::= { fsipv6AddrSelPolicyEntry 12 }


-- fsipv6AddrSelPolicyTable END


-- Support for Scope Zone Interface Map Table - START

--fsipv6IfScopeZoneMapTable BEGIN

fsipv6IfScopeZoneMapTable OBJECT-TYPE
    SYNTAX     SEQUENCE OF FsIpv6IfScopeZoneMapEntry
    MAX-ACCESS not-accessible
    STATUS     current
    DESCRIPTION
           "A zone index identifies an instance of  a specific scope uniquely 
            within the system.The zone index is used to associate unambiguously 
            an IPv6 address to a specific zone.
            
            Following are the changes that has been done in fsipv6IfScopeZoneMapTable

                1) The Zone-Index which is of type InetZoneIndex in stdipvx.mib
                   is changed to DisplayString for user convenience.As the user is 
                   aware of the zones by the scope-zone name rather than the index
                   (i.e Linklocal1 or sitelocal1,scope61,scope71) it has been changed 
                   to DisplayString. But the index associated with the scope-zone is 
                   displayed by ipv6ScopeZoneIndexTable.
                2) The InetZoneIndex definition in INET-ADDRESS-MIB says that the zone-index 
                   will typically be the interface index for link-local address, but as per 
                   the design the Zone-Index is taken as a free flowing number starting 
                   from the value 1, hence the value of ipv6ScopeZoneIndexLinkLocal shall not be                                                 
                   complaint with InetZoneIndex definition.
                 3) It is also mentioned that the zone-index value of 0 refers to the default 
                   zone. But the design implements the default scope-zone index for every                                                
                   scope by the fsipv6ScopeMemberEntry mib table. Hence the default-zone index 
                   of value 0 is also not supported 
                4) The scope-zone index that are not configured on an interface shall take a
                   alpha numeric value of invalid in FsIpv6IfScopeZoneMapEntry and -1 for the 
                   index value in ipv6ScopeZoneIndexTable. "
            

    REFERENCE "Section 2.7 of RFC 4291"
    ::= { fsipv6Tables 15 }

fsipv6IfScopeZoneMapEntry OBJECT-TYPE
    SYNTAX     FsIpv6IfScopeZoneMapEntry
    MAX-ACCESS not-accessible
    STATUS     current
    DESCRIPTION
           "Each entry contains the list of scope identifiers on a given
            interface. Its a unique value assigned for each scope on an 
            interface."
    INDEX { fsipv6ScopeZoneIndexIfIndex }
    ::= { fsipv6IfScopeZoneMapTable 1 }

FsIpv6IfScopeZoneMapEntry ::= SEQUENCE {
        fsipv6ScopeZoneIndexIfIndex            InterfaceIndex,
        fsipv6ScopeZoneIndexInterfaceLocal     DisplayString,
        fsipv6ScopeZoneIndexLinkLocal          DisplayString,
        fsipv6ScopeZoneIndex3                  DisplayString,
        fsipv6ScopeZoneIndexAdminLocal         DisplayString,
        fsipv6ScopeZoneIndexSiteLocal          DisplayString,
        fsipv6ScopeZoneIndex6                  DisplayString,
        fsipv6ScopeZoneIndex7                  DisplayString,
        fsipv6ScopeZoneIndexOrganizationLocal  DisplayString,
        fsipv6ScopeZoneIndex9                  DisplayString,
        fsipv6ScopeZoneIndexA                  DisplayString,
        fsipv6ScopeZoneIndexB                  DisplayString,
        fsipv6ScopeZoneIndexC                  DisplayString,
        fsipv6ScopeZoneIndexD                  DisplayString,
        fsipv6ScopeZoneIndexE                  DisplayString,
        fsipv6IfScopeZoneCreationStatus            INTEGER,
        fsipv6IfScopeZoneRowStatus               RowStatus
    }

fsipv6ScopeZoneIndexIfIndex OBJECT-TYPE
    SYNTAX     InterfaceIndex
    MAX-ACCESS not-accessible
    STATUS     current
    DESCRIPTION
           "The index value that uniquely identifies the interface to
            which these scopes belong.  The interface identified by a
            particular value of this index is the same interface as
            identified by the same value of the IF-MIB's ifIndex."
    DEFVAL  { "Invalid" }
    ::= { fsipv6IfScopeZoneMapEntry 1 }

fsipv6ScopeZoneIndexInterfaceLocal OBJECT-TYPE
    SYNTAX     DisplayString
    MAX-ACCESS read-write
    STATUS     current
    DESCRIPTION
           "The zone index for the Interface local scope on this interface."
    DEFVAL  { "Invalid" }
    ::= { fsipv6IfScopeZoneMapEntry 2 }

fsipv6ScopeZoneIndexLinkLocal OBJECT-TYPE
    SYNTAX     DisplayString
    MAX-ACCESS read-write
    STATUS     current
    DESCRIPTION
           "The zone index for the link-local scope on this interface.
            The index value corresponding to this scope-zone can be known from
            ipv6ScopeZoneIndexLinkLocal"
    DEFVAL  { "Invalid" }
    ::= { fsipv6IfScopeZoneMapEntry 3 }

fsipv6ScopeZoneIndex3 OBJECT-TYPE
    SYNTAX     DisplayString
    MAX-ACCESS read-write
    STATUS     current
    DESCRIPTION
           "The zone index for scope 3 on this interface.  The index value corresponding 
            to this scope-zone can be known from ipv6ScopeZoneIndex3"
    DEFVAL  { "Invalid" }
    ::= { fsipv6IfScopeZoneMapEntry 4 }

fsipv6ScopeZoneIndexAdminLocal OBJECT-TYPE
    SYNTAX     DisplayString
    MAX-ACCESS read-write
    STATUS     current
    DESCRIPTION
           "The zone index for the admin-local scope on this interface.The index value 
            corresponding to this scope-zone can be known from ipv6ScopeZoneIndexAdminLocal"
    DEFVAL  { "Invalid" }
    ::= { fsipv6IfScopeZoneMapEntry 5 }

fsipv6ScopeZoneIndexSiteLocal OBJECT-TYPE
    SYNTAX     DisplayString
    MAX-ACCESS read-write
    STATUS     current
    DESCRIPTION
           "The zone index for the site-local scope on this interface.The index value
            corresponding to this scope-zone can be known from ipv6ScopeZoneIndexSiteLocal "
    DEFVAL  { "Invalid" }
    ::= { fsipv6IfScopeZoneMapEntry 6 }

fsipv6ScopeZoneIndex6 OBJECT-TYPE
    SYNTAX     DisplayString
    MAX-ACCESS read-write
    STATUS     current
    DESCRIPTION
           "The zone index for scope 6 on this interface.The index value
            corresponding to this scope-zone can be known from ipv6ScopeZoneIndex6 "
    DEFVAL  { "Invalid" }
    ::= { fsipv6IfScopeZoneMapEntry 7 }

fsipv6ScopeZoneIndex7 OBJECT-TYPE
    SYNTAX     DisplayString
    MAX-ACCESS read-write
    STATUS     current
    DESCRIPTION
           "The zone index for scope 7 on this interface.The index value
            corresponding to this scope-zone can be known from ipv6ScopeZoneIndex7"
    DEFVAL  { "Invalid" }
    ::= { fsipv6IfScopeZoneMapEntry 8 }

fsipv6ScopeZoneIndexOrganizationLocal OBJECT-TYPE
    SYNTAX     DisplayString
    MAX-ACCESS read-write
    STATUS     current
    DESCRIPTION
           "The zone index for the organization-local scope on this
            interface.The index value corresponding to this scope-zone 
            can be known from ipv6ScopeZoneIndexOrganizationLocal"
    DEFVAL  { "Invalid" }
    ::= { fsipv6IfScopeZoneMapEntry 9 }

fsipv6ScopeZoneIndex9 OBJECT-TYPE
    SYNTAX     DisplayString
    MAX-ACCESS read-write
    STATUS     current
    DESCRIPTION
           "The zone index for scope 9 on this interface.The index value
            corresponding to this scope-zone can be known from 
            ipv6ScopeZoneIndex9"
    DEFVAL  { "Invalid" }
    ::= { fsipv6IfScopeZoneMapEntry 10 }

fsipv6ScopeZoneIndexA OBJECT-TYPE
    SYNTAX     DisplayString
    MAX-ACCESS read-write
    STATUS     current
    DESCRIPTION
           "The zone index for scope A on this interface.The index value
            corresponding to this scope-zone can be known from 
            ipv6ScopeZoneIndexA"
    DEFVAL  { "Invalid" }
    ::= { fsipv6IfScopeZoneMapEntry 11 }

fsipv6ScopeZoneIndexB OBJECT-TYPE
    SYNTAX     DisplayString
    MAX-ACCESS read-write
    STATUS     current
    DESCRIPTION
           "The zone index for scope B on this interface.The index value
            corresponding to this scope-zone can be known from 
            ipv6ScopeZoneIndexB"
    DEFVAL  { "Invalid" }
    ::= { fsipv6IfScopeZoneMapEntry 12 }

fsipv6ScopeZoneIndexC OBJECT-TYPE
    SYNTAX     DisplayString
    MAX-ACCESS read-write
    STATUS     current
    DESCRIPTION
           "The zone index for scope C on this interface.The index value
            corresponding to this scope-zone can be known from 
            ipv6ScopeZoneIndexC"
    DEFVAL  { "Invalid" }
    ::= { fsipv6IfScopeZoneMapEntry 13 }

fsipv6ScopeZoneIndexD OBJECT-TYPE
    SYNTAX     DisplayString
    MAX-ACCESS read-write
    STATUS     current
    DESCRIPTION
           "The zone index for scope D on this interface.The index value
            corresponding to this scope-zone can be known from 
            ipv6ScopeZoneIndexD"
    DEFVAL  { "Invalid" }
    ::= { fsipv6IfScopeZoneMapEntry 14 }
 
fsipv6ScopeZoneIndexE OBJECT-TYPE
    SYNTAX     DisplayString
    MAX-ACCESS read-write
    STATUS     current
    DESCRIPTION
           "The zone index for scope E on this interface."
    DEFVAL  { "Invalid" }
    ::= { fsipv6IfScopeZoneMapEntry 15 }

fsipv6IfScopeZoneCreationStatus OBJECT-TYPE
    SYNTAX  INTEGER {
               notcreated(0),
               automatic(1),
                mgmt(2),
                overridden(3)
              }
    MAX-ACCESS     read-only
    STATUS     current
    DESCRIPTION
       "Flag to determine if the scope-zone index is configured automatically
       or by configuration.When an IPv6 interface is created by default the
       linklocal scope is created and the creation status of it is automatic.When
       a user creates a scope-zone the creation status is updated as manual.When
       an indication is receievd from higher layer protocol regarding the detection
       of interfaces on the same link, in that case whatever might be the configuration
       status (i.e automatic or manual) is changed to overridden. It means if the
       scope-zone on the standby links if its automatic or manually created both will
       be over-ridden and configured with the scope-zone of the active link"
    DEFVAL  { notcreated }
    ::= { fsipv6IfScopeZoneMapEntry 16 }

fsipv6IfScopeZoneRowStatus OBJECT-TYPE
    SYNTAX     RowStatus 
    MAX-ACCESS read-create
    STATUS     current
    DESCRIPTION 
          "The rowstatus of the scope-zone index table, used in 
           accordance to creation and deletion of scope-zones.To create
           a row in this table manager sets this object to createAndGo(4).
           The rowentry can be deleted automatically only when the creation 
           status is set to auto,else the rowstatus is set to NotInService. "
    ::= { fsipv6IfScopeZoneMapEntry 17 }

-- Support for Scope-Zone   - END 

-- Support for Scope-Zone Table - START

--fsipv6ScopeZoneTable BEGIN

fsipv6ScopeZoneTable OBJECT-TYPE
    SYNTAX     SEQUENCE OF FsIpv6ScopeZoneEntry
    MAX-ACCESS not-accessible
    STATUS     current
    DESCRIPTION
            " The table is used to map each scope-zone index 
              with the interface to which it has been associated.
              This table is indeed used while forwarding packets 
              to find out what all interfaces belong to a particular 
              scope-zone"
    ::= { fsipv6Tables 16 }

fsipv6ScopeZoneEntry OBJECT-TYPE
    SYNTAX     FsIpv6ScopeZoneEntry
    MAX-ACCESS not-accessible
    STATUS     current
    DESCRIPTION
            "An entry in the Scope-Zone Index Member Table.Each
             entry specifies the interface indices associated with 
             a particular scope-zone index "
    INDEX   { fsipv6ScopeZoneName }
     ::= { fsipv6ScopeZoneTable 1 }

FsIpv6ScopeZoneEntry ::= SEQUENCE {
	fsipv6ScopeZoneName                    DisplayString,
        fsipv6ScopeZoneIndex                   InetZoneIndex,
        fsipv6ScopeZoneCreationStatus          INTEGER,
        fsipv6ScopeZoneInterfaceList           InterfaceList,
        fsipv6IsDefaultScopeZone               INTEGER
 }

fsipv6ScopeZoneName OBJECT-TYPE
    SYNTAX     DisplayString
    MAX-ACCESS not-accessible
    STATUS     current
    DESCRIPTION
           " Displays the scope zone name value(i.e linklocal1,
             interfacelocal2) for the scope-zone index"
    ::= { fsipv6ScopeZoneEntry 1 }

fsipv6ScopeZoneIndex OBJECT-TYPE
    SYNTAX     InetZoneIndex 
    MAX-ACCESS read-only
    STATUS     current
    DESCRIPTION
           "A unique value for each scope
            on an interface. It is recommended that values are
            assigned contiguously starting from 1. "
    ::= { fsipv6ScopeZoneEntry 2 }

fsipv6ScopeZoneCreationStatus OBJECT-TYPE
    SYNTAX  INTEGER {
                automatic(1),
                mgmt(2),
                overridden(3)
              }
    MAX-ACCESS read-only
    STATUS     current
    DESCRIPTION
       "Flag to determine if the scope-zone index is configured automatically
       or by configuration.When an IPv6 interface is created by default the
       linklocal scope is created and the creation status of it is automatic.When
       a user creates a scope-zone the creation status is updated as manual.When
       an indication is receievd from higher layer protocol regarding the detection
       of interfaces on the same link, in that case whatever might be the configuration
       status (i.e automatic or manual) is changed to overridden. It means if the  
       scope-zone on the standby links is overridden by the scope-zone of the active 
       link regardless Of whether the associated zone is created manually/automatically"
    ::= { fsipv6ScopeZoneEntry 3 }

fsipv6ScopeZoneInterfaceList OBJECT-TYPE
    SYNTAX     InterfaceList 
    MAX-ACCESS read-only
    STATUS     current
    DESCRIPTION
           " This MIB object displays all the interfaces that are part of/members of this 
             scope-zone index. These interfaces have the corresponding bit set in the octetlist. "
    ::= { fsipv6ScopeZoneEntry 4 }

fsipv6IsDefaultScopeZone OBJECT-TYPE
    SYNTAX     INTEGER {
                 yes(1),
                 no(2)
               }
    MAX-ACCESS read-write
    STATUS     current
    DESCRIPTION
           " yes- indicates that zone is default zone for the associated scope
             No - indicates that zone is not the default zone for the associated scope"
    DEFVAL { no }
    ::= { fsipv6ScopeZoneEntry 5 }


--fsipv6ScopeZoneTable END

-- fsipv6SENDSentPktStatsTable BEGIN

    -- IPv6 SEND Sent Packet statistics

    fsipv6SENDSentPktStatsTable OBJECT-TYPE
    SYNTAX      SEQUENCE OF Fsipv6SENDSentPktStatsEntry
    MAX-ACCESS  not-accessible
    STATUS      current
    DESCRIPTION
    "This table contains the sent packet statistics in Secure Neighbor Discovery."
    ::= { fsipv6Tables 17 }

    fsipv6SENDSentPktStatsEntry OBJECT-TYPE
    SYNTAX      Fsipv6SENDSentPktStatsEntry
    MAX-ACCESS  not-accessible
    STATUS      current
    DESCRIPTION
    "This object displays the statistics about a particular type of packet in Secure Neighbor Discovery"
    INDEX   { fsipv6IfIndex, fsipv6SENDSentPktType }
    ::= {  fsipv6SENDSentPktStatsTable 1 }

    Fsipv6SENDSentPktStatsEntry ::=
    SEQUENCE {
        fsipv6SENDSentPktType           INTEGER,
        fsipv6SENDSentCgaOptPkts            Counter32,
        fsipv6SENDSentCertOptPkts           Counter32,
        fsipv6SENDSentMtuOptPkts            Counter32,
        fsipv6SENDSentNonceOptPkts          Counter32,
        fsipv6SENDSentPrefixOptPkts         Counter32,
        fsipv6SENDSentRedirHdrPkts          Counter32,
        fsipv6SENDSentRsaOptPkts            Counter32,
        fsipv6SENDSentSrcLinkAddrPkts       Counter32,
        fsipv6SENDSentTgtLinkAddrPkts       Counter32,
        fsipv6SENDSentTaOptPkts             Counter32,
        fsipv6SENDSentTimeStampOptPkts      Counter32
        
    }

    fsipv6SENDSentPktType OBJECT-TYPE
    SYNTAX      INTEGER {
                            ns (1),
                            na (2),
                            rs (3),
                            ra (4),
                            rd (5),
                            cps (6),
                            cpa (7)
    }
    MAX-ACCESS  not-accessible
    STATUS      current
    DESCRIPTION
    "This object displays the sent packet type in Secure Neighbor Discovery.
     The options include;
     1 indicates Neighbor Solicitation is set
     2 indicates Neighbor Advertisement is set
     3 indicates Router Solicitation is set
     4 indicates Router Advertisement is set
     5 indicates Redirect Message is set
     6 indicates Certificate Path Solicitation is set
     7 indicates Certificate Path Advertisement is set"
    ::= { fsipv6SENDSentPktStatsEntry 1 }

    fsipv6SENDSentCgaOptPkts OBJECT-TYPE
    SYNTAX      Counter32
    MAX-ACCESS  read-only
    STATUS      current
    DESCRIPTION
    "This object displays the number of packets sent with CGA Option"
    ::= { fsipv6SENDSentPktStatsEntry 2 }
    
    fsipv6SENDSentCertOptPkts OBJECT-TYPE
    SYNTAX      Counter32
    MAX-ACCESS  read-only 
    STATUS      current
    DESCRIPTION
    "This object displays the number of packets sent with Certificate Option"
    ::= { fsipv6SENDSentPktStatsEntry 3 }
    
    fsipv6SENDSentMtuOptPkts OBJECT-TYPE
    SYNTAX      Counter32
    MAX-ACCESS  read-only 
    STATUS      current
    DESCRIPTION
    "This object displays the number of packets sent with MTU option "
    ::= { fsipv6SENDSentPktStatsEntry 4 }
    
    fsipv6SENDSentNonceOptPkts OBJECT-TYPE
    SYNTAX      Counter32
    MAX-ACCESS  read-only 
    STATUS      current
    DESCRIPTION
    "This object displays the number of packets sent with Nonce Option "
    ::= { fsipv6SENDSentPktStatsEntry 5 }
    
    fsipv6SENDSentPrefixOptPkts OBJECT-TYPE
    SYNTAX      Counter32
    MAX-ACCESS  read-only 
    STATUS      current
    DESCRIPTION
    "This object displays the number of packets sent with Prefix Option "
    ::= { fsipv6SENDSentPktStatsEntry 6 }
    
    fsipv6SENDSentRedirHdrPkts OBJECT-TYPE
    SYNTAX      Counter32
    MAX-ACCESS  read-only 
    STATUS      current
    DESCRIPTION
    "This object displays the number of packets sent with Redirect Header Option"
    ::= { fsipv6SENDSentPktStatsEntry 7 }
    
    fsipv6SENDSentRsaOptPkts OBJECT-TYPE
    SYNTAX      Counter32
    MAX-ACCESS  read-only 
    STATUS      current
    DESCRIPTION
    "This object displays the number of packets sent with RSA Option"
    ::= { fsipv6SENDSentPktStatsEntry 8 }
    
    fsipv6SENDSentSrcLinkAddrPkts OBJECT-TYPE
    SYNTAX      Counter32
    MAX-ACCESS  read-only 
    STATUS      current
    DESCRIPTION
    "This object displays the number of packets sent with Source LinkLayer Address"
    ::= { fsipv6SENDSentPktStatsEntry 9 }
    
    fsipv6SENDSentTgtLinkAddrPkts OBJECT-TYPE
    SYNTAX      Counter32
    MAX-ACCESS  read-only 
    STATUS      current
    DESCRIPTION
    "This object displays the number of packets sent with Target LinkLayer Address "
    ::= { fsipv6SENDSentPktStatsEntry 10 }
    
    fsipv6SENDSentTaOptPkts OBJECT-TYPE
    SYNTAX      Counter32
    MAX-ACCESS  read-only 
    STATUS      current
    DESCRIPTION
    "This object displays the number of packets sent with Trust Anchor Option"
    ::= { fsipv6SENDSentPktStatsEntry 11 }
    
    fsipv6SENDSentTimeStampOptPkts OBJECT-TYPE
    SYNTAX      Counter32
    MAX-ACCESS  read-only 
    STATUS      current
    DESCRIPTION
    "This object displays the number of packets sent with TimeStamp Option"
    ::= { fsipv6SENDSentPktStatsEntry 12 }
    
-- fsipv6SENDSentPktStatsTable END

-- fsipv6SENDRcvPktStatsTable BEGIN

    -- IPv6 SEND Received Packet Statistics

    fsipv6SENDRcvPktStatsTable OBJECT-TYPE
    SYNTAX      SEQUENCE OF Fsipv6SENDRcvPktStatsEntry
    MAX-ACCESS  not-accessible
    STATUS      current
    DESCRIPTION
    "This table contains the received packet statistics in Secure Neighbor Discovery."
    ::= { fsipv6Tables 18 }

    fsipv6SENDRcvPktStatsEntry OBJECT-TYPE
    SYNTAX      Fsipv6SENDRcvPktStatsEntry
    MAX-ACCESS  not-accessible
    STATUS      current
    DESCRIPTION
    "This object displays the statistics about a particular type of packet in Secure Neighbor Discovery"
    INDEX   { fsipv6IfIndex, fsipv6SENDRcvPktType }
    ::= {  fsipv6SENDRcvPktStatsTable 1 }

    Fsipv6SENDRcvPktStatsEntry ::=
    SEQUENCE {
        fsipv6SENDRcvPktType            INTEGER,
        fsipv6SENDRcvCgaOptPkts             Counter32,
        fsipv6SENDRcvCertOptPkts            Counter32,
        fsipv6SENDRcvMtuOptPkts             Counter32,
        fsipv6SENDRcvNonceOptPkts           Counter32, 
        fsipv6SENDRcvPrefixOptPkts          Counter32,
        fsipv6SENDRcvRedirHdrPkts           Counter32,
        fsipv6SENDRcvRsaOptPkts            Counter32,
        fsipv6SENDRcvSrcLinkAddrPkts        Counter32,
        fsipv6SENDRcvTgtLinkAddrPkts        Counter32,
        fsipv6SENDRcvTaOptPkts              Counter32,
        fsipv6SENDRcvTimeStampOptPkts       Counter32
        
    }

    fsipv6SENDRcvPktType OBJECT-TYPE
    SYNTAX      INTEGER {
                            ns (1),
                            na (2),
                            rs (3),
                            ra (4),
                            rd (5),
                            cps (6),
                            cpa (7)
    }
    MAX-ACCESS  not-accessible
    STATUS      current
    DESCRIPTION
    "This object displays the received packet type in Secure Neighbor Discovery
     1 indicates Neighbor Solicitation is set
     2 indicates Neighbor Advertisement is set
     3 indicates Router Solicitation is set
     4 indicates Router Advertisement is set
     5 indicates Redirect Message is set
     6 indicates Certificate Path Solicitation is set
     7 indicates Certificate Path Advertisement is set"
    ::= { fsipv6SENDRcvPktStatsEntry 1 }

    fsipv6SENDRcvCgaOptPkts OBJECT-TYPE
    SYNTAX      Counter32
    MAX-ACCESS  read-only 
    STATUS      current
    DESCRIPTION
    "This object displays the number of packets received with CGA Option"
    ::= { fsipv6SENDRcvPktStatsEntry 2 }
    
    fsipv6SENDRcvCertOptPkts OBJECT-TYPE
    SYNTAX      Counter32
    MAX-ACCESS  read-only 
    STATUS      current
    DESCRIPTION
    "This object displays the number of packets received with Certificate Option"
    ::= { fsipv6SENDRcvPktStatsEntry 3 }
    
    fsipv6SENDRcvMtuOptPkts OBJECT-TYPE
    SYNTAX      Counter32
    MAX-ACCESS  read-only 
    STATUS      current
    DESCRIPTION
    "This object displays the number of packets received with MTU option "
    ::= { fsipv6SENDRcvPktStatsEntry 4 }
    
    fsipv6SENDRcvNonceOptPkts OBJECT-TYPE
    SYNTAX      Counter32
    MAX-ACCESS  read-only 
    STATUS      current
    DESCRIPTION
    "This object displays the number of packets received with Nonce Option "
    ::= { fsipv6SENDRcvPktStatsEntry 5 }
    
    
    fsipv6SENDRcvPrefixOptPkts OBJECT-TYPE
    SYNTAX      Counter32
    MAX-ACCESS  read-only 
    STATUS      current
    DESCRIPTION
    "This object displays the number of packets received with Prefix Option "
    ::= { fsipv6SENDRcvPktStatsEntry 6 }
    
    fsipv6SENDRcvRedirHdrPkts OBJECT-TYPE
    SYNTAX      Counter32
    MAX-ACCESS  read-only 
    STATUS      current
    DESCRIPTION
    "This object displays the number of packets received with Redirect Header Option"
    ::= { fsipv6SENDRcvPktStatsEntry 7 }
    
    fsipv6SENDRcvRsaOptPkts OBJECT-TYPE
    SYNTAX      Counter32
    MAX-ACCESS  read-only 
    STATUS      current
    DESCRIPTION
    "This object displays the number of packets received with RSA Option"
    ::= { fsipv6SENDRcvPktStatsEntry 8 }
    
    fsipv6SENDRcvSrcLinkAddrPkts OBJECT-TYPE
    SYNTAX      Counter32
    MAX-ACCESS  read-only 
    STATUS      current
    DESCRIPTION
    "This object displays the number of packets received with Source LinkLayer Address"
    ::= { fsipv6SENDRcvPktStatsEntry 9 }
    
    fsipv6SENDRcvTgtLinkAddrPkts OBJECT-TYPE
    SYNTAX      Counter32
    MAX-ACCESS  read-only
    STATUS      current
    DESCRIPTION
    "This object displays the number of packets received with Target LinkLayer Address "
    ::= { fsipv6SENDRcvPktStatsEntry 10 }
    
    fsipv6SENDRcvTaOptPkts OBJECT-TYPE
    SYNTAX      Counter32
    MAX-ACCESS  read-only 
    STATUS      current
    DESCRIPTION
    "This object displays the number of packets recieved with Trust Anchor Option"
    ::= { fsipv6SENDRcvPktStatsEntry 11 }
    
    fsipv6SENDRcvTimeStampOptPkts OBJECT-TYPE
    SYNTAX      Counter32
    MAX-ACCESS  read-only 
    STATUS      current
    DESCRIPTION
    "This object displays the number of packets received with TimeStamp Option"
    ::= { fsipv6SENDRcvPktStatsEntry 12 }

-- fsipv6SENDRcvPktStatsTable END

-- fsipv6SentDrpPktStatsTable BEGIN

    --IPv6 SEND Dropped Packets Statistics

    fsipv6SENDDrpPktStatsTable OBJECT-TYPE
    SYNTAX      SEQUENCE OF Fsipv6SENDDrpPktStatsEntry
    MAX-ACCESS  not-accessible
    STATUS      current
    DESCRIPTION
    "This table contains the Dropped packet statistics in Secure Neighbor Discovery."
    ::= { fsipv6Tables 19 }

    fsipv6SENDDrpPktStatsEntry OBJECT-TYPE
    SYNTAX      Fsipv6SENDDrpPktStatsEntry
    MAX-ACCESS  not-accessible
    STATUS      current
    DESCRIPTION
    "This entry displays the statistics about a particular type of packet in Secure Neighbor Discovery"
    INDEX   { fsipv6IfIndex, fsipv6SENDDrpPktType }
    ::= {  fsipv6SENDDrpPktStatsTable 1 }

    Fsipv6SENDDrpPktStatsEntry ::=
    SEQUENCE {
        fsipv6SENDDrpPktType            INTEGER,
        fsipv6SENDDrpCgaOptPkts             Counter32,
        fsipv6SENDDrpCertOptPkts            Counter32,
        fsipv6SENDDrpMtuOptPkts             Counter32,
        fsipv6SENDDrpNonceOptPkts           Counter32,
        fsipv6SENDDrpPrefixOptPkts          Counter32,
        fsipv6SENDDrpRedirHdrPkts           Counter32,
        fsipv6SENDDrpRsaOptPkts             Counter32,
        fsipv6SENDDrpSrcLinkAddrPkts        Counter32,
        fsipv6SENDDrpTgtLinkAddrPkts        Counter32,
        fsipv6SENDDrpTaOptPkts              Counter32,
        fsipv6SENDDrpTimeStampOptPkts       Counter32
        
    }

    fsipv6SENDDrpPktType OBJECT-TYPE
    SYNTAX      INTEGER {
                            ns (1),
                            na (2),
                            rs (3),
                            ra (4),
                            rd (5),
                            cps (6),
                            cpa (7)
    }
    MAX-ACCESS  not-accessible
    STATUS      current
    DESCRIPTION
    "This object specifies the dropped packet type in Secure Neighbor Discovery.
     The options include;
     1 indicates Neighbor Solicitation is set
     2 indicates Neighbor Advertisement is set
     3 indicates Router Solicitation is set 
     4 indicates Router Advertisement is set 
     5 indicates Redirect Message is set
     6 indicates Certificate Path Solicitation is set
     7 indicates Certificate Path Advertisement is set"
    ::= { fsipv6SENDDrpPktStatsEntry 1 }

    fsipv6SENDDrpCgaOptPkts OBJECT-TYPE
    SYNTAX      Counter32
    MAX-ACCESS  read-only 
    STATUS      current
    DESCRIPTION
    "This object displays the number of packets dropped with CGA Option"
    ::= { fsipv6SENDDrpPktStatsEntry 2 }
    
    fsipv6SENDDrpCertOptPkts OBJECT-TYPE
    SYNTAX      Counter32
    MAX-ACCESS  read-only 
    STATUS      current
    DESCRIPTION
    "This object displays the number of packets dropped with Certificate Option"
    ::= { fsipv6SENDDrpPktStatsEntry 3 }
    
    fsipv6SENDDrpMtuOptPkts OBJECT-TYPE
    SYNTAX      Counter32
    MAX-ACCESS  read-only 
    STATUS      current
    DESCRIPTION
    "This object displays the number of packets dropped with MTU option "
    ::= { fsipv6SENDDrpPktStatsEntry 4 }
    
    fsipv6SENDDrpNonceOptPkts OBJECT-TYPE
    SYNTAX      Counter32
    MAX-ACCESS  read-only 
    STATUS      current
    DESCRIPTION
    "This object displays the number of packets dropped with Nonce Option "
    ::= { fsipv6SENDDrpPktStatsEntry 5 }
    
    
    fsipv6SENDDrpPrefixOptPkts OBJECT-TYPE
    SYNTAX      Counter32
    MAX-ACCESS  read-only 
    STATUS      current
    DESCRIPTION
    "This object displays the number of packets dropped with Prefix Option "
    ::= { fsipv6SENDDrpPktStatsEntry 6 }
    
    fsipv6SENDDrpRedirHdrPkts OBJECT-TYPE
    SYNTAX      Counter32
    MAX-ACCESS  read-only 
    STATUS      current
    DESCRIPTION
    "This object displays the number of packets dropped with Redirect Header Option"
    ::= { fsipv6SENDDrpPktStatsEntry 7 }
    
    fsipv6SENDDrpRsaOptPkts OBJECT-TYPE
    SYNTAX      Counter32
    MAX-ACCESS  read-only 
    STATUS      current
    DESCRIPTION
    "This object displays the number of packets dropped with RSA Option"
    ::= { fsipv6SENDDrpPktStatsEntry 8 }
    
    fsipv6SENDDrpSrcLinkAddrPkts OBJECT-TYPE
    SYNTAX      Counter32
    MAX-ACCESS  read-only 
    STATUS      current
    DESCRIPTION
    "This object displays the number of packets dropped with Source LinkLayer Address"
    ::= { fsipv6SENDDrpPktStatsEntry 9 }
    
    fsipv6SENDDrpTgtLinkAddrPkts OBJECT-TYPE
    SYNTAX      Counter32 
    MAX-ACCESS  read-only 
    STATUS      current
    DESCRIPTION
    "This object displays the number of packets dropped with Target LinkLayer Address "
    ::= { fsipv6SENDDrpPktStatsEntry 10 }
    
    fsipv6SENDDrpTaOptPkts OBJECT-TYPE
    SYNTAX      Counter32
    MAX-ACCESS  read-only 
    STATUS      current
    DESCRIPTION
    "This object displays the number of packets dropped with Trust Anchor Option"
    ::= { fsipv6SENDDrpPktStatsEntry 11 }
    
    fsipv6SENDDrpTimeStampOptPkts OBJECT-TYPE
    SYNTAX      Counter32
    MAX-ACCESS  read-only 
    STATUS      current
    DESCRIPTION
    "This object displays the number of packets dropped with TimeStamp Option"
    ::= { fsipv6SENDDrpPktStatsEntry 12 }

-- fsipv6SENDDrpPktStatsTable END

-- RFC 4191 Default router preference 
-- RouteInfo Table begins 

          fsipv6RARouteInfoTable   OBJECT-TYPE
              SYNTAX   SEQUENCE OF Fsipv6RARouteInfoEntry
              MAX-ACCESS   not-accessible
              STATUS   current
              DESCRIPTION
                 "This table contains the information about the more specific route which 
		  are advertised through route information option in router 
		  advertisement message."
              ::= { fsipv6Tables 20 }

          fsipv6RARouteInfoEntry OBJECT-TYPE
              SYNTAX  Fsipv6RARouteInfoEntry
              MAX-ACCESS   not-accessible
              STATUS   current
              DESCRIPTION
                 "The entry in the IPv6 Address specific route information Table 
                  which defines a route to be advertised in the router advertisement 
                  message send on an IPv6 interface."
              INDEX  {fsipv6RARouteIfIndex,
                      fsipv6RARoutePrefix,
                      fsipv6RARoutePrefixLen
                     }
              ::= { fsipv6RARouteInfoTable 1 }

          Fsipv6RARouteInfoEntry ::=
              SEQUENCE {
                 fsipv6RARouteIfIndex
                     InterfaceIndex,
                 fsipv6RARoutePrefix
                     OCTET STRING,
                 fsipv6RARoutePrefixLen
                     Integer32,
                 fsipv6RARoutePreference
                     INTEGER,
                 fsipv6RARouteLifetime
                     Unsigned32,
                 fsipv6RARouteRowStatus
                     RowStatus 
              }

          fsipv6RARouteIfIndex OBJECT-TYPE
              SYNTAX   InterfaceIndex
              MAX-ACCESS  not-accessible
              STATUS   current
              DESCRIPTION
                 "The index value which uniquely identifies the IPv6
                 interface on which this route information entry is
                 to be advertised. The interface identified by a
                 particular value of this index is the same interface
                 as identified by the same value of fsipv6IfIndex."
              ::= { fsipv6RARouteInfoEntry 1 }


          fsipv6RARoutePrefix OBJECT-TYPE
              SYNTAX   OCTET STRING (SIZE (16))
              MAX-ACCESS   not-accessible
              STATUS   current
              DESCRIPTION
                 "The IPv6 specific route to which this entry's route 
                  information pertains."
              ::= { fsipv6RARouteInfoEntry 2 }


          fsipv6RARoutePrefixLen OBJECT-TYPE
              SYNTAX   Integer32 (0..128)
              MAX-ACCESS  not-accessible
              STATUS   current
              DESCRIPTION
                 "The length of the prefix (in bits) associated with
                 the IPv6 address prefix of this entry."
              ::= { fsipv6RARouteInfoEntry 3 }

          fsipv6RARoutePreference OBJECT-TYPE
              SYNTAX   INTEGER {
                           low(0),
                           medium(1),
                           high(2)
                       }
              MAX-ACCESS   read-write 
              STATUS   current
              DESCRIPTION
                 "The preference value of this route information
                  entry."
	      DEFVAL { medium }
              ::= { fsipv6RARouteInfoEntry 4 }

          fsipv6RARouteLifetime OBJECT-TYPE
              SYNTAX   Unsigned32 (0..4294967295)
              MAX-ACCESS   read-write
              STATUS   current
              DESCRIPTION
                 "The Lifetime of this route information entry"
              DEFVAL { 4294967295 }
              ::= { fsipv6RARouteInfoEntry 5 }

          fsipv6RARouteRowStatus OBJECT-TYPE
              SYNTAX            RowStatus
              MAX-ACCESS   read-create
              STATUS   current
              DESCRIPTION
                "This object is used to create or delete the entry in the RARouteTable"
              ::= { fsipv6RARouteInfoEntry 6 }

-- RouteInfo Table ends
-- fsipv6Tables END

         -- IPv6 ICMP statistics


         fsipv6IcmpInMsgs OBJECT-TYPE
             SYNTAX     Counter32
             MAX-ACCESS     read-only
             STATUS     current
             DESCRIPTION
                 "The total number of ICMP messages which
                 the entity received.  Note that this counter
                 includes all those counted by fsipv6IcmpInErrors."
             ::= { fsipv6Icmp 1 }


         fsipv6IcmpInErrors OBJECT-TYPE
             SYNTAX     Counter32
             MAX-ACCESS     read-only
             STATUS     current
             DESCRIPTION
              "The number of ICMP messages which the entity
              received but determined as having ICMP-specific
              errors (bad ICMP checksums, bad length, etc.)."
             ::= { fsipv6Icmp 2 }


         fsipv6IcmpInDestUnreachs OBJECT-TYPE
             SYNTAX     Counter32
             MAX-ACCESS     read-only
             STATUS     current
             DESCRIPTION
              "The number of ICMP Destination Unreachable
              messages received."
             ::= { fsipv6Icmp 3 }


         fsipv6IcmpInTimeExcds OBJECT-TYPE
             SYNTAX     Counter32
             MAX-ACCESS     read-only
             STATUS     current
             DESCRIPTION
              "The number of ICMP Time Exceeded messages
               received."
             ::= { fsipv6Icmp 4 }


         fsipv6IcmpInParmProbs OBJECT-TYPE
             SYNTAX     Counter32
             MAX-ACCESS     read-only
             STATUS     current
             DESCRIPTION
              "The number of ICMP Parameter Problem messages
               received."
             ::= { fsipv6Icmp 5 }


         fsipv6IcmpInPktTooBigs OBJECT-TYPE
             SYNTAX     Counter32
             MAX-ACCESS     read-only
             STATUS     current
             DESCRIPTION
              "The number of ICMP Packet Too Big messages
              received."
             ::= { fsipv6Icmp 6 }


         fsipv6IcmpInEchos OBJECT-TYPE
             SYNTAX     Counter32
             MAX-ACCESS     read-only
             STATUS     current
             DESCRIPTION
              "The number of ICMP Echo (request) messages
               received."
             ::= { fsipv6Icmp 7 }


         fsipv6IcmpInEchoReps OBJECT-TYPE
             SYNTAX     Counter32
             MAX-ACCESS     read-only
             STATUS     current
             DESCRIPTION
              "The number of ICMP Echo Reply messages received."
             ::= { fsipv6Icmp 8 }


         fsipv6IcmpInRouterSolicits OBJECT-TYPE
             SYNTAX     Counter32
             MAX-ACCESS     read-only
             STATUS     current
             DESCRIPTION
              "The number of ICMP Router Solicit messages
               received."
             ::= { fsipv6Icmp 9 }


         fsipv6IcmpInRouterAdvertisements OBJECT-TYPE
             SYNTAX     Counter32
             MAX-ACCESS     read-only
             STATUS     current
             DESCRIPTION
              "The number of ICMP Router Advertisement messages
              received."
             ::= { fsipv6Icmp 10 }


         fsipv6IcmpInNeighborSolicits OBJECT-TYPE
             SYNTAX     Counter32
             MAX-ACCESS     read-only
             STATUS     current
             DESCRIPTION
              "The number of ICMP Neighbor Solicit messages
               received."
             ::= { fsipv6Icmp 11 }


         fsipv6IcmpInNeighborAdvertisements OBJECT-TYPE
             SYNTAX     Counter32
             MAX-ACCESS     read-only
             STATUS     current
             DESCRIPTION
              "The number of ICMP Neighbor Advertisement
              messages received."
             ::= { fsipv6Icmp 12 }


         fsipv6IcmpInRedirects OBJECT-TYPE
             SYNTAX     Counter32
             MAX-ACCESS     read-only
             STATUS     current
             DESCRIPTION
              "The number of Redirect messages received."
             ::= { fsipv6Icmp 13 }


         fsipv6IcmpInAdminProhib OBJECT-TYPE
             SYNTAX     Counter32
             MAX-ACCESS     read-only
             STATUS     current
             DESCRIPTION
              "Number of ICMP destination unreachable/communication
              administratively prohibited messages received."
             ::= { fsipv6Icmp 14 }


         fsipv6IcmpOutMsgs OBJECT-TYPE
             SYNTAX     Counter32
             MAX-ACCESS     read-only
             STATUS     current
             DESCRIPTION
              "The total number of ICMP messages which this
              entity attempted to send.  Note that this counter
              includes all those counted by icmpOutErrors."
             ::= { fsipv6Icmp 15 }


         fsipv6IcmpOutErrors OBJECT-TYPE
             SYNTAX     Counter32
             MAX-ACCESS     read-only
             STATUS     current
             DESCRIPTION
              "The number of ICMP messages which this entity did
              not send due to problems discovered within ICMP
              such as a lack of buffers.  This value should not
              include errors discovered outside the ICMP layer
              such as the inability of IPv6 to route the resultant
              datagram.  In some implementations there may be no
              types of error which contribute to this counter's
              value."
             ::= { fsipv6Icmp 16 }


         fsipv6IcmpOutDestUnreachs OBJECT-TYPE
             SYNTAX     Counter32
             MAX-ACCESS     read-only
             STATUS     current
             DESCRIPTION
              "The number of ICMP Destination Unreachable
              messages sent."
             ::= { fsipv6Icmp 17 }


         fsipv6IcmpOutTimeExcds OBJECT-TYPE
             SYNTAX     Counter32
             MAX-ACCESS     read-only
             STATUS     current
             DESCRIPTION
              "The number of ICMP Time Exceeded messages sent."
             ::= { fsipv6Icmp 18 }


         fsipv6IcmpOutParmProbs OBJECT-TYPE
             SYNTAX     Counter32
             MAX-ACCESS     read-only
             STATUS     current
             DESCRIPTION
              "The number of ICMP Parameter Problem messages
              sent."
             ::= { fsipv6Icmp 19 }


         fsipv6IcmpOutPktTooBigs OBJECT-TYPE
             SYNTAX     Counter32
             MAX-ACCESS     read-only
             STATUS     current
             DESCRIPTION
              "The number of ICMP Packet Too Big messages sent."
             ::= { fsipv6Icmp 20 }


         fsipv6IcmpOutEchos OBJECT-TYPE
             SYNTAX     Counter32
             MAX-ACCESS     read-only
             STATUS     current
             DESCRIPTION
              "The number of ICMP Echo (request) messages sent."
             ::= { fsipv6Icmp 21 }


         fsipv6IcmpOutEchoReps OBJECT-TYPE
             SYNTAX     Counter32
             MAX-ACCESS     read-only
             STATUS     current
             DESCRIPTION
              "The number of ICMP Echo Reply messages sent."
             ::= { fsipv6Icmp 22 }


         fsipv6IcmpOutRouterSolicits OBJECT-TYPE
             SYNTAX     Counter32
             MAX-ACCESS     read-only
             STATUS     current
             DESCRIPTION
              "The number of ICMP Router Solicitation messages
               sent."
             ::= { fsipv6Icmp 23 }


         fsipv6IcmpOutRouterAdvertisements OBJECT-TYPE
             SYNTAX     Counter32
             MAX-ACCESS     read-only
             STATUS     current
             DESCRIPTION
              "The number of ICMP Router Advertisement messages
              received."
             ::= { fsipv6Icmp 24 }


         fsipv6IcmpOutNeighborSolicits OBJECT-TYPE
             SYNTAX     Counter32
             MAX-ACCESS     read-only
             STATUS     current
             DESCRIPTION
              "The number of ICMP Neighbor Solicitation
               messages sent."
             ::= { fsipv6Icmp 25 }


         fsipv6IcmpOutNeighborAdvertisements OBJECT-TYPE
             SYNTAX     Counter32
             MAX-ACCESS     read-only
             STATUS     current
             DESCRIPTION
              "The number of ICMP Neighbor Advertisement
              messages
              received."
             ::= { fsipv6Icmp 26 }


         fsipv6IcmpOutRedirects OBJECT-TYPE
             SYNTAX     Counter32
             MAX-ACCESS     read-only
             STATUS     current
             DESCRIPTION
              "The number of Redirect messages sent. For
              a host, this object will always be zero,
              since hosts do not send redirects."
             ::= { fsipv6Icmp 27 }


         fsipv6IcmpOutAdminProhib OBJECT-TYPE
             SYNTAX     Counter32
             MAX-ACCESS     read-only
             STATUS     current
             DESCRIPTION
               "Number of ICMP destination unreachable/
               communication administratively prohibited
               messages sent."
             ::= { fsipv6Icmp 28 }


         fsipv6IcmpInBadCode OBJECT-TYPE
             SYNTAX     Counter32
             MAX-ACCESS     read-only
             STATUS     current
             DESCRIPTION
               "Number of received ICMP messages having unrecognized type of
                message "
             ::= { fsipv6Icmp 29 }

         fsipv6IcmpInNARouterFlagSet OBJECT-TYPE
             SYNTAX     Counter32
             MAX-ACCESS     read-only
             STATUS     current
             DESCRIPTION
               "The number of ICMP Neighbor Advertisement received with Router
                Flag Set"
             ::= { fsipv6Icmp 30 }

         fsipv6IcmpInNASolicitedFlagSet OBJECT-TYPE
             SYNTAX     Counter32
             MAX-ACCESS     read-only
             STATUS     current
             DESCRIPTION
               "The number of ICMP Neighbor Advertisement received with Solicited
                Flag Set"
             ::= { fsipv6Icmp 31 }

         fsipv6IcmpInNAOverrideFlagSet OBJECT-TYPE
             SYNTAX     Counter32
             MAX-ACCESS     read-only
             STATUS     current
             DESCRIPTION
               "The number of ICMP Neighbor Advertisement received with Override
                Flag Set"
             ::= { fsipv6Icmp 32 }

         fsipv6IcmpOutNARouterFlagSet OBJECT-TYPE
             SYNTAX     Counter32
             MAX-ACCESS     read-only
             STATUS     current
             DESCRIPTION
               "The number of ICMP Neighbor Advertisement sent with Router
                Flag Set"
             ::= { fsipv6Icmp 33 }

         fsipv6IcmpOutNASolicitedFlagSet OBJECT-TYPE
             SYNTAX     Counter32
             MAX-ACCESS     read-only
             STATUS     current
             DESCRIPTION
               "The number of ICMP Neighbor Advertisement sent with Solicited
                Flag Set"
             ::= { fsipv6Icmp 34 }

         fsipv6IcmpOutNAOverrideFlagSet OBJECT-TYPE
             SYNTAX     Counter32
             MAX-ACCESS     read-only
             STATUS     current
             DESCRIPTION
               "The number of ICMP Neighbor Advertisement sent with Override
                Flag Set"
             ::= { fsipv6Icmp 35 }


         -- The IPv6 UDP group

fsipv6UdpScalars  OBJECT IDENTIFIER ::= { fsipv6Udp 1 }

--fsipv6UdpScalars BEGIN

         fsipv6UdpInDatagrams OBJECT-TYPE
             SYNTAX     Counter32
             MAX-ACCESS     read-only
             STATUS     current
             DESCRIPTION
               "The total number of UDP datagrams delivered to
                UDP users."
             ::= { fsipv6UdpScalars 1 }


         fsipv6UdpNoPorts OBJECT-TYPE
             SYNTAX     Counter32
             MAX-ACCESS     read-only
             STATUS     current
             DESCRIPTION
               "The total number of received UDP datagrams
                for which there was no application at
                the destination port."
             ::= { fsipv6UdpScalars 2 }


         fsipv6UdpInErrors OBJECT-TYPE
             SYNTAX     Counter32
             MAX-ACCESS     read-only
             STATUS     current
             DESCRIPTION
               "The number of received UDP datagrams that
                could not be delivered for reasons other
                than the lack of an application at
                the destination port."
             ::= { fsipv6UdpScalars 3 }


         fsipv6UdpOutDatagrams OBJECT-TYPE
             SYNTAX     Counter32
             MAX-ACCESS     read-only
             STATUS     current
             DESCRIPTION
               "The total number of UDP datagrams sent
                from this entity."
             ::= { fsipv6UdpScalars 4 }

-- fsipv6UdpScalars END

-- IPv6 Routing Table

          -- The IPv6 routing table contains an entry for each
          -- valid IPv6 unicast routes that can be used for packet
          -- forwarding. There are no entries for Multicast and Link-Local
          -- addresses.

          -- This table contains static and dynamic routes as well as routes
          -- to directly connected networks which are derived from the
          -- configured address prefixes. Thus entries exist in this table
          -- even if RIPng protocol is not running.

          -- Entries created/deleted from SNMP, dynamically through RIPng
          -- protocol or derived from configured address prefixes.

	 fsipv6RouteTable   OBJECT-TYPE
              SYNTAX   SEQUENCE OF Fsipv6RouteEntry
              MAX-ACCESS   not-accessible
              STATUS   current
              DESCRIPTION
                 "This table contains dynamic routes that are learnt
                 through dynamic routing protocol as well as local routes
                 derived from configured address prefixes and statically
                 configured routes."
              ::= { fsipv6Route 1 }


         fsipv6RouteEntry   OBJECT-TYPE
              SYNTAX   Fsipv6RouteEntry
              MAX-ACCESS   not-accessible
              STATUS   current
              DESCRIPTION
                 "An entry in the IPv6 Routing Table. An entry can be created
                 by means of the routing protocol, derived from configured
                 address prefixes as well as statically configured. There
                 can be a static route as well as dynamic routes with the
                 same destination and prefix length."
              INDEX  { fsipv6RouteDest,
                       fsipv6RoutePfxLength,
                       fsipv6RouteProtocol,
                       fsipv6RouteNextHop
                     }
              ::= { fsipv6RouteTable 1 }


         Fsipv6RouteEntry  ::=
              SEQUENCE {
                 fsipv6RouteDest
                     OCTET STRING,
                 fsipv6RoutePfxLength
                     Integer32,
                 fsipv6RouteProtocol
                     INTEGER,
                 fsipv6RouteNextHop
                     OCTET STRING,
                 fsipv6RouteIfIndex
                     InterfaceIndex,
                 fsipv6RouteMetric
                     Unsigned32,
                 fsipv6RouteType
                     INTEGER,
                 fsipv6RouteTag
                     Unsigned32,
                 fsipv6RouteAge
                     Integer32,
                 fsipv6RouteAdminStatus
                     RowStatus,
                 fsipv6RouteAddrType
                     INTEGER,
                 fsipv6RouteHwStatus
                     INTEGER,
                 fsipv6RoutePreference
                     Integer32
              }


          fsipv6RouteDest  OBJECT-TYPE
              SYNTAX   OCTET STRING (SIZE (16))
              MAX-ACCESS  not-accessible
              STATUS   current
              DESCRIPTION
                 "The destination IPv6 address of this route.
                  This object will not take a Link-Local or Multicast address
                  value."
              ::= { fsipv6RouteEntry 1 }


          fsipv6RoutePfxLength OBJECT-TYPE
              SYNTAX   Integer32 (1..128)
              MAX-ACCESS   not-accessible
              STATUS   current
              DESCRIPTION
                 "Indicates the prefix length of the destination
                  address."
              ::= { fsipv6RouteEntry 2 }


          fsipv6RouteProtocol OBJECT-TYPE
              SYNTAX     INTEGER {
                            other(1),        -- none of the following


                            local(2),        -- non-protocol information,
                                             -- e.g., manually configured
                                             -- entries

                            netmgmt(3),      -- static route

                            ndisc(4),        -- e.g., Redirect
                                             -- the following are all
                                             -- dynamic routing protocols

                            rip(5),          -- RIPng

                            ospf(6),         -- Open Shortest Path First

                            bgp(7),          -- Border Gateway Protocol
                            idrp(8),         -- InterDomain Routing Protocol
                            igrp(9),         -- InterGateway Routing Protocol
                            kernel(12)       -- routes installed by kernel

                         }
              MAX-ACCESS    not-accessible
              STATUS   current
              DESCRIPTION
                 "The routing mechanism via which this route was
                 learned. If it has value local(2), it indicates this
                 route was derived from a configured address prefix."
              ::= { fsipv6RouteEntry 3 }


          fsipv6RouteNextHop  OBJECT-TYPE
              SYNTAX   OCTET STRING (SIZE (16))
              MAX-ACCESS   not-accessible
              STATUS   current
              DESCRIPTION
                 "Next hop IPv6 Address for this route. For direct routes
                 it has the value ::0."
              ::= { fsipv6RouteEntry 4 }


          fsipv6RouteIfIndex  OBJECT-TYPE
              SYNTAX   InterfaceIndex
              MAX-ACCESS   read-write
              STATUS   current
              DESCRIPTION
                 "The index value which uniquely identifies the interface
                  through which the next hop of this route should be reached.
                  The interface identified by a particular value of this index
                  is the same interface as identified by the same value of
                  fsipv6IfIndex."
              ::= { fsipv6RouteEntry 5 }


          fsipv6RouteMetric  OBJECT-TYPE
              SYNTAX   Unsigned32 (1..4294967295)
              MAX-ACCESS   read-write
              STATUS   current
              DESCRIPTION
                 "The routing metric associated with this route."
              DEFVAL { 1 }
              ::= { fsipv6RouteEntry 6 }


          fsipv6RouteType OBJECT-TYPE
              SYNTAX   INTEGER  {
                            other(1),     -- none of the following
                            
                                          -- an route indicating that
                                          -- packets to destinations
                                          -- matching this route are
                            discard(2),   -- to be discarded
    
                                          -- route to directly
                            local(3),     -- connected (sub-)network

                                          -- route to a remote
                            remote(4)     -- destination
                       }
              MAX-ACCESS   read-write
              STATUS   current
              DESCRIPTION
               "The type of route. Note that 'local(3)' refers
                to a route for which the next hop is the final
                destination; 'remote(4)' refers to a route for
                which  the  next  hop is not the final
                destination; 'discard(2)' refers to a route
                indicating that packets to destinations matching
                this route are to be discarded (sometimes called
                black-hole route). In this implementation
                discard(2) is not supported."
              ::= { fsipv6RouteEntry 7 }


          fsipv6RouteTag OBJECT-TYPE
              SYNTAX   Unsigned32 (0..4294967295)
              MAX-ACCESS   read-write
              STATUS   current
              DESCRIPTION
                 "This object specifies whether this route is an internal
                 or external route. Value 0 represent routes are internal
                 to the routing domain and Value > 0 represent routes
                 are external to the routing domain. For routes learnt
                 through dynamic routing protocol, this object derives its
                 value from the packet. For routes which are statically
                 configured, this object should be configured. The higher
                 order 2 bytes refers to the tag value and the lower order
                 2 byter refers to the next-hop AS number. "
              ::= { fsipv6RouteEntry 8 }


          fsipv6RouteAge  OBJECT-TYPE
              SYNTAX   Integer32
              MAX-ACCESS   read-only
              STATUS   current
              DESCRIPTION
                "The number of seconds since this route was last
                updated or otherwise determined to be correct. For
                statically configured routes and locally derived routes,
                this object has value 0."
              ::= { fsipv6RouteEntry 9 }

          fsipv6RouteAdminStatus  OBJECT-TYPE
              SYNTAX    RowStatus
              MAX-ACCESS   read-create
              STATUS   current
              DESCRIPTION
                "Administrative Status of the route. This object is used
                 to create or delete the route entry. The fsipv6RouteIfIndex
                 needs to be set, before the route entry is made active. 
                 CreateAndGo is not supported."
              ::= { fsipv6RouteEntry 10 }

          fsipv6RouteAddrType OBJECT-TYPE
              SYNTAX   INTEGER {
                            unicast(1),
                            anycast(2)
                       }
              MAX-ACCESS   read-write
              STATUS   current
              DESCRIPTION
                "Indicates whether the destination address in the route entry
                 is unicast or  anycast."
              DEFVAL { 1 }
              ::= { fsipv6RouteEntry 11 }

          fsipv6RouteHwStatus OBJECT-TYPE
              SYNTAX   INTEGER {
                            present(1),
                            not-present(2)
                       }
              MAX-ACCESS   read-only
              STATUS   current
              DESCRIPTION
                "Indicates whether the route entry is either present or not
                 present in the hardware."
              ::= { fsipv6RouteEntry 12 }

          fsipv6RoutePreference OBJECT-TYPE
              SYNTAX   Integer32 (1.. 255)
              MAX-ACCESS   read-write
              STATUS   current
              DESCRIPTION
                "This Object specifies the Administrative distance of the route  entry. This value will be used by the 
                 forwarding algorithm to choose the best route "
              ::= { fsipv6RouteEntry 13 }

--ipv6RouteTable END

-- fsipv6PrefTable BEGIN
         -- IPv6 Protocol Preference 

         -- The IPv6 Protocol Preference table defines the preference value
         -- for each protocol and the best routes will be determined based
         -- on this preference value. Protocol with lower value is the
         -- preferred.

         fsipv6PrefTable OBJECT-TYPE
             SYNTAX      SEQUENCE OF Fsipv6PrefEntry
             MAX-ACCESS      not-accessible
             STATUS      current
             DESCRIPTION
               "The IPv6 Preference table contains information on the 
                Preference Value for each supported protocol."
             ::= { fsipv6Route 2 }


         fsipv6PrefEntry OBJECT-TYPE
             SYNTAX     Fsipv6PrefEntry
             MAX-ACCESS     not-accessible
             STATUS     current
             DESCRIPTION
               "An entry containing objects about a particular protocols
                preference value."
             INDEX   { fsipv6Protocol }
             ::= { fsipv6PrefTable 1 }


         Fsipv6PrefEntry ::= SEQUENCE {
                 fsipv6Protocol
                     INTEGER,
                 fsipv6Preference
                     Unsigned32
         }


         fsipv6Protocol OBJECT-TYPE
             SYNTAX     INTEGER {
                            other(1), 
                            local(2),
                            netmgmt(3),
                            ndisc(4),
                            rip(5),
                            ospf(6),
                            bgp(7),
                            idrp(8),
                            igrp(9)
                         }
             MAX-ACCESS   not-accessible
             STATUS     current
             DESCRIPTION
               "A unique value identifying the protocol whose preference
                value needs to be processed."
             ::= { fsipv6PrefEntry 1 }


          fsipv6Preference OBJECT-TYPE
              SYNTAX   Unsigned32 (0..255)
              MAX-ACCESS   read-write
              STATUS   current
              DESCRIPTION
    		  "Preference of the route learned by a particular protocol. 
               This value is used while choosing the best path. 
               Lesser the value, highest is the preference. "
              ::= { fsipv6PrefEntry 2 }


-- fsipv6Test Group
-- This group defines objects for IP6TEST.

   fsIpv6TestRedEntryTime  OBJECT-TYPE
        SYNTAX   Integer32
        MAX-ACCESS   read-only
        STATUS   current
        DESCRIPTION " Time when the node starts entering active state
            from standby state "
        ::= { fsipv6Test 1 }

    fsIpv6TestRedExitTime  OBJECT-TYPE
        SYNTAX   Integer32
        MAX-ACCESS   read-only
        STATUS   current
        DESCRIPTION " Time when the node completes entering active state
            from standby state "
        ::= { fsipv6Test 2 }

-- fsipv6Test END

-- fsipv6RaRDNSSTable BEGIN
         -- IPv6 Interface Table

         -- The IPv6 RDNSS table defines on which
         -- IPv6 tools RADVD is running. 
         -- Entries of this table are created/deleted from SNMP.


         fsipv6IfRaRDNSSTable OBJECT-TYPE
             SYNTAX      SEQUENCE OF Fsipv6IfRaRDNSSEntry
             MAX-ACCESS      not-accessible
             STATUS      current
             DESCRIPTION
               "The IPv6 RDNSS table contains information on the
               entity's RADVD confi on which IPv6."
             ::= { fsipv6RaRDNSSTable 1 }


         fsipv6IfRaRDNSSEntry OBJECT-TYPE
             SYNTAX     Fsipv6IfRaRDNSSEntry
             MAX-ACCESS     not-accessible
             STATUS     current
             DESCRIPTION
               "RDNSS entry containing objects about a particular
               IPv6 interface. The entry is created or deleted from SNMP."
             INDEX   { fsipv6IfIndex }
             ::= { fsipv6IfRaRDNSSTable 1 }

         Fsipv6IfRaRDNSSEntry ::= SEQUENCE {
		 fsipv6IfRaRDNSSIndex
                        InterfaceIndex,
                 fsipv6IfRadvRDNSSOpen
                        INTEGER,
                 fsipv6IfRaRDNSSPreference
                        Integer32,
                 fsipv6IfRaRDNSSLifetime
                        Unsigned32,
                 fsipv6IfRaRDNSSAddrOne   
		        Ipv6Address,
                 fsipv6IfRaRDNSSAddrTwo   
		        Ipv6Address,
                 fsipv6IfRaRDNSSAddrThree   
		        Ipv6Address,
                 fsipv6IfRaRDNSSRowStatus
                        RowStatus,
                 fsipv6IfDomainNameOne
                        OCTET STRING,
                 fsipv6IfDomainNameTwo
                        OCTET STRING,
                 fsipv6IfDomainNameThree
                        OCTET STRING,
                 fsipv6IfDnsLifeTime
                        Integer32,
                 fsipv6IfRaRDNSSAddrOneLife
                        Unsigned32,
                 fsipv6IfRaRDNSSAddrTwoLife
                        Unsigned32,
                 fsipv6IfRaRDNSSAddrThreeLife
                        Unsigned32,
                 fsipv6IfDomainNameOneLife
                        Unsigned32,
                 fsipv6IfDomainNameTwoLife
                        Unsigned32,
                 fsipv6IfDomainNameThreeLife
                        Unsigned32
	}

         fsipv6IfRaRDNSSIndex OBJECT-TYPE
             SYNTAX     InterfaceIndex
             MAX-ACCESS   not-accessible
             STATUS     current
             DESCRIPTION
               "A unique value identifying the particular IPv6
               interface."
             ::= { fsipv6IfRaRDNSSEntry 1 }

         fsipv6IfRadvRDNSSOpen OBJECT-TYPE
                SYNTAX  INTEGER {
                    on(1),
                    off(2)
                }
                MAX-ACCESS     read-write
                STATUS         current
                DESCRIPTION
                   "If this object has value on(1), indicates that RDNSS continues to
                    be available to hosts even if they moved to a different  subnet.
                    If it has value off(2),RDNSS will not be available to hosts."
                DEFVAL   { off }
                ::= { fsipv6IfRaRDNSSEntry 2 }

         fsipv6IfRaRDNSSPreference OBJECT-TYPE
                 SYNTAX  Integer32 (0..15)
                 MAX-ACCESS     read-write
                 STATUS         current
                 DESCRIPTION
                    "The  preference of the DNS server, compared to other DNS servers
                    is  advertised and used."
                 DEFVAL    { 8 }
                 ::= { fsipv6IfRaRDNSSEntry 3 }

         fsipv6IfRaRDNSSLifetime OBJECT-TYPE
                 SYNTAX   Unsigned32 (0..4294967295)
                 MAX-ACCESS      read-write
                 STATUS          current
                 DESCRIPTION
                     "The maximum duration how long the RDNSS  entries  are  used  for
                     name  resolution.  A  value  of 0 means the nameserver should no
                     longer be used.  The maximum duration how long the RDNSS entries
                     are  used for name resolution. A value of 0 means the nameserver
                     should no longer be used.  The value, if not 0, must be at least
                     MaxRtrAdvInterval.  To ensure stale RDNSS info gets removed in a
                     timely   fashion,   this   should   not    be    greater    than
                     2*MaxRtrAdvInterval."
                 ::= { fsipv6IfRaRDNSSEntry 4 }

         fsipv6IfRaRDNSSAddrOne OBJECT-TYPE
                SYNTAX      Ipv6Address
                MAX-ACCESS  read-write
                STATUS      current
                DESCRIPTION
                "The IPv6 address to which this entry's addressing
                information pertains."
            ::= { fsipv6IfRaRDNSSEntry 5}

         fsipv6IfRaRDNSSAddrTwo OBJECT-TYPE
                SYNTAX      Ipv6Address
                MAX-ACCESS  read-write
                STATUS      current
                DESCRIPTION
                "The IPv6 address to which this entry's addressing
                information pertains."
            ::= { fsipv6IfRaRDNSSEntry 6}

         fsipv6IfRaRDNSSAddrThree OBJECT-TYPE
                SYNTAX      Ipv6Address
                MAX-ACCESS  read-write
                STATUS      current
                DESCRIPTION
                "The IPv6 address to which this entry's addressing
                information pertains."
            ::= { fsipv6IfRaRDNSSEntry 7}


         fsipv6IfRaRDNSSRowStatus OBJECT-TYPE
                SYNTAX      RowStatus
                MAX-ACCESS  read-write
                STATUS      current
                DESCRIPTION
                "The RDNSS row status to which this entry's radvd
                information pertains."
            ::= { fsipv6IfRaRDNSSEntry 8}

         fsipv6IfDomainNameOne OBJECT-TYPE
                SYNTAX      OCTET STRING (SIZE (255))
                MAX-ACCESS  read-write
                STATUS      current
                DESCRIPTION
                "The DNS Domain name to which this entry's domainname
                information pertains."
            ::= { fsipv6IfRaRDNSSEntry 9}


         fsipv6IfDomainNameTwo OBJECT-TYPE
                SYNTAX      OCTET STRING (SIZE (255))
                MAX-ACCESS  read-write
                STATUS      current
                DESCRIPTION
                "The DNS Domain name to which this entry's domainname
                information pertains."
            ::= { fsipv6IfRaRDNSSEntry 10}


         fsipv6IfDomainNameThree OBJECT-TYPE
                SYNTAX      OCTET STRING (SIZE (255))
                MAX-ACCESS  read-write
                STATUS      current
                DESCRIPTION
                "The DNS Domain name to which this entry's domainname
                information pertains."
            ::= { fsipv6IfRaRDNSSEntry 11}

          fsipv6IfDnsLifeTime OBJECT-TYPE
                SYNTAX  Integer32 (0..3600000)
                MAX-ACCESS  read-write
                STATUS  current
                DESCRIPTION
                   "Life time to be configured for the connected router"
            ::= { fsipv6IfRaRDNSSEntry 12}
            fsipv6IfRaRDNSSAddrOneLife OBJECT-TYPE
                 SYNTAX   Unsigned32 (0..4294967295)
                 MAX-ACCESS      read-write
                 STATUS          current
                 DESCRIPTION
                     "The maximum duration how long the RDNSS  entries  are  used  for
                     name  resolution.  A  value  of 0 means the nameserver should no
                     longer be used.  The maximum duration how long the RDNSS entries
                     are  used for name resolution. A value of 0 means the nameserver
                     should no longer be used.  The value, if not 0, must be at least
                     MaxRtrAdvInterval.  To ensure stale RDNSS info gets removed in a
                     timely   fashion,   this   should   not    be    greater    than
                     2*MaxRtrAdvInterval."
                 ::= { fsipv6IfRaRDNSSEntry 13 }

           fsipv6IfRaRDNSSAddrTwoLife OBJECT-TYPE
                 SYNTAX   Unsigned32 (0..4294967295)
                 MAX-ACCESS      read-write
                 STATUS          current
                 DESCRIPTION
                     "The maximum duration how long the RDNSS  entries  are  used  for
                     name  resolution.  A  value  of 0 means the nameserver should no
                     longer be used.  The maximum duration how long the RDNSS entries
                     are  used for name resolution. A value of 0 means the nameserver
                     should no longer be used.  The value, if not 0, must be at least
                     MaxRtrAdvInterval.  To ensure stale RDNSS info gets removed in a
                     timely   fashion,   this   should   not    be    greater    than
                     2*MaxRtrAdvInterval."
                 ::= { fsipv6IfRaRDNSSEntry 14 }
 
         fsipv6IfRaRDNSSAddrThreeLife OBJECT-TYPE
                 SYNTAX   Unsigned32 (0..4294967295)
                 MAX-ACCESS      read-write
                 STATUS          current
                 DESCRIPTION
                     "The maximum duration how long the RDNSS  entries  are  used  for
                     name  resolution.  A  value  of 0 means the nameserver should no
                     longer be used.  The maximum duration how long the RDNSS entries
                     are  used for name resolution. A value of 0 means the nameserver
                     should no longer be used.  The value, if not 0, must be at least
                     MaxRtrAdvInterval.  To ensure stale RDNSS info gets removed in a
                     timely   fashion,   this   should   not    be    greater    than
                     2*MaxRtrAdvInterval."
                 ::= { fsipv6IfRaRDNSSEntry 15 }
         
         fsipv6IfDomainNameOneLife  OBJECT-TYPE
                 SYNTAX   Unsigned32 (0..4294967295)
                MAX-ACCESS  read-write
                STATUS  current
                DESCRIPTION
                   "Life time to be configured for the connected router"
                ::= { fsipv6IfRaRDNSSEntry 16}
   
        fsipv6IfDomainNameTwoLife OBJECT-TYPE
                 SYNTAX   Unsigned32 (0..4294967295)
                MAX-ACCESS  read-write
                STATUS  current
                DESCRIPTION
                   "Life time to be configured for the connected router"
                ::= { fsipv6IfRaRDNSSEntry 17}

       fsipv6IfDomainNameThreeLife OBJECT-TYPE
                 SYNTAX   Unsigned32 (0..4294967295)
                MAX-ACCESS  read-write
                STATUS  current
                DESCRIPTION
                   "Life time to be configured for the connected router"
                ::= { fsipv6IfRaRDNSSEntry 18}
 
END
