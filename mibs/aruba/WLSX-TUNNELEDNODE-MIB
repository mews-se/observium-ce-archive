-- ArubaOS 8.12.0.4_91755
-- vim:set ts=4 sw=4:
WLSX-TUNNELEDNODE-MIB DEFINITIONS ::= BEGIN

   IMPORTS
       TEXTUAL-CONVENTION FROM SNMPv2-TC 
       
       MODULE-IDENTITY,
       OBJECT-TYPE,
       snmpModules,
       Integer32,
       Unsigned32,
	   Counter32,
	   IpAddress,
	   NOTIFICATION-TYPE
           FROM SNMPv2-SMI

       TDomain,
       DisplayString,
       PhysAddress,
       TAddress,
       TimeInterval,
       RowStatus,
       StorageType,
       TestAndIncr,
	   MacAddress,
	   TruthValue
           FROM SNMPv2-TC

       OBJECT-GROUP
           FROM SNMPv2-CONF
		wlsxEnterpriseMibModules
			FROM ARUBA-MIB;

   wlsxTunneledNodeMIB MODULE-IDENTITY
       LAST-UPDATED "202008141745Z"
       ORGANIZATION "Aruba, a Hewlett Packard Enterprise company"
       CONTACT-INFO
            "Postal:    3333 Scott Blvd,
                        Santa Clara, CA 95054
            E-mail:     aruba-ext-eng-reg@hpe.com
            Phone:      408 227 4500
            Fax:        408 752 0626" 
       DESCRIPTION
           "This MIB module defines MIB objects which provide
            information about the Controller Transport Service (Cts) in the 
			Aruba controller."
       REVISION        "202008141745Z"
       DESCRIPTION
           "The initial revision."
       ::= { wlsxEnterpriseMibModules 17 }

   wlsxTunneledNodeOpGroup     	OBJECT IDENTIFIER ::= { wlsxTunneledNodeMIB 1 }

   wlsxTunneledNodeRequestTable OBJECT-TYPE
	SYNTAX			SEQUENCE OF WlsxTunneledNodeRequestEntry
	MAX-ACCESS		not-accessible
	STATUS			current
	DESCRIPTION
		"
		"
	::= { wlsxTunneledNodeOpGroup 1 }

	wlsxTunneledNodeRequestEntry OBJECT-TYPE
		SYNTAX WlsxTunneledNodeRequestEntry
		MAX-ACCESS not-accessible
		STATUS	current
		DESCRIPTION
			""
		INDEX { wlsxTunneledNodeMAC }
		::= { wlsxTunneledNodeRequestTable 1 }

	WlsxTunneledNodeRequestEntry ::=
		SEQUENCE {
            wlsxTunneledNodeMAC MacAddress,
			wlsxTunneledNodeIp	IpAddress,
			wlsxNumTunnels	    Integer32,
            wlsxTunneledNodeType  Integer32
		}

    wlsxTunneledNodeMAC OBJECT-TYPE
        SYNTAX  MacAddress
        MAX-ACCESS  not-accessible
        STATUS  current
        DESCRIPTION
            " 
            MAC address of the Tunneled Node
            "
        ::= { wlsxTunneledNodeRequestEntry 1 }

	wlsxTunneledNodeIp OBJECT-TYPE
		SYNTAX 	IpAddress
		MAX-ACCESS read-only
		STATUS	current
		DESCRIPTION
			"
            IP address of the Tunneled Node
			"
		::= { wlsxTunneledNodeRequestEntry 2 }

	wlsxNumTunnels OBJECT-TYPE
		SYNTAX 	Integer32
		MAX-ACCESS read-only
		STATUS	current
		DESCRIPTION
			"
				Number of tunnels originating from Tunneled Node
			"
		::= { wlsxTunneledNodeRequestEntry 3 }

     wlsxTunneledNodeType OBJECT-TYPE
        SYNTAX  INTEGER {
                    others(1),
                    corvina(2)
                }
        MAX-ACCESS read-only
        STATUS  current
        DESCRIPTION
            "
                Device type of the tunnel
            "
        ::= { wlsxTunneledNodeRequestEntry 4 }


END
