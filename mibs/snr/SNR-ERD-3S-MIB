SNR-ERD-3S-MIB DEFINITIONS ::= BEGIN

IMPORTS
	MODULE-IDENTITY, OBJECT-TYPE, NOTIFICATION-TYPE, enterprises, IpAddress, Opaque, Integer32	
		FROM SNMPv2-SMI
	DisplayString, TEXTUAL-CONVENTION
		FROM SNMPv2-TC
	NOTIFICATION-GROUP, OBJECT-GROUP, MODULE-COMPLIANCE
		FROM SNMPv2-CONF
	
	; 

snrErd3 MODULE-IDENTITY
	LAST-UPDATED	"202102251200Z"
	ORGANIZATION	"NAG "
	CONTACT-INFO	"erd@nag.ru"
	DESCRIPTION
		"The MIB module for SNR-ERD-3"
	REVISION		"202102251200Z"
	DESCRIPTION		"SMIv2 format" 
	REVISION		"201504291200Z"
	DESCRIPTION		"Initial revision." 
	::= { snrErd 4 }
	
snr			OBJECT IDENTIFIER	::= { enterprises 40418 }
snrErd		OBJECT IDENTIFIER	::= { snr 2 }

erd3traps			OBJECT IDENTIFIER	::= { snrErd3 0 }
erd3ipAddressEntry	OBJECT IDENTIFIER	::= { snrErd3 1 }
erd3resetsSet		OBJECT IDENTIFIER	::= { snrErd3 2 }
erd3sensesSet1		OBJECT IDENTIFIER	::= { snrErd3 3 }
erd3sensesSet2		OBJECT IDENTIFIER	::= { snrErd3 4 }
erd3commS			OBJECT IDENTIFIER	::= { snrErd3 5 }
erd3upsMonitoring	OBJECT IDENTIFIER	::= { snrErd3 6 }
erd3Conformance		OBJECT IDENTIFIER	::= { snrErd3 100 }

erd3temperatureSensorsOut	OBJECT IDENTIFIER	::= { erd3sensesSet2 2 }

erd3Groups			OBJECT IDENTIFIER	::= { erd3Conformance 1 }
erd3Compliances		OBJECT IDENTIFIER	::= { erd3Conformance 2 }


Float ::= TEXTUAL-CONVENTION
    STATUS      current
    DESCRIPTION
        "A single precision floating-point number.  The semantics
        and encoding are identical for type 'single' defined in
        IEEE Standard for Binary Floating-Point,
        ANSI/IEEE Std 754-1985.
        The value is restricted to the BER serialization of
        the following ASN.1 type:
            FLOATTYPE ::= [120] IMPLICIT FloatType
        (note: the value 120 is the sum of '30'h and '48'h)
        The BER serialization of the length for values of
        this type must use the definite length, short
        encoding form.

        For example, the BER serialization of value 123
        of type FLOATTYPE is '9f780442f60000'h.  (The tag
        is '9f78'h; the length is '04'h; and the value is
        '42f60000'h.) The BER serialization of value
        '9f780442f60000'h of data type Opaque is
        '44079f780442f60000'h. (The tag is '44'h; the length
        is '07'h; and the value is '9f780442f60000'h."
	SYNTAX      Opaque (SIZE(7))



-- Traps

erd3temperatureSensorAlarm	NOTIFICATION-TYPE
	STATUS		current
	DESCRIPTION	"Check the text of message"		
::= { erd3traps  0 }

erd3temperatureSensorRelease	NOTIFICATION-TYPE
	STATUS		current
	DESCRIPTION	"Check the text of message"		
::= { erd3traps 1 }

erd3signal1Contact8Alarm	NOTIFICATION-TYPE
	STATUS		current
	DESCRIPTION	"Check the text of message"		
::= { erd3traps 2 }

erd3signal1Contact8Ok	NOTIFICATION-TYPE
	STATUS		current
	DESCRIPTION	"Check the text of message"		
::= { erd3traps 3 }

erd3signal2Contact9Alarm	NOTIFICATION-TYPE
	STATUS		current
	DESCRIPTION	"Check the text of message"		
::= { erd3traps 4 }

erd3signal2Contact9Ok	NOTIFICATION-TYPE
	STATUS		current
	DESCRIPTION	"Check the text of message"		
::= { erd3traps 5 }

erd3voltageSignal1Alarm	NOTIFICATION-TYPE
	STATUS		current
	DESCRIPTION	"Check the text of message"		
::= { erd3traps 6 }

erd3voltageSignal1Ok	NOTIFICATION-TYPE
	STATUS		current
	DESCRIPTION	"Check the text of message"		
::= { erd3traps 7 }

erd3voltageSignal2Alarm	NOTIFICATION-TYPE
	STATUS		current
	DESCRIPTION	"Check the text of message"		
::= { erd3traps 8 }

erd3voltageSignal2Ok	NOTIFICATION-TYPE
	STATUS		current
	DESCRIPTION	"Check the text of message"		
::= { erd3traps 9 }

erd3anySensorSignal1contact5Alarm	NOTIFICATION-TYPE
	STATUS		current
	DESCRIPTION	"Check the text of message"		
::= { erd3traps 10 }

erd3anySensorSignal1contact5Ok	NOTIFICATION-TYPE
	STATUS		current
	DESCRIPTION	"Check the text of message"		
::= { erd3traps 11 }

erd3anySensorSignal2contact6Alarm	NOTIFICATION-TYPE
	STATUS		current
	DESCRIPTION	"Check the text of message"		
::= { erd3traps 12 }

erd3anySensorSignal2contact6Ok	NOTIFICATION-TYPE
	STATUS		current
	DESCRIPTION	"Check the text of message"		
::= { erd3traps 13 }

erd3anySensorSignal3contact7Alarm	NOTIFICATION-TYPE
	STATUS		current
	DESCRIPTION	"Check the text of message"		
::= { erd3traps 14 }

erd3anySensorSignal3contact7Ok	NOTIFICATION-TYPE
	STATUS		current
	DESCRIPTION	"Check the text of message"		
::= { erd3traps 15 }

erd3voltageAlarm		NOTIFICATION-TYPE
	STATUS		current
	DESCRIPTION	"Check the text of message"		
::= { erd3traps 16 }

erd3voltageOk		NOTIFICATION-TYPE
	STATUS		current
	DESCRIPTION	"Check the text of message"		
::= { erd3traps 17 }

erd3remoteControlContact11On	NOTIFICATION-TYPE
	STATUS		current
	DESCRIPTION	"Check the text of message"		
::= { erd3traps 18 }

erd3remoteControlContact11Off	NOTIFICATION-TYPE
	STATUS		current
	DESCRIPTION	"Check the text of message"		
::= { erd3traps 19 }

erd3resetedSmartContact10	NOTIFICATION-TYPE
	STATUS		current
	DESCRIPTION	"Check the text of message"		
::= { erd3traps 20 }

erd3temperatureSensorOutAlarm	NOTIFICATION-TYPE
	STATUS		current
	DESCRIPTION	"Check the text of message"		
::= { erd3traps 23 }

erd3temperatureSensorOutRelease	NOTIFICATION-TYPE
	STATUS		current
	DESCRIPTION	"Check the text of message"		
::= { erd3traps 24 }

erd3temperatureSensorOutFail	NOTIFICATION-TYPE
	STATUS		current
	DESCRIPTION	"Check the text of message"		
::= { erd3traps 25 }

erd3temperatureSensorOutOk	NOTIFICATION-TYPE
	STATUS		current
	DESCRIPTION	"Check the text of message"		
::= { erd3traps 26 }

erd3upsUtilityFail		NOTIFICATION-TYPE
	STATUS		current
	DESCRIPTION	"Check the text of message"		
::= { erd3traps 30 }

erd3upsUtilityOk		NOTIFICATION-TYPE
	STATUS		current
	DESCRIPTION	"Check the text of message"		
::= { erd3traps 31 }


-- ipAddressEntry

erd3ipAddress		OBJECT-TYPE
	SYNTAX		IpAddress
        MAX-ACCESS	read-write
        STATUS		current
        DESCRIPTION	"myIp"
::= {erd3ipAddressEntry 1}

erd3ipGatewayAddress	OBJECT-TYPE
	SYNTAX		IpAddress
	MAX-ACCESS	read-write
	STATUS		current
	DESCRIPTION	"DGIp"
::= {erd3ipAddressEntry 2}

erd3ipMonitoringDevice	OBJECT-TYPE
	SYNTAX		IpAddress
        MAX-ACCESS	read-write 
        STATUS		current
        DESCRIPTION	"monitoredIP"
::= {erd3ipAddressEntry 3}

erd3ipForTrap		OBJECT-TYPE
	SYNTAX		IpAddress 
	MAX-ACCESS	read-write
	STATUS		current
	DESCRIPTION	"ipForTrap"
::= {erd3ipAddressEntry 4}


-- resetsSet

erd3resetSmartContact10	OBJECT-TYPE
	SYNTAX		INTEGER  
			{
				bypass	(0),
				reset	(1)
			}
	MAX-ACCESS	read-write
	STATUS		current
	DESCRIPTION	" "    
::= { erd3resetsSet 1}

erd3numberOfResetPositives	OBJECT-TYPE
	SYNTAX		INTEGER {resetPositives (0)}
	MAX-ACCESS	read-write
	STATUS		current
	DESCRIPTION	" "
::= { erd3resetsSet 2 }


erd3remoteControlContact11	OBJECT-TYPE
	SYNTAX		INTEGER 
			{
				manON			(0),
				manOFF			(1),
				manualSetON		(2),
				termostatSetON	(3),
				switch			(4),
				autoON			(5),
				autoOFF			(6)
			}
	MAX-ACCESS	read-write
	STATUS		current
	DESCRIPTION	" "
::= { erd3resetsSet 3 }


-- sensesSet1

erd3monitorAlarmSignal1Contact8	OBJECT-TYPE
	SYNTAX			INTEGER 
				{
					sensorOff	(0),
					doorIsClose	(1),
					doorIsOpen	(2),
					sensorOn	(3)
				}
	MAX-ACCESS		read-write
	STATUS			current
	DESCRIPTION		" "
::= { erd3sensesSet1 1}

erd3monitorAlarmSignal2Contact9	OBJECT-TYPE
	SYNTAX			INTEGER 
				{
					sensorOff	(0),
					doorIsClose	(1),
					doorIsOpen	(2),
					sensorOn	(3)
				}
	MAX-ACCESS		read-write
	STATUS			current
	DESCRIPTION		" "
::= { erd3sensesSet1 2 }

erd3numberOfAlarmPositives		OBJECT-TYPE
	SYNTAX			INTEGER {resetPositives (0)}
	MAX-ACCESS		read-write
	STATUS			current
	DESCRIPTION		" "
::= { erd3sensesSet1 3 }

erd3monitorAnySensorSignal1contact5	OBJECT-TYPE
	SYNTAX			INTEGER 
				{
					sensorOff	(0),
					sensorIs0	(1),
					sensorIs1	(2),
					sensorOn	(3)
				}
	MAX-ACCESS		read-write
	STATUS			current
	DESCRIPTION		" "
::= { erd3sensesSet1 4 }

erd3monitorAnySensorSignal2contact6	OBJECT-TYPE
	SYNTAX			INTEGER 
				{
					sensorOff	(0),
					sensorIs0	(1),
					sensorIs1	(2),
					sensorOn	(3)
				}
	MAX-ACCESS		read-write
	STATUS			current
	DESCRIPTION		" "
::= { erd3sensesSet1 5 }

erd3monitorAnySensorSignal3contact7	OBJECT-TYPE
	SYNTAX			INTEGER 
				{
					sensorOff	(0),
					sensorIs0	(1),
					sensorIs1	(2),
					sensorOn	(3)			
				}
	MAX-ACCESS		read-write
	STATUS			current
	DESCRIPTION		" "
::= { erd3sensesSet1 6 }

erd3monitorVoltageSignal1		OBJECT-TYPE
	SYNTAX			INTEGER 
				{
					sensorOff(0),
					voltageIsNo(1),
					voltageIsYes(2),
					sensorOn(3)
				}
	MAX-ACCESS		read-write
	STATUS			current
	DESCRIPTION		" "
::= { erd3sensesSet1 7 }

erd3monitorVoltageSignal2		OBJECT-TYPE
	SYNTAX			INTEGER 
				{
					sensorOff (0),
					voltageIsNo (1),
					voltageIsYes (2),
					sensorOn(3)
				}
	MAX-ACCESS		read-write
	STATUS			current
	DESCRIPTION		" "
::= { erd3sensesSet1 8 }


-- sensesSet2

erd3temperatureSensor		OBJECT-TYPE
	SYNTAX			Integer32 
	MAX-ACCESS		read-only
	STATUS			current
	DESCRIPTION		" "
::= { erd3sensesSet2 1 }


erd3temperatureSensorOutSerial1	OBJECT-TYPE
	SYNTAX			OCTET STRING
	MAX-ACCESS		read-only
	STATUS			current
	DESCRIPTION		" "
::= { erd3temperatureSensorsOut 1 }

erd3temperatureSensorOut1		OBJECT-TYPE
	SYNTAX			Integer32
	MAX-ACCESS		read-only
	STATUS			current
	DESCRIPTION		" "
::= { erd3temperatureSensorsOut 2 }

erd3temperatureSensorOutSerial2	OBJECT-TYPE
	SYNTAX			OCTET STRING
	MAX-ACCESS		read-only
	STATUS			current
	DESCRIPTION		" "
::= { erd3temperatureSensorsOut 3 }

erd3temperatureSensorOut2		OBJECT-TYPE
	SYNTAX			Integer32
	MAX-ACCESS		read-only
	STATUS			current
	DESCRIPTION		" "
::= { erd3temperatureSensorsOut 4 }

erd3temperatureSensorOutSerial3	OBJECT-TYPE
	SYNTAX			OCTET STRING
	MAX-ACCESS		read-only
	STATUS			current
	DESCRIPTION		" "
::= { erd3temperatureSensorsOut 5 }

erd3temperatureSensorOut3		OBJECT-TYPE
	SYNTAX			Integer32
	MAX-ACCESS		read-only
	STATUS			current
	DESCRIPTION		" "
::= { erd3temperatureSensorsOut 6 }

erd3temperatureSensorOutSerial4	OBJECT-TYPE
	SYNTAX			OCTET STRING
	MAX-ACCESS		read-only
	STATUS			current
	DESCRIPTION		" "
::= { erd3temperatureSensorsOut 7 }

erd3temperatureSensorOut4		OBJECT-TYPE
	SYNTAX			Integer32
	MAX-ACCESS		read-only
	STATUS			current
	DESCRIPTION		" "
::= { erd3temperatureSensorsOut 8 }

erd3temperatureSensorOutSerial5	OBJECT-TYPE
	SYNTAX			OCTET STRING
	MAX-ACCESS		read-only
	STATUS			current
	DESCRIPTION		" "
::= { erd3temperatureSensorsOut 9 }

erd3temperatureSensorOut5		OBJECT-TYPE
	SYNTAX			Integer32
	MAX-ACCESS		read-only
	STATUS			current
	DESCRIPTION		" "
::= { erd3temperatureSensorsOut 10 }

erd3voltageSensorContact12		OBJECT-TYPE
	SYNTAX			Integer32 
	MAX-ACCESS		read-only
	STATUS			current
	DESCRIPTION		" "
::= { erd3sensesSet2 3 }

erd3sysVoltageAlarm			OBJECT-TYPE
	SYNTAX			Integer32 
	MAX-ACCESS		read-write
	STATUS			current
	DESCRIPTION		" "
::= { erd3sensesSet2 4 }


-- commS

erd3communityString		OBJECT-TYPE
	SYNTAX		DisplayString (SIZE(0..10))
	MAX-ACCESS	read-write
	STATUS		current
	DESCRIPTION	" "
::= {erd3commS 1}

erd3trapMode		OBJECT-TYPE
	SYNTAX		INTEGER 
			{
				cyclically	(0),
				once		(1)
			}
	MAX-ACCESS	read-write
	STATUS		current
	DESCRIPTION	" "
::= {erd3commS 2}

erd3alarmSense1Name		OBJECT-TYPE
	SYNTAX		DisplayString (SIZE(0..10))
	MAX-ACCESS	read-write
	STATUS		current
	DESCRIPTION	" "
::= {erd3commS 3}

erd3alarmSense2Name		OBJECT-TYPE
	SYNTAX		DisplayString (SIZE(0..10))
	MAX-ACCESS	read-write
	STATUS		current
	DESCRIPTION	" "
::= {erd3commS 4}

erd3userSense1Name		OBJECT-TYPE
	SYNTAX		DisplayString (SIZE(0..10))
	MAX-ACCESS	read-write
	STATUS		current
	DESCRIPTION	" "
::= {erd3commS 5}

erd3userSense2Name		OBJECT-TYPE
	SYNTAX		DisplayString (SIZE(0..10))
	MAX-ACCESS	read-write
	STATUS		current
	DESCRIPTION	" "
::= {erd3commS 6}

erd3userSense3Name		OBJECT-TYPE
	SYNTAX		DisplayString (SIZE(0..10))
	MAX-ACCESS	read-write
	STATUS		current
	DESCRIPTION	" "
::= {erd3commS 7}


erd3dataType		OBJECT-TYPE
	SYNTAX		INTEGER 
			{
				integer	(0),      
				float	(1),
				uni	(2)
			}
	MAX-ACCESS	read-write
	STATUS		current
	DESCRIPTION	" "
::= {erd3commS 10}



-- upsMonitoring

erd3batteryVoltage			OBJECT-TYPE
	SYNTAX			Float
	MAX-ACCESS		read-only
	STATUS			current
	DESCRIPTION		" "
::= { erd3upsMonitoring 1 }

erd3upsTemperature			OBJECT-TYPE
	SYNTAX			Float 
	MAX-ACCESS		read-only
	STATUS			current
	DESCRIPTION		" "
::= { erd3upsMonitoring 2 }

erd3inputVoltage			OBJECT-TYPE
	SYNTAX			Float 
	MAX-ACCESS		read-only
	STATUS			current
	DESCRIPTION		" "
::= { erd3upsMonitoring 3 }

erd3outputVoltage			OBJECT-TYPE
	SYNTAX			Float 
	MAX-ACCESS		read-only
	STATUS			current
	DESCRIPTION		" "
::= { erd3upsMonitoring 4 }

erd3upsLoading			OBJECT-TYPE
	SYNTAX			Integer32 
	MAX-ACCESS		read-only
	STATUS			current
	DESCRIPTION		" "
::= { erd3upsMonitoring 5 }

erd3upsStatus			OBJECT-TYPE
	SYNTAX			INTEGER 
				{
					utilityOk	(0),
					utilityFail	(1),
					unknown		(2)
				}
	MAX-ACCESS		read-only
	STATUS			current
	DESCRIPTION		" "
::= { erd3upsMonitoring 6 }


erd3TrapGroup		NOTIFICATION-GROUP  
	NOTIFICATIONS 
	{
		erd3temperatureSensorAlarm,
		erd3temperatureSensorRelease,   
		erd3signal1Contact8Alarm,

		erd3signal1Contact8Ok,
		erd3signal2Contact9Alarm,

		erd3signal2Contact9Ok,
		erd3voltageSignal1Alarm,
		erd3voltageSignal1Ok,
		erd3voltageSignal2Alarm,
		erd3voltageSignal2Ok,
		erd3anySensorSignal1contact5Alarm,
		erd3anySensorSignal1contact5Ok,
		erd3anySensorSignal2contact6Alarm,
		erd3anySensorSignal2contact6Ok,
		erd3anySensorSignal3contact7Alarm,
		erd3anySensorSignal3contact7Ok,
		erd3voltageAlarm,
		erd3voltageOk,
		erd3remoteControlContact11On,
		erd3remoteControlContact11Off,
		erd3resetedSmartContact10,
		erd3temperatureSensorOutAlarm,
		erd3temperatureSensorOutRelease,
		erd3temperatureSensorOutFail,
		erd3temperatureSensorOutOk,
		
		erd3upsUtilityFail,
		erd3upsUtilityOk
	}
	STATUS current
	DESCRIPTION	" "
::= { erd3Groups 1 }

erd3ipAddressEntryGroup OBJECT-GROUP
    OBJECTS {	
				erd3ipAddress, erd3ipGatewayAddress, erd3ipMonitoringDevice, erd3ipForTrap
			}
    STATUS  current
    DESCRIPTION
            "A collection of objects providing SNR-ERD-3 network parameters"
    ::= { erd3Groups 2 }
	
erd3resetsSetGroup OBJECT-GROUP
    OBJECTS {	
				erd3resetSmartContact10, erd3numberOfResetPositives, erd3remoteControlContact11
			}
    STATUS  current
    DESCRIPTION
            "A collection of objects providing SNR-ERD-3 dio parameters"
    ::= { erd3Groups 3 }
	
erd3sensesSet1Group OBJECT-GROUP
    OBJECTS {	
				erd3monitorAlarmSignal1Contact8, erd3monitorAlarmSignal2Contact9, erd3numberOfAlarmPositives, erd3monitorAnySensorSignal1contact5, erd3monitorAnySensorSignal2contact6, erd3monitorAnySensorSignal3contact7, erd3monitorVoltageSignal1, erd3monitorVoltageSignal2
			}
    STATUS  current
    DESCRIPTION
            "A collection of objects providing SNR-ERD-3 dio parameters"
    ::= { erd3Groups 4 }
	
erd3sensesSet2Group OBJECT-GROUP
    OBJECTS {	
				erd3temperatureSensor, erd3voltageSensorContact12, erd3sysVoltageAlarm
			}
    STATUS  current
    DESCRIPTION
            "A collection of objects providing SNR-ERD-3 inner sensors parameters"
    ::= { erd3Groups 5 }
	
erd3temperatureSensorsOutGroup OBJECT-GROUP
    OBJECTS {	
				erd3temperatureSensorOutSerial1, erd3temperatureSensorOut1, erd3temperatureSensorOutSerial2, erd3temperatureSensorOut2, erd3temperatureSensorOutSerial3, erd3temperatureSensorOut3, erd3temperatureSensorOutSerial4, erd3temperatureSensorOut4, erd3temperatureSensorOutSerial5, erd3temperatureSensorOut5
			}
    STATUS  current
    DESCRIPTION
            "A collection of objects providing SNR-ERD-3 outer sensors parameters"
    ::= { erd3Groups 6 }
	
erd3commSGroup OBJECT-GROUP
    OBJECTS {	
				erd3communityString, erd3trapMode, erd3alarmSense1Name, erd3alarmSense2Name, erd3userSense1Name, erd3userSense2Name, erd3userSense3Name, erd3dataType
			}
    STATUS  current
    DESCRIPTION
            "A collection of objects providing SNR-ERD-3 common parameters"
    ::= { erd3Groups 7 }
	
erd3upsMonitoringGroup OBJECT-GROUP
    OBJECTS {	
				erd3batteryVoltage, erd3upsTemperature, erd3inputVoltage, erd3outputVoltage, erd3upsLoading, erd3upsStatus
			}
    STATUS  current
    DESCRIPTION
            "A collection of objects providing SNR-ERD-3 UPS parameters"
    ::= { erd3Groups 8 }
	
erd3Compliance MODULE-COMPLIANCE
	STATUS     current
	DESCRIPTION
				"The compliance statement for SNR-ERD-3 that support all functions."
	MODULE -- this module
	MANDATORY-GROUPS { 	erd3TrapGroup,
						erd3ipAddressEntryGroup,
						erd3resetsSetGroup,
						erd3sensesSet1Group,
						erd3sensesSet2Group,
						erd3temperatureSensorsOutGroup,
						erd3commSGroup,
						erd3upsMonitoringGroup}
	::= { erd3Compliances 1 }

END
