-- OPTIX-SDH-LINEBOARD-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-LINEBOARD-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY,NOTIFICATION-TYPE
            FROM SNMPv2-SMI
        optixLogBoardId,optixLogSubCardId
            FROM OPTIX-BOARD-MANAGE-MIB
        optixPortId
            FROM OPTIX-PORT-MANAGE-MIB 
        ;

    optixSdhLineBoard MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations ofline board management."
        REVISION "201204200000Z"
        DESCRIPTION
            "The initial revision of this MIB module1."
        ::={ optixProvisionSdh 40 }

    -- 1.3.6.1.4.1.2011.2.25.4.10.40.1
    optixSdhLineBoardGroup OBJECT IDENTIFIER ::= { optixSdhLineBoard 1 }

    -- 1.3.6.1.4.1.2011.2.25.4.10.40.1.1
    optixSdhJ0Table OBJECT-TYPE
        SYNTAX SEQUENCE OF OptixSdhJ0Entry
        MAX-ACCESS not-accessible
        STATUS current
        DESCRIPTION
            "This table describes configurations of J0 byte management of the SDH line board."
        ::= { optixSdhLineBoardGroup 1 }

    -- 1.3.6.1.4.1.2011.2.25.4.10.40.1.1.1
    optixSdhJ0Entry OBJECT-TYPE
        SYNTAX OptixSdhJ0Entry
        MAX-ACCESS not-accessible
        STATUS current
        DESCRIPTION
            "Thisentry describes configurations of J0 byte management of the SDH line board."
        INDEX{ optixLogBoardId,optixLogSubCardId,optixPortId }
        ::= { optixSdhJ0Table 1 }

    OptixSdhJ0Entry ::=
        SEQUENCE {
            optixSdhLineBoardSRJ0Mode
                Unsigned32,
            optixSdhLineBoardSRJ0Value
                OCTET STRING,
            optixSdhLineBoardSTJ0Mode
                Unsigned32,
            optixSdhLineBoardSTJ0Value
                OCTET STRING,
            optixSdhLineBoardRJ0Mode
                Unsigned32,
            optixSdhLineBoardRJ0Value
                OCTET STRING,
            optixSdhLineBoardSRJ0Mask
                OCTET STRING,
            optixSdhLineBoardSTJ0Mask
                OCTET STRING,
            optixSdhLineBoardTestAls
                INTEGER
        }

    -- 1.3.6.1.4.1.2011.2.25.4.10.40.1.1.1.1
    optixSdhLineBoardSRJ0Mode OBJECT-TYPE
        SYNTAX Unsigned32
        MAX-ACCESS read-write
        STATUS current
        DESCRIPTION
            "This object indicates the J0 byte to be received mode. Value range: 0,1,3."
        ::= { optixSdhJ0Entry 1 }

    -- 1.3.6.1.4.1.2011.2.25.4.10.40.1.1.1.2
    optixSdhLineBoardSRJ0Value OBJECT-TYPE
        SYNTAX OCTET STRING(SIZE(0..16))
        MAX-ACCESS read-write
        STATUS current
        DESCRIPTION
            "This object indicates the value of the J0 byte to be received.16 UC string When mode is 0,1; 1 UC char When mode is 3;When mode is 0,the highest bit of first byte must be 1."
        ::= { optixSdhJ0Entry 2 }

    -- 1.3.6.1.4.1.2011.2.25.4.10.40.1.1.1.3
    optixSdhLineBoardSTJ0Mode OBJECT-TYPE
        SYNTAX Unsigned32
        MAX-ACCESS read-write
        STATUS current
        DESCRIPTION
            "This object indicates the J0 byte to be transmitted mode. Value range: 0,1,3."
        ::= { optixSdhJ0Entry 3 }

    -- 1.3.6.1.4.1.2011.2.25.4.10.40.1.1.1.4
    optixSdhLineBoardSTJ0Value OBJECT-TYPE
        SYNTAX OCTET STRING(SIZE(0..16))
        MAX-ACCESS read-write
        STATUS current
        DESCRIPTION
            "This object indicates the J0 byte to be transmitted mode.16 UC string When mode is 0,1; 1 UC char When mode is 3;When mode is 0,the highest bit of first byte must be 1."
        ::= { optixSdhJ0Entry 4 }

    -- 1.3.6.1.4.1.2011.2.25.4.10.40.1.1.1.5
    optixSdhLineBoardRJ0Mode OBJECT-TYPE
        SYNTAX Unsigned32
        MAX-ACCESS read-only
        STATUS current
        DESCRIPTION
            "This object indicates the received J0 bytemode. Value range: 0, 1, 3."
        ::= { optixSdhJ0Entry 5 }

    -- 1.3.6.1.4.1.2011.2.25.4.10.40.1.1.1.6
    optixSdhLineBoardRJ0Value OBJECT-TYPE
        SYNTAX OCTET STRING(SIZE(0..16))
        MAX-ACCESS read-only
        STATUS current
        DESCRIPTION
            "This object indicates the value of the received J0 byte.16 UC string When mode is 0,1; 1 UC char When mode is 3;When mode is 0,the highest bit of first byte must be 1."
        ::= { optixSdhJ0Entry 6 }

    -- 1.3.6.1.4.1.2011.2.25.4.10.40.1.1.1.7
    optixSdhLineBoardSRJ0Mask OBJECT-TYPE
        SYNTAX OCTET STRING
        MAX-ACCESS read-write
        STATUS current
        DESCRIPTION
            "This object indicates the Mask of J0 byte to be received."
        ::= { optixSdhJ0Entry 7 }

    -- 1.3.6.1.4.1.2011.2.25.4.10.40.1.1.1.8
    optixSdhLineBoardSTJ0Mask OBJECT-TYPE
        SYNTAX OCTET STRING
        MAX-ACCESS read-write
        STATUS current
        DESCRIPTION
            "This object indicates the Mask of J0 byte to be transmitted."
        ::= { optixSdhJ0Entry 8 }

    -- 1.3.6.1.4.1.2011.2.25.4.10.40.1.1.1.9
    optixSdhLineBoardTestAls OBJECT-TYPE
        SYNTAX INTEGER
        {
            start(1),
            invalid(255)
        }
        MAX-ACCESS read-write
        STATUS current
        DESCRIPTION
            "This object indicates start test ALS of the SDH line board,query invalied. 1: start, 255: invalid"
        ::= { optixSdhJ0Entry 9 }

    -- 1.3.6.1.4.1.2011.2.25.4.10.40.1.2
    optixSdhLineBoardVC4Table OBJECT-TYPE
        SYNTAX SEQUENCE OF OptixSdhLineBoardVC4Entry
        MAX-ACCESS not-accessible
        STATUS current
        DESCRIPTION
            "This table describes configurations ofVC4 timeslot management of the SDH line board."
        ::= { optixSdhLineBoardGroup 2 }

    -- 1.3.6.1.4.1.2011.2.25.4.10.40.1.2.1
    optixSdhLineBoardVC4Entry OBJECT-TYPE
        SYNTAX OptixSdhLineBoardVC4Entry
        MAX-ACCESS not-accessible
        STATUS current
        DESCRIPTION
            "Thisentry describes configurations of VC4 timeslot management of the SDH line board."
        INDEX{ optixLogBoardId,optixLogSubCardId,optixPortId,optixSdhHP }
        ::= { optixSdhLineBoardVC4Table 1 }

    OptixSdhLineBoardVC4Entry ::=
        SEQUENCE {
            optixSdhHP
                Unsigned32,
            optixSdhLineBoardSRJ1Mode
                Unsigned32,
            optixSdhLineBoardSRJ1Value
                OCTET STRING,
            optixSdhLineBoardSTJ1Mode
                Unsigned32,
            optixSdhLineBoardSTJ1Value
                OCTET STRING,
            optixSdhLineBoardRJ1Mode
                Unsigned32,
            optixSdhLineBoardRJ1Value
                OCTET STRING,
            optixSdhLineBoardSRC2Value
                INTEGER,
            optixSdhLineBoardSTC2Value
                INTEGER,
            optixSdhLineBoardRC2Value
                INTEGER,
            optixSdhLineBoardPassmode
                INTEGER,
            optixSdhLineBoardSRJ1Mask
                OCTET STRING,
            optixSdhLineBoardSTJ1Mask
                OCTET STRING
        }

    -- 1.3.6.1.4.1.2011.2.25.4.10.40.1.2.1.1
    optixSdhHP OBJECT-TYPE
        SYNTAX Unsigned32
        MAX-ACCESS not-accessible
        STATUS current
        DESCRIPTION
            "This object indicates the high-order channel ID. Value range: 1 to 2."
        ::= { optixSdhLineBoardVC4Entry 1 }

    -- 1.3.6.1.4.1.2011.2.25.4.10.40.1.2.1.2
    optixSdhLineBoardSRJ1Mode OBJECT-TYPE
        SYNTAX Unsigned32
        MAX-ACCESS read-write
        STATUS current
        DESCRIPTION
            "This object indicates the J1 byte to be received mode. Value range: 0 to 3."
        ::= { optixSdhLineBoardVC4Entry 2 }

    -- 1.3.6.1.4.1.2011.2.25.4.10.40.1.2.1.3
    optixSdhLineBoardSRJ1Value OBJECT-TYPE
        SYNTAX OCTET STRING(SIZE(0..64))
        MAX-ACCESS read-write
        STATUS current
        DESCRIPTION
            "This object indicates the value of the J1 byte to be received.len 16 in mode 0&1, len 64 in mode 2, 1 UC in mode 3, When mode is 0,the highest bit of first byte must be 1;When mode is 1, the first byte of J1valule will be ignored."
        ::= { optixSdhLineBoardVC4Entry 3 }

    -- 1.3.6.1.4.1.2011.2.25.4.10.40.1.2.1.4
    optixSdhLineBoardSTJ1Mode OBJECT-TYPE
        SYNTAX Unsigned32
        MAX-ACCESS read-write
        STATUS current
        DESCRIPTION
            "This object indicates the J1 byte to be transmitted mode. Value range: 0 to 3."
        ::= { optixSdhLineBoardVC4Entry 4 }

    -- 1.3.6.1.4.1.2011.2.25.4.10.40.1.2.1.5
    optixSdhLineBoardSTJ1Value OBJECT-TYPE
        SYNTAX OCTET STRING(SIZE(0..64))
        MAX-ACCESS read-write
        STATUS current
        DESCRIPTION
            "This object indicates the value of the J1 byte to be transmitted.len 16 in mode 0&1, len 64 in mode 2, 1 UC in mode 3, When mode is 0,the highest bit of first byte must be 1;When mode is 1, the first byte of J1valule will be ignored."
        ::= { optixSdhLineBoardVC4Entry 5 }

    -- 1.3.6.1.4.1.2011.2.25.4.10.40.1.2.1.6
    optixSdhLineBoardRJ1Mode OBJECT-TYPE
        SYNTAX Unsigned32
        MAX-ACCESS read-only
        STATUS current
        DESCRIPTION
            "This object indicates the received J1 byte mode. Value range: 0 to 3."
        ::= { optixSdhLineBoardVC4Entry 6 }

    -- 1.3.6.1.4.1.2011.2.25.4.10.40.1.2.1.7
    optixSdhLineBoardRJ1Value OBJECT-TYPE
        SYNTAX OCTET STRING(SIZE(0..64))
        MAX-ACCESS read-only
        STATUS current
        DESCRIPTION
            "This object indicates the value of the received J1 byte..len 16 in mode 0&1, len 64 in mode 2, 1 UC in mode 3, When mode is 0,the highest bit of first byte must be 1;When mode is 1, the first byte of J1valule will be ignored."
        ::= { optixSdhLineBoardVC4Entry 7 }

    -- 1.3.6.1.4.1.2011.2.25.4.10.40.1.2.1.8
    optixSdhLineBoardSRC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-write
        STATUS current
        DESCRIPTION
            "This object indicates the value of theC2 byte to be received. 0: uneq, 1: unsp, 2: tugs, 3: tulock, 4: asyn, 5: develop, 18: a140, 19: atm, 20: man, 21: fddi, 22: ppp, 23: resvp1, 24: laps, 25: resvp2, 26: enet, 27: gfp, 207: resv, 225: resvn1, 252: resvn2, 254: test, 255: ais"
        ::= { optixSdhLineBoardVC4Entry 8 }

    -- 1.3.6.1.4.1.2011.2.25.4.10.40.1.2.1.9
    optixSdhLineBoardSTC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-write
        STATUS current
        DESCRIPTION
            "This object indicates the value of theC2 byte to be transmitted. 0: uneq, 1: unsp, 2: tugs, 3: tulock, 4: asyn, 5: develop, 18: a140, 19: atm, 20: man, 21: fddi, 22: ppp, 23: resvp1, 24: laps, 25: resvp2, 26: enet, 27: gfp, 207: resv, 225: resvn1, 252: resvn2, 254: test, 255: ais"
        ::= { optixSdhLineBoardVC4Entry 9 }

    -- 1.3.6.1.4.1.2011.2.25.4.10.40.1.2.1.10
    optixSdhLineBoardRC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-only
        STATUS current
        DESCRIPTION
            "This object indicates the value of the receivedC2 byte. 0: uneq, 1: unsp, 2: tugs, 3: tulock, 4: asyn, 5: develop, 18: a140, 19: atm, 20: man, 21: fddi, 22: ppp, 23: resvp1, 24: laps, 25: resvp2, 26: enet, 27: gfp, 207: resv, 225: resvn1, 252: resvn2, 254: test, 255: ais"
        ::= { optixSdhLineBoardVC4Entry 10 }

    -- 1.3.6.1.4.1.2011.2.25.4.10.40.1.2.1.11
    optixSdhLineBoardPassmode OBJECT-TYPE
        SYNTAX INTEGER
        {
            term(0),
            pass(1),
            auto(2)
        }
        MAX-ACCESS read-write
        STATUS current
        DESCRIPTION
            "This object indicates the overhead processing mode. 0: term, 1: pass, 2: auto"
        ::= { optixSdhLineBoardVC4Entry 11 }

    -- 1.3.6.1.4.1.2011.2.25.4.10.40.1.2.1.12
    optixSdhLineBoardSRJ1Mask OBJECT-TYPE
        SYNTAX OCTET STRING (SIZE(0..16))
        MAX-ACCESS read-write
        STATUS current
        DESCRIPTION
            "This object indicates the Mask of J1 byte to be transmitted."
        ::= { optixSdhLineBoardVC4Entry 12 }

    -- 1.3.6.1.4.1.2011.2.25.4.10.40.1.2.1.13
    optixSdhLineBoardSTJ1Mask OBJECT-TYPE
        SYNTAX OCTET STRING
        MAX-ACCESS read-write
        STATUS current
        DESCRIPTION
            "This object indicates the Mask of J1 byte to be transmitted."
        ::= { optixSdhLineBoardVC4Entry 13 }

    -- 1.3.6.1.4.1.2011.2.25.4.10.40.1.3
    optixSdhLineBoardVC12Table OBJECT-TYPE
        SYNTAX SEQUENCE OF OptixSdhLineBoardVC12Entry
        MAX-ACCESS not-accessible
        STATUS current
        DESCRIPTION
            "This table describes configurations of VC12 timeslot management of the SDH line board."
        ::= { optixSdhLineBoardGroup 3 }

    -- 1.3.6.1.4.1.2011.2.25.4.10.40.1.3.1
    optixSdhLineBoardVC12Entry OBJECT-TYPE
        SYNTAX OptixSdhLineBoardVC12Entry
        MAX-ACCESS not-accessible
        STATUS current
        DESCRIPTION
            "This entry describes configurations of VC12 timeslot management of the SDH line board."
        INDEX{ optixLogBoardId,optixLogSubCardId,optixPortId,optixSdhHP,optixSdhLP }
        ::= { optixSdhLineBoardVC12Table 1 }

    OptixSdhLineBoardVC12Entry ::=
        SEQUENCE {
            optixSdhLP
                Unsigned32,
            optixSdhLineBoardSRJ2Mode
                Unsigned32,
            optixSdhLineBoardSRJ2Value
                OCTET STRING,
            optixSdhLineBoardSTJ2Mode
                Unsigned32,
            optixSdhLineBoardSTJ2Value
                OCTET STRING,
            optixSdhLineBoardSRV5Value
                Unsigned32,
            optixSdhLineBoardSTV5Value
                Unsigned32,
            optixSdhLineBoardRJ2Mode
                Unsigned32,
            optixSdhLineBoardRJ2Value
                OCTET STRING,
            optixSdhLineBoardRV5Value
                Unsigned32
        }

    -- 1.3.6.1.4.1.2011.2.25.4.10.40.1.3.1.1
    optixSdhLP OBJECT-TYPE
        SYNTAX Unsigned32
        MAX-ACCESS not-accessible
        STATUS current
        DESCRIPTION
            "This object indicates the low-order channel ID."
        ::= { optixSdhLineBoardVC12Entry 1 }

    -- 1.3.6.1.4.1.2011.2.25.4.10.40.1.3.1.2
    optixSdhLineBoardSRJ2Mode OBJECT-TYPE
        SYNTAX Unsigned32
        MAX-ACCESS read-write
        STATUS current
        DESCRIPTION
            "This object indicates the J2 byte to be received mode. Value range: 0 to 1."
        ::= { optixSdhLineBoardVC12Entry 2 }

    -- 1.3.6.1.4.1.2011.2.25.4.10.40.1.3.1.3
    optixSdhLineBoardSRJ2Value OBJECT-TYPE
        SYNTAX OCTET STRING(SIZE(0..16))
        MAX-ACCESS read-write
        STATUS current
        DESCRIPTION
            "This object indicates the value of the J2 byte to be received.16 byte string if j2mode is 1; 1 UC if j2mode is 0."
        ::= { optixSdhLineBoardVC12Entry 3 }

    -- 1.3.6.1.4.1.2011.2.25.4.10.40.1.3.1.4
    optixSdhLineBoardSTJ2Mode OBJECT-TYPE
        SYNTAX Unsigned32
        MAX-ACCESS read-write
        STATUS current
        DESCRIPTION
            "This object indicates the J2 byte to be transmitted mode. Value range: 0 to 1."
        ::= { optixSdhLineBoardVC12Entry 4 }

    -- 1.3.6.1.4.1.2011.2.25.4.10.40.1.3.1.5
    optixSdhLineBoardSTJ2Value OBJECT-TYPE
        SYNTAX OCTET STRING(SIZE(0..16))
        MAX-ACCESS read-write
        STATUS current
        DESCRIPTION
            "This object indicates the value of the J2 byte to be transmitted.16 byte string if j2mode is 1; 1 UC if j2mode is 0."
        ::= { optixSdhLineBoardVC12Entry 5 }

    -- 1.3.6.1.4.1.2011.2.25.4.10.40.1.3.1.6
    optixSdhLineBoardSRV5Value OBJECT-TYPE
        SYNTAX Unsigned32
        MAX-ACCESS read-write
        STATUS current
        DESCRIPTION
            "This object indicates the value of theV5 byte to be received. Value range: 0,2."
        ::= { optixSdhLineBoardVC12Entry 6 }

    -- 1.3.6.1.4.1.2011.2.25.4.10.40.1.3.1.7
    optixSdhLineBoardSTV5Value OBJECT-TYPE
        SYNTAX Unsigned32
        MAX-ACCESS read-write
        STATUS current
        DESCRIPTION
            "This object indicates the value of theV5 byte to be transmitted. Value range: 0,2."
        ::= { optixSdhLineBoardVC12Entry 7 }

    -- 1.3.6.1.4.1.2011.2.25.4.10.40.1.3.1.8
    optixSdhLineBoardRJ2Mode OBJECT-TYPE
        SYNTAX Unsigned32
        MAX-ACCESS read-only
        STATUS current
        DESCRIPTION
            "This object indicates the received J2 byte mode. Value range: 0-1."
        ::= { optixSdhLineBoardVC12Entry 8 }

    -- 1.3.6.1.4.1.2011.2.25.4.10.40.1.3.1.9
    optixSdhLineBoardRJ2Value OBJECT-TYPE
        SYNTAX OCTET STRING (SIZE(0..16))
        MAX-ACCESS read-only
        STATUS current
        DESCRIPTION
            "This object indicates the value of the received J2 byte.16 byte string if j2mode is 1; 1 UC if j2mode is 0."
        ::= { optixSdhLineBoardVC12Entry 9 }

    -- 1.3.6.1.4.1.2011.2.25.4.10.40.1.3.1.10
    optixSdhLineBoardRV5Value OBJECT-TYPE
        SYNTAX Unsigned32
        MAX-ACCESS read-only
        STATUS current
        DESCRIPTION
            "This object indicates the value of the received V5 byte. Value range: 0 to 2."
        ::= { optixSdhLineBoardVC12Entry 10 }

    -- 1.3.6.1.4.1.2011.2.25.4.10.40.1.4
    optixSdhLineBoardAlmClkswTable OBJECT-TYPE
        SYNTAX SEQUENCE OF OptixSdhLineBoardAlmClkswEntry
        MAX-ACCESS not-accessible
        STATUS current
        DESCRIPTION
            "This table describes configurations ofalarm management of the SDH line board."
        ::= { optixSdhLineBoardGroup 4 }

    -- 1.3.6.1.4.1.2011.2.25.4.10.40.1.4.1
    optixSdhLineBoardAlmClkswEntry OBJECT-TYPE
        SYNTAX OptixSdhLineBoardAlmClkswEntry
        MAX-ACCESS not-accessible
        STATUS current
        DESCRIPTION
            "This entry describes configurations ofalarm management of the SDH line board."
        INDEX{ optixLogBoardId,optixLogSubCardId,optixPortId,optixSdhLineBoardAlmId }
        ::= { optixSdhLineBoardAlmClkswTable 1 }

    OptixSdhLineBoardAlmClkswEntry ::=
        SEQUENCE {
            optixSdhLineBoardAlmId
                INTEGER,
            optixSdhLineBoardClkswEnable
                INTEGER
        }

    -- 1.3.6.1.4.1.2011.2.25.4.10.40.1.4.1.1
    optixSdhLineBoardAlmId OBJECT-TYPE
        SYNTAX INTEGER
        {
            msais(33),
            b2exc(35)
        }
        MAX-ACCESS not-accessible
        STATUS current
        DESCRIPTION
            "This object indicates the alarm ID. 33: msais, 35: b2exc"
        ::= { optixSdhLineBoardAlmClkswEntry 1 }

    -- 1.3.6.1.4.1.2011.2.25.4.10.40.1.4.1.2
    optixSdhLineBoardClkswEnable OBJECT-TYPE
        SYNTAX INTEGER
        {
            disable(0),
            enable(1)
        }
        MAX-ACCESS read-write
        STATUS current
        DESCRIPTION
            "This object indicates the enable status of the clock switching. 0: disable, 1: enable"
        ::= { optixSdhLineBoardAlmClkswEntry 2 }

    -- 1.3.6.1.4.1.2011.2.25.4.10.40.1.5
    optixSdhLineBoardB1B2B3ThTable OBJECT-TYPE
        SYNTAX SEQUENCE OF OptixSdhLineBoardB1B2B3ThEntry
        MAX-ACCESS not-accessible
        STATUS current
        DESCRIPTION
            "This table describes the configurations of bit error threshold or deterioration threshold."
        ::= { optixSdhLineBoardGroup 5 }

    -- 1.3.6.1.4.1.2011.2.25.4.10.40.1.5.1
    optixSdhLineBoardB1B2B3ThEntry OBJECT-TYPE
        SYNTAX OptixSdhLineBoardB1B2B3ThEntry
        MAX-ACCESS not-accessible
        STATUS current
        DESCRIPTION
            "This entry describes the configurations of the bit error threshold or deterioration threshold."
        INDEX{ optixLogBoardId,optixLogSubCardId,optixPortId,optixSdhLineBoardThType }
        ::= { optixSdhLineBoardB1B2B3ThTable 1 }

    OptixSdhLineBoardB1B2B3ThEntry ::=
        SEQUENCE {
            optixSdhLineBoardThType
                Unsigned32,
            optixSdhLineBoardExecTh
                Unsigned32,
            optixSdhLineBoardSdTh
                Unsigned32
        }

    -- 1.3.6.1.4.1.2011.2.25.4.10.40.1.5.1.1
    optixSdhLineBoardThType OBJECT-TYPE
        SYNTAX Unsigned32
        MAX-ACCESS not-accessible
        STATUS current
        DESCRIPTION
            "This object indicates the threshold type. 1: B1 threshold, 2: B2 threshold, 3: B3 threshold, 4: B3 threshold in VC-3s, 5: BIP2, 6: B3-IEC. This parameter can be set to 0."
        ::= { optixSdhLineBoardB1B2B3ThEntry 1 }

    -- 1.3.6.1.4.1.2011.2.25.4.10.40.1.5.1.2
    optixSdhLineBoardExecTh OBJECT-TYPE
        SYNTAX Unsigned32
        MAX-ACCESS read-write
        STATUS current
        DESCRIPTION
            "This object indicates the level of performance threshold-crossing. 1: 1.0E-9, 2: 1.0E-8, 3: 1.0E-7, 4: 1.0E-6, 5: 1.0E-5, 6: 1.0E-4, 7: 1.0E-3. The default value is 3 (1.0E-7)."
        ::= { optixSdhLineBoardB1B2B3ThEntry 2 }

    -- 1.3.6.1.4.1.2011.2.25.4.10.40.1.5.1.3
    optixSdhLineBoardSdTh OBJECT-TYPE
        SYNTAX Unsigned32
        MAX-ACCESS read-write
        STATUS current
        DESCRIPTION
            "This object indicates the level of performance deterioration. 1: 1.0E-9, 2: 1.0E-8, 3: 1.0E-7, 4: 1.0E-6, 5: 1.0E-5, 6: 1.0E-4, 7: 1.0E-3. The default value is 6 (1.0E-4)."
        ::= { optixSdhLineBoardB1B2B3ThEntry 3 }

    -- 1.3.6.1.4.1.2011.2.25.4.10.40.1.6
    optixSdhLineBoardMember OBJECT IDENTIFIER ::= { optixSdhLineBoardGroup 6 }

    -- 1.3.6.1.4.1.2011.2.25.4.10.40.1.6.1
    optixSdhBitTestBid OBJECT-TYPE
        SYNTAX Unsigned32
        MAX-ACCESS accessible-for-notify
        STATUS current
        DESCRIPTION
            "This parameter indicates the board ID for the SDH bit test."
        ::= { optixSdhLineBoardMember 1 }

    -- 1.3.6.1.4.1.2011.2.25.4.10.40.1.6.2
    optixSdhBitTestTime OBJECT-TYPE
        SYNTAX Unsigned32
        MAX-ACCESS accessible-for-notify
        STATUS current
        DESCRIPTION
            "This parameter indicates the bit test time, which counts from 0x0001(The unit is either second in a short-time test, or minute in a long- and very long-time test)"
        ::= { optixSdhLineBoardMember 2 }

    -- 1.3.6.1.4.1.2011.2.25.4.10.40.1.6.3
    optixSdhBitTestSubcardId OBJECT-TYPE
        SYNTAX Unsigned32
        MAX-ACCESS accessible-for-notify
        STATUS current
        DESCRIPTION
            "This parameter indicates the subboard ID for the SDH bit test."
        ::= { optixSdhLineBoardMember 3 }

    -- 1.3.6.1.4.1.2011.2.25.4.10.40.1.6.4
    optixSdhBitTestPortID OBJECT-TYPE
        SYNTAX Unsigned32
        MAX-ACCESS accessible-for-notify
        STATUS current
        DESCRIPTION
            "This parameter indicates the port ID for the SDH bit test."
        ::= { optixSdhLineBoardMember 4 }

    -- 1.3.6.1.4.1.2011.2.25.4.10.40.1.6.5
    optixSdhBitTestVc4p OBJECT-TYPE
        SYNTAX Unsigned32
        MAX-ACCESS accessible-for-notify
        STATUS current
        DESCRIPTION
            "This parameter indicates the VC4 path for the SDH bit test."
        ::= { optixSdhLineBoardMember 5 }

    -- 1.3.6.1.4.1.2011.2.25.4.10.40.1.6.6
    optixSdhBitTestAu3p OBJECT-TYPE
        SYNTAX Unsigned32
        MAX-ACCESS accessible-for-notify
        STATUS current
        DESCRIPTION
            "This parameter indicates the AU3 path for the SDH bit test."
        ::= { optixSdhLineBoardMember 6 }

    -- 1.3.6.1.4.1.2011.2.25.4.10.40.1.6.7
    optixSdhBitTestTotalErrNum OBJECT-TYPE
        SYNTAX Unsigned32
        MAX-ACCESS accessible-for-notify
        STATUS current
        DESCRIPTION
            "This parameter indicates the total number of bit errors in the reporting period of the SDH bit test."
        ::= { optixSdhLineBoardMember 7 }

    -- 1.3.6.1.4.1.2011.2.25.4.10.40.1.7
    optixSdhLineBoardEvent OBJECT IDENTIFIER ::= { optixSdhLineBoardGroup 7 }

    -- 1.3.6.1.4.1.2011.2.25.4.10.40.1.7.1
    optixSdhBitTestLu NOTIFICATION-TYPE
        OBJECTS{ optixSdhBitTestBid,optixSdhBitTestTime,optixSdhBitTestSubcardId,optixSdhBitTestPortID,optixSdhBitTestVc4p,optixSdhBitTestAu3p,optixSdhBitTestTotalErrNum }
        STATUS current
        DESCRIPTION
            "This parameter indicates the pseudo-code test event for the PRBS line board or cross-connect board."
        ::= { optixSdhLineBoardEvent 1 }

END
