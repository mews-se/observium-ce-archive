-- OPTIX-RTN-AES-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-AES-MGR-MIB DEFINITIONS ::= BEGIN
    IMPORTS
        optixProvisionRtn
            FROM OPTIX-OID-MIB
        OBJECT-GROUP,MODULE-COMPLIANCE
            FROM SNMPv2-CONF
        Unsigned32,OBJECT-TYPE,MODULE-IDENTITY,NOTIFICATION-TYPE
            FROM SNMPv2-SMI
        TEXTUAL-CONVENTION,DateAndTime
            FROM SNMPv2-TC
        OPTIXRtnEnableStateType
            FROM OPTIX-RTN-GENNERAL-MIB
        optixRtnBoardID,optixRtnSubCardID,optixRtnPortID
            FROM OPTIX-RTN-IFBOARD-ATTRIB-MIB
        ;

    optixRtnAesMgr MODULE-IDENTITY
        LAST-UPDATED "201410201858Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module describes AES-related configuration and query functions on RTNs, including the encryption enabling status, encryption and authentication information, encryption mode, key exchange period, forced exchange of encryption keys, remaining validity period of encryption keys, encryption key exchange history, and encryption key exchange status."
        REVISION "201410201858Z"
        DESCRIPTION
            "The initial revision of this MIB module1."
        ::={ optixProvisionRtn 8 }

    OPTIXRtnAesMode ::= TEXTUAL-CONVENTION
        STATUS current
        DESCRIPTION
            "Encryption mode:0-aesccm128,1-aesccm192,2-aesccm256"
        SYNTAX INTEGER
        {
            aesccm256(2)
        }

    OPTIXRtnAesKeySwitchStatus ::= TEXTUAL-CONVENTION
        STATUS current
        DESCRIPTION
            "Encryption key exchange status: 0-forcibly stopped, 1-authentication failed, 2-authentication succeeded, 3-negotiation failed, 4-negotiation succeeded, 5-self-check failed"
        SYNTAX INTEGER
        {
            forcestop(0),
            authenticationfail(1),
            authenticationsuccess(2),
            negotiationfail(3),
            negotiationsuccess(4),
            selfcheckerror(5)
        }

    OPTIXRtnAesKeySwitchResult ::= TEXTUAL-CONVENTION
        STATUS current
        DESCRIPTION
            "Encryption key negotiation result: 0-negotiation succeeded, 1-negotiation failed, 2-forcibly initialized"
        SYNTAX INTEGER
        {
            negosuccess(0),
            negofail(1),
            negoforceinit(2)
        }

    OPTIXRtnAesKeyForceSwitch ::= TEXTUAL-CONVENTION
        STATUS current
        DESCRIPTION
            "om"
        SYNTAX INTEGER
        {
            forceswitch(1)
        }

    -- 1.3.6.1.4.1.2011.2.25.4.40.8.1
    optixRtnAesAttr OBJECT IDENTIFIER ::= { optixRtnAesMgr 1 }

    -- 1.3.6.1.4.1.2011.2.25.4.40.8.1.1
    optixRtnAesGeneralAttrTable OBJECT-TYPE
        SYNTAX SEQUENCE OF OptixRtnAesGeneralAttrEntry
        MAX-ACCESS not-accessible
        STATUS current
        DESCRIPTION
            "This table describes basic AES attributes."
        ::= { optixRtnAesAttr 1 }

    -- 1.3.6.1.4.1.2011.2.25.4.40.8.1.1.1
    optixRtnAesGeneralAttrEntry OBJECT-TYPE
        SYNTAX OptixRtnAesGeneralAttrEntry
        MAX-ACCESS not-accessible
        STATUS current
        DESCRIPTION
            "Management entry of basic AES configuration attributes"
        INDEX{ optixRtnBoardID,optixRtnSubCardID,optixRtnPortID }
        ::= { optixRtnAesGeneralAttrTable 1 }

    OptixRtnAesGeneralAttrEntry ::=
        SEQUENCE {
            optixRtnAesEnableStatus
                OPTIXRtnEnableStateType,
            optixRtnAesAKInfo
                OCTET STRING,
            optixRtnAesMode
                OPTIXRtnAesMode,
            optixRtnAesKeySwitchTime
                Unsigned32,
            optixRtnForceSwitchAesKey
                OPTIXRtnAesKeyForceSwitch,
            optixRtnAesKeySwitchStatus
                OPTIXRtnAesKeySwitchStatus,
            optixRtnAesKeyReminderTime
                Unsigned32
        }

    -- 1.3.6.1.4.1.2011.2.25.4.40.8.1.1.1.1
    optixRtnAesEnableStatus OBJECT-TYPE
        SYNTAX OPTIXRtnEnableStateType
        MAX-ACCESS read-write
        STATUS current
        DESCRIPTION
            "encryption enabling status"
        ::= { optixRtnAesGeneralAttrEntry 1 }

    -- 1.3.6.1.4.1.2011.2.25.4.40.8.1.1.1.2
    optixRtnAesAKInfo OBJECT-TYPE
        SYNTAX OCTET STRING
        MAX-ACCESS read-write
        STATUS current
        DESCRIPTION
            "encryption and authentication information"
        ::= { optixRtnAesGeneralAttrEntry 2 }

    -- 1.3.6.1.4.1.2011.2.25.4.40.8.1.1.1.3
    optixRtnAesMode OBJECT-TYPE
        SYNTAX OPTIXRtnAesMode
        MAX-ACCESS read-write
        STATUS current
        DESCRIPTION
            "encryption mode"
        ::= { optixRtnAesGeneralAttrEntry 3 }

    -- 1.3.6.1.4.1.2011.2.25.4.40.8.1.1.1.4
    optixRtnAesKeySwitchTime OBJECT-TYPE
        SYNTAX Unsigned32
        MAX-ACCESS read-write
        STATUS current
        DESCRIPTION
            "key exchange period"
        ::= { optixRtnAesGeneralAttrEntry 4 }

    -- 1.3.6.1.4.1.2011.2.25.4.40.8.1.1.1.5
    optixRtnForceSwitchAesKey OBJECT-TYPE
        SYNTAX OPTIXRtnAesKeyForceSwitch
        MAX-ACCESS read-write
        STATUS current
        DESCRIPTION
            "forced exchange of encryption keys"
        ::= { optixRtnAesGeneralAttrEntry 5 }

    -- 1.3.6.1.4.1.2011.2.25.4.40.8.1.1.1.6
    optixRtnAesKeySwitchStatus OBJECT-TYPE
        SYNTAX OPTIXRtnAesKeySwitchStatus
        MAX-ACCESS read-only
        STATUS current
        DESCRIPTION
            "encryption key exchange status"
        ::= { optixRtnAesGeneralAttrEntry 6 }

    -- 1.3.6.1.4.1.2011.2.25.4.40.8.1.1.1.7
    optixRtnAesKeyReminderTime OBJECT-TYPE
        SYNTAX Unsigned32
        MAX-ACCESS read-only
        STATUS current
        DESCRIPTION
            "remaining validity period of encryption keys"
        ::= { optixRtnAesGeneralAttrEntry 7 }

    -- 1.3.6.1.4.1.2011.2.25.4.40.8.1.2
    optixRtnAesKeySwitchRecordTable OBJECT-TYPE
        SYNTAX SEQUENCE OF OptixRtnAesKeySwitchRecordEntry
        MAX-ACCESS not-accessible
        STATUS current
        DESCRIPTION
            "This table describes the related information of encryption key exchange history records, including the start time, end time,reslut and reason of encryption key exchange."
        ::= { optixRtnAesAttr 2 }

    -- 1.3.6.1.4.1.2011.2.25.4.40.8.1.2.1
    optixRtnAesKeySwitchRecordEntry OBJECT-TYPE
        SYNTAX OptixRtnAesKeySwitchRecordEntry
        MAX-ACCESS not-accessible
        STATUS current
        DESCRIPTION
            "Management entry of encryption key exchange history records."
        INDEX{ optixRtnAesSwRecordBoardID,optixRtnAesSwRecordSubCardID,optixRtnAesSwRecordPortID,optixRtnAesSwRecordNum,optixRtnAesSwRecordNo }
        ::= { optixRtnAesKeySwitchRecordTable 1 }

    OptixRtnAesKeySwitchRecordEntry ::=
        SEQUENCE {
            optixRtnAesSwRecordBoardID
                Unsigned32,
            optixRtnAesSwRecordSubCardID
                Unsigned32,
            optixRtnAesSwRecordPortID
                Unsigned32,
            optixRtnAesSwRecordNum
                Unsigned32,
            optixRtnAesSwRecordNo
                Unsigned32,
            optixRtnAesSwRecordStarttime
                DateAndTime,
            optixRtnAesSwRecordEndtime
                DateAndTime,
            optixRtnAesSwRecordResult
                OPTIXRtnAesKeySwitchResult,
            optixRtnAesSwRecordReason
                Unsigned32
        }

    -- 1.3.6.1.4.1.2011.2.25.4.40.8.1.2.1.1
    optixRtnAesSwRecordBoardID OBJECT-TYPE
        SYNTAX Unsigned32
        MAX-ACCESS not-accessible
        STATUS current
        DESCRIPTION
            "Board id of encryption key exchange"
        ::= { optixRtnAesKeySwitchRecordEntry 1 }

    -- 1.3.6.1.4.1.2011.2.25.4.40.8.1.2.1.2
    optixRtnAesSwRecordSubCardID OBJECT-TYPE
        SYNTAX Unsigned32
        MAX-ACCESS not-accessible
        STATUS current
        DESCRIPTION
            "Subcard id of encryption key exchange"
        ::= { optixRtnAesKeySwitchRecordEntry 2 }

    -- 1.3.6.1.4.1.2011.2.25.4.40.8.1.2.1.3
    optixRtnAesSwRecordPortID OBJECT-TYPE
        SYNTAX Unsigned32
        MAX-ACCESS not-accessible
        STATUS current
        DESCRIPTION
            "Port id of encryption key exchange"
        ::= { optixRtnAesKeySwitchRecordEntry 3 }

    -- 1.3.6.1.4.1.2011.2.25.4.40.8.1.2.1.4
    optixRtnAesSwRecordNum OBJECT-TYPE
        SYNTAX Unsigned32 (1..512)
        MAX-ACCESS not-accessible
        STATUS current
        DESCRIPTION
            "Total number of encryption key exchange history records"
        ::= { optixRtnAesKeySwitchRecordEntry 4 }

    -- 1.3.6.1.4.1.2011.2.25.4.40.8.1.2.1.5
    optixRtnAesSwRecordNo OBJECT-TYPE
        SYNTAX Unsigned32 (1..512)
        MAX-ACCESS not-accessible
        STATUS current
        DESCRIPTION
            "Key exchange history record No. XXX"
        ::= { optixRtnAesKeySwitchRecordEntry 5 }

    -- 1.3.6.1.4.1.2011.2.25.4.40.8.1.2.1.6
    optixRtnAesSwRecordStarttime OBJECT-TYPE
        SYNTAX DateAndTime
        MAX-ACCESS read-only
        STATUS current
        DESCRIPTION
            "Start time of encryption key exchange"
        ::= { optixRtnAesKeySwitchRecordEntry 6 }

    -- 1.3.6.1.4.1.2011.2.25.4.40.8.1.2.1.7
    optixRtnAesSwRecordEndtime OBJECT-TYPE
        SYNTAX DateAndTime
        MAX-ACCESS read-only
        STATUS current
        DESCRIPTION
            "End time of encryption key exchange"
        ::= { optixRtnAesKeySwitchRecordEntry 7 }

    -- 1.3.6.1.4.1.2011.2.25.4.40.8.1.2.1.8
    optixRtnAesSwRecordResult OBJECT-TYPE
        SYNTAX OPTIXRtnAesKeySwitchResult
        MAX-ACCESS read-only
        STATUS current
        DESCRIPTION
            "Result of encryption key exchange"
        ::= { optixRtnAesKeySwitchRecordEntry 8 }

    -- 1.3.6.1.4.1.2011.2.25.4.40.8.1.2.1.9
    optixRtnAesSwRecordReason OBJECT-TYPE
        SYNTAX Unsigned32
        MAX-ACCESS read-only
        STATUS current
        DESCRIPTION
            "Reason of encryption key exchange"
        ::= { optixRtnAesKeySwitchRecordEntry 9 }
	
    -- 1.3.6.1.4.1.2011.2.25.4.40.8.3
    optixRtnAESVerInfoMgr OBJECT IDENTIFIER ::= { optixRtnAesMgr 3 }
    
    -- 1.3.6.1.4.1.2011.2.25.4.40.8.3.1
    optixRtnIAesVerInfo OBJECT-TYPE
        SYNTAX  OCTET STRING       
        MAX-ACCESS read-only
        STATUS current
        DESCRIPTION
            " the information of AES  version."
        ::= { optixRtnAESVerInfoMgr 1 }

END
