-- OPTIX-SDH-EOW-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-EOW-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        optixLogBoardId
            FROM OPTIX-BOARD-MANAGE-MIB
        optixPortId
            FROM OPTIX-PORT-MANAGE-MIB
        RowStatus
            FROM SNMPv2-TC
        ;

    optixSdhEow MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations of orderwire management."
        REVISION "201204200000Z"
        DESCRIPTION
            "The initial revision of this MIB module1."
        ::={ optixProvisionSdh 50 }

    -- 1.3.6.1.4.1.2011.2.25.4.10.50.1
    optixSdhEowGroup OBJECT IDENTIFIER ::= { optixSdhEow 1 }

    -- 1.3.6.1.4.1.2011.2.25.4.10.50.1.1
    optixEowTable OBJECT-TYPE
        SYNTAX SEQUENCE OF OptixEowEntry
        MAX-ACCESS not-accessible
        STATUS current
        DESCRIPTION
            "This table describes the basicorderwire configurations."
        ::= { optixSdhEowGroup 1 }

    -- 1.3.6.1.4.1.2011.2.25.4.10.50.1.1.1
    optixEowEntry OBJECT-TYPE
        SYNTAX OptixEowEntry
        MAX-ACCESS not-accessible
        STATUS current
        DESCRIPTION
            "Thisentry describes the basic orderwire configurations."
        INDEX{ optixLogBoardId }
        ::= { optixEowTable 1 }

    OptixEowEntry ::=
        SEQUENCE {
            optixEowTelLen
                Unsigned32,
            optixEowReqTime
                Unsigned32,
            optixEowE1orE2Byte
                INTEGER,
            optixEowMeetNum
                Unsigned32,
            optixEowGroupTelNum
                Unsigned32,
            optixEowSubnetLen
                Unsigned32
        }

    -- 1.3.6.1.4.1.2011.2.25.4.10.50.1.1.1.1
    optixEowTelLen OBJECT-TYPE
        SYNTAX Unsigned32
        MAX-ACCESS read-write
        STATUS current
        DESCRIPTION
            "This object indicates the length (range 3 to 8) of the orderwire call number"
        ::= { optixEowEntry 1 }

    -- 1.3.6.1.4.1.2011.2.25.4.10.50.1.1.1.2
    optixEowReqTime OBJECT-TYPE
        SYNTAX Unsigned32
        MAX-ACCESS read-write
        STATUS current
        DESCRIPTION
            "This object indicates the call waiting time. Value range: 1 to 9."
        ::= { optixEowEntry 2 }

    -- 1.3.6.1.4.1.2011.2.25.4.10.50.1.1.1.3
    optixEowE1orE2Byte OBJECT-TYPE
        SYNTAX INTEGER
        {
            e1(0),
            e2(1)
        }
        MAX-ACCESS read-write
        STATUS current
        DESCRIPTION
            "This parameter indicates the E1/E2 bytes selective receiving of orderwires. 0: E1 1: E2"
        ::= { optixEowEntry 3 }

    -- 1.3.6.1.4.1.2011.2.25.4.10.50.1.1.1.4
    optixEowMeetNum OBJECT-TYPE
        SYNTAX Unsigned32
        MAX-ACCESS read-write
        STATUS current
        DESCRIPTION
            "This object indicates the meet number (range 100 to 99999999) of which the value depends on tellen"
        ::= { optixEowEntry 4 }

    -- 1.3.6.1.4.1.2011.2.25.4.10.50.1.1.1.5
    optixEowGroupTelNum OBJECT-TYPE
        SYNTAX Unsigned32
        MAX-ACCESS read-only
        STATUS current
        DESCRIPTION
            "This object indicates the group telphone number. This parameter takes a fixed value of 888."
        ::= { optixEowEntry 5 }

    -- 1.3.6.1.4.1.2011.2.25.4.10.50.1.1.1.6
    optixEowSubnetLen OBJECT-TYPE
        SYNTAX Unsigned32
        MAX-ACCESS read-write
        STATUS current
        DESCRIPTION
            "This object indicates the subnet ID length. Value range: 1 or 2."
        ::= { optixEowEntry 6 }

    -- 1.3.6.1.4.1.2011.2.25.4.10.50.1.2
    optixEowTelTable OBJECT-TYPE
        SYNTAX SEQUENCE OF OptixEowTelEntry
        MAX-ACCESS not-accessible
        STATUS current
        DESCRIPTION
            "This table describes the basiccall configurations."
        ::= { optixSdhEowGroup 2 }

    -- 1.3.6.1.4.1.2011.2.25.4.10.50.1.2.1
    optixEowTelEntry OBJECT-TYPE
        SYNTAX OptixEowTelEntry
        MAX-ACCESS not-accessible
        STATUS current
        DESCRIPTION
            "Thisentry describes the basic call configurations."
        INDEX{ optixLogBoardId,optixEowTelNum }
        ::= { optixEowTelTable 1 }

    OptixEowTelEntry ::=
        SEQUENCE {
            optixEowTelNum
                Unsigned32,
            optixEowTelNumber
                Unsigned32
        }

    -- 1.3.6.1.4.1.2011.2.25.4.10.50.1.2.1.1
    optixEowTelNum OBJECT-TYPE
        SYNTAX Unsigned32
        MAX-ACCESS not-accessible
        STATUS current
        DESCRIPTION
            "This object indicates the numbersequence. Value range: 1 to N. RTN equipment supports only 1."
        ::= { optixEowTelEntry 1 }

    -- 1.3.6.1.4.1.2011.2.25.4.10.50.1.2.1.2
    optixEowTelNumber OBJECT-TYPE
        SYNTAX Unsigned32
        MAX-ACCESS read-write
        STATUS current
        DESCRIPTION
            "This object indicates the phone number. Value range: 100 to 9999999."
        ::= { optixEowTelEntry 2 }

    -- 1.3.6.1.4.1.2011.2.25.4.10.50.1.3
    optixEowSubnetTable OBJECT-TYPE
        SYNTAX SEQUENCE OF OptixEowSubnetEntry
        MAX-ACCESS not-accessible
        STATUS current
        DESCRIPTION
            "This table describes the basicsubnet configurations."
        ::= { optixSdhEowGroup 3 }

    -- 1.3.6.1.4.1.2011.2.25.4.10.50.1.3.1
    optixEowSubnetEntry OBJECT-TYPE
        SYNTAX OptixEowSubnetEntry
        MAX-ACCESS not-accessible
        STATUS current
        DESCRIPTION
            "Thisentry describes the basic subnet configurations."
        INDEX{ optixLogBoardId,optixLogBoardId,optixPortId }
        ::= { optixEowSubnetTable 1 }

    OptixEowSubnetEntry ::=
        SEQUENCE {
            optixEowSubnetId
                Unsigned32
        }

    -- 1.3.6.1.4.1.2011.2.25.4.10.50.1.3.1.1
    optixEowSubnetId OBJECT-TYPE
        SYNTAX Unsigned32
        MAX-ACCESS read-write
        STATUS current
        DESCRIPTION
            "This object indicates the subnet ID, which must be a hexademical number that ranges from 0x01 to 0x99, and consists of only digits 0 to 9 but no characters A to F"
        ::= { optixEowSubnetEntry 1 }

    -- 1.3.6.1.4.1.2011.2.25.4.10.50.1.4
    optixEowPortUsedTable OBJECT-TYPE
        SYNTAX SEQUENCE OF OptixEowPortUsedEntry
        MAX-ACCESS not-accessible
        STATUS current
        DESCRIPTION
            "This table describes the basic configurations ofport usage."
        ::= { optixSdhEowGroup 4 }

    -- 1.3.6.1.4.1.2011.2.25.4.10.50.1.4.1
    optixEowPortUsedEntry OBJECT-TYPE
        SYNTAX OptixEowPortUsedEntry
        MAX-ACCESS not-accessible
        STATUS current
        DESCRIPTION
            "Thisentry describes the basic configurations of port usage."
        INDEX{ optixLogBoardId,optixEowIuBid,optixPortId }
        ::= { optixEowPortUsedTable 1 }

    OptixEowPortUsedEntry ::=
        SEQUENCE {
            optixEowIuBid
                Unsigned32,
            optixEowLineUsed
                INTEGER,
            optixEowMeetLineUsed
                INTEGER
        }

    -- 1.3.6.1.4.1.2011.2.25.4.10.50.1.4.1.1
    optixEowIuBid OBJECT-TYPE
        SYNTAX Unsigned32
        MAX-ACCESS not-accessible
        STATUS current
        DESCRIPTION
            "This object indicates the slot ID and board ID of the common service management line board"
        ::= { optixEowPortUsedEntry 1 }

    -- 1.3.6.1.4.1.2011.2.25.4.10.50.1.4.1.2
    optixEowLineUsed OBJECT-TYPE
        SYNTAX INTEGER
        {
            unused(0),
            used(1)
        }
        MAX-ACCESS read-write
        STATUS current
        DESCRIPTION
            "This object indicates the optical port usage information. 0: unused, 1: used"
        ::= { optixEowPortUsedEntry 2 }

    -- 1.3.6.1.4.1.2011.2.25.4.10.50.1.4.1.3
    optixEowMeetLineUsed OBJECT-TYPE
        SYNTAX INTEGER
        {
            unused(0),
            used(1)
        }
        MAX-ACCESS read-write
        STATUS current
        DESCRIPTION
            "This object indicates the meet optical port usage information. 0: unused, 1: used"
        ::= { optixEowPortUsedEntry 3 }

    -- 1.3.6.1.4.1.2011.2.25.4.10.50.1.5
    optixDataPortTable OBJECT-TYPE
        SYNTAX SEQUENCE OF OptixDataPortEntry
        MAX-ACCESS not-accessible
        STATUS current
        DESCRIPTION
            "Thistable describes the basicbroadcast data port configurations."
        ::= { optixSdhEowGroup 5 }

    -- 1.3.6.1.4.1.2011.2.25.4.10.50.1.5.1
    optixDataPortEntry OBJECT-TYPE
        SYNTAX OptixDataPortEntry
        MAX-ACCESS not-accessible
        STATUS current
        DESCRIPTION
            "Thisentry describes the basic broadcast data port configurations."
        INDEX{ optixLogBoardId,optixDataPortOhSlot,optixDataPortSlavePortId }
        ::= { optixDataPortTable 1 }

    OptixDataPortEntry ::=
        SEQUENCE {
            optixDataPortOhSlot
                Unsigned32,
            optixDataPortSlavePortId
                Unsigned32,
            optixDataPortMainPortId
                Unsigned32,
            optixDataPortSlavePortNum
                Unsigned32
        }

    -- 1.3.6.1.4.1.2011.2.25.4.10.50.1.5.1.1
    optixDataPortOhSlot OBJECT-TYPE
        SYNTAX Unsigned32
        MAX-ACCESS not-accessible
        STATUS current
        DESCRIPTION
            "This object indicates the overhead byte. Serial1 to Serial4. Value range: 1 to 4."
        ::= { optixDataPortEntry 1 }

    -- 1.3.6.1.4.1.2011.2.25.4.10.50.1.5.1.2
    optixDataPortSlavePortId OBJECT-TYPE
        SYNTAX Unsigned32
        MAX-ACCESS read-only
        STATUS current
        DESCRIPTION
            "This object indicates the slave port number of broadcast data. The value is determined by the slot ID and port ID of the line board."
        ::= { optixDataPortEntry 2 }

    -- 1.3.6.1.4.1.2011.2.25.4.10.50.1.5.1.3
    optixDataPortMainPortId OBJECT-TYPE
        SYNTAX Unsigned32
        MAX-ACCESS read-only
        STATUS current
        DESCRIPTION
            "This object indicates themaster port number of broadcast data. The value is determined by the slot ID and port ID of the line board."
        ::= { optixDataPortEntry 3 }

    -- 1.3.6.1.4.1.2011.2.25.4.10.50.1.5.1.4
    optixDataPortSlavePortNum OBJECT-TYPE
        SYNTAX Unsigned32
        MAX-ACCESS read-only
        STATUS current
        DESCRIPTION
            "This object indicates the number of slave ports of broadcast data."
        ::= { optixDataPortEntry 4 }

    -- 1.3.6.1.4.1.2011.2.25.4.10.50.1.6
    optixF1PortTable OBJECT-TYPE
        SYNTAX SEQUENCE OF OptixF1PortEntry
        MAX-ACCESS not-accessible
        STATUS current
        DESCRIPTION
            "This table describes the basicF1 portconfigurations."
        ::= { optixSdhEowGroup 6 }

    -- 1.3.6.1.4.1.2011.2.25.4.10.50.1.6.1
    optixF1PortEntry OBJECT-TYPE
        SYNTAX OptixF1PortEntry
        MAX-ACCESS not-accessible
        STATUS current
        DESCRIPTION
            "This entry describes the basic F1 port configurations."
        INDEX{ optixLogBoardId,optixF1PortId }
        ::= { optixF1PortTable 1 }

    OptixF1PortEntry ::=
        SEQUENCE {
            optixF1PortId
                Unsigned32,
            optixF1PortInputPort
                Unsigned32,
            optixF1PortOutputPort
                Unsigned32
        }

    -- 1.3.6.1.4.1.2011.2.25.4.10.50.1.6.1.1
    optixF1PortId OBJECT-TYPE
        SYNTAX Unsigned32
        MAX-ACCESS not-accessible
        STATUS current
        DESCRIPTION
            "This object indicates the F1 port number that ranges 1 to 7"
        ::= { optixF1PortEntry 1 }

    -- 1.3.6.1.4.1.2011.2.25.4.10.50.1.6.1.2
    optixF1PortInputPort OBJECT-TYPE
        SYNTAX Unsigned32
        MAX-ACCESS read-write
        STATUS current
        DESCRIPTION
            "This object indicates the upstream port of the F1 port. The value is determined by the slot ID and port ID of the line board. This parameter can also take the value of 0xff00."
        ::= { optixF1PortEntry 2 }

    -- 1.3.6.1.4.1.2011.2.25.4.10.50.1.6.1.3
    optixF1PortOutputPort OBJECT-TYPE
        SYNTAX Unsigned32
        MAX-ACCESS read-write
        STATUS current
        DESCRIPTION
            "This object indicates the downstream port of the F1 port. The value is determined by the slot ID and port ID of the line board."
        ::= { optixF1PortEntry 3 }

    -- 1.3.6.1.4.1.2011.2.25.4.10.50.1.7
    optixDataPortEXTTable OBJECT-TYPE
        SYNTAX SEQUENCE OF OptixDataPortEXTEntry
        MAX-ACCESS not-accessible
        STATUS current
        DESCRIPTION
            "Thistable describes the basicbroadcast data port configurations."
        ::= { optixSdhEowGroup 7 }

    -- 1.3.6.1.4.1.2011.2.25.4.10.50.1.7.1
    optixDataPortEXTEntry OBJECT-TYPE
        SYNTAX OptixDataPortEXTEntry
        MAX-ACCESS not-accessible
        STATUS current
        DESCRIPTION
            "Thisentry describes the basic broadcast data port configurations."
        INDEX{ optixLogBoardId,optixDataPortOhSlot }
        ::= { optixDataPortEXTTable 1 }

    OptixDataPortEXTEntry ::=
        SEQUENCE {
            optixEXTDataPortOhSlot
                Unsigned32,
            optixEXTDataPortMainPortId
                Unsigned32,
            optixEXTDataPortSlavePortNum
                Unsigned32,
            optixEXTDataPortSlavePortId
                OCTET STRING,
            optixEXTDataPortRowStatus
                RowStatus
        }

    -- 1.3.6.1.4.1.2011.2.25.4.10.50.1.7.1.1
    optixEXTDataPortOhSlot OBJECT-TYPE
        SYNTAX Unsigned32
        MAX-ACCESS not-accessible
        STATUS current
        DESCRIPTION
            "This object indicates the overhead byte. Serial1 to Serial4. Value range: 1 to 4."
        ::= { optixDataPortEXTEntry 1 }

    -- 1.3.6.1.4.1.2011.2.25.4.10.50.1.7.1.2
    optixEXTDataPortMainPortId OBJECT-TYPE
        SYNTAX Unsigned32
        MAX-ACCESS read-create
        STATUS current
        DESCRIPTION
            "This object indicates themaster port number of broadcast data. The value is determined by the slot ID and port ID of the line board."
        ::= { optixDataPortEXTEntry 2 }

    -- 1.3.6.1.4.1.2011.2.25.4.10.50.1.7.1.3
    optixEXTDataPortSlavePortNum OBJECT-TYPE
        SYNTAX Unsigned32
        MAX-ACCESS read-create
        STATUS current
        DESCRIPTION
            "This object indicates the number of slave ports of broadcast data. Value range: 1 to N. RTN equipment supports only 1."
        ::= { optixDataPortEXTEntry 3 }

    -- 1.3.6.1.4.1.2011.2.25.4.10.50.1.7.1.4
    optixEXTDataPortSlavePortId OBJECT-TYPE
        SYNTAX OCTET STRING (SIZE(0..128))
        MAX-ACCESS read-create
        STATUS current
        DESCRIPTION
            "This object indicates the slave port number of broadcast data. The value is determined by the slot ID and port ID of the line board."
        ::= { optixDataPortEXTEntry 4 }

    -- 1.3.6.1.4.1.2011.2.25.4.10.50.1.7.1.255
    optixEXTDataPortRowStatus OBJECT-TYPE
        SYNTAX RowStatus
        MAX-ACCESS read-create
        STATUS current
        DESCRIPTION
            "This object indicates the RowStatus of broadcast data."
        ::= { optixDataPortEXTEntry 255 }

END
