-- OPTIX-PKT-ARP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-ARP-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,IpAddress
            FROM SNMPv2-SMI
        RowStatus,MacAddress
            FROM SNMPv2-TC
        optixLogBoardId,optixLogSubCardId
            FROM OPTIX-BOARD-MANAGE-MIB
        optixPortId
            FROM OPTIX-PORT-MANAGE-MIB
        ;

    optixPktArp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the ARP configuration information of device"
        REVISION "201204200000Z"
        DESCRIPTION
            "The initial revision of this MIB module1."
        ::={ optixProvisionPtn 23 }

    -- 1.3.6.1.4.1.2011.2.25.4.50.23.1
    optixPktArpGroup OBJECT IDENTIFIER ::= { optixPktArp 1 }

    -- 1.3.6.1.4.1.2011.2.25.4.50.23.1.1
    optixArpTable OBJECT-TYPE
        SYNTAX SEQUENCE OF OptixArpEntry
        MAX-ACCESS not-accessible
        STATUS current
        DESCRIPTION
            "This table describes the basic configurations of ARPs."
        ::= { optixPktArpGroup 1 }

    -- 1.3.6.1.4.1.2011.2.25.4.50.23.1.1.1
    optixArpEntry OBJECT-TYPE
        SYNTAX OptixArpEntry
        MAX-ACCESS not-accessible
        STATUS current
        DESCRIPTION
            "This entry describes the basic configurations of ARPs."
        INDEX{ optixArpIp,optixArpType }
        ::= { optixArpTable 1 }

    OptixArpEntry ::=
        SEQUENCE {
            optixArpIp
                IpAddress,
            optixArpType
                INTEGER,
            optixArpMac
                OCTET STRING,
            optixArpRowStatus
                RowStatus
        }

    -- 1.3.6.1.4.1.2011.2.25.4.50.23.1.1.1.1
    optixArpIp OBJECT-TYPE
        SYNTAX IpAddress
        MAX-ACCESS not-accessible
        STATUS current
        DESCRIPTION
            "This object indicates the IP address of the ARP table. Value range in dotted decimal notation: 0.0.0.0 to 255.255.255.255."
        ::= { optixArpEntry 1 }

    -- 1.3.6.1.4.1.2011.2.25.4.50.23.1.1.1.2
    optixArpType OBJECT-TYPE
        SYNTAX INTEGER
        {
            static(0),
            dynamic(1),
            all(2)
        }
        MAX-ACCESS not-accessible
        STATUS current
        DESCRIPTION
            "This object indicates the type of the ARP table. 0: static, 1: dynamic, 2: all"
        ::= { optixArpEntry 2 }

    -- 1.3.6.1.4.1.2011.2.25.4.50.23.1.1.1.3
    optixArpMac OBJECT-TYPE
        SYNTAX OCTET STRING
        MAX-ACCESS read-create
        STATUS current
        DESCRIPTION
            "This object indicates the MAC address of the ARP table."
        ::= { optixArpEntry 3 }

    -- 1.3.6.1.4.1.2011.2.25.4.50.23.1.1.1.255
    optixArpRowStatus OBJECT-TYPE
        SYNTAX RowStatus
        MAX-ACCESS read-create
        STATUS current
        DESCRIPTION
            "This object indicates the row status of the ARP table."
        ::= { optixArpEntry 255 }

    -- 1.3.6.1.4.1.2011.2.25.4.50.23.1.3
    optixArpEXTTable OBJECT-TYPE
        SYNTAX SEQUENCE OF OptixArpEXTEntry
        MAX-ACCESS not-accessible
        STATUS current
        DESCRIPTION
            "This table describes the basic configurations of ARPs."
        ::= { optixPktArpGroup 3 }

    -- 1.3.6.1.4.1.2011.2.25.4.50.23.1.3.1
    optixArpEXTEntry OBJECT-TYPE
        SYNTAX OptixArpEXTEntry
        MAX-ACCESS not-accessible
        STATUS current
        DESCRIPTION
            "This entry describes the basic configurations of ARPs."
        INDEX{ optixEXTArpType }
        ::= { optixArpEXTTable 1 }

    OptixArpEXTEntry ::=
        SEQUENCE {
            optixEXTArpType
                INTEGER,
            optixEXTArpRowStatus
                RowStatus
        }

    -- 1.3.6.1.4.1.2011.2.25.4.50.23.1.3.1.1
    optixEXTArpType OBJECT-TYPE
        SYNTAX INTEGER
        {
            static(0),
            dynamic(1),
            all(2)
        }
        MAX-ACCESS not-accessible
        STATUS current
        DESCRIPTION
            "This object indicates the type of the ARP table. 0: static, 1: dynamic, 2: all"
        ::= { optixArpEXTEntry 1 }

    -- 1.3.6.1.4.1.2011.2.25.4.50.23.1.3.1.255
    optixEXTArpRowStatus OBJECT-TYPE
        SYNTAX RowStatus
        MAX-ACCESS read-create
        STATUS current
        DESCRIPTION
            "This object indicates the row status of the ARP table."
        ::= { optixArpEXTEntry 255 }

    -- 1.3.6.1.4.1.2011.2.25.4.50.23.1.4
    optixPktArpstatTable OBJECT-TYPE
        SYNTAX SEQUENCE OF OptixPktArpstatEntry
        MAX-ACCESS not-accessible
        STATUS current
        DESCRIPTION
            "This table describes the receive and transmit technologies of static ARP packets."
        ::= { optixPktArpGroup 4 }

    -- 1.3.6.1.4.1.2011.2.25.4.50.23.1.4.1
    optixPktArpstatEntry OBJECT-TYPE
        SYNTAX OptixPktArpstatEntry
        MAX-ACCESS not-accessible
        STATUS current
        DESCRIPTION
            "This entry describes the receive and transmit technologies of static ARP packets."
        INDEX{ optixLogBoardId,optixLogSubCardId,optixPortId }
        ::= { optixPktArpstatTable 1 }

    OptixPktArpstatEntry ::=
        SEQUENCE {
            optixPktArpVisp2PtcReqNum
                Unsigned32,
            optixPktArpPtc2ChipReqNum
                Unsigned32,
            optixPktArpChip2PtcReqNum
                Unsigned32,
            optixPktArpPtc2VispReqNum
                Unsigned32,
            optixPktArpVisp2PtnRspNum
                Unsigned32,
            optixPktArpPtc2ChipRspNum
                Unsigned32,
            optixPktArpChip2PtnRspNum
                Unsigned32,
            optixPktArpPtc2VispRspNum
                Unsigned32
        }

    -- 1.3.6.1.4.1.2011.2.25.4.50.23.1.4.1.1
    optixPktArpVisp2PtcReqNum OBJECT-TYPE
        SYNTAX Unsigned32
        MAX-ACCESS read-only
        STATUS current
        DESCRIPTION
            "This object indicates the number of ARP request packets received by PTC from VISP."
        ::= { optixPktArpstatEntry 1 }

    -- 1.3.6.1.4.1.2011.2.25.4.50.23.1.4.1.2
    optixPktArpPtc2ChipReqNum OBJECT-TYPE
        SYNTAX Unsigned32
        MAX-ACCESS read-only
        STATUS current
        DESCRIPTION
            "This object indicates the number of ARP request packets sent by PTC to chips."
        ::= { optixPktArpstatEntry 2 }

    -- 1.3.6.1.4.1.2011.2.25.4.50.23.1.4.1.3
    optixPktArpChip2PtcReqNum OBJECT-TYPE
        SYNTAX Unsigned32
        MAX-ACCESS read-only
        STATUS current
        DESCRIPTION
            "This object indicates the number of ARP request packets received by PTC from chips."
        ::= { optixPktArpstatEntry 3 }

    -- 1.3.6.1.4.1.2011.2.25.4.50.23.1.4.1.4
    optixPktArpPtc2VispReqNum OBJECT-TYPE
        SYNTAX Unsigned32
        MAX-ACCESS read-only
        STATUS current
        DESCRIPTION
            "This object indicates the number of ARP request packets sent by PTC to VISP."
        ::= { optixPktArpstatEntry 4 }

    -- 1.3.6.1.4.1.2011.2.25.4.50.23.1.4.1.5
    optixPktArpVisp2PtnRspNum OBJECT-TYPE
        SYNTAX Unsigned32
        MAX-ACCESS read-only
        STATUS current
        DESCRIPTION
            "This object indicates the number of ARP response packets received by PTC from VISP."
        ::= { optixPktArpstatEntry 5 }

    -- 1.3.6.1.4.1.2011.2.25.4.50.23.1.4.1.6
    optixPktArpPtc2ChipRspNum OBJECT-TYPE
        SYNTAX Unsigned32
        MAX-ACCESS read-only
        STATUS current
        DESCRIPTION
            "This object indicates the number of ARP response packets sent by PTC to chips."
        ::= { optixPktArpstatEntry 6 }

    -- 1.3.6.1.4.1.2011.2.25.4.50.23.1.4.1.7
    optixPktArpChip2PtnRspNum OBJECT-TYPE
        SYNTAX Unsigned32
        MAX-ACCESS read-only
        STATUS current
        DESCRIPTION
            "This object indicates the number of ARP response packets received by PTC from chips."
        ::= { optixPktArpstatEntry 7 }

    -- 1.3.6.1.4.1.2011.2.25.4.50.23.1.4.1.8
    optixPktArpPtc2VispRspNum OBJECT-TYPE
        SYNTAX Unsigned32
        MAX-ACCESS read-only
        STATUS current
        DESCRIPTION
            "This object indicates the number of ARP response packets sent by PTC to VISP."
        ::= { optixPktArpstatEntry 8 }

    -- 1.3.6.1.4.1.2011.2.25.4.50.23.2
    optixPktArpstatGroup OBJECT IDENTIFIER ::= { optixPktArp 2 }

    -- 1.3.6.1.4.1.2011.2.25.4.50.23.2.1
    optixArpCHIP2PTCNUM OBJECT-TYPE
        SYNTAX Unsigned32
        MAX-ACCESS read-only
        STATUS current
        DESCRIPTION
            "This object indicates the CHIP2PTCNUM of the ARP"
        ::= { optixPktArpstatGroup 1 }

    -- 1.3.6.1.4.1.2011.2.25.4.50.23.2.2
    optixArpPTC2VISPNUM OBJECT-TYPE
        SYNTAX Unsigned32
        MAX-ACCESS read-only
        STATUS current
        DESCRIPTION
            "This object indicates the PTC2VISPNUM of the ARP"
        ::= { optixPktArpstatGroup 2 }

    -- 1.3.6.1.4.1.2011.2.25.4.50.23.2.3
    optixArpNEFullFlag OBJECT-TYPE
        SYNTAX INTEGER
        {
            no(0),
            yes(1)
        }
        MAX-ACCESS read-only
        STATUS current
        DESCRIPTION
            "This object indicates the Full Flag of the ARP table."
        ::= { optixPktArpstatGroup 3 }

END
