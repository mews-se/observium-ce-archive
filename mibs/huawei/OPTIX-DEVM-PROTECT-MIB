-- OPTIX-DEVM-PROTECT-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-DEVM-PROTECT-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY,NOTIFICATION-TYPE
            FROM SNMPv2-SMI
        RowStatus
            FROM SNMPv2-TC
        ;

    optixDevmProtection MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the protection of board"
        REVISION "201204170000Z"
        DESCRIPTION
            "The initial revision of this MIB module."
        REVISION "201204170000Z"
        DESCRIPTION
            "The initial revision of this MIB module."
        ::={ optixProvisionEqpt 16 }

    -- 1.3.6.1.4.1.2011.2.25.4.30.16.1
    optixDpsProtection OBJECT IDENTIFIER ::= { optixDevmProtection 1 }

    -- 1.3.6.1.4.1.2011.2.25.4.30.16.1.1
    optixDpsTable OBJECT-TYPE
        SYNTAX SEQUENCE OF OptixDpsEntry
        MAX-ACCESS not-accessible
        STATUS current
        DESCRIPTION
            "This table describes the DPS protection group information."
        ::= { optixDpsProtection 1 }

    -- 1.3.6.1.4.1.2011.2.25.4.30.16.1.1.1
    optixDpsEntry OBJECT-TYPE
        SYNTAX OptixDpsEntry
        MAX-ACCESS not-accessible
        STATUS current
        DESCRIPTION
            "This entry describes the DPS protection group information."
        INDEX{ optixDpsIdIndex }
        ::= { optixDpsTable 1 }

    OptixDpsEntry ::=
        SEQUENCE {
            optixDpsIdIndex
                Unsigned32,
            optixDpsFstBid
                Unsigned32,
            optixDpsSndBid
                Unsigned32,
            optixDpsType
                INTEGER,
            optixDpsLevel
                INTEGER,
            optixDpsState
                INTEGER,
            optixDpsWorkBid
                Unsigned32,
            optixDpsProBid
                Unsigned32,
            optixDpsSwtichDstBid
                Unsigned32,
            optixDpsRowStatus
                RowStatus
        }

    -- 1.3.6.1.4.1.2011.2.25.4.30.16.1.1.1.1
    optixDpsIdIndex OBJECT-TYPE
        SYNTAX Unsigned32
        MAX-ACCESS not-accessible
        STATUS current
        DESCRIPTION
            "This object indicates the DPS protection group ID. Value range: 1 to 254."
        DEFVAL{ 0 }
        ::= { optixDpsEntry 1 }

    -- 1.3.6.1.4.1.2011.2.25.4.30.16.1.1.1.2
    optixDpsFstBid OBJECT-TYPE
        SYNTAX Unsigned32
        MAX-ACCESS read-only
        STATUS current
        DESCRIPTION
            "This object indicates the slot ID of the first protection unit."
        ::= { optixDpsEntry 2 }

    -- 1.3.6.1.4.1.2011.2.25.4.30.16.1.1.1.3
    optixDpsSndBid OBJECT-TYPE
        SYNTAX Unsigned32
        MAX-ACCESS read-only
        STATUS current
        DESCRIPTION
            "This object indicates the slot ID of thesecond protection unit."
        ::= { optixDpsEntry 3 }

    -- 1.3.6.1.4.1.2011.2.25.4.30.16.1.1.1.4
    optixDpsType OBJECT-TYPE
        SYNTAX INTEGER
        {
            xcs(1),
            scc(3),
            eth1j1(5)
        }
        MAX-ACCESS read-only
        STATUS current
        DESCRIPTION
            "This object indicates the DPS protection group type. 1: XCS, 3: SCC, 5: ETH 1+1"
        ::= { optixDpsEntry 4 }

    -- 1.3.6.1.4.1.2011.2.25.4.30.16.1.1.1.5
    optixDpsLevel OBJECT-TYPE
        SYNTAX INTEGER
        {
            dpsNull(0),
            dpsVc4(1),
            dpsVc12n3(2),
            dpsVc12(3),
            dpsVc3(4)
        }
        MAX-ACCESS read-only
        STATUS current
        DESCRIPTION
            "This object indicates the DPS protection group level. 0: dpsNull, 1: dpsVc4, 2: dpsVc12n3, 3: dpsVc12, 4: dpsVc3"
        ::= { optixDpsEntry 5 }

    -- 1.3.6.1.4.1.2011.2.25.4.30.16.1.1.1.6
    optixDpsState OBJECT-TYPE
        SYNTAX INTEGER
        {
            adding(1),
            deleting(2),
            active(3)
        }
        MAX-ACCESS read-only
        STATUS current
        DESCRIPTION
            "This object indicates the DPS protection group status. 1: adding, 2: deleting, 3: active"
        ::= { optixDpsEntry 6 }

    -- 1.3.6.1.4.1.2011.2.25.4.30.16.1.1.1.7
    optixDpsWorkBid OBJECT-TYPE
        SYNTAX Unsigned32
        MAX-ACCESS read-only
        STATUS current
        DESCRIPTION
            "This object indicates the slot ID of the working board in the DPS protection group."
        ::= { optixDpsEntry 7 }

    -- 1.3.6.1.4.1.2011.2.25.4.30.16.1.1.1.8
    optixDpsProBid OBJECT-TYPE
        SYNTAX Unsigned32
        MAX-ACCESS read-only
        STATUS current
        DESCRIPTION
            "This object indicates the slot ID of the protection board in the DPS protection group."
        ::= { optixDpsEntry 8 }

    -- 1.3.6.1.4.1.2011.2.25.4.30.16.1.1.1.10
    optixDpsSwtichDstBid OBJECT-TYPE
        SYNTAX Unsigned32
        MAX-ACCESS read-create
        STATUS current
        DESCRIPTION
            "This node describes the destination board of an external switching."
        ::= { optixDpsEntry 10 }

    -- 1.3.6.1.4.1.2011.2.25.4.30.16.1.1.1.255
    optixDpsRowStatus OBJECT-TYPE
        SYNTAX RowStatus
        MAX-ACCESS read-create
        STATUS current
        DESCRIPTION
            "This object indicates the row status."
        DEFVAL{ active }
        ::= { optixDpsEntry 255 }

    -- 1.3.6.1.4.1.2011.2.25.4.30.16.2
    optixDpsswitchTrapMember OBJECT IDENTIFIER ::= { optixDevmProtection 2 }

    -- 1.3.6.1.4.1.2011.2.25.4.30.16.2.1
    optixDpsswitchIndex OBJECT-TYPE
        SYNTAX Unsigned32
        MAX-ACCESS accessible-for-notify
        STATUS current
        DESCRIPTION
            "the Dps Index of Dps switch Event"
        ::= { optixDpsswitchTrapMember 1 }

    -- 1.3.6.1.4.1.2011.2.25.4.30.16.2.2
    optixDpsswitchMstBid OBJECT-TYPE
        SYNTAX Unsigned32
        MAX-ACCESS accessible-for-notify
        STATUS current
        DESCRIPTION
            "the Master Board ID of Dps switch Event"
        ::= { optixDpsswitchTrapMember 2 }

    -- 1.3.6.1.4.1.2011.2.25.4.30.16.2.3
    optixDpsswitchSlvBid OBJECT-TYPE
        SYNTAX Unsigned32
        MAX-ACCESS accessible-for-notify
        STATUS current
        DESCRIPTION
            "the Slave Board Id of Dps switch Event"
        ::= { optixDpsswitchTrapMember 3 }

    -- 1.3.6.1.4.1.2011.2.25.4.30.16.3
    optixDpsswitchTrapReport OBJECT IDENTIFIER ::= { optixDevmProtection 3 }

    -- 1.3.6.1.4.1.2011.2.25.4.30.16.3.1
    optixDpsswitchTrap NOTIFICATION-TYPE
        OBJECTS{ optixDpsswitchSlvBid,optixDpsswitchMstBid,optixDpsswitchIndex }
        STATUS current
        DESCRIPTION
            "the Event of  Dps switch Report"
        ::= { optixDpsswitchTrapReport 1 }

END
