-- OPTIX-SDH-RMSP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-RMSP-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY,NOTIFICATION-TYPE
            FROM SNMPv2-SMI
        RowStatus
            FROM SNMPv2-TC
        ;

    optixSdhRmsp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describesRMSP configurations."
        REVISION "201204200000Z"
        DESCRIPTION
            "The initial revision of this MIB module1."
        ::={ optixProvisionSdh 51 }

    -- 1.3.6.1.4.1.2011.2.25.4.10.51.10
    optixSdhRmspGroup OBJECT IDENTIFIER ::= { optixSdhRmsp 10 }

    -- 1.3.6.1.4.1.2011.2.25.4.10.51.10.1
    optixSdhRmspgTable OBJECT-TYPE
        SYNTAX SEQUENCE OF OptixSdhRmspgEntry
        MAX-ACCESS not-accessible
        STATUS current
        DESCRIPTION
            "This table describes the RMSP group configurations."
        ::= { optixSdhRmspGroup 1 }

    -- 1.3.6.1.4.1.2011.2.25.4.10.51.10.1.1
    optixSdhRmspgEntry OBJECT-TYPE
        SYNTAX OptixSdhRmspgEntry
        MAX-ACCESS not-accessible
        STATUS current
        DESCRIPTION
            "Thisentry describes the RMSP group configurations."
        INDEX{ optixSdhRmspgid }
        ::= { optixSdhRmspgTable 1 }

    OptixSdhRmspgEntry ::=
        SEQUENCE {
            optixSdhRmspgid
                Unsigned32,
            optixSdhRmspRevertMode
                INTEGER,
            optixSdhRmspActiveFlag
                INTEGER,
            optixSdhRmspLocalNodeId
                Unsigned32,
            optixSdhRmspWestNodeId
                Unsigned32,
            optixSdhRmspEastNodeId
                Unsigned32,
            optixSdhRmspWtrTime
                Unsigned32,
            optixSdhRmspSdEnable
                INTEGER,
            optixSdhRmspWestSwreq
                INTEGER,
            optixSdhRmspWestSwsta
                INTEGER,
            optixSdhRmspWestSwflag
                INTEGER,
            optixSdhRmspEastSwreq
                INTEGER,
            optixSdhRmspEastSwsta
                INTEGER,
            optixSdhRmspEastSwflag
                INTEGER,
            optixSdhRmspProtocolType
                INTEGER,
            optixSdhRmspHoldOfftime
                Unsigned32,
            optixSdhRmspWChannelsState
                INTEGER,
            optixSdhRmspEChannelsState
                INTEGER,
            optixSdhRmspWestReqSite
                INTEGER,
            optixSdhRmspEastReqSite
                INTEGER,
            optixSdhRmspuidWest1
                INTEGER,
            optixSdhRmspAu4MapWest1
                OCTET STRING,
            optixSdhRmspBidWest1
                Unsigned32,
            optixSdhRmspSubidWest1
                Unsigned32,
            optixSdhRmspPidWest1
                Unsigned32,
            optixSdhRmspuidWest2
                INTEGER,
            optixSdhRmspAu4MapWest2
                OCTET STRING,
            optixSdhRmspBidWest2
                Unsigned32,
            optixSdhRmspSubidWest2
                Unsigned32,
            optixSdhRmspPidWest2
                Unsigned32,
            optixSdhRmspuidEast1
                INTEGER,
            optixSdhRmspAu4MapEast1
                OCTET STRING,
            optixSdhRmspBidEast1
                Unsigned32,
            optixSdhRmspSubidEast1
                Unsigned32,
            optixSdhRmspPidEast1
                Unsigned32,
            optixSdhRmspuidEast2
                INTEGER,
            optixSdhRmspAu4MapEast2
                OCTET STRING,
            optixSdhRmspBidEast2
                Unsigned32,
            optixSdhRmspSubidEast2
                Unsigned32,
            optixSdhRmspPidEast2
                Unsigned32,
            optixSdhRmspStartFlag
                INTEGER,
            optixSdhRmspRowStatus
                RowStatus
        }

    -- 1.3.6.1.4.1.2011.2.25.4.10.51.10.1.1.1
    optixSdhRmspgid OBJECT-TYPE
        SYNTAX Unsigned32
        MAX-ACCESS not-accessible
        STATUS current
        DESCRIPTION
            "This object indicates the RMSP group ID. Value range: 1 to 3 and 0 (all)."
        ::= { optixSdhRmspgEntry 1 }

    -- 1.3.6.1.4.1.2011.2.25.4.10.51.10.1.1.2
    optixSdhRmspRevertMode OBJECT-TYPE
        SYNTAX INTEGER
        {
            snmp2fbi(1),
            snmp2funi(2),
            snmp4f(3)
        }
        MAX-ACCESS read-create
        STATUS current
        DESCRIPTION
            "This object indicates the revertive mode of the RMSP group. 1: snmp2fbi, 2: snmp2funi, 3: snmp4f"
        ::= { optixSdhRmspgEntry 2 }

    -- 1.3.6.1.4.1.2011.2.25.4.10.51.10.1.1.3
    optixSdhRmspActiveFlag OBJECT-TYPE
        SYNTAX INTEGER
        {
            adding(1),
            deleting(2),
            active(3)
        }
        MAX-ACCESS read-only
        STATUS current
        DESCRIPTION
            "This object indicates the current status of the RMSP group. 1: adding, 2: deleting, 3: active"
        ::= { optixSdhRmspgEntry 3 }

    -- 1.3.6.1.4.1.2011.2.25.4.10.51.10.1.1.4
    optixSdhRmspLocalNodeId OBJECT-TYPE
        SYNTAX Unsigned32
        MAX-ACCESS read-create
        STATUS current
        DESCRIPTION
            "This object indicates the local node ID of the RMSP group. Value range: 0 to 15."
        ::= { optixSdhRmspgEntry 4 }

    -- 1.3.6.1.4.1.2011.2.25.4.10.51.10.1.1.5
    optixSdhRmspWestNodeId OBJECT-TYPE
        SYNTAX Unsigned32
        MAX-ACCESS read-create
        STATUS current
        DESCRIPTION
            "This object indicates thewest node ID of the RMSP group. Value range: 0 to 15."
        ::= { optixSdhRmspgEntry 5 }

    -- 1.3.6.1.4.1.2011.2.25.4.10.51.10.1.1.6
    optixSdhRmspEastNodeId OBJECT-TYPE
        SYNTAX Unsigned32
        MAX-ACCESS read-create
        STATUS current
        DESCRIPTION
            "This object indicates the east node ID of the RMSP group. Value range: 0 to 15."
        ::= { optixSdhRmspgEntry 6 }

    -- 1.3.6.1.4.1.2011.2.25.4.10.51.10.1.1.7
    optixSdhRmspWtrTime OBJECT-TYPE
        SYNTAX Unsigned32
        MAX-ACCESS read-create
        STATUS current
        DESCRIPTION
            "This object indicates the WTR time of the RMSP group. Value range: 6 to 720 (unit: s)."
        ::= { optixSdhRmspgEntry 7 }

    -- 1.3.6.1.4.1.2011.2.25.4.10.51.10.1.1.8
    optixSdhRmspSdEnable OBJECT-TYPE
        SYNTAX INTEGER
        {
            disable(0),
            enable(1)
        }
        MAX-ACCESS read-create
        STATUS current
        DESCRIPTION
            "This object indicates the enable status of the RMSP SD switching. 0: disable, 1: enable"
        ::= { optixSdhRmspgEntry 8 }

    -- 1.3.6.1.4.1.2011.2.25.4.10.51.10.1.1.9
    optixSdhRmspWestSwreq OBJECT-TYPE
        SYNTAX INTEGER
        {
            sfP(240),
            lpS(248),
            fsS(224),
            fsR(208),
            sfS(192),
            sfR(176),
            sdP(160),
            sdS(144),
            sdR(128),
            msS(112),
            msR(96),
            wtr(80),
            exerS(64),
            exerR(48),
            rrS(32),
            rrR(16),
            nr(0),
            sfPUlowS(241),
            lpSUlowS(249),
            fsRUlowS(209),
            sfRUlowS(177),
            sdPUlowS(161),
            sdRUlowS(129),
            msRUlowS(97),
            wtRUlowS(81),
            exerRUlows(49),
            nrUlowS(1),
            sfPUlowR(242),
            lpSUlowR(250),
            fsSUlowR(226),
            sfSUlowR(194),
            sdPUlowR(162),
            sdSUlowR(146),
            msSlowR(114),
            wtrUlowR(82),
            exerSUlowR(66),
            nrUlowR(2),
            sfPUlowSUlowR(243),
            lpSUlowSUlowR(251),
            sdPUlowSUlowR(163),
            nrUlowSUlowR(3),
            nrUlpa(4),
            lpsUlpa(252),
            nrUlowSUlpa(5),
            lpSUlowSUlpa(253),
            nrUlowRUlpa(6),
            lpsUlowRUlpa(254),
            nrUlowSUlowRUlpa(7),
            lpSUlowSUlowRUlpa(255),
            fsSUlw(239),
            fsRUlw(223),
            sfSUlw(207),
            sfRUlw(191),
            sdPUlw(175),
            sdSUlw(159),
            sdRUlw(143),
            msSUlw(127),
            msRUlw(111),
            wtRUlw(95),
            exerSUlw(79),
            exerRUlw(63),
            rrSUlw(47),
            rrRUlw(31),
            nrUlw(15)
        }
        MAX-ACCESS read-only
        STATUS current
        DESCRIPTION
            "This object indicates the west switching request of the RMSP group. 240: sfP, 248: lpS, 224: fsS, 208: fsR, 192: sfS, 176: sfR, 160: sdP, 144: sdS, 128: sdR, 112: msS, 96: msR, 80: wtr, 64: exerS, 48: exerR, 32: rrS, 16: rrR, 0: nr, 241: sfPUlowS, 249: lpSUlowS, 209: fsRUlowS, 177: sfRUlowS, 161: sdPUlowS, 129: sdRUlowS, 97: msRUlowS, 81: wtRUlowS, 49: exerRUlows, 1: nrUlowS, 242: sfPUlowR, 250: lpSUlowR, 226: fsSUlowR, 194: sfSUlowR, 162: sdPUlowR, 146: sdSUlowR, 114: msSlowR, 82: wtrUlowR, 66: exerSUlowR, 2: nrUlowR, 243: sfPUlowSUlowR, 251: lpSUlowSUlowR, 163: sdPUlowSUlowR, 3: nrUlowSUlowR, 4: nrUlpa, 252: lpsUlpa, 5: nrUlowSUlpa(5), 253: lpSUlowSUlpa, 6: nrUlowRUlpa, 254: lpsUlowRUlpa, 7: nrUlowSUlowRUlpa, 255: lpSUlowSUlowRUlpa, 239: fsSUlw, 223: fsRUlw, 207: sfSUlw, 191: sfRUlw, 175: sdPUlw, 159: sdSUlw, 143: sdRUlw, 127: msSUlw, 111: msRUlw, 95: wtRUlw, 79: exerSUlw, 63: exerRUlw, 47: rrSUlw, 31: rrRUlw, 15: nrUlw"
        ::= { optixSdhRmspgEntry 9 }

    -- 1.3.6.1.4.1.2011.2.25.4.10.51.10.1.1.10
    optixSdhRmspWestSwsta OBJECT-TYPE
        SYNTAX INTEGER
        {
            stop(0),
            i(1),
            s(4),
            p(6),
            starting(255)
        }
        MAX-ACCESS read-only
        STATUS current
        DESCRIPTION
            "This object indicates the west switchingstatus of the RMSP group. 0: stop, 1: i, 4: s, 6: p, 255: starting"
        ::= { optixSdhRmspgEntry 10 }

    -- 1.3.6.1.4.1.2011.2.25.4.10.51.10.1.1.11
    optixSdhRmspWestSwflag OBJECT-TYPE
        SYNTAX INTEGER
        {
            off(0),
            on(1)
        }
        MAX-ACCESS read-only
        STATUS current
        DESCRIPTION
            "This object indicates the west switchingof the RMSP group. 0: off, 1: on"
        ::= { optixSdhRmspgEntry 11 }

    -- 1.3.6.1.4.1.2011.2.25.4.10.51.10.1.1.12
    optixSdhRmspEastSwreq OBJECT-TYPE
        SYNTAX INTEGER
        {
            sfP(240),
            lpS(248),
            fsS(224),
            fsR(208),
            sfS(192),
            sfR(176),
            sdP(160),
            sdS(144),
            sdR(128),
            msS(112),
            msR(96),
            wtr(80),
            exerS(64),
            exerR(48),
            rrS(32),
            rrR(16),
            nr(0),
            sfPUlowS(241),
            lpSUlowS(249),
            fsRUlowS(209),
            sfRUlowS(177),
            sdPUlowS(161),
            sdRUlowS(129),
            msRUlowS(97),
            wtRUlowS(81),
            exerRUlows(49),
            nrUlowS(1),
            sfPUlowR(242),
            lpSUlowR(250),
            fsSUlowR(226),
            sfSUlowR(194),
            sdPUlowR(162),
            sdSUlowR(146),
            msSlowR(114),
            wtrUlowR(82),
            exerSUlowR(66),
            nrUlowR(2),
            sfPUlowSUlowR(243),
            lpSUlowSUlowR(251),
            sdPUlowSUlowR(163),
            nrUlowSUlowR(3),
            nrUlpa(4),
            lpsUlpa(252),
            nrUlowSUlpa(5),
            lpSUlowSUlpa(253),
            nrUlowRUlpa(6),
            lpsUlowRUlpa(254),
            nrUlowSUlowRUlpa(7),
            lpSUlowSUlowRUlpa(255),
            fsSUlw(239),
            fsRUlw(223),
            sfSUlw(207),
            sfRUlw(191),
            sdPUlw(175),
            sdSUlw(159),
            sdRUlw(143),
            msSUlw(127),
            msRUlw(111),
            wtRUlw(95),
            exerSUlw(79),
            exerRUlw(63),
            rrSUlw(47),
            rrRUlw(31),
            nrUlw(15)
        }
        MAX-ACCESS read-only
        STATUS current
        DESCRIPTION
            "This object indicates the east switching request of the RMSP group. 240: sfP, 248: lpS, 224: fsS, 208: fsR, 192: sfS, 176: sfR, 160: sdP, 144: sdS, 128: sdR, 112: msS, 96: msR, 80: wtr, 64: exerS, 48: exerR, 32: rrS, 16: rrR, 0: nr, 241: sfPUlowS, 249: lpSUlowS, 209: fsRUlowS, 177: sfRUlowS, 161: sdPUlowS, 129: sdRUlowS, 97: msRUlowS, 81: wtRUlowS, 49: exerRUlows, 1: nrUlowS, 242: sfPUlowR, 250: lpSUlowR, 226: fsSUlowR, 194: sfSUlowR, 162: sdPUlowR, 146: sdSUlowR, 114: msSlowR, 82: wtrUlowR, 66: exerSUlowR, 2: nrUlowR, 243: sfPUlowSUlowR, 251: lpSUlowSUlowR, 163: sdPUlowSUlowR, 3: nrUlowSUlowR, 4: nrUlpa, 252: lpsUlpa, 5: nrUlowSUlpa(5), 253: lpSUlowSUlpa, 6: nrUlowRUlpa, 254: lpsUlowRUlpa, 7: nrUlowSUlowRUlpa, 255: lpSUlowSUlowRUlpa, 239: fsSUlw, 223: fsRUlw, 207: sfSUlw, 191: sfRUlw, 175: sdPUlw, 159: sdSUlw, 143: sdRUlw, 127: msSUlw, 111: msRUlw, 95: wtRUlw, 79: exerSUlw, 63: exerRUlw, 47: rrSUlw, 31: rrRUlw, 15: nrUlw"
        ::= { optixSdhRmspgEntry 12 }

    -- 1.3.6.1.4.1.2011.2.25.4.10.51.10.1.1.13
    optixSdhRmspEastSwsta OBJECT-TYPE
        SYNTAX INTEGER
        {
            stop(0),
            i(1),
            s(4),
            p(6),
            starting(255)
        }
        MAX-ACCESS read-only
        STATUS current
        DESCRIPTION
            "This object indicates the east switching status of the RMSP group. 0: stop, 1: i, 4: s, 6: p, 255: starting"
        ::= { optixSdhRmspgEntry 13 }

    -- 1.3.6.1.4.1.2011.2.25.4.10.51.10.1.1.14
    optixSdhRmspEastSwflag OBJECT-TYPE
        SYNTAX INTEGER
        {
            off(0),
            on(1)
        }
        MAX-ACCESS read-only
        STATUS current
        DESCRIPTION
            "This object indicates the east switching of the RMSP group. 0: off, 1: on"
        ::= { optixSdhRmspgEntry 14 }

    -- 1.3.6.1.4.1.2011.2.25.4.10.51.10.1.1.15
    optixSdhRmspProtocolType OBJECT-TYPE
        SYNTAX INTEGER
        {
            old(0),
            new(1),
            restruct(2),
            transoceanic(3)
        }
        MAX-ACCESS read-create
        STATUS current
        DESCRIPTION
            "This object indicates the protocol type of the RMSP group. 0: old, 1: new, 2: restruct, 3: transoceanic"
        ::= { optixSdhRmspgEntry 15 }

    -- 1.3.6.1.4.1.2011.2.25.4.10.51.10.1.1.16
    optixSdhRmspHoldOfftime OBJECT-TYPE
        SYNTAX Unsigned32
        MAX-ACCESS read-create
        STATUS current
        DESCRIPTION
            "This object indicates the RMSP switching delay time. Value range: 0 to 100 (unit: 100 ms). If there is no delay time, the returned value is 0."
        ::= { optixSdhRmspgEntry 16 }

    -- 1.3.6.1.4.1.2011.2.25.4.10.51.10.1.1.17
    optixSdhRmspWChannelsState OBJECT-TYPE
        SYNTAX INTEGER
        {
            rmsLock(15),
            rmsUnlock(31),
            rmsSforce(14),
            rmsSforceclr(30),
            rmsRforce(13),
            rmsRforceclr(29),
            rmsSman(7),
            rmsSmanclr(23),
            rmsRman(6),
            rmsRmanclr(22),
            rmsSexer(4),
            rmsSexerclr(20),
            rmsRexer(3),
            rmsRexerclr(19),
            rmsClearwtr(21),
            rmsClearall(16)
        }
        MAX-ACCESS read-only
        STATUS current
        DESCRIPTION
            "This object indicates the westlocking status of the RMSP group. 15: rmsLock, 31: rmsUnlock, 14: rmsSforce, 30: rmsSforceclr, 13: rmsRforce, 29: rmsRforceclr, 7: rmsSman, 23: rmsSmanclr, 6: rmsRman, 22: rmsRmanclr, 4: rmsSexer, 20: rmsSexerclr, 3: rmsRexer, 19: rmsRexerclr, 21: rmsClearwtr, 16: rmsClearall"
        ::= { optixSdhRmspgEntry 17 }

    -- 1.3.6.1.4.1.2011.2.25.4.10.51.10.1.1.18
    optixSdhRmspEChannelsState OBJECT-TYPE
        SYNTAX INTEGER
        {
            rmsLock(15),
            rmsUnlock(31),
            rmsSforce(14),
            rmsSforceclr(30),
            rmsRforce(13),
            rmsRforceclr(29),
            rmsSman(7),
            rmsSmanclr(23),
            rmsRman(6),
            rmsRmanclr(22),
            rmsSexer(4),
            rmsSexerclr(20),
            rmsRexer(3),
            rmsRexerclr(19),
            rmsClearwtr(21),
            rmsClearall(16)
        }
        MAX-ACCESS read-only
        STATUS current
        DESCRIPTION
            "This object indicates the east locking status of the RMSP group. 15: rmsLock, 31: rmsUnlock, 14: rmsSforce, 30: rmsSforceclr, 13: rmsRforce, 29: rmsRforceclr, 7: rmsSman, 23: rmsSmanclr, 6: rmsRman, 22: rmsRmanclr, 4: rmsSexer, 20: rmsSexerclr, 3: rmsRexer, 19: rmsRexerclr, 21: rmsClearwtr, 16: rmsClearall"
        ::= { optixSdhRmspgEntry 18 }

    -- 1.3.6.1.4.1.2011.2.25.4.10.51.10.1.1.19
    optixSdhRmspWestReqSite OBJECT-TYPE
        SYNTAX INTEGER
        {
            near(1),
            far(2)
        }
        MAX-ACCESS read-only
        STATUS current
        DESCRIPTION
            "This object indicates the westremote/local endof the RMSP group. 1: near, 2: far"
        ::= { optixSdhRmspgEntry 19 }

    -- 1.3.6.1.4.1.2011.2.25.4.10.51.10.1.1.20
    optixSdhRmspEastReqSite OBJECT-TYPE
        SYNTAX INTEGER
        {
            near(1),
            far(2)
        }
        MAX-ACCESS read-only
        STATUS current
        DESCRIPTION
            "This object indicates the east remote/local end of the RMSP group. 1: near, 2: far"
        ::= { optixSdhRmspgEntry 20 }

    -- 1.3.6.1.4.1.2011.2.25.4.10.51.10.1.1.21
    optixSdhRmspuidWest1 OBJECT-TYPE
        SYNTAX INTEGER
        {
            west1(0),
            west2(1),
            east1(2),
            east2(3)
        }
        MAX-ACCESS read-create
        STATUS current
        DESCRIPTION
            "This object indicates the RMSP protection unit ID. 0: west1, 1: west2, 2: east1, 3: east2"
        ::= { optixSdhRmspgEntry 21 }

    -- 1.3.6.1.4.1.2011.2.25.4.10.51.10.1.1.22
    optixSdhRmspAu4MapWest1 OBJECT-TYPE
        SYNTAX OCTET STRING (SIZE(0..32))
        MAX-ACCESS read-create
        STATUS current
        DESCRIPTION
            "This object indicates theAu4 usageof the RMSP group."
        ::= { optixSdhRmspgEntry 22 }

    -- 1.3.6.1.4.1.2011.2.25.4.10.51.10.1.1.23
    optixSdhRmspBidWest1 OBJECT-TYPE
        SYNTAX Unsigned32
        MAX-ACCESS read-create
        STATUS current
        DESCRIPTION
            "This object indicates the slot ID of the RMSP group."
        ::= { optixSdhRmspgEntry 23 }

    -- 1.3.6.1.4.1.2011.2.25.4.10.51.10.1.1.24
    optixSdhRmspSubidWest1 OBJECT-TYPE
        SYNTAX Unsigned32
        MAX-ACCESS read-create
        STATUS current
        DESCRIPTION
            "This object indicates the subboard ID of the RMSP group."
        ::= { optixSdhRmspgEntry 24 }

    -- 1.3.6.1.4.1.2011.2.25.4.10.51.10.1.1.25
    optixSdhRmspPidWest1 OBJECT-TYPE
        SYNTAX Unsigned32
        MAX-ACCESS read-create
        STATUS current
        DESCRIPTION
            "This object indicates the port number of the RMSP group."
        ::= { optixSdhRmspgEntry 25 }

    -- 1.3.6.1.4.1.2011.2.25.4.10.51.10.1.1.26
    optixSdhRmspuidWest2 OBJECT-TYPE
        SYNTAX INTEGER
        {
            west1(0),
            west2(1),
            east1(2),
            east2(3)
        }
        MAX-ACCESS read-create
        STATUS current
        DESCRIPTION
            "This object indicates the ID of RMSP protection unit. Value list: 0-west1, 1-west2, 2-east1, 3-east2"
        ::= { optixSdhRmspgEntry 26 }

    -- 1.3.6.1.4.1.2011.2.25.4.10.51.10.1.1.27
    optixSdhRmspAu4MapWest2 OBJECT-TYPE
        SYNTAX OCTET STRING (SIZE(0..32))
        MAX-ACCESS read-create
        STATUS current
        DESCRIPTION
            "This object indicates theAu4 usageof the RMSP group."
        ::= { optixSdhRmspgEntry 27 }

    -- 1.3.6.1.4.1.2011.2.25.4.10.51.10.1.1.28
    optixSdhRmspBidWest2 OBJECT-TYPE
        SYNTAX Unsigned32
        MAX-ACCESS read-create
        STATUS current
        DESCRIPTION
            "This object indicates the slot ID of the RMSP group."
        ::= { optixSdhRmspgEntry 28 }

    -- 1.3.6.1.4.1.2011.2.25.4.10.51.10.1.1.29
    optixSdhRmspSubidWest2 OBJECT-TYPE
        SYNTAX Unsigned32
        MAX-ACCESS read-create
        STATUS current
        DESCRIPTION
            "This object indicates the subboard ID of the RMSP group."
        ::= { optixSdhRmspgEntry 29 }

    -- 1.3.6.1.4.1.2011.2.25.4.10.51.10.1.1.30
    optixSdhRmspPidWest2 OBJECT-TYPE
        SYNTAX Unsigned32
        MAX-ACCESS read-create
        STATUS current
        DESCRIPTION
            "This object indicates the port number of the RMSP group."
        ::= { optixSdhRmspgEntry 30 }

    -- 1.3.6.1.4.1.2011.2.25.4.10.51.10.1.1.31
    optixSdhRmspuidEast1 OBJECT-TYPE
        SYNTAX INTEGER
        {
            west1(0),
            west2(1),
            east1(2),
            east2(3)
        }
        MAX-ACCESS read-create
        STATUS current
        DESCRIPTION
            "This object indicates the RMSP protection unit ID. 0: west1, 1: west2, 2: east1, 3: east2"
        ::= { optixSdhRmspgEntry 31 }

    -- 1.3.6.1.4.1.2011.2.25.4.10.51.10.1.1.32
    optixSdhRmspAu4MapEast1 OBJECT-TYPE
        SYNTAX OCTET STRING (SIZE(0..32))
        MAX-ACCESS read-create
        STATUS current
        DESCRIPTION
            "This object indicates theAu4 usageof the RMSP group."
        ::= { optixSdhRmspgEntry 32 }

    -- 1.3.6.1.4.1.2011.2.25.4.10.51.10.1.1.33
    optixSdhRmspBidEast1 OBJECT-TYPE
        SYNTAX Unsigned32
        MAX-ACCESS read-create
        STATUS current
        DESCRIPTION
            "This object indicates the slot ID of the RMSP group."
        ::= { optixSdhRmspgEntry 33 }

    -- 1.3.6.1.4.1.2011.2.25.4.10.51.10.1.1.34
    optixSdhRmspSubidEast1 OBJECT-TYPE
        SYNTAX Unsigned32
        MAX-ACCESS read-create
        STATUS current
        DESCRIPTION
            "This object indicates the subboard ID of the RMSP group."
        ::= { optixSdhRmspgEntry 34 }

    -- 1.3.6.1.4.1.2011.2.25.4.10.51.10.1.1.35
    optixSdhRmspPidEast1 OBJECT-TYPE
        SYNTAX Unsigned32
        MAX-ACCESS read-create
        STATUS current
        DESCRIPTION
            "This object indicates the port number of the RMSP group."
        ::= { optixSdhRmspgEntry 35 }

    -- 1.3.6.1.4.1.2011.2.25.4.10.51.10.1.1.36
    optixSdhRmspuidEast2 OBJECT-TYPE
        SYNTAX INTEGER
        {
            west1(0),
            west2(1),
            east1(2),
            east2(3)
        }
        MAX-ACCESS read-create
        STATUS current
        DESCRIPTION
            "This object indicates the RMSP protection unit ID. 0: west1, 1: west2, 2: east1, 3: east2"
        ::= { optixSdhRmspgEntry 36 }

    -- 1.3.6.1.4.1.2011.2.25.4.10.51.10.1.1.37
    optixSdhRmspAu4MapEast2 OBJECT-TYPE
        SYNTAX OCTET STRING (SIZE(0..32))
        MAX-ACCESS read-create
        STATUS current
        DESCRIPTION
            "This object indicates theAu4 usageof the RMSP group."
        ::= { optixSdhRmspgEntry 37 }

    -- 1.3.6.1.4.1.2011.2.25.4.10.51.10.1.1.38
    optixSdhRmspBidEast2 OBJECT-TYPE
        SYNTAX Unsigned32
        MAX-ACCESS read-create
        STATUS current
        DESCRIPTION
            "This object indicates the slot ID of the RMSP group."
        ::= { optixSdhRmspgEntry 38 }

    -- 1.3.6.1.4.1.2011.2.25.4.10.51.10.1.1.39
    optixSdhRmspSubidEast2 OBJECT-TYPE
        SYNTAX Unsigned32
        MAX-ACCESS read-create
        STATUS current
        DESCRIPTION
            "This object indicates the subboard ID of the RMSP group."
        ::= { optixSdhRmspgEntry 39 }

    -- 1.3.6.1.4.1.2011.2.25.4.10.51.10.1.1.40
    optixSdhRmspPidEast2 OBJECT-TYPE
        SYNTAX Unsigned32
        MAX-ACCESS read-create
        STATUS current
        DESCRIPTION
            "This object indicates the port number of the RMSP group."
        ::= { optixSdhRmspgEntry 40 }

    -- 1.3.6.1.4.1.2011.2.25.4.10.51.10.1.1.41
    optixSdhRmspStartFlag OBJECT-TYPE
        SYNTAX INTEGER
        {
            protocolStop(0),
            protocolStart(1)
        }
        MAX-ACCESS read-create
        STATUS current
        DESCRIPTION
            "This object indicates the start flag of the RMSP group. 0: protocolStop, 1: protocolStart"
        ::= { optixSdhRmspgEntry 41 }

    -- 1.3.6.1.4.1.2011.2.25.4.10.51.10.1.1.255
    optixSdhRmspRowStatus OBJECT-TYPE
        SYNTAX RowStatus
        MAX-ACCESS read-create
        STATUS current
        DESCRIPTION
            "This object indicates the row status of the RMSP group."
        ::= { optixSdhRmspgEntry 255 }

    -- 1.3.6.1.4.1.2011.2.25.4.10.51.10.2
    optixSdhRmspuTable OBJECT-TYPE
        SYNTAX SEQUENCE OF OptixSdhRmspuEntry
        MAX-ACCESS not-accessible
        STATUS current
        DESCRIPTION
            "This table describes the configurations of RMSPprotection units."
        ::= { optixSdhRmspGroup 2 }

    -- 1.3.6.1.4.1.2011.2.25.4.10.51.10.2.1
    optixSdhRmspuEntry OBJECT-TYPE
        SYNTAX OptixSdhRmspuEntry
        MAX-ACCESS not-accessible
        STATUS current
        DESCRIPTION
            "This entry describes the configurations of RMSPprotection units."
        INDEX{ optixSdhRmspgid,optixSdhRmspuid }
        ::= { optixSdhRmspuTable 1 }

    OptixSdhRmspuEntry ::=
        SEQUENCE {
            optixSdhRmspuid
                INTEGER,
            optixSdhRmspExtSwitchCmd
                INTEGER
        }

    -- 1.3.6.1.4.1.2011.2.25.4.10.51.10.2.1.1
    optixSdhRmspuid OBJECT-TYPE
        SYNTAX INTEGER
        {
            west1(0),
            west2(1),
            east1(2),
            east2(3)
        }
        MAX-ACCESS not-accessible
        STATUS current
        DESCRIPTION
            "This object indicates the RMSPprotection unitID. 0: west1, 1: west2, 2: east1, 3: east2"
        ::= { optixSdhRmspuEntry 1 }

    -- 1.3.6.1.4.1.2011.2.25.4.10.51.10.2.1.2
    optixSdhRmspExtSwitchCmd OBJECT-TYPE
        SYNTAX INTEGER
        {
            rmsLock(15),
            rmsUnlock(31),
            rmsSforce(14),
            rmsSforceclr(30),
            rmsRforce(13),
            rmsRforceclr(29),
            rmsSman(7),
            rmsSmanclr(23),
            rmsRman(6),
            rmsRmanclr(22),
            rmsSexer(4),
            rmsSexerclr(20),
            rmsRexer(3),
            rmsRexerclr(19),
            rmsClearall(16),
            rmsLockallring(12),
            rmsUnlockallring(28),
            rmsLockworkring(10),
            rmsUnlockworkring(26),
            rmsLocksection(11),
            rmsUnlocksection(27),
            rmsClearwtr(21),
            rmsInvalid(0)
        }
        MAX-ACCESS read-write
        STATUS current
        DESCRIPTION
            "This object indicates the RMSP external switching cmd. 15: rmsLock, 31: rmsUnlock, 14: rmsSforce, 30: rmsSforceclr, 13: rmsRforce, 29: rmsRforceclr, 7: rmsSman, rmsSmanclr, 6: rmsRman, 22: rmsRmanclr, 4: rmsSexer, 20: rmsSexerclr, 3: rmsRexer, 19: rmsRexerclr, 16: rmsClearall, 12: rmsLockallring, 28: rmsUnlockallring, 10: rmsLockworkring, 26: rmsUnlockworkring, 11: rmsLocksection, 27: rmsUnlocksection, 21: rmsClearwtr, 0: rmsInvalid"
        ::= { optixSdhRmspuEntry 2 }

    -- 1.3.6.1.4.1.2011.2.25.4.10.51.10.4
    optixMsprSwitchMember OBJECT IDENTIFIER ::= { optixSdhRmspGroup 4 }

    -- 1.3.6.1.4.1.2011.2.25.4.10.51.10.4.1
    optixSdhSwitchRmspgid OBJECT-TYPE
        SYNTAX Unsigned32
        MAX-ACCESS accessible-for-notify
        STATUS current
        DESCRIPTION
            "This parameter specifies RMSP id."
        ::= { optixMsprSwitchMember 1 }

    -- 1.3.6.1.4.1.2011.2.25.4.10.51.10.4.2
    optixSdhRmspSwitchWestSwreq OBJECT-TYPE
        SYNTAX INTEGER
        {
            sfP(240),
            lpS(248),
            fsS(224),
            fsR(208),
            sfS(192),
            sfR(176),
            sdP(160),
            sdS(144),
            sdR(128),
            msS(112),
            msR(96),
            wtr(80),
            exerS(64),
            exerR(48),
            rrS(32),
            rrR(16),
            nr(0),
            sfPUlowS(241),
            lpSUlowS(249),
            fsRUlowS(209),
            sfRUlowS(177),
            sdPUlowS(161),
            sdRUlowS(129),
            msRUlowS(97),
            wtRUlowS(81),
            exerRUlows(49),
            nrUlowS(1),
            sfPUlowR(242),
            lpSUlowR(250),
            fsSUlowR(226),
            sfSUlowR(194),
            sdPUlowR(162),
            sdSUlowR(146),
            msSlowR(114),
            wtrUlowR(82),
            exerSUlowR(66),
            nrUlowR(2),
            sfPUlowSUlowR(243),
            lpSUlowSUlowR(251),
            sdPUlowSUlowR(163),
            nrUlowSUlowR(3),
            nrUlpa(4),
            lpsUlpa(252),
            nrUlowSUlpa(5),
            lpSUlowSUlpa(253),
            nrUlowRUlpa(6),
            lpsUlowRUlpa(254),
            nrUlowSUlowRUlpa(7),
            lpSUlowSUlowRUlpa(255),
            fsSUlw(239),
            fsRUlw(223),
            sfSUlw(207),
            sfRUlw(191),
            sdPUlw(175),
            sdSUlw(159),
            sdRUlw(143),
            msSUlw(127),
            msRUlw(111),
            wtRUlw(95),
            exerSUlw(79),
            exerRUlw(63),
            rrSUlw(47),
            rrRUlw(31),
            nrUlw(15)
        }
        MAX-ACCESS accessible-for-notify
        STATUS current
        DESCRIPTION
            "This parameter specifies RMSP west switch request. 240: sfP, 248: lpS, 224: fsS, 208: fsR, 192: sfS, 176: sfR, 160: sdP, 144: sdS, 128: sdR, 112: msS, 96: msR, 80: wtr, 64: exerS, 48: exerR, 32: rrS, 16: rrR, 0: nr, 241: sfPUlowS, 249: lpSUlowS, 209: fsRUlowS, 177: sfRUlowS, 161: sdPUlowS, 129: sdRUlowS, 97: msRUlowS, 81: wtRUlowS, 49: exerRUlows, 1: nrUlowS, 242: sfPUlowR, 250: lpSUlowR, 226: fsSUlowR, 194: sfSUlowR, 162: sdPUlowR, 146: sdSUlowR, 114: msSlowR, 82: wtrUlowR, 66: exerSUlowR, 2: nrUlowR, 243: sfPUlowSUlowR, 251: lpSUlowSUlowR, 163: sdPUlowSUlowR, 3: nrUlowSUlowR, 4: nrUlpa, 252: lpsUlpa, 5: nrUlowSUlpa(5), 253: lpSUlowSUlpa, 6: nrUlowRUlpa, 254: lpsUlowRUlpa, 7: nrUlowSUlowRUlpa, 255: lpSUlowSUlowRUlpa, 239: fsSUlw, 223: fsRUlw, 207: sfSUlw, 191: sfRUlw, 175: sdPUlw, 159: sdSUlw, 143: sdRUlw, 127: msSUlw, 111: msRUlw, 95: wtRUlw, 79: exerSUlw, 63: exerRUlw, 47: rrSUlw, 31: rrRUlw, 15: nrUlw"
        ::= { optixMsprSwitchMember 2 }

    -- 1.3.6.1.4.1.2011.2.25.4.10.51.10.4.3
    optixSdhRmspSwitchWestSwsta OBJECT-TYPE
        SYNTAX INTEGER
        {
            stop(0),
            i(1),
            s(4),
            p(6),
            starting(255)
        }
        MAX-ACCESS accessible-for-notify
        STATUS current
        DESCRIPTION
            "This parameter specifies RMSP west switch state. 0: stop, 1: i, 4: s, 6: p, 255: starting"
        ::= { optixMsprSwitchMember 3 }

    -- 1.3.6.1.4.1.2011.2.25.4.10.51.10.4.4
    optixSdhRmspSwitchWestSwflag OBJECT-TYPE
        SYNTAX INTEGER
        {
            off(0),
            on(1)
        }
        MAX-ACCESS accessible-for-notify
        STATUS current
        DESCRIPTION
            "This parameter specifies RMSP west swithc flag. 0: off, 1: on"
        ::= { optixMsprSwitchMember 4 }

    -- 1.3.6.1.4.1.2011.2.25.4.10.51.10.4.5
    optixSdhRmspSwitchEastSwreq OBJECT-TYPE
        SYNTAX INTEGER
        {
            sfP(240),
            lpS(248),
            fsS(224),
            fsR(208),
            sfS(192),
            sfR(176),
            sdP(160),
            sdS(144),
            sdR(128),
            msS(112),
            msR(96),
            wtr(80),
            exerS(64),
            exerR(48),
            rrS(32),
            rrR(16),
            nr(0),
            sfPUlowS(241),
            lpSUlowS(249),
            fsRUlowS(209),
            sfRUlowS(177),
            sdPUlowS(161),
            sdRUlowS(129),
            msRUlowS(97),
            wtRUlowS(81),
            exerRUlows(49),
            nrUlowS(1),
            sfPUlowR(242),
            lpSUlowR(250),
            fsSUlowR(226),
            sfSUlowR(194),
            sdPUlowR(162),
            sdSUlowR(146),
            msSlowR(114),
            wtrUlowR(82),
            exerSUlowR(66),
            nrUlowR(2),
            sfPUlowSUlowR(243),
            lpSUlowSUlowR(251),
            sdPUlowSUlowR(163),
            nrUlowSUlowR(3),
            nrUlpa(4),
            lpsUlpa(252),
            nrUlowSUlpa(5),
            lpSUlowSUlpa(253),
            nrUlowRUlpa(6),
            lpsUlowRUlpa(254),
            nrUlowSUlowRUlpa(7),
            lpSUlowSUlowRUlpa(255),
            fsSUlw(239),
            fsRUlw(223),
            sfSUlw(207),
            sfRUlw(191),
            sdPUlw(175),
            sdSUlw(159),
            sdRUlw(143),
            msSUlw(127),
            msRUlw(111),
            wtRUlw(95),
            exerSUlw(79),
            exerRUlw(63),
            rrSUlw(47),
            rrRUlw(31),
            nrUlw(15)
        }
        MAX-ACCESS accessible-for-notify
        STATUS current
        DESCRIPTION
            "This parameter specifies RMSP east switch request. 240: sfP, 248: lpS, 224: fsS, 208: fsR, 192: sfS, 176: sfR, 160: sdP, 144: sdS, 128: sdR, 112: msS, 96: msR, 80: wtr, 64: exerS, 48: exerR, 32: rrS, 16: rrR, 0: nr, 241: sfPUlowS, 249: lpSUlowS, 209: fsRUlowS, 177: sfRUlowS, 161: sdPUlowS, 129: sdRUlowS, 97: msRUlowS, 81: wtRUlowS, 49: exerRUlows, 1: nrUlowS, 242: sfPUlowR, 250: lpSUlowR, 226: fsSUlowR, 194: sfSUlowR, 162: sdPUlowR, 146: sdSUlowR, 114: msSlowR, 82: wtrUlowR, 66: exerSUlowR, 2: nrUlowR, 243: sfPUlowSUlowR, 251: lpSUlowSUlowR, 163: sdPUlowSUlowR, 3: nrUlowSUlowR, 4: nrUlpa, 252: lpsUlpa, 5: nrUlowSUlpa(5), 253: lpSUlowSUlpa, 6: nrUlowRUlpa, 254: lpsUlowRUlpa, 7: nrUlowSUlowRUlpa, 255: lpSUlowSUlowRUlpa, 239: fsSUlw, 223: fsRUlw, 207: sfSUlw, 191: sfRUlw, 175: sdPUlw, 159: sdSUlw, 143: sdRUlw, 127: msSUlw, 111: msRUlw, 95: wtRUlw, 79: exerSUlw, 63: exerRUlw, 47: rrSUlw, 31: rrRUlw, 15: nrUlw"
        ::= { optixMsprSwitchMember 5 }

    -- 1.3.6.1.4.1.2011.2.25.4.10.51.10.4.6
    optixSdhRmspSwitchEastSwsta OBJECT-TYPE
        SYNTAX INTEGER
        {
            stop(0),
            i(1),
            s(4),
            p(6),
            starting(255)
        }
        MAX-ACCESS accessible-for-notify
        STATUS current
        DESCRIPTION
            "This parameter specifies RMSP east switch state. 0: stop, 1: i, 4: s, 6: p, 255: starting"
        ::= { optixMsprSwitchMember 6 }

    -- 1.3.6.1.4.1.2011.2.25.4.10.51.10.4.7
    optixSdhRmspSwitchEastSwflag OBJECT-TYPE
        SYNTAX INTEGER
        {
            off(0),
            on(1)
        }
        MAX-ACCESS accessible-for-notify
        STATUS current
        DESCRIPTION
            "This parameter specifies RMSP east switch flag. 0: off, 1: on"
        ::= { optixMsprSwitchMember 7 }

    -- 1.3.6.1.4.1.2011.2.25.4.10.51.10.4.8
    optixSdhRmspSwitchWestReqSite OBJECT-TYPE
        SYNTAX INTEGER
        {
            near(1),
            far(2)
        }
        MAX-ACCESS accessible-for-notify
        STATUS current
        DESCRIPTION
            "This parameter specifies RMSP west request site. 1: near, 2: far"
        ::= { optixMsprSwitchMember 8 }

    -- 1.3.6.1.4.1.2011.2.25.4.10.51.10.4.9
    optixSdhRmspSwitchEastReqSite OBJECT-TYPE
        SYNTAX INTEGER
        {
            near(1),
            far(2)
        }
        MAX-ACCESS accessible-for-notify
        STATUS current
        DESCRIPTION
            "This parameter specifies RMSP east request site. 1: near, 2: far"
        ::= { optixMsprSwitchMember 9 }

    -- 1.3.6.1.4.1.2011.2.25.4.10.51.10.4.10
    optixSdhRmspNoteState OBJECT-TYPE
        SYNTAX INTEGER
        {
            isLone(1),
            noLone(0)
        }
        MAX-ACCESS accessible-for-notify
        STATUS current
        DESCRIPTION
            "This parameter specifies RMSP note state. 1: isLone, 0: noLone"
        ::= { optixMsprSwitchMember 10 }

    -- 1.3.6.1.4.1.2011.2.25.4.10.51.10.4.11
    optixSdhRmspSquelState OBJECT-TYPE
        SYNTAX INTEGER
        {
            noSquelch(0),
            westSquelch(1),
            eastSquelch(2)
        }
        MAX-ACCESS accessible-for-notify
        STATUS current
        DESCRIPTION
            "This parameter specifies RMSP squel state. 0: noSquelch, 1: westSquelch, 2: eastSquelch"
        ::= { optixMsprSwitchMember 11 }

    -- 1.3.6.1.4.1.2011.2.25.4.10.51.10.4.12
    optixSdhRmspSwitchReason OBJECT-TYPE
        SYNTAX INTEGER
        {
            localReq(1),
            extReq(2),
            kReq(3),
            expireOfTimer(4)
        }
        MAX-ACCESS accessible-for-notify
        STATUS current
        DESCRIPTION
            "This parameter specifies RMSP Switch Reason. 1: localReq, 2: extReq, 3: kReq, 4: expireOfTimer"
        ::= { optixMsprSwitchMember 12 }

    -- 1.3.6.1.4.1.2011.2.25.4.10.51.10.4.13
    optixSdhRmspDir OBJECT-TYPE
        SYNTAX INTEGER
        {
            west(0),
            east(2)
        }
        MAX-ACCESS accessible-for-notify
        STATUS current
        DESCRIPTION
            "This parameter specifies RMSP request DIR. 0: west, 2: east"
        ::= { optixMsprSwitchMember 13 }

    -- 1.3.6.1.4.1.2011.2.25.4.10.51.10.4.14
    optixSdhRmspChannelsState OBJECT-TYPE
        SYNTAX INTEGER
        {
            rmsLock(15),
            rmsUnlock(31),
            rmsSforce(14),
            rmsSforceclr(30),
            rmsRforce(13),
            rmsRforceclr(29),
            rmsSman(7),
            rmsSmanclr(23),
            rmsRman(6),
            rmsRmanclr(22),
            rmsSexer(4),
            rmsSexerclr(20),
            rmsRexer(3),
            rmsRexerclr(19),
            rmsClearwtr(21),
            rmsClearall(16)
        }
        MAX-ACCESS accessible-for-notify
        STATUS current
        DESCRIPTION
            "This parameter specifies RMSP lock state. 15: rmsLock, 31: rmsUnlock, 14: rmsSforce, 30: rmsSforceclr, 13: rmsRforce, 29: rmsRforceclr, 7: rmsSman, 23: rmsSmanclr, 6: rmsRman, 22: rmsRmanclr, 4: rmsSexer, 20: rmsSexerclr, 3: rmsRexer, 19: rmsRexerclr, 21: rmsClearwtr, 16: rmsClearall"
        ::= { optixMsprSwitchMember 14 }

    -- 1.3.6.1.4.1.2011.2.25.4.10.51.10.5
    optixRmspEvent OBJECT IDENTIFIER ::= { optixSdhRmspGroup 5 }

    -- 1.3.6.1.4.1.2011.2.25.4.10.51.10.5.1
    optixMssprSwitchTrap NOTIFICATION-TYPE
        OBJECTS{ optixSdhSwitchRmspgid,optixSdhRmspSwitchWestSwreq,optixSdhRmspSwitchWestSwsta,optixSdhRmspSwitchWestSwflag,optixSdhRmspSwitchEastSwreq,optixSdhRmspSwitchEastSwsta,optixSdhRmspSwitchEastSwflag,optixSdhRmspSwitchWestReqSite,optixSdhRmspSwitchEastReqSite,optixSdhRmspNoteState,optixSdhRmspSquelState }
        STATUS current
        DESCRIPTION
            "This parameter specifie RMSP statechange event"
        ::= { optixRmspEvent 1 }

    -- 1.3.6.1.4.1.2011.2.25.4.10.51.10.5.2
    optixMssprSwitch03Trap NOTIFICATION-TYPE
        OBJECTS{ optixSdhSwitchRmspgid,optixSdhRmspSwitchWestSwreq,optixSdhRmspSwitchWestSwsta,optixSdhRmspSwitchWestSwflag,optixSdhRmspSwitchEastSwreq,optixSdhRmspSwitchEastSwsta,optixSdhRmspSwitchEastSwflag,optixSdhRmspSwitchWestReqSite,optixSdhRmspSwitchEastReqSite,optixSdhRmspSwitchReason }
        STATUS current
        DESCRIPTION
            "This parameter specifie RMSP statechange event"
        ::= { optixRmspEvent 2 }

    -- 1.3.6.1.4.1.2011.2.25.4.10.51.10.5.3
    optixMssprExtReqUnexeTrap NOTIFICATION-TYPE
        OBJECTS{ optixSdhSwitchRmspgid,optixSdhRmspDir,optixSdhRmspChannelsState }
        STATUS current
        DESCRIPTION
            "This parameter specifie RMSP rote port not requair event"
        ::= { optixRmspEvent 3 }

END
