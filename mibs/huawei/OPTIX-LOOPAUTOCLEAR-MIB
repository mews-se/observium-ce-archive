-- OPTIX-LOOPAUTOCLEAR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-LOOPAUTOCLEAR-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY,NOTIFICATION-TYPE
            FROM SNMPv2-SMI
        ;

    optixLoopAutoclear MODULE-IDENTITY
        LAST-UPDATED "201204240000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies loop automatic cleared information"
        REVISION "201204240000Z"
        DESCRIPTION
            "The initial revision of this MIB module."
        REVISION "201204240000Z"
        DESCRIPTION
            "The initial revision of this MIB module."
        ::={ optixProvisionEqpt 13 }

    -- 1.3.6.1.4.1.2011.2.25.4.30.13.1
    optixLoopAutoclearGroup OBJECT IDENTIFIER ::= { optixLoopAutoclear 1 }

    -- 1.3.6.1.4.1.2011.2.25.4.30.13.1.1
    optixLoopAutoclearTable OBJECT-TYPE
        SYNTAX SEQUENCE OF OptixLoopAutoclearEntry
        MAX-ACCESS not-accessible
        STATUS current
        DESCRIPTION
            "This table describes the loopback auto-release function configuredon devices."
        ::= { optixLoopAutoclearGroup 1 }

    -- 1.3.6.1.4.1.2011.2.25.4.30.13.1.1.1
    optixLoopAutoclearEntry OBJECT-TYPE
        SYNTAX OptixLoopAutoclearEntry
        MAX-ACCESS not-accessible
        STATUS current
        DESCRIPTION
            "Thisentry describes the loopback auto-release function configured on devices."
        INDEX{ optixClearType }
        ::= { optixLoopAutoclearTable 1 }

    OptixLoopAutoclearEntry ::=
        SEQUENCE {
            optixClearType
                INTEGER,
            optixClearFlag
                INTEGER,
            optixClearTime
                Unsigned32
        }

    -- 1.3.6.1.4.1.2011.2.25.4.30.13.1.1.1.1
    optixClearType OBJECT-TYPE
        SYNTAX INTEGER
        {
            all(0),
            au4loop(1),
            portloop(2),
            lasershut(5),
            vc3loop(8),
            vc12loop(9),
            ethport(10),
            odumute(11),
            ifloop(13),
            oduloop(14),
            atmport(16),
            acmswitch(19),
            oduswitch(25)
        }
        MAX-ACCESS not-accessible
        STATUS current
        DESCRIPTION
            "Thisobject indicates the loopback auto-release type. 0: all, 1: au4loop, 2: portloop, 5: lasershut, 8: vc3loop, 9: vc12loop, 10: ethport, 11: odumute, 13: ifloop, 14: oduloop, 16: atmport, 19: acmswitch, 25: oduswitch"
        ::= { optixLoopAutoclearEntry 1 }

    -- 1.3.6.1.4.1.2011.2.25.4.30.13.1.1.1.2
    optixClearFlag OBJECT-TYPE
        SYNTAX INTEGER
        {
            disable(0),
            enable(1)
        }
        MAX-ACCESS read-write
        STATUS current
        DESCRIPTION
            "This object indicates the enable status of the loopback auto-release function. 0: disable, 1: enable"
        ::= { optixLoopAutoclearEntry 2 }

    -- 1.3.6.1.4.1.2011.2.25.4.30.13.1.1.1.3
    optixClearTime OBJECT-TYPE
        SYNTAX Unsigned32
        MAX-ACCESS read-write
        STATUS current
        DESCRIPTION
            "This object indicates the loopback auto-release time. Value range: 1 to 2880 (unit: minute). The default value is 5."
        ::= { optixLoopAutoclearEntry 3 }

    -- 1.3.6.1.4.1.2011.2.25.4.30.13.1.2
    optixLoopAutoclearTrapMember OBJECT IDENTIFIER ::= { optixLoopAutoclearGroup 2 }

    -- 1.3.6.1.4.1.2011.2.25.4.30.13.1.2.1
    optixLoopAutoclearType OBJECT-TYPE
        SYNTAX INTEGER
        {
            au4loop(1),
            portloop(2),
            vc3loop(8),
            ethport(10),
            vc12loop(9),
            lasershut(5),
            atmport(16),
            odumute(11),
            ifloop(13),
            acmswitch(19),
            all(0),
            oduloop(14),
            oduswitch(25)
        }
        MAX-ACCESS accessible-for-notify
        STATUS current
        DESCRIPTION
            "the Type of Autoclear Event"
        ::= { optixLoopAutoclearTrapMember 1 }

    -- 1.3.6.1.4.1.2011.2.25.4.30.13.1.2.2
    optixLoopAutoclearBid OBJECT-TYPE
        SYNTAX Unsigned32
        MAX-ACCESS accessible-for-notify
        STATUS current
        DESCRIPTION
            "the Board of Autoclear Event"
        ::= { optixLoopAutoclearTrapMember 2 }

    -- 1.3.6.1.4.1.2011.2.25.4.30.13.1.2.3
    optixLoopAutoclearSBid OBJECT-TYPE
        SYNTAX Unsigned32
        MAX-ACCESS accessible-for-notify
        STATUS current
        DESCRIPTION
            "the SubBoard of Autoclear Event"
        ::= { optixLoopAutoclearTrapMember 3 }

    -- 1.3.6.1.4.1.2011.2.25.4.30.13.1.2.4
    optixLoopAutoclearPort OBJECT-TYPE
        SYNTAX Unsigned32
        MAX-ACCESS accessible-for-notify
        STATUS current
        DESCRIPTION
            "the Port of Autoclear Event"
        ::= { optixLoopAutoclearTrapMember 4 }

    -- 1.3.6.1.4.1.2011.2.25.4.30.13.1.2.5
    optixLoopAutoclearPath OBJECT-TYPE
        SYNTAX Unsigned32
        MAX-ACCESS accessible-for-notify
        STATUS current
        DESCRIPTION
            "the Path of Autoclear Event"
        ::= { optixLoopAutoclearTrapMember 5 }

    -- 1.3.6.1.4.1.2011.2.25.4.30.13.1.3
    optixLoopAutoclearTrapReport OBJECT IDENTIFIER ::= { optixLoopAutoclearGroup 3 }

    -- 1.3.6.1.4.1.2011.2.25.4.30.13.1.3.1
    optixLoopAutoclearTrap NOTIFICATION-TYPE
        OBJECTS{ optixLoopAutoclearPath,optixLoopAutoclearPort,optixLoopAutoclearSBid,optixLoopAutoclearBid,optixLoopAutoclearType }
        STATUS current
        DESCRIPTION
            "the Event of Autoclear Report"
        ::= { optixLoopAutoclearTrapReport 1 }

END
