-- OPTIX-SDH-LMSP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-LMSP-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY,Integer32,NOTIFICATION-TYPE
            FROM SNMPv2-SMI
        RowStatus
            FROM SNMPv2-TC
        ;

    optixSdhLmsp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describesLMSP configurations."
        REVISION "201204200000Z"
        DESCRIPTION
            "The initial revision of this MIB module1."
        ::={ optixProvisionSdh 41 }

    -- 1.3.6.1.4.1.2011.2.25.4.10.41.5
    optixSdhLmspGroup OBJECT IDENTIFIER ::= { optixSdhLmsp 5 }

    -- 1.3.6.1.4.1.2011.2.25.4.10.41.5.1
    optixSdhLmspgTable OBJECT-TYPE
        SYNTAX SEQUENCE OF OptixSdhLmspgEntry
        MAX-ACCESS not-accessible
        STATUS current
        DESCRIPTION
            "This table describes the LMSP group configurations."
        ::= { optixSdhLmspGroup 1 }

    -- 1.3.6.1.4.1.2011.2.25.4.10.41.5.1.1
    optixSdhLmspgEntry OBJECT-TYPE
        SYNTAX OptixSdhLmspgEntry
        MAX-ACCESS not-accessible
        STATUS current
        DESCRIPTION
            "This entry describes the LMSP group configurations."
        INDEX{ optixSdhLmspgid }
        ::= { optixSdhLmspgTable 1 }

    OptixSdhLmspgEntry ::=
        SEQUENCE {
            optixSdhLmspgid
                Unsigned32,
            optixSdhLmspProtectType
                INTEGER,
            optixSdhLmspWorkChnNum
                Unsigned32,
            optixSdhLmspRevertMode
                INTEGER,
            optixSdhLmspOpMode
                INTEGER,
            optixSdhLmspActiveFlag
                INTEGER,
            optixSdhLmspWtrTime
                Unsigned32,
            optixSdhLmspSdEnable
                INTEGER,
            optixSdhLmspSwitchReq
                INTEGER,
            optixSdhLmspSwitchSta
                INTEGER,
            optixSdhLmspHoldOffTime
                Unsigned32,
            optixSdhLmspK2Mode
                INTEGER,
            optixSdhLmspKLevel
                INTEGER,
            optixSdhLmspProtocolType
                INTEGER,
            optixSdhLmspuid0
                Unsigned32,
            optixSdhLmspBid0
                Unsigned32,
            optixSdhLmspSubid0
                Unsigned32,
            optixSdhLmspPortid0
                Unsigned32,
            optixSdhLmspAu4Map0
                OCTET STRING,
            optixSdhLmspReqSite0
                INTEGER,
            optixSdhLmspuid1
                Unsigned32,
            optixSdhLmspBid1
                Unsigned32,
            optixSdhLmspSubid1
                Unsigned32,
            optixSdhLmspPortid1
                Unsigned32,
            optixSdhLmspAu4Map1
                OCTET STRING,
            optixSdhLmspReqSite1
                INTEGER,
            optixSdhLmspuid2
                Unsigned32,
            optixSdhLmspBid2
                Unsigned32,
            optixSdhLmspSubid2
                Unsigned32,
            optixSdhLmspPortid2
                Unsigned32,
            optixSdhLmspAu4Map2
                OCTET STRING,
            optixSdhLmspReqSite2
                INTEGER,
            optixSdhLmspuid3
                Unsigned32,
            optixSdhLmspBid3
                Unsigned32,
            optixSdhLmspSubid3
                Unsigned32,
            optixSdhLmspPortid3
                Unsigned32,
            optixSdhLmspAu4Map3
                OCTET STRING,
            optixSdhLmspReqSite3
                INTEGER,
            optixSdhLmspuid4
                Unsigned32,
            optixSdhLmspBid4
                Unsigned32,
            optixSdhLmspSubid4
                Unsigned32,
            optixSdhLmspPortid4
                Unsigned32,
            optixSdhLmspAu4Map4
                OCTET STRING,
            optixSdhLmspReqSite4
                INTEGER,
            optixSdhLmspuid5
                Unsigned32,
            optixSdhLmspBid5
                Unsigned32,
            optixSdhLmspSubid5
                Unsigned32,
            optixSdhLmspPortid5
                Unsigned32,
            optixSdhLmspAu4Map5
                OCTET STRING,
            optixSdhLmspReqSite5
                INTEGER,
            optixSdhLmspuid6
                Unsigned32,
            optixSdhLmspBid6
                Unsigned32,
            optixSdhLmspSubid6
                Unsigned32,
            optixSdhLmspPortid6
                Unsigned32,
            optixSdhLmspAu4Map6
                OCTET STRING,
            optixSdhLmspReqSite6
                INTEGER,
            optixSdhLmspuid7
                Unsigned32,
            optixSdhLmspBid7
                Unsigned32,
            optixSdhLmspSubid7
                Unsigned32,
            optixSdhLmspPortid7
                Unsigned32,
            optixSdhLmspAu4Map7
                OCTET STRING,
            optixSdhLmspReqSite7
                INTEGER,
            optixSdhLmspuid8
                Unsigned32,
            optixSdhLmspBid8
                Unsigned32,
            optixSdhLmspSubid8
                Unsigned32,
            optixSdhLmspPortid8
                Unsigned32,
            optixSdhLmspAu4Map8
                OCTET STRING,
            optixSdhLmspReqSite8
                INTEGER,
            optixSdhLmspuid9
                Unsigned32,
            optixSdhLmspBid9
                Unsigned32,
            optixSdhLmspSubid9
                Unsigned32,
            optixSdhLmspPortid9
                Unsigned32,
            optixSdhLmspAu4Map9
                OCTET STRING,
            optixSdhLmspReqSite9
                INTEGER,
            optixSdhLmspuid10
                Unsigned32,
            optixSdhLmspBid10
                Unsigned32,
            optixSdhLmspSubid10
                Unsigned32,
            optixSdhLmspPortid10
                Unsigned32,
            optixSdhLmspAu4Map10
                OCTET STRING,
            optixSdhLmspReqSite10
                INTEGER,
            optixSdhLmspuid11
                Unsigned32,
            optixSdhLmspBid11
                Unsigned32,
            optixSdhLmspSubid11
                Unsigned32,
            optixSdhLmspPortid11
                Unsigned32,
            optixSdhLmspAu4Map11
                OCTET STRING,
            optixSdhLmspReqSite11
                INTEGER,
            optixSdhLmspuid12
                Unsigned32,
            optixSdhLmspBid12
                Unsigned32,
            optixSdhLmspSubid12
                Unsigned32,
            optixSdhLmspPortid12
                Unsigned32,
            optixSdhLmspAu4Map12
                OCTET STRING,
            optixSdhLmspReqSite12
                INTEGER,
            optixSdhLmspuid13
                Unsigned32,
            optixSdhLmspBid13
                Unsigned32,
            optixSdhLmspSubid13
                Unsigned32,
            optixSdhLmspPortid13
                Unsigned32,
            optixSdhLmspAu4Map13
                OCTET STRING,
            optixSdhLmspReqSite13
                INTEGER,
            optixSdhLmspuid14
                Unsigned32,
            optixSdhLmspBid14
                Unsigned32,
            optixSdhLmspSubid14
                Unsigned32,
            optixSdhLmspPortid14
                Unsigned32,
            optixSdhLmspAu4Map14
                OCTET STRING,
            optixSdhLmspReqSite14
                INTEGER,
            optixSdhLmspStartFlag
                INTEGER,
            optixSdhLmspgRowStatus
                RowStatus
        }

    -- 1.3.6.1.4.1.2011.2.25.4.10.41.5.1.1.1
    optixSdhLmspgid OBJECT-TYPE
        SYNTAX Unsigned32
        MAX-ACCESS not-accessible
        STATUS current
        DESCRIPTION
            "This object indicates the LMSP group ID."
        ::= { optixSdhLmspgEntry 1 }

    -- 1.3.6.1.4.1.2011.2.25.4.10.41.5.1.1.2
    optixSdhLmspProtectType OBJECT-TYPE
        SYNTAX INTEGER
        {
            snmp1j1(0),
            snmp1pn(1)
        }
        MAX-ACCESS read-create
        STATUS current
        DESCRIPTION
            "This object indicates the LMSP protection type. 0: 1+1 protection, 1: 1:N protection"
        ::= { optixSdhLmspgEntry 2 }

    -- 1.3.6.1.4.1.2011.2.25.4.10.41.5.1.1.3
    optixSdhLmspWorkChnNum OBJECT-TYPE
        SYNTAX Unsigned32
        MAX-ACCESS read-create
        STATUS current
        DESCRIPTION
            "This object indicates the number of LMSP working channels. Value range: 1 to 14."
        ::= { optixSdhLmspgEntry 3 }

    -- 1.3.6.1.4.1.2011.2.25.4.10.41.5.1.1.4
    optixSdhLmspRevertMode OBJECT-TYPE
        SYNTAX INTEGER
        {
            norvt(0),
            rvt(1)
        }
        MAX-ACCESS read-create
        STATUS current
        DESCRIPTION
            "This object indicates the LMSP revertive mode. 0: non-revertive, 1: revertive"
        ::= { optixSdhLmspgEntry 4 }

    -- 1.3.6.1.4.1.2011.2.25.4.10.41.5.1.1.5
    optixSdhLmspOpMode OBJECT-TYPE
        SYNTAX INTEGER
        {
            uniend(0),
            biend(1)
        }
        MAX-ACCESS read-create
        STATUS current
        DESCRIPTION
            "This object indicates the single-/dual-ended flag of the LMSP group. 0: single-ended, 1: dual-ended"
        ::= { optixSdhLmspgEntry 5 }

    -- 1.3.6.1.4.1.2011.2.25.4.10.41.5.1.1.6
    optixSdhLmspActiveFlag OBJECT-TYPE
        SYNTAX INTEGER
        {
            adding(1),
            deleting(2),
            active(3)
        }
        MAX-ACCESS read-only
        STATUS current
        DESCRIPTION
            "This object indicates the LMSP activation flag. 0x01: to be added, 0x02: to be deleted, 0x03: activiated"
        ::= { optixSdhLmspgEntry 6 }

    -- 1.3.6.1.4.1.2011.2.25.4.10.41.5.1.1.7
    optixSdhLmspWtrTime OBJECT-TYPE
        SYNTAX Unsigned32
        MAX-ACCESS read-create
        STATUS current
        DESCRIPTION
            "This object indicates the WTR time of the LMSP group. Value range: 6 to 720 (unit: s)."
        ::= { optixSdhLmspgEntry 7 }

    -- 1.3.6.1.4.1.2011.2.25.4.10.41.5.1.1.8
    optixSdhLmspSdEnable OBJECT-TYPE
        SYNTAX INTEGER
        {
            disable(0),
            enable(1)
        }
        MAX-ACCESS read-create
        STATUS current
        DESCRIPTION
            "This object indicates the enable status of the LMSP SD switching. 0: disable, 1: enable"
        ::= { optixSdhLmspgEntry 8 }

    -- 1.3.6.1.4.1.2011.2.25.4.10.41.5.1.1.9
    optixSdhLmspSwitchReq OBJECT-TYPE
        SYNTAX INTEGER
        {
            lpsNr(0),
            lpsDnr(16),
            lpsExer(64),
            lpsWtr(96),
            lpsMs(128),
            lpsSdLow(160),
            lpsSd(176),
            lpsSfLow(192),
            lpsSf(208),
            lpsFs(224),
            lpsLp(240)
        }
        MAX-ACCESS read-only
        STATUS current
        DESCRIPTION
            "This object indicates the LMSP switching request. 0: lpsNr, 16: lpsDnr, 64: lpsExer, 96: lpsWtr, 128: lpsMs, 160: lpsSdLow, 176: lpsSd, 192: lpsSfLow, 208: lpsSf, 224: lpsFs, 240: lpsLp"
        ::= { optixSdhLmspgEntry 9 }

    -- 1.3.6.1.4.1.2011.2.25.4.10.41.5.1.1.10
    optixSdhLmspSwitchSta OBJECT-TYPE
        SYNTAX INTEGER
        {
            stop(0),
            i(1),
            s(4),
            starting(255)
        }
        MAX-ACCESS read-only
        STATUS current
        DESCRIPTION
            "This object indicates the LMSP switching status. 0: stop(0), 1: i, 4: s, 255: starting"
        ::= { optixSdhLmspgEntry 10 }

    -- 1.3.6.1.4.1.2011.2.25.4.10.41.5.1.1.11
    optixSdhLmspHoldOffTime OBJECT-TYPE
        SYNTAX Unsigned32
        MAX-ACCESS read-create
        STATUS current
        DESCRIPTION
            "This object indicates the LMSP switching delay time. Value range: 0 to 100 (unit: 100 ms). If there is no delay time, the returned value is 0."
        ::= { optixSdhLmspgEntry 11 }

    -- 1.3.6.1.4.1.2011.2.25.4.10.41.5.1.1.12
    optixSdhLmspK2Mode OBJECT-TYPE
        SYNTAX INTEGER
        {
            noindicate(0),
            indicate(1)
        }
        MAX-ACCESS read-create
        STATUS current
        DESCRIPTION
            "This object indicates the last three bits of the K2 byte of the LMSP group, which represents the single-/dual-ended mode. 0: noindicate, 1: indicate"
        ::= { optixSdhLmspgEntry 12 }

    -- 1.3.6.1.4.1.2011.2.25.4.10.41.5.1.1.13
    optixSdhLmspKLevel OBJECT-TYPE
        SYNTAX INTEGER
        {
            kHigh(0),
            kLow(1)
        }
        MAX-ACCESS read-create
        STATUS current
        DESCRIPTION
            "This object indicates the priority level of the SF and SD in the K byte. 0: kHigh, 1: kLow"
        ::= { optixSdhLmspgEntry 13 }

    -- 1.3.6.1.4.1.2011.2.25.4.10.41.5.1.1.14
    optixSdhLmspProtocolType OBJECT-TYPE
        SYNTAX INTEGER
        {
            old(0),
            new(1),
            restruct(2),
            transoceanic(3)
        }
        MAX-ACCESS read-create
        STATUS current
        DESCRIPTION
            "This object indicates the protocol type of the LMSP group. 0: old, 1: new, 2: restruct, 3: transoceanic"
        ::= { optixSdhLmspgEntry 14 }

    -- 1.3.6.1.4.1.2011.2.25.4.10.41.5.1.1.15
    optixSdhLmspuid0 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 15 }

    -- 1.3.6.1.4.1.2011.2.25.4.10.41.5.1.1.16
    optixSdhLmspBid0 OBJECT-TYPE
        SYNTAX Unsigned32
        MAX-ACCESS read-create
        STATUS current
        DESCRIPTION
            "This object indicates the slot ID of the LMSP group. The value is determined by the line board."
        ::= { optixSdhLmspgEntry 16 }

    -- 1.3.6.1.4.1.2011.2.25.4.10.41.5.1.1.17
    optixSdhLmspSubid0 OBJECT-TYPE
        SYNTAX Unsigned32
        MAX-ACCESS read-create
        STATUS current
        DESCRIPTION
            "This object indicates the subboard ID of the LMSP group. The value is determined by the line board."
        ::= { optixSdhLmspgEntry 17 }

    -- 1.3.6.1.4.1.2011.2.25.4.10.41.5.1.1.18
    optixSdhLmspPortid0 OBJECT-TYPE
        SYNTAX Unsigned32
        MAX-ACCESS read-create
        STATUS current
        DESCRIPTION
            "This object indicates the port number of the LMSP group. The value is determined by the line board."
        ::= { optixSdhLmspgEntry 18 }

    -- 1.3.6.1.4.1.2011.2.25.4.10.41.5.1.1.19
    optixSdhLmspAu4Map0 OBJECT-TYPE
        SYNTAX OCTET STRING (SIZE(0..32))
        MAX-ACCESS read-create
        STATUS current
        DESCRIPTION
            "This object indicates the LMSP group Au4 mapping."
        ::= { optixSdhLmspgEntry 19 }

    -- 1.3.6.1.4.1.2011.2.25.4.10.41.5.1.1.20
    optixSdhLmspReqSite0 OBJECT-TYPE
        SYNTAX INTEGER
        {
            near(1),
            far(2)
        }
        MAX-ACCESS read-only
        STATUS current
        DESCRIPTION
            "This object indicates the LMSP remote/local end. 1: near, 2: far"
        ::= { optixSdhLmspgEntry 20 }

    -- 1.3.6.1.4.1.2011.2.25.4.10.41.5.1.1.21
    optixSdhLmspuid1 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 21 }

    -- 1.3.6.1.4.1.2011.2.25.4.10.41.5.1.1.22
    optixSdhLmspBid1 OBJECT-TYPE
        SYNTAX Unsigned32
        MAX-ACCESS read-create
        STATUS current
        DESCRIPTION
            "This object indicates the slot ID of the LMSP group. The value is determined by the line board."
        ::= { optixSdhLmspgEntry 22 }

    -- 1.3.6.1.4.1.2011.2.25.4.10.41.5.1.1.23
    optixSdhLmspSubid1 OBJECT-TYPE
        SYNTAX Unsigned32
        MAX-ACCESS read-create
        STATUS current
        DESCRIPTION
            "This object indicates the subboard ID of the LMSP group. The value is determined by the line board."
        ::= { optixSdhLmspgEntry 23 }

    -- 1.3.6.1.4.1.2011.2.25.4.10.41.5.1.1.24
    optixSdhLmspPortid1 OBJECT-TYPE
        SYNTAX Unsigned32
        MAX-ACCESS read-create
        STATUS current
        DESCRIPTION
            "This object indicates the port number of the LMSP group. The value is determined by the line board."
        ::= { optixSdhLmspgEntry 24 }

    -- 1.3.6.1.4.1.2011.2.25.4.10.41.5.1.1.25
    optixSdhLmspAu4Map1 OBJECT-TYPE
        SYNTAX OCTET STRING (SIZE(0..32))
        MAX-ACCESS read-create
        STATUS current
        DESCRIPTION
            "This object indicates the LMSP group Au4 mapping. The value is determined by the line board."
        ::= { optixSdhLmspgEntry 25 }

    -- 1.3.6.1.4.1.2011.2.25.4.10.41.5.1.1.26
    optixSdhLmspReqSite1 OBJECT-TYPE
        SYNTAX INTEGER
        {
            near(1),
            far(2)
        }
        MAX-ACCESS read-only
        STATUS current
        DESCRIPTION
            "This object indicates the LMSP remote/local end. 1: near, 2: far"
        ::= { optixSdhLmspgEntry 26 }

    -- 1.3.6.1.4.1.2011.2.25.4.10.41.5.1.1.27
    optixSdhLmspuid2 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 27 }

    -- 1.3.6.1.4.1.2011.2.25.4.10.41.5.1.1.28
    optixSdhLmspBid2 OBJECT-TYPE
        SYNTAX Unsigned32
        MAX-ACCESS read-create
        STATUS current
        DESCRIPTION
            "This object indicates the slot ID of the LMSP group. The value is determined by the line board."
        ::= { optixSdhLmspgEntry 28 }

    -- 1.3.6.1.4.1.2011.2.25.4.10.41.5.1.1.29
    optixSdhLmspSubid2 OBJECT-TYPE
        SYNTAX Unsigned32
        MAX-ACCESS read-create
        STATUS current
        DESCRIPTION
            "This object indicates the subboard ID of the LMSP group. The value is determined by the line board."
        ::= { optixSdhLmspgEntry 29 }

    -- 1.3.6.1.4.1.2011.2.25.4.10.41.5.1.1.30
    optixSdhLmspPortid2 OBJECT-TYPE
        SYNTAX Unsigned32
        MAX-ACCESS read-create
        STATUS current
        DESCRIPTION
            "This object indicates the port number of the LMSP group. The value is determined by the line board."
        ::= { optixSdhLmspgEntry 30 }

    -- 1.3.6.1.4.1.2011.2.25.4.10.41.5.1.1.31
    optixSdhLmspAu4Map2 OBJECT-TYPE
        SYNTAX OCTET STRING (SIZE(0..32))
        MAX-ACCESS read-create
        STATUS current
        DESCRIPTION
            "This object indicates the LMSP group Au4 mapping. The value is determined by the line board"
        ::= { optixSdhLmspgEntry 31 }

    -- 1.3.6.1.4.1.2011.2.25.4.10.41.5.1.1.32
    optixSdhLmspReqSite2 OBJECT-TYPE
        SYNTAX INTEGER
        {
            near(1),
            far(2)
        }
        MAX-ACCESS read-only
        STATUS current
        DESCRIPTION
            "This object indicates the LMSP remote/local end. 1: near, 2: far"
        ::= { optixSdhLmspgEntry 32 }

    -- 1.3.6.1.4.1.2011.2.25.4.10.41.5.1.1.33
    optixSdhLmspuid3 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 33 }

    -- 1.3.6.1.4.1.2011.2.25.4.10.41.5.1.1.34
    optixSdhLmspBid3 OBJECT-TYPE
        SYNTAX Unsigned32
        MAX-ACCESS read-create
        STATUS current
        DESCRIPTION
            "This object indicates the slot ID of the LMSP group. The value is determined by the line board."
        ::= { optixSdhLmspgEntry 34 }

    -- 1.3.6.1.4.1.2011.2.25.4.10.41.5.1.1.35
    optixSdhLmspSubid3 OBJECT-TYPE
        SYNTAX Unsigned32
        MAX-ACCESS read-create
        STATUS current
        DESCRIPTION
            "This object indicates the subboard ID of the LMSP group. The value is determined by the line board."
        ::= { optixSdhLmspgEntry 35 }

    -- 1.3.6.1.4.1.2011.2.25.4.10.41.5.1.1.36
    optixSdhLmspPortid3 OBJECT-TYPE
        SYNTAX Unsigned32
        MAX-ACCESS read-create
        STATUS current
        DESCRIPTION
            "This object indicates the port number of the LMSP group. The value is determined by the line board."
        ::= { optixSdhLmspgEntry 36 }

    -- 1.3.6.1.4.1.2011.2.25.4.10.41.5.1.1.37
    optixSdhLmspAu4Map3 OBJECT-TYPE
        SYNTAX OCTET STRING (SIZE(0..32))
        MAX-ACCESS read-create
        STATUS current
        DESCRIPTION
            "This object indicates the LMSP group Au4 mapping."
        ::= { optixSdhLmspgEntry 37 }

    -- 1.3.6.1.4.1.2011.2.25.4.10.41.5.1.1.38
    optixSdhLmspReqSite3 OBJECT-TYPE
        SYNTAX INTEGER
        {
            near(1),
            far(2)
        }
        MAX-ACCESS read-only
        STATUS current
        DESCRIPTION
            "This object indicates the LMSP remote/local end. 1: near, 2: far"
        ::= { optixSdhLmspgEntry 38 }

    -- 1.3.6.1.4.1.2011.2.25.4.10.41.5.1.1.39
    optixSdhLmspuid4 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 39 }

    -- 1.3.6.1.4.1.2011.2.25.4.10.41.5.1.1.40
    optixSdhLmspBid4 OBJECT-TYPE
        SYNTAX Unsigned32
        MAX-ACCESS read-create
        STATUS current
        DESCRIPTION
            "This object indicates the slot ID of the LMSP group. The value is determined by the line board."
        ::= { optixSdhLmspgEntry 40 }

    -- 1.3.6.1.4.1.2011.2.25.4.10.41.5.1.1.41
    optixSdhLmspSubid4 OBJECT-TYPE
        SYNTAX Unsigned32
        MAX-ACCESS read-create
        STATUS current
        DESCRIPTION
            "This object indicates the subboard ID of the LMSP group. The value is determined by the line board."
        ::= { optixSdhLmspgEntry 41 }

    -- 1.3.6.1.4.1.2011.2.25.4.10.41.5.1.1.42
    optixSdhLmspPortid4 OBJECT-TYPE
        SYNTAX Unsigned32
        MAX-ACCESS read-create
        STATUS current
        DESCRIPTION
            "This object indicates the port number of the LMSP group. The value is determined by the line board."
        ::= { optixSdhLmspgEntry 42 }

    -- 1.3.6.1.4.1.2011.2.25.4.10.41.5.1.1.43
    optixSdhLmspAu4Map4 OBJECT-TYPE
        SYNTAX OCTET STRING (SIZE(0..32))
        MAX-ACCESS read-create
        STATUS current
        DESCRIPTION
            "This object indicates the LMSP group Au4 mapping."
        ::= { optixSdhLmspgEntry 43 }

    -- 1.3.6.1.4.1.2011.2.25.4.10.41.5.1.1.44
    optixSdhLmspReqSite4 OBJECT-TYPE
        SYNTAX INTEGER
        {
            near(1),
            far(2)
        }
        MAX-ACCESS read-only
        STATUS current
        DESCRIPTION
            "This object indicates the LMSP remote/local end. 1: near, 2: far"
        ::= { optixSdhLmspgEntry 44 }

    -- 1.3.6.1.4.1.2011.2.25.4.10.41.5.1.1.45
    optixSdhLmspuid5 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 45 }

    -- 1.3.6.1.4.1.2011.2.25.4.10.41.5.1.1.46
    optixSdhLmspBid5 OBJECT-TYPE
        SYNTAX Unsigned32
        MAX-ACCESS read-create
        STATUS current
        DESCRIPTION
            "This object indicates the slot ID of the LMSP group. The value is determined by the line board."
        ::= { optixSdhLmspgEntry 46 }

    -- 1.3.6.1.4.1.2011.2.25.4.10.41.5.1.1.47
    optixSdhLmspSubid5 OBJECT-TYPE
        SYNTAX Unsigned32
        MAX-ACCESS read-create
        STATUS current
        DESCRIPTION
            "This object indicates the subboard ID of the LMSP group. The value is determined by the line board."
        ::= { optixSdhLmspgEntry 47 }

    -- 1.3.6.1.4.1.2011.2.25.4.10.41.5.1.1.48
    optixSdhLmspPortid5 OBJECT-TYPE
        SYNTAX Unsigned32
        MAX-ACCESS read-create
        STATUS current
        DESCRIPTION
            "This object indicates the port number of the LMSP group. The value is determined by the line board."
        ::= { optixSdhLmspgEntry 48 }

    -- 1.3.6.1.4.1.2011.2.25.4.10.41.5.1.1.49
    optixSdhLmspAu4Map5 OBJECT-TYPE
        SYNTAX OCTET STRING (SIZE(0..32))
        MAX-ACCESS read-create
        STATUS current
        DESCRIPTION
            "This object indicates the LMSP group Au4 mapping. The value is determined by the line board."
        ::= { optixSdhLmspgEntry 49 }

    -- 1.3.6.1.4.1.2011.2.25.4.10.41.5.1.1.50
    optixSdhLmspReqSite5 OBJECT-TYPE
        SYNTAX INTEGER
        {
            near(1),
            far(2)
        }
        MAX-ACCESS read-only
        STATUS current
        DESCRIPTION
            "This object indicates the LMSP remote/local end."
        ::= { optixSdhLmspgEntry 50 }

    -- 1.3.6.1.4.1.2011.2.25.4.10.41.5.1.1.51
    optixSdhLmspuid6 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 51 }

    -- 1.3.6.1.4.1.2011.2.25.4.10.41.5.1.1.52
    optixSdhLmspBid6 OBJECT-TYPE
        SYNTAX Unsigned32
        MAX-ACCESS read-create
        STATUS current
        DESCRIPTION
            "This object indicates the slot ID of the LMSP group. The value is determined by the line board."
        ::= { optixSdhLmspgEntry 52 }

    -- 1.3.6.1.4.1.2011.2.25.4.10.41.5.1.1.53
    optixSdhLmspSubid6 OBJECT-TYPE
        SYNTAX Unsigned32
        MAX-ACCESS read-create
        STATUS current
        DESCRIPTION
            "This object indicates the subboard ID of the LMSP group. The value is determined by the line board."
        ::= { optixSdhLmspgEntry 53 }

    -- 1.3.6.1.4.1.2011.2.25.4.10.41.5.1.1.54
    optixSdhLmspPortid6 OBJECT-TYPE
        SYNTAX Unsigned32
        MAX-ACCESS read-create
        STATUS current
        DESCRIPTION
            "This object indicates the port number of the LMSP group. The value is determined by the line board."
        ::= { optixSdhLmspgEntry 54 }

    -- 1.3.6.1.4.1.2011.2.25.4.10.41.5.1.1.55
    optixSdhLmspAu4Map6 OBJECT-TYPE
        SYNTAX OCTET STRING (SIZE(0..32))
        MAX-ACCESS read-create
        STATUS current
        DESCRIPTION
            "This object indicates the LMSP group Au4 mapping."
        ::= { optixSdhLmspgEntry 55 }

    -- 1.3.6.1.4.1.2011.2.25.4.10.41.5.1.1.56
    optixSdhLmspReqSite6 OBJECT-TYPE
        SYNTAX INTEGER
        {
            near(1),
            far(2)
        }
        MAX-ACCESS read-only
        STATUS current
        DESCRIPTION
            "This object indicates the LMSP remote/local end."
        ::= { optixSdhLmspgEntry 56 }

    -- 1.3.6.1.4.1.2011.2.25.4.10.41.5.1.1.57
    optixSdhLmspuid7 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 57 }

    -- 1.3.6.1.4.1.2011.2.25.4.10.41.5.1.1.58
    optixSdhLmspBid7 OBJECT-TYPE
        SYNTAX Unsigned32
        MAX-ACCESS read-create
        STATUS current
        DESCRIPTION
            "This object indicates the slot ID of the LMSP group. The value is determined by the line board."
        ::= { optixSdhLmspgEntry 58 }

    -- 1.3.6.1.4.1.2011.2.25.4.10.41.5.1.1.59
    optixSdhLmspSubid7 OBJECT-TYPE
        SYNTAX Unsigned32
        MAX-ACCESS read-create
        STATUS current
        DESCRIPTION
            "This object indicates the subboard ID of the LMSP group. The value is determined by the line board."
        ::= { optixSdhLmspgEntry 59 }

    -- 1.3.6.1.4.1.2011.2.25.4.10.41.5.1.1.60
    optixSdhLmspPortid7 OBJECT-TYPE
        SYNTAX Unsigned32
        MAX-ACCESS read-create
        STATUS current
        DESCRIPTION
            "This object indicates the port number of the LMSP group. The value is determined by the line board."
        ::= { optixSdhLmspgEntry 60 }

    -- 1.3.6.1.4.1.2011.2.25.4.10.41.5.1.1.61
    optixSdhLmspAu4Map7 OBJECT-TYPE
        SYNTAX OCTET STRING (SIZE(0..32))
        MAX-ACCESS read-create
        STATUS current
        DESCRIPTION
            "This object indicates the LMSP group Au4 mapping."
        ::= { optixSdhLmspgEntry 61 }

    -- 1.3.6.1.4.1.2011.2.25.4.10.41.5.1.1.62
    optixSdhLmspReqSite7 OBJECT-TYPE
        SYNTAX INTEGER
        {
            near(1),
            far(2)
        }
        MAX-ACCESS read-only
        STATUS current
        DESCRIPTION
            "This object indicates the LMSP remote/local end."
        ::= { optixSdhLmspgEntry 62 }

    -- 1.3.6.1.4.1.2011.2.25.4.10.41.5.1.1.63
    optixSdhLmspuid8 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 63 }

    -- 1.3.6.1.4.1.2011.2.25.4.10.41.5.1.1.64
    optixSdhLmspBid8 OBJECT-TYPE
        SYNTAX Unsigned32
        MAX-ACCESS read-create
        STATUS current
        DESCRIPTION
            "This object indicates the slot ID of the LMSP group. The value is determined by the line board."
        ::= { optixSdhLmspgEntry 64 }

    -- 1.3.6.1.4.1.2011.2.25.4.10.41.5.1.1.65
    optixSdhLmspSubid8 OBJECT-TYPE
        SYNTAX Unsigned32
        MAX-ACCESS read-create
        STATUS current
        DESCRIPTION
            "This object indicates the subboard ID of the LMSP group. The value is determined by the line board."
        ::= { optixSdhLmspgEntry 65 }

    -- 1.3.6.1.4.1.2011.2.25.4.10.41.5.1.1.66
    optixSdhLmspPortid8 OBJECT-TYPE
        SYNTAX Unsigned32
        MAX-ACCESS read-create
        STATUS current
        DESCRIPTION
            "This object indicates the port number of the LMSP group. The value is determined by the line board."
        ::= { optixSdhLmspgEntry 66 }

    -- 1.3.6.1.4.1.2011.2.25.4.10.41.5.1.1.67
    optixSdhLmspAu4Map8 OBJECT-TYPE
        SYNTAX OCTET STRING (SIZE(0..32))
        MAX-ACCESS read-create
        STATUS current
        DESCRIPTION
            "This object indicates the LMSP group Au4 mapping."
        ::= { optixSdhLmspgEntry 67 }

    -- 1.3.6.1.4.1.2011.2.25.4.10.41.5.1.1.68
    optixSdhLmspReqSite8 OBJECT-TYPE
        SYNTAX INTEGER
        {
            near(1),
            far(2)
        }
        MAX-ACCESS read-only
        STATUS current
        DESCRIPTION
            "This object indicates the LMSP remote/local end."
        ::= { optixSdhLmspgEntry 68 }

    -- 1.3.6.1.4.1.2011.2.25.4.10.41.5.1.1.69
    optixSdhLmspuid9 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 69 }

    -- 1.3.6.1.4.1.2011.2.25.4.10.41.5.1.1.70
    optixSdhLmspBid9 OBJECT-TYPE
        SYNTAX Unsigned32
        MAX-ACCESS read-create
        STATUS current
        DESCRIPTION
            "This object indicates the slot ID of the LMSP group. The value is determined by the line board."
        ::= { optixSdhLmspgEntry 70 }

    -- 1.3.6.1.4.1.2011.2.25.4.10.41.5.1.1.71
    optixSdhLmspSubid9 OBJECT-TYPE
        SYNTAX Unsigned32
        MAX-ACCESS read-create
        STATUS current
        DESCRIPTION
            "This object indicates the subboard ID of the LMSP group. The value is determined by the line board."
        ::= { optixSdhLmspgEntry 71 }

    -- 1.3.6.1.4.1.2011.2.25.4.10.41.5.1.1.72
    optixSdhLmspPortid9 OBJECT-TYPE
        SYNTAX Unsigned32
        MAX-ACCESS read-create
        STATUS current
        DESCRIPTION
            "This object indicates the port number of the LMSP group. The value is determined by the line board."
        ::= { optixSdhLmspgEntry 72 }

    -- 1.3.6.1.4.1.2011.2.25.4.10.41.5.1.1.73
    optixSdhLmspAu4Map9 OBJECT-TYPE
        SYNTAX OCTET STRING (SIZE(0..32))
        MAX-ACCESS read-create
        STATUS current
        DESCRIPTION
            "This object indicates the LMSP group Au4 mapping."
        ::= { optixSdhLmspgEntry 73 }

    -- 1.3.6.1.4.1.2011.2.25.4.10.41.5.1.1.74
    optixSdhLmspReqSite9 OBJECT-TYPE
        SYNTAX INTEGER
        {
            near(1),
            far(2)
        }
        MAX-ACCESS read-only
        STATUS current
        DESCRIPTION
            "This object indicates the LMSP remote/local end. 1: near, 2: far"
        ::= { optixSdhLmspgEntry 74 }

    -- 1.3.6.1.4.1.2011.2.25.4.10.41.5.1.1.75
    optixSdhLmspuid10 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 75 }

    -- 1.3.6.1.4.1.2011.2.25.4.10.41.5.1.1.76
    optixSdhLmspBid10 OBJECT-TYPE
        SYNTAX Unsigned32
        MAX-ACCESS read-create
        STATUS current
        DESCRIPTION
            "This object indicates the slot ID of the LMSP group. The value is determined by the line board."
        ::= { optixSdhLmspgEntry 76 }

    -- 1.3.6.1.4.1.2011.2.25.4.10.41.5.1.1.77
    optixSdhLmspSubid10 OBJECT-TYPE
        SYNTAX Unsigned32
        MAX-ACCESS read-create
        STATUS current
        DESCRIPTION
            "This object indicates the subboard ID of the LMSP group. The value is determined by the line board."
        ::= { optixSdhLmspgEntry 77 }

    -- 1.3.6.1.4.1.2011.2.25.4.10.41.5.1.1.78
    optixSdhLmspPortid10 OBJECT-TYPE
        SYNTAX Unsigned32
        MAX-ACCESS read-create
        STATUS current
        DESCRIPTION
            "This object indicates the port number of the LMSP group. The value is determined by the line board."
        ::= { optixSdhLmspgEntry 78 }

    -- 1.3.6.1.4.1.2011.2.25.4.10.41.5.1.1.79
    optixSdhLmspAu4Map10 OBJECT-TYPE
        SYNTAX OCTET STRING (SIZE(0..32))
        MAX-ACCESS read-create
        STATUS current
        DESCRIPTION
            "This object indicates the LMSP group Au4 mapping."
        ::= { optixSdhLmspgEntry 79 }

    -- 1.3.6.1.4.1.2011.2.25.4.10.41.5.1.1.80
    optixSdhLmspReqSite10 OBJECT-TYPE
        SYNTAX INTEGER
        {
            near(1),
            far(2)
        }
        MAX-ACCESS read-only
        STATUS current
        DESCRIPTION
            "This object indicates the LMSP remote/local end. 1: near, 2: far"
        ::= { optixSdhLmspgEntry 80 }

    -- 1.3.6.1.4.1.2011.2.25.4.10.41.5.1.1.81
    optixSdhLmspuid11 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 81 }

    -- 1.3.6.1.4.1.2011.2.25.4.10.41.5.1.1.82
    optixSdhLmspBid11 OBJECT-TYPE
        SYNTAX Unsigned32
        MAX-ACCESS read-create
        STATUS current
        DESCRIPTION
            "This object indicates the slot ID of the LMSP group. The value is determined by the line board."
        ::= { optixSdhLmspgEntry 82 }

    -- 1.3.6.1.4.1.2011.2.25.4.10.41.5.1.1.83
    optixSdhLmspSubid11 OBJECT-TYPE
        SYNTAX Unsigned32
        MAX-ACCESS read-create
        STATUS current
        DESCRIPTION
            "This object indicates the subboard ID of the LMSP group. The value is determined by the line board."
        ::= { optixSdhLmspgEntry 83 }

    -- 1.3.6.1.4.1.2011.2.25.4.10.41.5.1.1.84
    optixSdhLmspPortid11 OBJECT-TYPE
        SYNTAX Unsigned32
        MAX-ACCESS read-create
        STATUS current
        DESCRIPTION
            "This object indicates the port number of the LMSP group. The value is determined by the line board."
        ::= { optixSdhLmspgEntry 84 }

    -- 1.3.6.1.4.1.2011.2.25.4.10.41.5.1.1.85
    optixSdhLmspAu4Map11 OBJECT-TYPE
        SYNTAX OCTET STRING (SIZE(0..32))
        MAX-ACCESS read-create
        STATUS current
        DESCRIPTION
            "This object indicates the LMSP group Au4 mapping."
        ::= { optixSdhLmspgEntry 85 }

    -- 1.3.6.1.4.1.2011.2.25.4.10.41.5.1.1.86
    optixSdhLmspReqSite11 OBJECT-TYPE
        SYNTAX INTEGER
        {
            near(1),
            far(2)
        }
        MAX-ACCESS read-only
        STATUS current
        DESCRIPTION
            "This object indicates the LMSP remote/local end. 1: near, 2: far"
        ::= { optixSdhLmspgEntry 86 }

    -- 1.3.6.1.4.1.2011.2.25.4.10.41.5.1.1.87
    optixSdhLmspuid12 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 87 }

    -- 1.3.6.1.4.1.2011.2.25.4.10.41.5.1.1.88
    optixSdhLmspBid12 OBJECT-TYPE
        SYNTAX Unsigned32
        MAX-ACCESS read-create
        STATUS current
        DESCRIPTION
            "This object indicates the slot ID of the LMSP group. The value is determined by the line board."
        ::= { optixSdhLmspgEntry 88 }

    -- 1.3.6.1.4.1.2011.2.25.4.10.41.5.1.1.89
    optixSdhLmspSubid12 OBJECT-TYPE
        SYNTAX Unsigned32
        MAX-ACCESS read-create
        STATUS current
        DESCRIPTION
            "This object indicates the subboard ID of the LMSP group. The value is determined by the line board."
        ::= { optixSdhLmspgEntry 89 }

    -- 1.3.6.1.4.1.2011.2.25.4.10.41.5.1.1.90
    optixSdhLmspPortid12 OBJECT-TYPE
        SYNTAX Unsigned32
        MAX-ACCESS read-create
        STATUS current
        DESCRIPTION
            "This object indicates the port number of the LMSP group. The value is determined by the line board."
        ::= { optixSdhLmspgEntry 90 }

    -- 1.3.6.1.4.1.2011.2.25.4.10.41.5.1.1.91
    optixSdhLmspAu4Map12 OBJECT-TYPE
        SYNTAX OCTET STRING (SIZE(0..32))
        MAX-ACCESS read-create
        STATUS current
        DESCRIPTION
            "This object indicates the LMSP group Au4 mapping."
        ::= { optixSdhLmspgEntry 91 }

    -- 1.3.6.1.4.1.2011.2.25.4.10.41.5.1.1.92
    optixSdhLmspReqSite12 OBJECT-TYPE
        SYNTAX INTEGER
        {
            near(1),
            far(2)
        }
        MAX-ACCESS read-only
        STATUS current
        DESCRIPTION
            "This object indicates the LMSP remote/local end. 1: near, 2: far"
        ::= { optixSdhLmspgEntry 92 }

    -- 1.3.6.1.4.1.2011.2.25.4.10.41.5.1.1.93
    optixSdhLmspuid13 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 93 }

    -- 1.3.6.1.4.1.2011.2.25.4.10.41.5.1.1.94
    optixSdhLmspBid13 OBJECT-TYPE
        SYNTAX Unsigned32
        MAX-ACCESS read-create
        STATUS current
        DESCRIPTION
            "This object indicates the slot ID of the LMSP group. The value is determined by the line board."
        ::= { optixSdhLmspgEntry 94 }

    -- 1.3.6.1.4.1.2011.2.25.4.10.41.5.1.1.95
    optixSdhLmspSubid13 OBJECT-TYPE
        SYNTAX Unsigned32
        MAX-ACCESS read-create
        STATUS current
        DESCRIPTION
            "This object indicates the subboard ID of the LMSP group. The value is determined by the line board."
        ::= { optixSdhLmspgEntry 95 }

    -- 1.3.6.1.4.1.2011.2.25.4.10.41.5.1.1.96
    optixSdhLmspPortid13 OBJECT-TYPE
        SYNTAX Unsigned32
        MAX-ACCESS read-create
        STATUS current
        DESCRIPTION
            "This object indicates the port number of the LMSP group. The value is determined by the line board."
        ::= { optixSdhLmspgEntry 96 }

    -- 1.3.6.1.4.1.2011.2.25.4.10.41.5.1.1.97
    optixSdhLmspAu4Map13 OBJECT-TYPE
        SYNTAX OCTET STRING (SIZE(0..32))
        MAX-ACCESS read-create
        STATUS current
        DESCRIPTION
            "This object indicates the LMSP group Au4 mapping."
        ::= { optixSdhLmspgEntry 97 }

    -- 1.3.6.1.4.1.2011.2.25.4.10.41.5.1.1.98
    optixSdhLmspReqSite13 OBJECT-TYPE
        SYNTAX INTEGER
        {
            near(1),
            far(2)
        }
        MAX-ACCESS read-only
        STATUS current
        DESCRIPTION
            "This object indicates the LMSP remote/local end. 1: near, 2: far"
        ::= { optixSdhLmspgEntry 98 }

    -- 1.3.6.1.4.1.2011.2.25.4.10.41.5.1.1.99
    optixSdhLmspuid14 OBJECT-TYPE
        SYNTAX Unsigned32
        MAX-ACCESS read-create
        STATUS current
        DESCRIPTION
            "This object indicates the LMSP protection unit ID. Value range for RTN 980: 0 to 7. Value range for RTN 950: 0 to 4."
        ::= { optixSdhLmspgEntry 99 }

    -- 1.3.6.1.4.1.2011.2.25.4.10.41.5.1.1.100
    optixSdhLmspBid14 OBJECT-TYPE
        SYNTAX Unsigned32
        MAX-ACCESS read-create
        STATUS current
        DESCRIPTION
            "This object indicates the slot ID of the LMSP group. The value is determined by the line board."
        ::= { optixSdhLmspgEntry 100 }

    -- 1.3.6.1.4.1.2011.2.25.4.10.41.5.1.1.101
    optixSdhLmspSubid14 OBJECT-TYPE
        SYNTAX Unsigned32
        MAX-ACCESS read-create
        STATUS current
        DESCRIPTION
            "This object indicates the subboard ID of the LMSP group. The value is determined by the line board."
        ::= { optixSdhLmspgEntry 101 }

    -- 1.3.6.1.4.1.2011.2.25.4.10.41.5.1.1.102
    optixSdhLmspPortid14 OBJECT-TYPE
        SYNTAX Unsigned32
        MAX-ACCESS read-create
        STATUS current
        DESCRIPTION
            "This object indicates the port number of the LMSP group. The value is determined by the line board."
        ::= { optixSdhLmspgEntry 102 }

    -- 1.3.6.1.4.1.2011.2.25.4.10.41.5.1.1.103
    optixSdhLmspAu4Map14 OBJECT-TYPE
        SYNTAX OCTET STRING (SIZE(0..32))
        MAX-ACCESS read-create
        STATUS current
        DESCRIPTION
            "This object indicates the LMSP group Au4 mapping."
        ::= { optixSdhLmspgEntry 103 }

    -- 1.3.6.1.4.1.2011.2.25.4.10.41.5.1.1.104
    optixSdhLmspReqSite14 OBJECT-TYPE
        SYNTAX INTEGER
        {
            near(1),
            far(2)
        }
        MAX-ACCESS read-only
        STATUS current
        DESCRIPTION
            "This object indicates the LMSP remote/local end. 1: near, 2: far"
        ::= { optixSdhLmspgEntry 104 }

    -- 1.3.6.1.4.1.2011.2.25.4.10.41.5.1.1.105
    optixSdhLmspStartFlag OBJECT-TYPE
        SYNTAX INTEGER
        {
            protocolStop(0),
            protocolStart(1)
        }
        MAX-ACCESS read-create
        STATUS current
        DESCRIPTION
            "This object indicates the start flag of the LMSP group. 0: protocolStop, 1: protocolStart"
        ::= { optixSdhLmspgEntry 105 }

    -- 1.3.6.1.4.1.2011.2.25.4.10.41.5.1.1.255
    optixSdhLmspgRowStatus OBJECT-TYPE
        SYNTAX RowStatus
        MAX-ACCESS read-create
        STATUS current
        DESCRIPTION
            "This object indicates the row status of the LMSP group."
        ::= { optixSdhLmspgEntry 255 }

    -- 1.3.6.1.4.1.2011.2.25.4.10.41.5.2
    optixSdhLmspuTable OBJECT-TYPE
        SYNTAX SEQUENCE OF OptixSdhLmspuEntry
        MAX-ACCESS not-accessible
        STATUS current
        DESCRIPTION
            "This table describes the configurations of LMSP protocol units."
        ::= { optixSdhLmspGroup 2 }

    -- 1.3.6.1.4.1.2011.2.25.4.10.41.5.2.1
    optixSdhLmspuEntry OBJECT-TYPE
        SYNTAX OptixSdhLmspuEntry
        MAX-ACCESS not-accessible
        STATUS current
        DESCRIPTION
            "This entry describes the configurations of LMSP units"
        INDEX{ optixSdhLmspgid,optixSdhLmspuid }
        ::= { optixSdhLmspuTable 1 }

    OptixSdhLmspuEntry ::=
        SEQUENCE {
            optixSdhLmspuid
                Unsigned32,
            optixSdhLmspuExtSwitchCmd
                INTEGER,
            optixSdhLmspuSwitchRequest
                INTEGER,
            optixSdhLmspuSwitchState
                INTEGER
        }

    -- 1.3.6.1.4.1.2011.2.25.4.10.41.5.2.1.1
    optixSdhLmspuid OBJECT-TYPE
        SYNTAX Unsigned32
        MAX-ACCESS not-accessible
        STATUS current
        DESCRIPTION
            "This object indicates the ID of LMSP unit"
        ::= { optixSdhLmspuEntry 1 }

    -- 1.3.6.1.4.1.2011.2.25.4.10.41.5.2.1.2
    optixSdhLmspuExtSwitchCmd OBJECT-TYPE
        SYNTAX INTEGER
        {
            lmsInvalid(0),
            lmsExer(4),
            lmsLockwork(5),
            lmsMan(8),
            lmsForce(14),
            lmsLock(15),
            lmsClearall(16),
            lmsExerclr(20),
            lmsUnlockwork(21),
            lmsClearwtr(22),
            lmsManclr(24),
            lmsForceclr(30),
            lmsUnlock(31)
        }
        MAX-ACCESS read-write
        STATUS current
        DESCRIPTION
            "This object indicates the external switching cmd of protocol unit ID. 15: lmsLock, 31: lmsUnlock, 14: lmsForce, 30: lmsForceclr, 8: lmsMan, 24: lmsManclr, 4: lmsExer, 20: lmsExerclr, 16: lmsClearall, 22: lmsClearwtr, 5: lmsLockwork, 21: lmsUnlockwork, 0: lmsInvalid"
        ::= { optixSdhLmspuEntry 2 }

    -- 1.3.6.1.4.1.2011.2.25.4.10.41.5.2.1.3
    optixSdhLmspuSwitchRequest OBJECT-TYPE
        SYNTAX INTEGER
        {
            lpsNr(0),
            lpsDnr(16),
            lpsExer(64),
            lpsWtr(96),
            lpsMs(128),
            lpsSdLow(160),
            lpsSd(176),
            lpsSfLow(192),
            lpsSf(208),
            lpsFs(224),
            lpsLp(240)
        }
        MAX-ACCESS read-only
        STATUS current
        DESCRIPTION
            "This object indicates the switching request of protocol unit ID. 0: lpsNr, 16: lpsDnr, 64: lpsExer, 96: lpsWtr, 128: lpsMs, 160: lpsSdLow, 176: lpsSd, 192: lpsSfLow, 208: lpsSf, 224: lpsFs, 240: lpsLp"
        ::= { optixSdhLmspuEntry 3 }

    -- 1.3.6.1.4.1.2011.2.25.4.10.41.5.2.1.4
    optixSdhLmspuSwitchState OBJECT-TYPE
        SYNTAX INTEGER
        {
            stop(0),
            i(1),
            s(4),
            starting(255)
        }
        MAX-ACCESS read-only
        STATUS current
        DESCRIPTION
            "This object indicates the LMSP switching status of protocol unit ID. 0: stop(0), 1: i, 4: s, 255: starting"
        ::= { optixSdhLmspuEntry 4 }

    -- 1.3.6.1.4.1.2011.2.25.4.10.41.5.5
    optixSdhLmspSWITCHEventMember OBJECT IDENTIFIER ::= { optixSdhLmspGroup 5 }

    -- 1.3.6.1.4.1.2011.2.25.4.10.41.5.5.1
    optixSdhLmspgidevt OBJECT-TYPE
        SYNTAX Unsigned32
        MAX-ACCESS accessible-for-notify
        STATUS current
        DESCRIPTION
            "This parameter specifies LMSP id"
        ::= { optixSdhLmspSWITCHEventMember 1 }

    -- 1.3.6.1.4.1.2011.2.25.4.10.41.5.5.2
    optixSdhLmspuidevt OBJECT-TYPE
        SYNTAX Unsigned32
        MAX-ACCESS accessible-for-notify
        STATUS current
        DESCRIPTION
            "This parameter specifies LMSP unit id"
        ::= { optixSdhLmspSWITCHEventMember 2 }

    -- 1.3.6.1.4.1.2011.2.25.4.10.41.5.5.3
    optixSdhLmspSwitchReqevt OBJECT-TYPE
        SYNTAX INTEGER
        {
            lpsNr(0),
            lpsDnr(16),
            lpsExer(64),
            lpsWtr(96),
            lpsMs(128),
            lpsSdLow(160),
            lpsSd(176),
            lpsSfLow(192),
            lpsSf(208),
            lpsFs(224),
            lpsLp(240)
        }
        MAX-ACCESS accessible-for-notify
        STATUS current
        DESCRIPTION
            "This parameter specifies LMSP switch request"
        ::= { optixSdhLmspSWITCHEventMember 3 }

    -- 1.3.6.1.4.1.2011.2.25.4.10.41.5.5.4
    optixSdhLmspSwitchStaevt OBJECT-TYPE
        SYNTAX INTEGER
        {
            stop(0),
            i(1),
            s(4),
            starting(255)
        }
        MAX-ACCESS accessible-for-notify
        STATUS current
        DESCRIPTION
            "This parameter specifies LMSP switch state"
        ::= { optixSdhLmspSWITCHEventMember 4 }

    -- 1.3.6.1.4.1.2011.2.25.4.10.41.5.5.5
    optixSdhLmspSwitchCmd OBJECT-TYPE
        SYNTAX INTEGER
        {
            lmsLock(15),
            lmsUnlock(31),
            lmsForce(14),
            lmsForceClr(30),
            lmsMan(8),
            lmsManClr(24),
            lmsExer(4),
            lmsExerClr(20),
            lmsClearAll(16),
            lmsClearWtr(22)
        }
        MAX-ACCESS accessible-for-notify
        STATUS current
        DESCRIPTION
            "This parameter indicates the LMSP protection  switch command."
        ::= { optixSdhLmspSWITCHEventMember 5 }

    -- 1.3.6.1.4.1.2011.2.25.4.10.41.5.5.6
    optixSdhLmspProtPuId OBJECT-TYPE
        SYNTAX Integer32
        MAX-ACCESS accessible-for-notify
        STATUS current
        DESCRIPTION
            "This parameter indicates the unit protected by LMSP."
        ::= { optixSdhLmspSWITCHEventMember 6 }

    -- 1.3.6.1.4.1.2011.2.25.4.10.41.5.5.7
    optixSdhLmspLrIndi OBJECT-TYPE
        SYNTAX INTEGER
        {
            na(0),
            local(1),
            remote(2)
        }
        MAX-ACCESS accessible-for-notify
        STATUS current
        DESCRIPTION
            "This parameter indicates the indication of LMSP remote-end or local-end."
        ::= { optixSdhLmspSWITCHEventMember 7 }

    -- 1.3.6.1.4.1.2011.2.25.4.10.41.5.5.8
    optixSdhLmspSwitchReason OBJECT-TYPE
        SYNTAX INTEGER
        {
            localReq(1),
            extReq(2),
            kReq(3),
            expireOfTimer(4)
        }
        MAX-ACCESS accessible-for-notify
        STATUS current
        DESCRIPTION
            "This parameter indicates the reason for LMSP switch."
        ::= { optixSdhLmspSWITCHEventMember 8 }

    -- 1.3.6.1.4.1.2011.2.25.4.10.41.5.6
    optixSdhLmspSWITCHEvent OBJECT IDENTIFIER ::= { optixSdhLmspGroup 6 }

    -- 1.3.6.1.4.1.2011.2.25.4.10.41.5.6.1
    optixSdhLmspSWITCH NOTIFICATION-TYPE
        OBJECTS{ optixSdhLmspgidevt,optixSdhLmspuidevt,optixSdhLmspSwitchReqevt,optixSdhLmspSwitchStaevt }
        STATUS current
        DESCRIPTION
            "This parameter specifies LMSP switch Event info"
        ::= { optixSdhLmspSWITCHEvent 1 }

    -- 1.3.6.1.4.1.2011.2.25.4.10.41.5.6.2
    optixSdhLmspSWITCHCmdUnexe NOTIFICATION-TYPE
        OBJECTS{ optixSdhLmspgidevt,optixSdhLmspSwitchCmd,optixSdhLmspuidevt }
        STATUS current
        DESCRIPTION
            "This patameter indicates no response of the LMSP remote end"
        ::= { optixSdhLmspSWITCHEvent 2 }

    -- 1.3.6.1.4.1.2011.2.25.4.10.41.5.6.3
    optixSdhLmspSwitchStateEvent NOTIFICATION-TYPE
        OBJECTS{ optixSdhLmspgidevt,optixSdhLmspuidevt,optixSdhLmspSwitchReqevt,optixSdhLmspSwitchStaevt,optixSdhLmspProtPuId,optixSdhLmspLrIndi,optixSdhLmspSwitchReason }
        STATUS current
        DESCRIPTION
            "This parameter indicates LMSP switch state event."
        ::= { optixSdhLmspSWITCHEvent 3 }

END
