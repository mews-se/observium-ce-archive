-- OPTIX-PKT-QOS-POINT-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-QOS-POINT-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        ;

    optixPktQosPoint MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the QOS service configuration information of device"
        REVISION "201204200000Z"
        DESCRIPTION
            "The initial revision of this MIB module1."
        ::={ optixProvisionPtn 31 }

    -- 1.3.6.1.4.1.2011.2.25.4.50.31.1
    optixPktQosPointGroup OBJECT IDENTIFIER ::= { optixPktQosPoint 1 }

    -- 1.3.6.1.4.1.2011.2.25.4.50.31.1.1
    optixQosPwTable OBJECT-TYPE
        SYNTAX SEQUENCE OF OptixQosPwEntry
        MAX-ACCESS not-accessible
        STATUS current
        DESCRIPTION
            "This table describes the basic QoS PW configurations."
        ::= { optixPktQosPointGroup 1 }

    -- 1.3.6.1.4.1.2011.2.25.4.50.31.1.1.1
    optixQosPwEntry OBJECT-TYPE
        SYNTAX OptixQosPwEntry
        MAX-ACCESS not-accessible
        STATUS current
        DESCRIPTION
            "This entry describes the basic QoS PW configurations."
        INDEX{ optixQosPwIndex,optixQosPwDirection }
        ::= { optixQosPwTable 1 }

    OptixQosPwEntry ::=
        SEQUENCE {
            optixQosPwIndex
                Unsigned32,
            optixQosPwDirection
                INTEGER,
            optixQosPwLspMode
                INTEGER,
            optixQosPwExp
                INTEGER,
            optixQosPwConfigCir
                Unsigned32,
            optixQosPwCbs
                Unsigned32,
            optixQosPwConfigPir
                Unsigned32,
            optixQosPwPbs
                Unsigned32,
            optixQosPwPolicyId
                Unsigned32,
            optixQosPwActualCIR
                Unsigned32,
            optixQosPwActualPIR
                Unsigned32,
            optixQosPwRowStatus
                RowStatus
        }

    -- 1.3.6.1.4.1.2011.2.25.4.50.31.1.1.1.1
    optixQosPwIndex OBJECT-TYPE
        SYNTAX Unsigned32
        MAX-ACCESS not-accessible
        STATUS current
        DESCRIPTION
            "This object indicates the PW index of the QoS module."
        ::= { optixQosPwEntry 1 }

    -- 1.3.6.1.4.1.2011.2.25.4.50.31.1.1.1.2
    optixQosPwDirection OBJECT-TYPE
        SYNTAX INTEGER
        {
            all(0),
            ingress(1),
            egress(2),
            none(255)
        }
        MAX-ACCESS not-accessible
        STATUS current
        DESCRIPTION
            "This object indicates the PWdirection of the QoS module."
        ::= { optixQosPwEntry 2 }

    -- 1.3.6.1.4.1.2011.2.25.4.50.31.1.1.1.3
    optixQosPwLspMode OBJECT-TYPE
        SYNTAX INTEGER
        {
            pipe(2),
            none(255)
        }
        MAX-ACCESS read-only
        STATUS current
        DESCRIPTION
            "This object indicates the PWLPS mode of the QoS module."
        ::= { optixQosPwEntry 3 }

    -- 1.3.6.1.4.1.2011.2.25.4.50.31.1.1.1.4
    optixQosPwExp OBJECT-TYPE
        SYNTAX INTEGER
        {
            none(255)
        }
        MAX-ACCESS read-only
        STATUS current
        DESCRIPTION
            "This object indicates the PWEXP value of the QoS module."
        ::= { optixQosPwEntry 4 }

    -- 1.3.6.1.4.1.2011.2.25.4.50.31.1.1.1.5
    optixQosPwConfigCir OBJECT-TYPE
        SYNTAX Unsigned32
        MAX-ACCESS read-create
        STATUS current
        DESCRIPTION
            "This object indicates the configured PW CIR of the QoS module."
        ::= { optixQosPwEntry 5 }

    -- 1.3.6.1.4.1.2011.2.25.4.50.31.1.1.1.6
    optixQosPwCbs OBJECT-TYPE
        SYNTAX Unsigned32
        MAX-ACCESS read-create
        STATUS current
        DESCRIPTION
            "This object indicates the PW CBS of the QoS module."
        ::= { optixQosPwEntry 6 }

    -- 1.3.6.1.4.1.2011.2.25.4.50.31.1.1.1.7
    optixQosPwConfigPir OBJECT-TYPE
        SYNTAX Unsigned32
        MAX-ACCESS read-create
        STATUS current
        DESCRIPTION
            "This object indicates the configured PW PIR of the QoS module."
        ::= { optixQosPwEntry 7 }

    -- 1.3.6.1.4.1.2011.2.25.4.50.31.1.1.1.8
    optixQosPwPbs OBJECT-TYPE
        SYNTAX Unsigned32
        MAX-ACCESS read-create
        STATUS current
        DESCRIPTION
            "This object indicates the PW PBS of the QoS module."
        ::= { optixQosPwEntry 8 }

    -- 1.3.6.1.4.1.2011.2.25.4.50.31.1.1.1.9
    optixQosPwPolicyId OBJECT-TYPE
        SYNTAX Unsigned32
        MAX-ACCESS read-create
        STATUS current
        DESCRIPTION
            "This object indicates the PW application policy ID of the QoS module."
        ::= { optixQosPwEntry 9 }

    -- 1.3.6.1.4.1.2011.2.25.4.50.31.1.1.1.10
    optixQosPwActualCIR OBJECT-TYPE
        SYNTAX Unsigned32
        MAX-ACCESS read-only
        STATUS current
        DESCRIPTION
            "This object indicates the PW actual CIR of the QoS module."
        ::= { optixQosPwEntry 10 }

    -- 1.3.6.1.4.1.2011.2.25.4.50.31.1.1.1.11
    optixQosPwActualPIR OBJECT-TYPE
        SYNTAX Unsigned32
        MAX-ACCESS read-only
        STATUS current
        DESCRIPTION
            "This object indicates the PW actual PIR of the QoS module."
        ::= { optixQosPwEntry 11 }

    -- 1.3.6.1.4.1.2011.2.25.4.50.31.1.1.1.255
    optixQosPwRowStatus OBJECT-TYPE
        SYNTAX RowStatus
        MAX-ACCESS read-create
        STATUS current
        DESCRIPTION
            "This object indicates thePW row status of the QoS module."
        ::= { optixQosPwEntry 255 }

    -- 1.3.6.1.4.1.2011.2.25.4.50.31.1.2
    optixQosPortTable OBJECT-TYPE
        SYNTAX SEQUENCE OF OptixQosPortEntry
        MAX-ACCESS not-accessible
        STATUS current
        DESCRIPTION
            "This table describes the QoS information of the port."
        ::= { optixPktQosPointGroup 2 }

    -- 1.3.6.1.4.1.2011.2.25.4.50.31.1.2.1
    optixQosPortEntry OBJECT-TYPE
        SYNTAX OptixQosPortEntry
        MAX-ACCESS not-accessible
        STATUS current
        DESCRIPTION
            "This entry describes the QoS information of the port."
        INDEX{ optixQosPortBoardId,optixQosPortSubcardId,optixQosPortPortId }
        ::= { optixQosPortTable 1 }

    OptixQosPortEntry ::=
        SEQUENCE {
            optixQosPortBoardId
                Unsigned32,
            optixQosPortSubcardId
                Unsigned32,
            optixQosPortPortId
                Unsigned32,
            optixQosPortPolicyId
                Unsigned32
        }

    -- 1.3.6.1.4.1.2011.2.25.4.50.31.1.2.1.1
    optixQosPortBoardId OBJECT-TYPE
        SYNTAX Unsigned32
        MAX-ACCESS not-accessible
        STATUS current
        DESCRIPTION
            "This object indicates the slot ID of the QoS module."
        ::= { optixQosPortEntry 1 }

    -- 1.3.6.1.4.1.2011.2.25.4.50.31.1.2.1.2
    optixQosPortSubcardId OBJECT-TYPE
        SYNTAX Unsigned32
        MAX-ACCESS not-accessible
        STATUS current
        DESCRIPTION
            "This object indicates the suboard ID of the QoS module."
        ::= { optixQosPortEntry 2 }

    -- 1.3.6.1.4.1.2011.2.25.4.50.31.1.2.1.3
    optixQosPortPortId OBJECT-TYPE
        SYNTAX Unsigned32
        MAX-ACCESS not-accessible
        STATUS current
        DESCRIPTION
            "This object indicates the port number of the QoS module."
        ::= { optixQosPortEntry 3 }

    -- 1.3.6.1.4.1.2011.2.25.4.50.31.1.2.1.4
    optixQosPortPolicyId OBJECT-TYPE
        SYNTAX Unsigned32
        MAX-ACCESS read-write
        STATUS current
        DESCRIPTION
            "This object indicates the policy ID of the QoS module."
        ::= { optixQosPortEntry 4 }

    -- 1.3.6.1.4.1.2011.2.25.4.50.31.1.3
    optixQosPortQosTable OBJECT-TYPE
        SYNTAX SEQUENCE OF OptixQosPortQosEntry
        MAX-ACCESS not-accessible
        STATUS current
        DESCRIPTION
            "This table describes the basic QoS port schedualing configurations."
        ::= { optixPktQosPointGroup 3 }

    -- 1.3.6.1.4.1.2011.2.25.4.50.31.1.3.1
    optixQosPortQosEntry OBJECT-TYPE
        SYNTAX OptixQosPortQosEntry
        MAX-ACCESS not-accessible
        STATUS current
        DESCRIPTION
            "This entry describes the basic QoS port schedualing configurations."
        INDEX{ optixQosPortBoardId,optixQosPortSubcardId,optixQosPortPortId,optixQosPortQosDir }
        ::= { optixQosPortQosTable 1 }

    OptixQosPortQosEntry ::=
        SEQUENCE {
            optixQosPortQosDir
                INTEGER,
            optixQosPortQosCir
                Unsigned32,
            optixQosPortQosCbs
                Unsigned32,
            optixQosPortQostPir
                Unsigned32,
            optixQosPortQosPbs
                Unsigned32,
            optixQosPortQosPolicyId
                Unsigned32,
            optixQosPortQosRowStatus
                RowStatus
        }

    -- 1.3.6.1.4.1.2011.2.25.4.50.31.1.3.1.1
    optixQosPortQosDir OBJECT-TYPE
        SYNTAX INTEGER
        {
            all(0),
            ingress(1),
            egress(2),
            none(255)
        }
        MAX-ACCESS not-accessible
        STATUS current
        DESCRIPTION
            "This object indicates the Qos port schedualing direction of the QoS module."
        ::= { optixQosPortQosEntry 1 }

    -- 1.3.6.1.4.1.2011.2.25.4.50.31.1.3.1.2
    optixQosPortQosCir OBJECT-TYPE
        SYNTAX Unsigned32
        MAX-ACCESS read-create
        STATUS current
        DESCRIPTION
            "This object indicates the QoS port scheduling CIR of the QoS module."
        ::= { optixQosPortQosEntry 2 }

    -- 1.3.6.1.4.1.2011.2.25.4.50.31.1.3.1.3
    optixQosPortQosCbs OBJECT-TYPE
        SYNTAX Unsigned32
        MAX-ACCESS read-create
        STATUS current
        DESCRIPTION
            "This object indicates the QoS port scheduling CBS of the QoS module."
        ::= { optixQosPortQosEntry 3 }

    -- 1.3.6.1.4.1.2011.2.25.4.50.31.1.3.1.4
    optixQosPortQostPir OBJECT-TYPE
        SYNTAX Unsigned32
        MAX-ACCESS read-create
        STATUS current
        DESCRIPTION
            "This object indicates the QoS port scheduling PIR of the QoS module."
        ::= { optixQosPortQosEntry 4 }

    -- 1.3.6.1.4.1.2011.2.25.4.50.31.1.3.1.5
    optixQosPortQosPbs OBJECT-TYPE
        SYNTAX Unsigned32
        MAX-ACCESS read-create
        STATUS current
        DESCRIPTION
            "This object indicates the QoS port scheduling PBS of the QoS module."
        ::= { optixQosPortQosEntry 5 }

    -- 1.3.6.1.4.1.2011.2.25.4.50.31.1.3.1.6
    optixQosPortQosPolicyId OBJECT-TYPE
        SYNTAX Unsigned32
        MAX-ACCESS read-only
        STATUS current
        DESCRIPTION
            "This object indicates the QoS port scheduling policy ID of the QoS module."
        ::= { optixQosPortQosEntry 6 }

    -- 1.3.6.1.4.1.2011.2.25.4.50.31.1.3.1.255
    optixQosPortQosRowStatus OBJECT-TYPE
        SYNTAX RowStatus
        MAX-ACCESS read-create
        STATUS current
        DESCRIPTION
            "This object indicates the Qos port row status."
        ::= { optixQosPortQosEntry 255 }

    -- 1.3.6.1.4.1.2011.2.25.4.50.31.1.4
    optixQosVuniPointTable OBJECT-TYPE
        SYNTAX SEQUENCE OF OptixQosVuniPointEntry
        MAX-ACCESS not-accessible
        STATUS current
        DESCRIPTION
            "This table describes the basic QoS V-uni information schedualing configurations."
        ::= { optixPktQosPointGroup 4 }

    -- 1.3.6.1.4.1.2011.2.25.4.50.31.1.4.1
    optixQosVuniPointEntry OBJECT-TYPE
        SYNTAX OptixQosVuniPointEntry
        MAX-ACCESS not-accessible
        STATUS current
        DESCRIPTION
            "This entry describes the basic QoS V-uni information schedualing configurations."
        INDEX{ optixQosVuniPointServiceID,optixQosVuniPointVuniID,optixQosVuniPointDir }
        ::= { optixQosVuniPointTable 1 }

    OptixQosVuniPointEntry ::=
        SEQUENCE {
            optixQosVuniPointServiceID
                Unsigned32,
            optixQosVuniPointVuniID
                Unsigned32,
            optixQosVuniPointDir
                INTEGER,
            optixQosVuniPointDefaultCOS
                INTEGER,
            optixQosVuniPointDefaultColor
                INTEGER,
            optixQosVuniPointConfigCIR
                Unsigned32,
            optixQosVuniPointCBS
                Unsigned32,
            optixQosVuniPointConfigPIR
                Unsigned32,
            optixQosVuniPointPBS
                Unsigned32,
            optixQosVuniPointPolicyID
                Unsigned32,
            optixQosVuniPointActualCIR
                Unsigned32,
            optixQosVuniPointActualPIR
                Unsigned32,
            optixQosVuniPointRowStatus
                RowStatus
        }

    -- 1.3.6.1.4.1.2011.2.25.4.50.31.1.4.1.1
    optixQosVuniPointServiceID OBJECT-TYPE
        SYNTAX Unsigned32
        MAX-ACCESS not-accessible
        STATUS current
        DESCRIPTION
            "This object indicates the Qos V-uni of the service ID module."
        ::= { optixQosVuniPointEntry 1 }

    -- 1.3.6.1.4.1.2011.2.25.4.50.31.1.4.1.2
    optixQosVuniPointVuniID OBJECT-TYPE
        SYNTAX Unsigned32
        MAX-ACCESS not-accessible
        STATUS current
        DESCRIPTION
            "This object indicates the Qos V-uni of the V-uni ID module."
        ::= { optixQosVuniPointEntry 2 }

    -- 1.3.6.1.4.1.2011.2.25.4.50.31.1.4.1.3
    optixQosVuniPointDir OBJECT-TYPE
        SYNTAX INTEGER
        {
            ingress(1),
            egress(2),
            none(255),
            all(0)
        }
        MAX-ACCESS not-accessible
        STATUS current
        DESCRIPTION
            "This object indicates the QoS V-uni of the direction module."
        ::= { optixQosVuniPointEntry 3 }

    -- 1.3.6.1.4.1.2011.2.25.4.50.31.1.4.1.4
    optixQosVuniPointDefaultCOS OBJECT-TYPE
        SYNTAX INTEGER
        {
            all(0),
            cs7(1),
            cs6(2),
            ef(3),
            af4(4),
            af3(5),
            af2(6),
            af1(7),
            be(8),
            none(255)
        }
        MAX-ACCESS read-only
        STATUS current
        DESCRIPTION
            "This object indicates the QoS V-uni of the default CoS module."
        ::= { optixQosVuniPointEntry 4 }

    -- 1.3.6.1.4.1.2011.2.25.4.50.31.1.4.1.5
    optixQosVuniPointDefaultColor OBJECT-TYPE
        SYNTAX INTEGER
        {
            red(1),
            yellow(2),
            green(3),
            none(255)
        }
        MAX-ACCESS read-only
        STATUS current
        DESCRIPTION
            "This object indicates the Qos V-uni of the default color module."
        ::= { optixQosVuniPointEntry 5 }

    -- 1.3.6.1.4.1.2011.2.25.4.50.31.1.4.1.6
    optixQosVuniPointConfigCIR OBJECT-TYPE
        SYNTAX Unsigned32
        MAX-ACCESS read-create
        STATUS current
        DESCRIPTION
            "This object indicates the Qos V-uni of the config CIR module."
        ::= { optixQosVuniPointEntry 6 }

    -- 1.3.6.1.4.1.2011.2.25.4.50.31.1.4.1.7
    optixQosVuniPointCBS OBJECT-TYPE
        SYNTAX Unsigned32
        MAX-ACCESS read-create
        STATUS current
        DESCRIPTION
            "This object indicates the Qos V-uni of the CBS module."
        ::= { optixQosVuniPointEntry 7 }

    -- 1.3.6.1.4.1.2011.2.25.4.50.31.1.4.1.8
    optixQosVuniPointConfigPIR OBJECT-TYPE
        SYNTAX Unsigned32
        MAX-ACCESS read-create
        STATUS current
        DESCRIPTION
            "This object indicates the Qos V-uni of the config PIR module."
        ::= { optixQosVuniPointEntry 8 }

    -- 1.3.6.1.4.1.2011.2.25.4.50.31.1.4.1.9
    optixQosVuniPointPBS OBJECT-TYPE
        SYNTAX Unsigned32
        MAX-ACCESS read-create
        STATUS current
        DESCRIPTION
            "This object indicates the Qos V-uni of the PBS module."
        ::= { optixQosVuniPointEntry 9 }

    -- 1.3.6.1.4.1.2011.2.25.4.50.31.1.4.1.10
    optixQosVuniPointPolicyID OBJECT-TYPE
        SYNTAX Unsigned32
        MAX-ACCESS read-create
        STATUS current
        DESCRIPTION
            "This object indicates the Qos V-uni of the policy ID module."
        ::= { optixQosVuniPointEntry 10 }

    -- 1.3.6.1.4.1.2011.2.25.4.50.31.1.4.1.11
    optixQosVuniPointActualCIR OBJECT-TYPE
        SYNTAX Unsigned32
        MAX-ACCESS read-only
        STATUS current
        DESCRIPTION
            "This object indicates the Qos V-uni of the Actual CIR module."
        ::= { optixQosVuniPointEntry 11 }

    -- 1.3.6.1.4.1.2011.2.25.4.50.31.1.4.1.12
    optixQosVuniPointActualPIR OBJECT-TYPE
        SYNTAX Unsigned32
        MAX-ACCESS read-only
        STATUS current
        DESCRIPTION
            "This object indicates the Qos V-uni of the Actual PIR module."
        ::= { optixQosVuniPointEntry 12 }

    -- 1.3.6.1.4.1.2011.2.25.4.50.31.1.4.1.255
    optixQosVuniPointRowStatus OBJECT-TYPE
        SYNTAX RowStatus
        MAX-ACCESS read-create
        STATUS current
        DESCRIPTION
            "This object indicates the basic QoS V-uni information row status."
        ::= { optixQosVuniPointEntry 255 }

    -- 1.3.6.1.4.1.2011.2.25.4.50.31.1.5
    optixQosSpecTable OBJECT-TYPE
        SYNTAX SEQUENCE OF OptixQosSpecEntry
        MAX-ACCESS not-accessible
        STATUS current
        DESCRIPTION
            "This table contains QoS module specifications."
        ::= { optixPktQosPointGroup 5 }

    -- 1.3.6.1.4.1.2011.2.25.4.50.31.1.5.1
    optixQosSpecEntry OBJECT-TYPE
        SYNTAX OptixQosSpecEntry
        MAX-ACCESS not-accessible
        STATUS current
        DESCRIPTION
            "This entry contains QoS module specifications."
        INDEX{ optixQosSpecAttrID,optixQosSpecIndex1,optixQosSpecIndex2,optixQosSpecIndex3 }
        ::= { optixQosSpecTable 1 }

    OptixQosSpecEntry ::=
        SEQUENCE {
            optixQosSpecAttrID
                Unsigned32,
            optixQosSpecIndex1
                Unsigned32,
            optixQosSpecIndex2
                Unsigned32,
            optixQosSpecIndex3
                Unsigned32,
            optixQosSpecDefault
                Unsigned32,
            optixQosSpecMin
                Unsigned32,
            optixQosSpecMax
                Unsigned32
        }

    -- 1.3.6.1.4.1.2011.2.25.4.50.31.1.5.1.1
    optixQosSpecAttrID OBJECT-TYPE
        SYNTAX Unsigned32
        MAX-ACCESS not-accessible
        STATUS current
        DESCRIPTION
            "This parameter is used to describe the attribute ID of the QoS module. 1: WRED queue length; 2: tail drop threshold"
        ::= { optixQosSpecEntry 1 }

    -- 1.3.6.1.4.1.2011.2.25.4.50.31.1.5.1.2
    optixQosSpecIndex1 OBJECT-TYPE
        SYNTAX Unsigned32
        MAX-ACCESS not-accessible
        STATUS current
        DESCRIPTION
            "This parameter is used to describe index 1 to the QoS module. If this parameter is not used, enter all Fs (invalid value)."
        ::= { optixQosSpecEntry 2 }

    -- 1.3.6.1.4.1.2011.2.25.4.50.31.1.5.1.3
    optixQosSpecIndex2 OBJECT-TYPE
        SYNTAX Unsigned32
        MAX-ACCESS not-accessible
        STATUS current
        DESCRIPTION
            "This parameter is used to describe index 2 to the QoS module. If this parameter is not used, enter all Fs (invalid value)."
        ::= { optixQosSpecEntry 3 }

    -- 1.3.6.1.4.1.2011.2.25.4.50.31.1.5.1.4
    optixQosSpecIndex3 OBJECT-TYPE
        SYNTAX Unsigned32
        MAX-ACCESS not-accessible
        STATUS current
        DESCRIPTION
            "This parameter is used to describe index 3 to the QoS module. If this parameter is not used, enter all Fs (invalid value)."
        ::= { optixQosSpecEntry 4 }

    -- 1.3.6.1.4.1.2011.2.25.4.50.31.1.5.1.5
    optixQosSpecDefault OBJECT-TYPE
        SYNTAX Unsigned32
        MAX-ACCESS read-only
        STATUS current
        DESCRIPTION
            "This parameter is used to describe the default value of the QoS attribute. Value range: 0-4294967295"
        ::= { optixQosSpecEntry 5 }

    -- 1.3.6.1.4.1.2011.2.25.4.50.31.1.5.1.6
    optixQosSpecMin OBJECT-TYPE
        SYNTAX Unsigned32
        MAX-ACCESS read-only
        STATUS current
        DESCRIPTION
            "This parameter is used to describe the minimum value of the QoS attribute. Value range: 0-4294967295"
        ::= { optixQosSpecEntry 6 }

    -- 1.3.6.1.4.1.2011.2.25.4.50.31.1.5.1.7
    optixQosSpecMax OBJECT-TYPE
        SYNTAX Unsigned32
        MAX-ACCESS read-only
        STATUS current
        DESCRIPTION
            "This parameter is used to describe the maximum value of the QoS attribute. Value range: 0-4294967295"
        ::= { optixQosSpecEntry 7 }

    -- 1.3.6.1.4.1.2011.2.25.4.50.31.1.6
    optixQosDscpOutMapingEN OBJECT-TYPE
        SYNTAX INTEGER
        {
            disable(0),
            enable(1)
        }
        MAX-ACCESS read-write
        STATUS current
        DESCRIPTION
            "This parameter is used to describe the DSCP reverse mapping enable status. 0: disable; 1: enable"
        ::= { optixPktQosPointGroup 6 }

    -- 1.3.6.1.4.1.2011.2.25.4.50.31.1.7
    optixQosQueueRealLenTable OBJECT-TYPE
        SYNTAX SEQUENCE OF OptixQosQueueRealLenEntry
        MAX-ACCESS not-accessible
        STATUS current
        DESCRIPTION
            "This table indicates the actual length of queried queues."
        ::= { optixPktQosPointGroup 7 }

    -- 1.3.6.1.4.1.2011.2.25.4.50.31.1.7.1
    optixQosQueueRealLenEntry OBJECT-TYPE
        SYNTAX OptixQosQueueRealLenEntry
        MAX-ACCESS not-accessible
        STATUS current
        DESCRIPTION
            "This entry indicates the actual length of queried queues."
        INDEX{ optixQosQueueRealLenType,optixQosQueueRealLenIndex1,optixQosQueueRealLenIndex2,optixQosQueueRealLenIndex3,optixQosQueueRealLenDir,optixQosQueueRealLenAttrid }
        ::= { optixQosQueueRealLenTable 1 }

    OptixQosQueueRealLenEntry ::=
        SEQUENCE {
            optixQosQueueRealLenType
                INTEGER,
            optixQosQueueRealLenIndex1
                Unsigned32,
            optixQosQueueRealLenIndex2
                Unsigned32,
            optixQosQueueRealLenIndex3
                Unsigned32,
            optixQosQueueRealLenDir
                INTEGER,
            optixQosQueueRealLenAttrid
                INTEGER,
            optixQosQueueRealLenCS7
                Unsigned32,
            optixQosQueueRealLenCS6
                Unsigned32,
            optixQosQueueRealLenEF
                Unsigned32,
            optixQosQueueRealLenAF4
                Unsigned32,
            optixQosQueueRealLenAF3
                Unsigned32,
            optixQosQueueRealLenAF2
                Unsigned32,
            optixQosQueueRealLenAF1
                Unsigned32,
            optixQosQueueRealLenBE
                Unsigned32
        }

    -- 1.3.6.1.4.1.2011.2.25.4.50.31.1.7.1.1
    optixQosQueueRealLenType OBJECT-TYPE
        SYNTAX INTEGER
        {
            port(1),
            vuni(2),
            pw(3),
            qinq(4)
        }
        MAX-ACCESS not-accessible
        STATUS current
        DESCRIPTION
            "This parameter indicates the types of QoS function points. Value range: port(1), vuni(2), pw(3), qinq(4)"
        ::= { optixQosQueueRealLenEntry 1 }

    -- 1.3.6.1.4.1.2011.2.25.4.50.31.1.7.1.2
    optixQosQueueRealLenIndex1 OBJECT-TYPE
        SYNTAX Unsigned32
        MAX-ACCESS not-accessible
        STATUS current
        DESCRIPTION
            "This parameter indicates QoS location parameter 1. Remarks: This parameter takes the value of all Fs if not being used."
        ::= { optixQosQueueRealLenEntry 2 }

    -- 1.3.6.1.4.1.2011.2.25.4.50.31.1.7.1.3
    optixQosQueueRealLenIndex2 OBJECT-TYPE
        SYNTAX Unsigned32
        MAX-ACCESS not-accessible
        STATUS current
        DESCRIPTION
            "This parameter indicates QoS location parameter 2. Remarks: This parameter takes the value of all Fs if not being used."
        ::= { optixQosQueueRealLenEntry 3 }

    -- 1.3.6.1.4.1.2011.2.25.4.50.31.1.7.1.4
    optixQosQueueRealLenIndex3 OBJECT-TYPE
        SYNTAX Unsigned32
        MAX-ACCESS not-accessible
        STATUS current
        DESCRIPTION
            "This parameter indicates QoS location parameter 3. Remarks: This parameter 3 takes the value of all Fs if not being used."
        ::= { optixQosQueueRealLenEntry 4 }

    -- 1.3.6.1.4.1.2011.2.25.4.50.31.1.7.1.5
    optixQosQueueRealLenDir OBJECT-TYPE
        SYNTAX INTEGER
        {
            ingress(1),
            egress(2),
            none(255)
        }
        MAX-ACCESS not-accessible
        STATUS current
        DESCRIPTION
            "This parameter indicates the QoS direction. Value range: ingress(1),egress(2),none(255)"
        ::= { optixQosQueueRealLenEntry 5 }

    -- 1.3.6.1.4.1.2011.2.25.4.50.31.1.7.1.6
    optixQosQueueRealLenAttrid OBJECT-TYPE
        SYNTAX INTEGER
        {
            wred(0),
            taildrop(1)
        }
        MAX-ACCESS not-accessible
        STATUS current
        DESCRIPTION
            "This parameter indicates the QoS attribute ID. Value range: Wred: 0, tail drop: 1."
        ::= { optixQosQueueRealLenEntry 6 }

    -- 1.3.6.1.4.1.2011.2.25.4.50.31.1.7.1.7
    optixQosQueueRealLenCS7 OBJECT-TYPE
        SYNTAX Unsigned32
        MAX-ACCESS read-only
        STATUS current
        DESCRIPTION
            "This parameter indicates the actual length of CS7 queues. Value range: 0 to 4294967295"
        ::= { optixQosQueueRealLenEntry 7 }

    -- 1.3.6.1.4.1.2011.2.25.4.50.31.1.7.1.8
    optixQosQueueRealLenCS6 OBJECT-TYPE
        SYNTAX Unsigned32
        MAX-ACCESS read-only
        STATUS current
        DESCRIPTION
            "This parameter indicates the actual length of CS6 queues. Value range: 0 to 4294967295"
        ::= { optixQosQueueRealLenEntry 8 }

    -- 1.3.6.1.4.1.2011.2.25.4.50.31.1.7.1.9
    optixQosQueueRealLenEF OBJECT-TYPE
        SYNTAX Unsigned32
        MAX-ACCESS read-only
        STATUS current
        DESCRIPTION
            "This parameter indicates the actual length of EF queues. Value range: 0 to 4294967295"
        ::= { optixQosQueueRealLenEntry 9 }

    -- 1.3.6.1.4.1.2011.2.25.4.50.31.1.7.1.10
    optixQosQueueRealLenAF4 OBJECT-TYPE
        SYNTAX Unsigned32
        MAX-ACCESS read-only
        STATUS current
        DESCRIPTION
            "This parameter indicates the actual length of AF4 queues. Value range: 0 to 4294967295"
        ::= { optixQosQueueRealLenEntry 10 }

    -- 1.3.6.1.4.1.2011.2.25.4.50.31.1.7.1.11
    optixQosQueueRealLenAF3 OBJECT-TYPE
        SYNTAX Unsigned32
        MAX-ACCESS read-only
        STATUS current
        DESCRIPTION
            "This parameter indicates the actual length of AF3 queues. Value range: 0 to 4294967295"
        ::= { optixQosQueueRealLenEntry 11 }

    -- 1.3.6.1.4.1.2011.2.25.4.50.31.1.7.1.12
    optixQosQueueRealLenAF2 OBJECT-TYPE
        SYNTAX Unsigned32
        MAX-ACCESS read-only
        STATUS current
        DESCRIPTION
            "This parameter indicates the actual length of AF2 queues. Value range: 0 to 4294967295"
        ::= { optixQosQueueRealLenEntry 12 }

    -- 1.3.6.1.4.1.2011.2.25.4.50.31.1.7.1.13
    optixQosQueueRealLenAF1 OBJECT-TYPE
        SYNTAX Unsigned32
        MAX-ACCESS read-only
        STATUS current
        DESCRIPTION
            "This parameter indicates the actual length of AF1 queues. Value range: 0 to 4294967295"
        ::= { optixQosQueueRealLenEntry 13 }

    -- 1.3.6.1.4.1.2011.2.25.4.50.31.1.7.1.14
    optixQosQueueRealLenBE OBJECT-TYPE
        SYNTAX Unsigned32
        MAX-ACCESS read-only
        STATUS current
        DESCRIPTION
            "This parameter indicates the actual length of BE queues. Value range: 0 to 4294967295"
        ::= { optixQosQueueRealLenEntry 14 }

END
