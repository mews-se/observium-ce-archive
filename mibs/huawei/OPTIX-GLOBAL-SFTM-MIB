-- OPTIX-GLOBAL-SFTM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-SFTM-MIB DEFINITIONS ::= BEGIN
    IMPORTS
        optixCommonGlobal
            FROM OPTIX-OID-MIB
        MODULE-IDENTITY,OBJECT-TYPE,Unsigned32
            FROM SNMPv2-SMI
        DisplayString
            FROM SNMPv2-TC
        ;

    optixGlobalSftm MODULE-IDENTITY
        LAST-UPDATED "201601251644Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "SFTM module"
        REVISION "201601251644Z"
        DESCRIPTION
            "The initial version"
        ::={ optixCommonGlobal 3 }

    -- 1.3.6.1.4.1.2011.2.25.3.40.3.1
    optixSftmManager OBJECT IDENTIFIER ::= { optixGlobalSftm 1 }

    -- 1.3.6.1.4.1.2011.2.25.3.40.3.1.1
    optixSftmGetBdinfoTable OBJECT-TYPE
        SYNTAX SEQUENCE OF OptixSftmGetBdinfoEntry
        MAX-ACCESS not-accessible
        STATUS current
        DESCRIPTION
            "Query manufacturer information"
        ::= { optixSftmManager 1 }

    -- 1.3.6.1.4.1.2011.2.25.3.40.3.1.1.1
    optixSftmGetBdinfoEntry OBJECT-TYPE
        SYNTAX OptixSftmGetBdinfoEntry
        MAX-ACCESS not-accessible
        STATUS current
        DESCRIPTION
            "Query the manufacturer information table"
        INDEX{ optixSftmGetBdInfoBid }
        ::= { optixSftmGetBdinfoTable 1 }

    OptixSftmGetBdinfoEntry ::=
        SEQUENCE {
            optixSftmGetBdInfoBid
                OCTET STRING,
            optixSftmGetBdInfoData
                OCTET STRING
        }

    -- 1.3.6.1.4.1.2011.2.25.3.40.3.1.1.1.1
    optixSftmGetBdInfoBid OBJECT-TYPE
        SYNTAX OCTET STRING (SIZE(0..8))
        MAX-ACCESS read-only
        STATUS current
        DESCRIPTION
            "Board ID"
        ::= { optixSftmGetBdinfoEntry 1 }

    -- 1.3.6.1.4.1.2011.2.25.3.40.3.1.1.1.2
    optixSftmGetBdInfoData OBJECT-TYPE
        SYNTAX OCTET STRING (SIZE(0..4620))
        MAX-ACCESS read-only
        STATUS current
        DESCRIPTION
            "Board manufacturer information"
        ::= { optixSftmGetBdinfoEntry 2 }

    -- 1.3.6.1.4.1.2011.2.25.3.40.3.2
    optixSftmDetailManager OBJECT IDENTIFIER ::= { optixGlobalSftm 2 }

    -- 1.3.6.1.4.1.2011.2.25.3.40.3.2.1
    optixVRCBVer OBJECT-TYPE
        SYNTAX OCTET STRING (SIZE(0..32))
        MAX-ACCESS read-only
        STATUS current
        DESCRIPTION
            "VRCB version information"
        ::= { optixSftmDetailManager 1 }

    -- 1.3.6.1.4.1.2011.2.25.3.40.3.2.2
    optixPKGVerActive OBJECT-TYPE
        SYNTAX OCTET STRING (SIZE(0..32))
        MAX-ACCESS read-only
        STATUS current
        DESCRIPTION
            "optixPKGVerActive"
        ::= { optixSftmDetailManager 2 }

    -- 1.3.6.1.4.1.2011.2.25.3.40.3.2.3
    optixPKGVerStandby OBJECT-TYPE
        SYNTAX OCTET STRING (SIZE(0..32))
        MAX-ACCESS read-only
        STATUS current
        DESCRIPTION
            "optixPKGVerStandby"
        ::= { optixSftmDetailManager 3 }

    -- 1.3.6.1.4.1.2011.2.25.3.40.3.3
    optixPatchManager OBJECT IDENTIFIER ::= { optixGlobalSftm 3 }

    -- 1.3.6.1.4.1.2011.2.25.3.40.3.3.1
    optixPatchListLen OBJECT-TYPE
        SYNTAX Unsigned32
        MAX-ACCESS read-only
        STATUS current
        DESCRIPTION
            "Patch information length"
        ::= { optixPatchManager 1 }

    -- 1.3.6.1.4.1.2011.2.25.3.40.3.3.2
    optixPatchListData OBJECT-TYPE
        SYNTAX OCTET STRING (SIZE(0..512))
        MAX-ACCESS read-only
        STATUS current
        DESCRIPTION
            "Patch information"
        ::= { optixPatchManager 2 }

    -- 1.3.6.1.4.1.2011.2.25.3.40.3.4
    optixLcsManager OBJECT IDENTIFIER ::= { optixGlobalSftm 4 }

    -- 1.3.6.1.4.1.2011.2.25.3.40.3.4.1
    optixLcsEsn OBJECT-TYPE
        SYNTAX OCTET STRING (SIZE(0..32))
        MAX-ACCESS read-only
        STATUS current
        DESCRIPTION
            "optixLcsEsn"
        ::= { optixLcsManager 1 }

    -- 1.3.6.1.4.1.2011.2.25.3.40.3.4.2
    optixLcsLcsInfo OBJECT-TYPE
        SYNTAX OCTET STRING (SIZE(0..1024))
        MAX-ACCESS read-only
        STATUS current
        DESCRIPTION
            "optixLcsLcsInfo"
        ::= { optixLcsManager 2 }

    -- 1.3.6.1.4.1.2011.2.25.3.40.3.4.3
    optixLcsSetAction OBJECT-TYPE
        SYNTAX INTEGER
        {
            active(1),
            rollback(2)
        }
        MAX-ACCESS read-write
        STATUS current
        DESCRIPTION
            "optixLcsSetAction"
        ::= { optixLcsManager 3 }

    -- 1.3.6.1.4.1.2011.2.25.3.40.3.4.4
    optixLcsSetRevoke OBJECT-TYPE
        SYNTAX OCTET STRING (SIZE(0..59))
        MAX-ACCESS read-write
        STATUS current
        DESCRIPTION
            "optixLcsSetRevoke"
        ::= { optixLcsManager 4 }

    -- 1.3.6.1.4.1.2011.2.25.3.40.3.5
    optixLcsTabManager OBJECT IDENTIFIER ::= { optixGlobalSftm 5 }

    -- 1.3.6.1.4.1.2011.2.25.3.40.3.5.1
    optixLcsCtrlItemExtTable OBJECT-TYPE
        SYNTAX SEQUENCE OF OptixLcsCtrlItemExtEntry
        MAX-ACCESS not-accessible
        STATUS current
        DESCRIPTION
            "optixLcsCtrlItemExtTable"
        ::= { optixLcsTabManager 1 }

    -- 1.3.6.1.4.1.2011.2.25.3.40.3.5.1.1
    optixLcsCtrlItemExtEntry OBJECT-TYPE
        SYNTAX OptixLcsCtrlItemExtEntry
        MAX-ACCESS not-accessible
        STATUS current
        DESCRIPTION
            "optixLcsCtrlItemExtEntry"
        INDEX{ optixLcsCtrlItemExtID }
        ::= { optixLcsCtrlItemExtTable 1 }

    OptixLcsCtrlItemExtEntry ::=
        SEQUENCE {
            optixLcsCtrlItemExtID
                Unsigned32,
            optixLcsCtrlItemExtName
                OCTET STRING,
            optixLcsCtrlItemExtType
                INTEGER,
            optixLcsCtrlItemExtCtrlVal
                Unsigned32,
            optixLcsCtrlItemExtUsedVal
                Unsigned32,
            optixLcsCtrlItemExtStatus
                INTEGER,
            optixLcsCtrlItemExtDeadline
                OCTET STRING,
            optixLcsCtrlItemExtDesc
                OCTET STRING,
            optixLcsCtrlItemExtRemark
                OCTET STRING
        }

    -- 1.3.6.1.4.1.2011.2.25.3.40.3.5.1.1.1
    optixLcsCtrlItemExtID OBJECT-TYPE
        SYNTAX Unsigned32
        MAX-ACCESS not-accessible
        STATUS current
        DESCRIPTION
            "optixLcsCtrlItemExtID"
        ::= { optixLcsCtrlItemExtEntry 1 }

    -- 1.3.6.1.4.1.2011.2.25.3.40.3.5.1.1.2
    optixLcsCtrlItemExtName OBJECT-TYPE
        SYNTAX OCTET STRING (SIZE(0..32))
        MAX-ACCESS read-only
        STATUS current
        DESCRIPTION
            "optixLcsCtrlItemExtName"
        ::= { optixLcsCtrlItemExtEntry 2 }

    -- 1.3.6.1.4.1.2011.2.25.3.40.3.5.1.1.3
    optixLcsCtrlItemExtType OBJECT-TYPE
        SYNTAX INTEGER
        {
            function(0),
            resource(1)
        }
        MAX-ACCESS read-only
        STATUS current
        DESCRIPTION
            "optixLcsCtrlItemExtType"
        ::= { optixLcsCtrlItemExtEntry 3 }

    -- 1.3.6.1.4.1.2011.2.25.3.40.3.5.1.1.4
    optixLcsCtrlItemExtCtrlVal OBJECT-TYPE
        SYNTAX Unsigned32
        MAX-ACCESS read-only
        STATUS current
        DESCRIPTION
            "optixLcsCtrlItemExtCtrlVal"
        ::= { optixLcsCtrlItemExtEntry 4 }

    -- 1.3.6.1.4.1.2011.2.25.3.40.3.5.1.1.5
    optixLcsCtrlItemExtUsedVal OBJECT-TYPE
        SYNTAX Unsigned32
        MAX-ACCESS read-only
        STATUS current
        DESCRIPTION
            "optixLcsCtrlItemExtUsedVal"
        ::= { optixLcsCtrlItemExtEntry 5 }

    -- 1.3.6.1.4.1.2011.2.25.3.40.3.5.1.1.6
    optixLcsCtrlItemExtStatus OBJECT-TYPE
        SYNTAX INTEGER
        {
            default(1),
            trial(2),
            normal(3),
            emergency(4)
        }
        MAX-ACCESS read-only
        STATUS current
        DESCRIPTION
            "optixLcsCtrlItemExtStatus"
        ::= { optixLcsCtrlItemExtEntry 6 }

    -- 1.3.6.1.4.1.2011.2.25.3.40.3.5.1.1.7
    optixLcsCtrlItemExtDeadline OBJECT-TYPE
        SYNTAX OCTET STRING (SIZE(0..12))
        MAX-ACCESS read-only
        STATUS current
        DESCRIPTION
            "optixLcsCtrlItemExtDeadline"
        ::= { optixLcsCtrlItemExtEntry 7 }

    -- 1.3.6.1.4.1.2011.2.25.3.40.3.5.1.1.8
    optixLcsCtrlItemExtDesc OBJECT-TYPE
        SYNTAX OCTET STRING (SIZE(0..128))
        MAX-ACCESS read-only
        STATUS current
        DESCRIPTION
            "optixLcsCtrlItemExtDesc"
        ::= { optixLcsCtrlItemExtEntry 8 }

    -- 1.3.6.1.4.1.2011.2.25.3.40.3.5.1.1.9
    optixLcsCtrlItemExtRemark OBJECT-TYPE
        SYNTAX OCTET STRING (SIZE(0..512))
        MAX-ACCESS read-only
        STATUS current
        DESCRIPTION
            "optixLcsCtrlItemExtRemark"
        ::= { optixLcsCtrlItemExtEntry 9 }

    -- 1.3.6.1.4.1.2011.2.25.3.40.3.5.2
    optixLcsCtrlItemTable OBJECT-TYPE
        SYNTAX SEQUENCE OF OptixLcsCtrlItemEntry
        MAX-ACCESS not-accessible
        STATUS current
        DESCRIPTION
            "optixLcsCtrlItemTable"
        ::= { optixLcsTabManager 2 }

    -- 1.3.6.1.4.1.2011.2.25.3.40.3.5.2.1
    optixLcsCtrlItemEntry OBJECT-TYPE
        SYNTAX OptixLcsCtrlItemEntry
        MAX-ACCESS not-accessible
        STATUS current
        DESCRIPTION
            "optixLcsCtrlItemEntry"
        INDEX{ optixLcsCtrlItemID }
        ::= { optixLcsCtrlItemTable 1 }

    OptixLcsCtrlItemEntry ::=
        SEQUENCE {
            optixLcsCtrlItemID
                Unsigned32,
            optixLcsCtrlItemName
                OCTET STRING,
            optixLcsCtrlItemType
                INTEGER,
            optixLcsCtrlItemCtrlVal
                Unsigned32,
            optixLcsCtrlItemUsedVal
                Unsigned32,
            optixLcsCtrlItemStatus
                INTEGER,
            optixLcsCtrlItemDeadline
                OCTET STRING,
            optixLcsCtrlItemDesc
                OCTET STRING
        }

    -- 1.3.6.1.4.1.2011.2.25.3.40.3.5.2.1.1
    optixLcsCtrlItemID OBJECT-TYPE
        SYNTAX Unsigned32
        MAX-ACCESS not-accessible
        STATUS current
        DESCRIPTION
            "optixLcsCtrlItemID"
        ::= { optixLcsCtrlItemEntry 1 }

    -- 1.3.6.1.4.1.2011.2.25.3.40.3.5.2.1.2
    optixLcsCtrlItemName OBJECT-TYPE
        SYNTAX OCTET STRING (SIZE(0..32))
        MAX-ACCESS read-only
        STATUS current
        DESCRIPTION
            "optixLcsCtrlItemName"
        ::= { optixLcsCtrlItemEntry 2 }

    -- 1.3.6.1.4.1.2011.2.25.3.40.3.5.2.1.3
    optixLcsCtrlItemType OBJECT-TYPE
        SYNTAX INTEGER
        {
            function(0),
            resource(1)
        }
        MAX-ACCESS read-only
        STATUS current
        DESCRIPTION
            "optixLcsCtrlItemType"
        ::= { optixLcsCtrlItemEntry 3 }

    -- 1.3.6.1.4.1.2011.2.25.3.40.3.5.2.1.4
    optixLcsCtrlItemCtrlVal OBJECT-TYPE
        SYNTAX Unsigned32
        MAX-ACCESS read-only
        STATUS current
        DESCRIPTION
            "optixLcsCtrlItemCtrlVal"
        ::= { optixLcsCtrlItemEntry 4 }

    -- 1.3.6.1.4.1.2011.2.25.3.40.3.5.2.1.5
    optixLcsCtrlItemUsedVal OBJECT-TYPE
        SYNTAX Unsigned32
        MAX-ACCESS read-only
        STATUS current
        DESCRIPTION
            "optixLcsCtrlItemUsedVal"
        ::= { optixLcsCtrlItemEntry 5 }

    -- 1.3.6.1.4.1.2011.2.25.3.40.3.5.2.1.6
    optixLcsCtrlItemStatus OBJECT-TYPE
        SYNTAX INTEGER
        {
            default(1),
            trial(2),
            normal(3),
            emergency(4)
        }
        MAX-ACCESS read-only
        STATUS current
        DESCRIPTION
            "optixLcsCtrlItemStatus"
        ::= { optixLcsCtrlItemEntry 6 }

    -- 1.3.6.1.4.1.2011.2.25.3.40.3.5.2.1.7
    optixLcsCtrlItemDeadline OBJECT-TYPE
        SYNTAX OCTET STRING (SIZE(0..12))
        MAX-ACCESS read-only
        STATUS current
        DESCRIPTION
            "optixLcsCtrlItemDeadline"
        ::= { optixLcsCtrlItemEntry 7 }

    -- 1.3.6.1.4.1.2011.2.25.3.40.3.5.2.1.8
    optixLcsCtrlItemDesc OBJECT-TYPE
        SYNTAX OCTET STRING (SIZE(0..128))
        MAX-ACCESS read-only
        STATUS current
        DESCRIPTION
            "optixLcsCtrlItemDesc"
        ::= { optixLcsCtrlItemEntry 8 }

    -- 1.3.6.1.4.1.2011.2.25.3.40.3.5.3
    optixLcsVerifyTable OBJECT-TYPE
        SYNTAX SEQUENCE OF OptixLcsVerifyEntry
        MAX-ACCESS not-accessible
        STATUS current
        DESCRIPTION
            "optixLcsVerifyTable"
        ::= { optixLcsTabManager 3 }

    -- 1.3.6.1.4.1.2011.2.25.3.40.3.5.3.1
    optixLcsVerifyEntry OBJECT-TYPE
        SYNTAX OptixLcsVerifyEntry
        MAX-ACCESS not-accessible
        STATUS current
        DESCRIPTION
            "optixLcsVerifyEntry"
        INDEX{ optixLcsVerifyITEMID }
        ::= { optixLcsVerifyTable 1 }

    OptixLcsVerifyEntry ::=
        SEQUENCE {
            optixLcsVerifyITEMID
                Unsigned32,
            optixLcsVerifyLKVFRESULT
                Unsigned32,
            optixLcsVerifyLSN
                OCTET STRING,
            optixLcsVerifyPRODUCT
                OCTET STRING,
            optixLcsVerifyVERSION
                OCTET STRING,
            optixLcsVerifyESN
                OCTET STRING,
            optixLcsVerifyNAME
                OCTET STRING,
            optixLcsVerifyTYPE
                INTEGER,
            optixLcsVerifyLKVAL
                Unsigned32,
            optixLcsVerifyDEADLINE
                OCTET STRING,
            optixLcsVerifyTRIALDAYS
                Unsigned32,
            optixLcsVerifyITEMVFRESULT
                Unsigned32
        }

    -- 1.3.6.1.4.1.2011.2.25.3.40.3.5.3.1.1
    optixLcsVerifyITEMID OBJECT-TYPE
        SYNTAX Unsigned32
        MAX-ACCESS not-accessible
        STATUS current
        DESCRIPTION
            "optixLcsVerifyITEMID"
        ::= { optixLcsVerifyEntry 1 }

    -- 1.3.6.1.4.1.2011.2.25.3.40.3.5.3.1.2
    optixLcsVerifyLKVFRESULT OBJECT-TYPE
        SYNTAX Unsigned32
        MAX-ACCESS read-only
        STATUS current
        DESCRIPTION
            "optixLcsVerifyLKVFRESULT"
        ::= { optixLcsVerifyEntry 2 }

    -- 1.3.6.1.4.1.2011.2.25.3.40.3.5.3.1.3
    optixLcsVerifyLSN OBJECT-TYPE
        SYNTAX OCTET STRING (SIZE(0..18))
        MAX-ACCESS read-only
        STATUS current
        DESCRIPTION
            "optixLcsVerifyLSN"
        ::= { optixLcsVerifyEntry 3 }

    -- 1.3.6.1.4.1.2011.2.25.3.40.3.5.3.1.4
    optixLcsVerifyPRODUCT OBJECT-TYPE
        SYNTAX OCTET STRING (SIZE(0..64))
        MAX-ACCESS read-only
        STATUS current
        DESCRIPTION
            "optixLcsVerifyPRODUCT"
        ::= { optixLcsVerifyEntry 4 }

    -- 1.3.6.1.4.1.2011.2.25.3.40.3.5.3.1.5
    optixLcsVerifyVERSION OBJECT-TYPE
        SYNTAX OCTET STRING (SIZE(0..64))
        MAX-ACCESS read-only
        STATUS current
        DESCRIPTION
            "optixLcsVerifyVERSION"
        ::= { optixLcsVerifyEntry 5 }

    -- 1.3.6.1.4.1.2011.2.25.3.40.3.5.3.1.6
    optixLcsVerifyESN OBJECT-TYPE
        SYNTAX OCTET STRING (SIZE(0..128))
        MAX-ACCESS read-only
        STATUS current
        DESCRIPTION
            "optixLcsVerifyESN"
        ::= { optixLcsVerifyEntry 6 }

    -- 1.3.6.1.4.1.2011.2.25.3.40.3.5.3.1.7
    optixLcsVerifyNAME OBJECT-TYPE
        SYNTAX OCTET STRING (SIZE(0..32))
        MAX-ACCESS read-only
        STATUS current
        DESCRIPTION
            "optixLcsVerifyNAME"
        ::= { optixLcsVerifyEntry 7 }

    -- 1.3.6.1.4.1.2011.2.25.3.40.3.5.3.1.8
    optixLcsVerifyTYPE OBJECT-TYPE
        SYNTAX INTEGER
        {
            function(0),
            resource(1)
        }
        MAX-ACCESS read-only
        STATUS current
        DESCRIPTION
            "optixLcsVerifyTYPE"
        ::= { optixLcsVerifyEntry 8 }

    -- 1.3.6.1.4.1.2011.2.25.3.40.3.5.3.1.9
    optixLcsVerifyLKVAL OBJECT-TYPE
        SYNTAX Unsigned32
        MAX-ACCESS read-only
        STATUS current
        DESCRIPTION
            "optixLcsVerifyLKVAL"
        ::= { optixLcsVerifyEntry 9 }

    -- 1.3.6.1.4.1.2011.2.25.3.40.3.5.3.1.10
    optixLcsVerifyDEADLINE OBJECT-TYPE
        SYNTAX OCTET STRING (SIZE(0..12))
        MAX-ACCESS read-only
        STATUS current
        DESCRIPTION
            "optixLcsVerifyDEADLINE"
        ::= { optixLcsVerifyEntry 10 }

    -- 1.3.6.1.4.1.2011.2.25.3.40.3.5.3.1.11
    optixLcsVerifyTRIALDAYS OBJECT-TYPE
        SYNTAX Unsigned32
        MAX-ACCESS read-only
        STATUS current
        DESCRIPTION
            "optixLcsVerifyTRIALDAYS"
        ::= { optixLcsVerifyEntry 11 }

    -- 1.3.6.1.4.1.2011.2.25.3.40.3.5.3.1.12
    optixLcsVerifyITEMVFRESULT OBJECT-TYPE
        SYNTAX Unsigned32
        MAX-ACCESS read-only
        STATUS current
        DESCRIPTION
            "optixLcsVerifyITEMVFRESULT"
        ::= { optixLcsVerifyEntry 12 }

    -- 1.3.6.1.4.1.2011.2.25.3.40.3.5.4
    optixLcsSaleInfoTable OBJECT-TYPE
        SYNTAX SEQUENCE OF OptixLcsSaleInfoEntry
        MAX-ACCESS not-accessible
        STATUS current
        DESCRIPTION
            "optixLcsSaleInfoTable"
        ::= { optixLcsTabManager 4 }

    -- 1.3.6.1.4.1.2011.2.25.3.40.3.5.4.1
    optixLcsSaleInfoEntry OBJECT-TYPE
        SYNTAX OptixLcsSaleInfoEntry
        MAX-ACCESS not-accessible
        STATUS current
        DESCRIPTION
            "optixLcsSaleInfoEntry"
        INDEX{ optixLcsSaleInfoIdx }
        ::= { optixLcsSaleInfoTable 1 }

    OptixLcsSaleInfoEntry ::=
        SEQUENCE {
            optixLcsSaleInfoIdx
                Unsigned32,
            optixLcsSaleInfoName
                OCTET STRING,
            optixLcsSaleInfoValue
                Unsigned32,
            optixLcsSaleInfoDeadline
                OCTET STRING,
            optixLcsSaleInfoEngUnit
                OCTET STRING,
            optixLcsSaleInfoEngDesp
                OCTET STRING,
            optixLcsSaleInfoChsUnit
                OCTET STRING,
            optixLcsSaleInfoChsDesp
                OCTET STRING,
            optixLcsSaleInfoProduct
                OCTET STRING,
            optixLcsSaleInfoPrdVersion
                OCTET STRING,
            optixLcsSaleInfoS2bbmlist
                OCTET STRING
        }

    -- 1.3.6.1.4.1.2011.2.25.3.40.3.5.4.1.1
    optixLcsSaleInfoIdx OBJECT-TYPE
        SYNTAX Unsigned32
        MAX-ACCESS not-accessible
        STATUS current
        DESCRIPTION
            "optixLcsSaleInfoIdx"
        ::= { optixLcsSaleInfoEntry 1 }

    -- 1.3.6.1.4.1.2011.2.25.3.40.3.5.4.1.2
    optixLcsSaleInfoName OBJECT-TYPE
        SYNTAX OCTET STRING (SIZE(0..32))
        MAX-ACCESS read-only
        STATUS current
        DESCRIPTION
            "optixLcsSaleInfoName"
        ::= { optixLcsSaleInfoEntry 2 }

    -- 1.3.6.1.4.1.2011.2.25.3.40.3.5.4.1.3
    optixLcsSaleInfoValue OBJECT-TYPE
        SYNTAX Unsigned32
        MAX-ACCESS read-only
        STATUS current
        DESCRIPTION
            "optixLcsSaleInfoValue"
        ::= { optixLcsSaleInfoEntry 3 }

    -- 1.3.6.1.4.1.2011.2.25.3.40.3.5.4.1.4
    optixLcsSaleInfoDeadline OBJECT-TYPE
        SYNTAX OCTET STRING (SIZE(0..24))
        MAX-ACCESS read-only
        STATUS current
        DESCRIPTION
            "optixLcsSaleInfoDeadline"
        ::= { optixLcsSaleInfoEntry 4 }

    -- 1.3.6.1.4.1.2011.2.25.3.40.3.5.4.1.5
    optixLcsSaleInfoEngUnit OBJECT-TYPE
        SYNTAX OCTET STRING (SIZE(0..64))
        MAX-ACCESS read-only
        STATUS current
        DESCRIPTION
            "optixLcsSaleInfoEngUnit"
        ::= { optixLcsSaleInfoEntry 5 }

    -- 1.3.6.1.4.1.2011.2.25.3.40.3.5.4.1.6
    optixLcsSaleInfoEngDesp OBJECT-TYPE
        SYNTAX OCTET STRING (SIZE(0..128))
        MAX-ACCESS read-only
        STATUS current
        DESCRIPTION
            "optixLcsSaleInfoEngDesp"
        ::= { optixLcsSaleInfoEntry 6 }

    -- 1.3.6.1.4.1.2011.2.25.3.40.3.5.4.1.7
    optixLcsSaleInfoChsUnit OBJECT-TYPE
        SYNTAX OCTET STRING (SIZE(0..64))
        MAX-ACCESS read-only
        STATUS current
        DESCRIPTION
            "optixLcsSaleInfoChsUnit"
        ::= { optixLcsSaleInfoEntry 7 }

    -- 1.3.6.1.4.1.2011.2.25.3.40.3.5.4.1.8
    optixLcsSaleInfoChsDesp OBJECT-TYPE
        SYNTAX OCTET STRING (SIZE(0..128))
        MAX-ACCESS read-only
        STATUS current
        DESCRIPTION
            "optixLcsSaleInfoChsDesp"
        ::= { optixLcsSaleInfoEntry 8 }

    -- 1.3.6.1.4.1.2011.2.25.3.40.3.5.4.1.9
    optixLcsSaleInfoProduct OBJECT-TYPE
        SYNTAX OCTET STRING (SIZE(0..64))
        MAX-ACCESS read-only
        STATUS current
        DESCRIPTION
            "optixLcsSaleInfoProduct"
        ::= { optixLcsSaleInfoEntry 9 }

    -- 1.3.6.1.4.1.2011.2.25.3.40.3.5.4.1.10
    optixLcsSaleInfoPrdVersion OBJECT-TYPE
        SYNTAX OCTET STRING (SIZE(0..32))
        MAX-ACCESS read-only
        STATUS current
        DESCRIPTION
            "optixLcsSaleInfoPrdVersion"
        ::= { optixLcsSaleInfoEntry 10 }

    -- 1.3.6.1.4.1.2011.2.25.3.40.3.5.4.1.11
    optixLcsSaleInfoS2bbmlist OBJECT-TYPE
        SYNTAX OCTET STRING (SIZE(0..512))
        MAX-ACCESS read-only
        STATUS current
        DESCRIPTION
            "optixLcsSaleInfoS2bbmlist"
        ::= { optixLcsSaleInfoEntry 11 }

    -- 1.3.6.1.4.1.2011.2.25.3.40.3.6
    optixSftmLoadsoft OBJECT IDENTIFIER ::= { optixGlobalSftm 6 }

    -- 1.3.6.1.4.1.2011.2.25.3.40.3.6.1
    optixSftmLoadsoftState OBJECT-TYPE
        SYNTAX INTEGER
        {
            close(0),
            open(1)
        }
        MAX-ACCESS read-write
        STATUS current
        DESCRIPTION
            "optixSftmLoadsoftState"
        ::= { optixSftmLoadsoft 1 }

    -- 1.3.6.1.4.1.2011.2.25.3.40.3.6.2
    optixSftmLoadsoftCurState OBJECT-TYPE
        SYNTAX INTEGER
        {
            idle(0),
            busy(1)
        }
        MAX-ACCESS read-only
        STATUS current
        DESCRIPTION
            "optixSftmLoadsoftCurState"
        ::= { optixSftmLoadsoft 2 }

    -- 1.3.6.1.4.1.2011.2.25.3.40.3.7
    optixSftmCopyRFile OBJECT IDENTIFIER ::= { optixGlobalSftm 7 }

    -- 1.3.6.1.4.1.2011.2.25.3.40.3.7.1
    optixSftmCopyRFileBid OBJECT-TYPE
        SYNTAX Unsigned32
        MAX-ACCESS read-write
        STATUS current
        DESCRIPTION
            "Board ID"
        ::= { optixSftmCopyRFile 1 }

    -- 1.3.6.1.4.1.2011.2.25.3.40.3.7.2
    optixSftmCopyRFileType OBJECT-TYPE
        SYNTAX INTEGER
        {
            swdl(1),
            dbfdl(2),
            dbful(3),
            rfr(4),
            rfbu(5),
            fcdl(7),
            seculog(8),
            oplog(9),
            pelog(10),
            infocol(11),
            post(12),
            posthis(13),
            patchpkg(15)
        }
        MAX-ACCESS read-write
        STATUS current
        DESCRIPTION
            "optixSftmCopyRFileType"
        ::= { optixSftmCopyRFile 2 }

    -- 1.3.6.1.4.1.2011.2.25.3.40.3.7.3
    optixSftmCopyRFileSrc OBJECT-TYPE
        SYNTAX OCTET STRING (SIZE(0..255))
        MAX-ACCESS read-write
        STATUS current
        DESCRIPTION
            "optixSftmCopyRFileSrc"
        ::= { optixSftmCopyRFile 3 }

    -- 1.3.6.1.4.1.2011.2.25.3.40.3.7.4
    optixSftmCopyRFileDst OBJECT-TYPE
        SYNTAX OCTET STRING (SIZE(0..255))
        MAX-ACCESS read-write
        STATUS current
        DESCRIPTION
            "optixSftmCopyRFileDst"
        ::= { optixSftmCopyRFile 4 }

    -- 1.3.6.1.4.1.2011.2.25.3.40.3.7.5
    optixSftmCopyRFileOverwrite OBJECT-TYPE
        SYNTAX INTEGER
        {
            deny(0),
            allow(1)
        }
        MAX-ACCESS read-write
        STATUS current
        DESCRIPTION
            "optixSftmCopyRFileOverwrite"
        ::= { optixSftmCopyRFile 5 }

    -- 1.3.6.1.4.1.2011.2.25.3.40.3.8
    optixSftmAbt OBJECT IDENTIFIER ::= { optixGlobalSftm 8 }

    -- 1.3.6.1.4.1.2011.2.25.3.40.3.8.1
    optixSftmAbtCmd OBJECT-TYPE
        SYNTAX OCTET STRING (SIZE(0..16))
        MAX-ACCESS read-write
        STATUS current
        DESCRIPTION
            "optixSftmAbtCmd"
        ::= { optixSftmAbt 1 }

    -- 1.3.6.1.4.1.2011.2.25.3.40.3.9
    optixSftmState OBJECT IDENTIFIER ::= { optixGlobalSftm 9 }

    -- 1.3.6.1.4.1.2011.2.25.3.40.3.9.1
    optixSftmStateTable OBJECT-TYPE
        SYNTAX SEQUENCE OF OptixSftmStateEntry
        MAX-ACCESS not-accessible
        STATUS current
        DESCRIPTION
            "optixSftmStateTable"
        ::= { optixSftmState 1 }

    -- 1.3.6.1.4.1.2011.2.25.3.40.3.9.1.1
    optixSftmStateEntry OBJECT-TYPE
        SYNTAX OptixSftmStateEntry
        MAX-ACCESS not-accessible
        STATUS current
        DESCRIPTION
            "optixSftmStateType"
        INDEX{ optixSftmStateType }
        ::= { optixSftmStateTable 1 }

    OptixSftmStateEntry ::=
        SEQUENCE {
            optixSftmStateType
                INTEGER,
            optixSftmStateMain
                INTEGER,
            optixSftmStateSub
                INTEGER
        }

    -- 1.3.6.1.4.1.2011.2.25.3.40.3.9.1.1.1
    optixSftmStateType OBJECT-TYPE
        SYNTAX INTEGER
        {
            swdl(1),
            dbfdl(2),
            dbful(3),
            rfr(4),
            rfbu(5),
            fcdl(7),
            seculog(8),
            oplog(9),
            pelog(10),
            infocol(11),
            post(12),
            posthis(13),
            patchpkg(15)
        }
        MAX-ACCESS not-accessible
        STATUS current
        DESCRIPTION
            "optixSftmStateType"
        ::= { optixSftmStateEntry 1 }

    -- 1.3.6.1.4.1.2011.2.25.3.40.3.9.1.1.2
    optixSftmStateMain OBJECT-TYPE
        SYNTAX INTEGER
        {
            normal(0),
            cpyFileStart(1),
            cpyFileEnd(2),
            cpyMemStart(3),
            cpyMemEnd(4),
            active(5),
            activated(6),
            rollback(7),
            cpyfileHalt(8),
            downloading(9),
            uploading(10),
            downloadend(11),
            prepareDbuploading(12),
            preparedbDone(13),
            committing(136)
        }
        MAX-ACCESS read-only
        STATUS current
        DESCRIPTION
            "optixSftmStateMain"
        ::= { optixSftmStateEntry 2 }

    -- 1.3.6.1.4.1.2011.2.25.3.40.3.9.1.1.3
    optixSftmStateSub OBJECT-TYPE
        SYNTAX INTEGER
        {
            normal(0),
            unstable(1),
            autosync(2),
            autoswdl(3),
            cpyfileHalt(4),
            activeSelf(5),
            activePeer(6),
            activeBd(7),
            swduInit(8),
            swdu(12),
            activePend(13),
            activeSwitch(14),
            pend(15),
            operateNormal(80),
            rollbackNormal(81),
            pretransErrNormal(82),
            dbziping(83)
        }
        MAX-ACCESS read-only
        STATUS current
        DESCRIPTION
            "optixSftmStateSub"
        ::= { optixSftmStateEntry 3 }

    -- 1.3.6.1.4.1.2011.2.25.3.40.3.10
    optixSwdlAction OBJECT IDENTIFIER ::= { optixGlobalSftm 10 }

    -- 1.3.6.1.4.1.2011.2.25.3.40.3.10.1
    optixSwdlActionDnldMem OBJECT-TYPE
        SYNTAX OCTET STRING (SIZE(0..16))
        MAX-ACCESS read-write
        STATUS current
        DESCRIPTION
            "Download files from memory."
        ::= { optixSwdlAction 1 }

    -- 1.3.6.1.4.1.2011.2.25.3.40.3.10.2
    optixSwdlActionActiveGroup OBJECT-TYPE
        SYNTAX OCTET STRING (SIZE(0..16))
        MAX-ACCESS read-write
        STATUS current
        DESCRIPTION
            "Activate one group."
        ::= { optixSwdlAction 2 }

    -- 1.3.6.1.4.1.2011.2.25.3.40.3.10.3
    optixSwdlActionCommit OBJECT-TYPE
        SYNTAX OCTET STRING (SIZE(0..16))
        MAX-ACCESS read-write
        STATUS current
        DESCRIPTION
            "Commit files."
        ::= { optixSwdlAction 3 }

    -- 1.3.6.1.4.1.2011.2.25.3.40.3.10.4
    optixSwdlActionClrPkg OBJECT-TYPE
        SYNTAX Unsigned32
        MAX-ACCESS read-write
        STATUS current
        DESCRIPTION
            "Clear the existing packages."
        ::= { optixSwdlAction 4 }

    -- 1.3.6.1.4.1.2011.2.25.3.40.3.11
    optixPatchWorkState OBJECT IDENTIFIER ::= { optixGlobalSftm 11 }

    -- 1.3.6.1.4.1.2011.2.25.3.40.3.11.1
    optixPatchWorkStateMain OBJECT-TYPE
        SYNTAX INTEGER
        {
            idle(0),
            matchbd(1),
            matchslv(2),
            dnlding(3),
            dnlded(4),
            install(5),
            installed(6),
            rollback(7),
            committing(8)
        }
        MAX-ACCESS read-only
        STATUS current
        DESCRIPTION
            "optixPatchWorkStateMain"
        ::= { optixPatchWorkState 1 }

    -- 1.3.6.1.4.1.2011.2.25.3.40.3.11.2
    optixPatchWorkStateSub OBJECT-TYPE
        SYNTAX INTEGER
        {
            null(0),
            dnldpkg(1),
            loadfile(2),
            loadmem(3),
            active(4),
            deactive(5),
            run(6),
            install(7),
            delete(8),
            rollback(9),
            cancel(10),
            bdonline(11),
            checkstate(12),
            dnldhalt(13),
            matchbd(14),
            matchslv(15),
            commit(16),
            autoexclude(17),
            checksccchange(18)
        }
        MAX-ACCESS read-only
        STATUS current
        DESCRIPTION
            "optixPatchWorkStateSub"
        ::= { optixPatchWorkState 2 }

    -- 1.3.6.1.4.1.2011.2.25.3.40.3.12
    optixPatchPkgInfo OBJECT IDENTIFIER ::= { optixGlobalSftm 12 }

    -- 1.3.6.1.4.1.2011.2.25.3.40.3.12.1
    optixPatchPkgInfoTable OBJECT-TYPE
        SYNTAX SEQUENCE OF OptixPatchPkgInfoEntry
        MAX-ACCESS not-accessible
        STATUS current
        DESCRIPTION
            "optixPatchPkgInfoTable"
        ::= { optixPatchPkgInfo 1 }

    -- 1.3.6.1.4.1.2011.2.25.3.40.3.12.1.1
    optixPatchPkgInfoEntry OBJECT-TYPE
        SYNTAX OptixPatchPkgInfoEntry
        MAX-ACCESS not-accessible
        STATUS current
        DESCRIPTION
            "optixPatchPkgInfoEntry"
        INDEX{ optixPatchPkgInfoPath }
        ::= { optixPatchPkgInfoTable 1 }

    OptixPatchPkgInfoEntry ::=
        SEQUENCE {
            optixPatchPkgInfoPath
                OCTET STRING,
            optixPatchPkgInfoType
                INTEGER,
            optixPatchPkgInfoErr
                INTEGER,
            optixPatchPkgInfoVer
                OCTET STRING
        }

    -- 1.3.6.1.4.1.2011.2.25.3.40.3.12.1.1.1
    optixPatchPkgInfoPath OBJECT-TYPE
        SYNTAX OCTET STRING (SIZE(0..80))
        MAX-ACCESS not-accessible
        STATUS current
        DESCRIPTION
            "optixPatchPkgInfoPath"
        ::= { optixPatchPkgInfoEntry 1 }

    -- 1.3.6.1.4.1.2011.2.25.3.40.3.12.1.1.2
    optixPatchPkgInfoType OBJECT-TYPE
        SYNTAX INTEGER
        {
            idle(1),
            current(2),
            run(3),
            back(4)
        }
        MAX-ACCESS read-only
        STATUS current
        DESCRIPTION
            "optixPatchPkgInfoType"
        ::= { optixPatchPkgInfoEntry 2 }

    -- 1.3.6.1.4.1.2011.2.25.3.40.3.12.1.1.3
    optixPatchPkgInfoErr OBJECT-TYPE
        SYNTAX INTEGER
        {
            ok(0),
            error(1),
            unitlostError(2),
            bdfileError(3),
            bdunitError(4)
        }
        MAX-ACCESS read-only
        STATUS current
        DESCRIPTION
            "optixPatchPkgInfoErr"
        ::= { optixPatchPkgInfoEntry 3 }

    -- 1.3.6.1.4.1.2011.2.25.3.40.3.12.1.1.4
    optixPatchPkgInfoVer OBJECT-TYPE
        SYNTAX OCTET STRING (SIZE(0..16))
        MAX-ACCESS read-only
        STATUS current
        DESCRIPTION
            "optixPatchPkgInfoVer"
        ::= { optixPatchPkgInfoEntry 4 }

    -- 1.3.6.1.4.1.2011.2.25.3.40.3.13
    optixPatchSetTime OBJECT IDENTIFIER ::= { optixGlobalSftm 13 }

    -- 1.3.6.1.4.1.2011.2.25.3.40.3.13.1
    optixPatchSetTimeType OBJECT-TYPE
        SYNTAX Unsigned32
        MAX-ACCESS read-write
        STATUS current
        DESCRIPTION
            "optixPatchSetTimeType"
        ::= { optixPatchSetTime 1 }

    -- 1.3.6.1.4.1.2011.2.25.3.40.3.13.2
    optixPatchSetTimeValue OBJECT-TYPE
        SYNTAX Unsigned32
        MAX-ACCESS read-write
        STATUS current
        DESCRIPTION
            "optixPatchSetTimeValue"
        ::= { optixPatchSetTime 2 }

    -- 1.3.6.1.4.1.2011.2.25.3.40.3.14
    optixPatchPkgInstall OBJECT IDENTIFIER ::= { optixGlobalSftm 14 }

    -- 1.3.6.1.4.1.2011.2.25.3.40.3.14.1
    optixPatchPkgInstallVer OBJECT-TYPE
        SYNTAX OCTET STRING (SIZE(0..16))
        MAX-ACCESS read-write
        STATUS current
        DESCRIPTION
            "optixPatchPkgInstallVer"
        ::= { optixPatchPkgInstall 1 }

    -- 1.3.6.1.4.1.2011.2.25.3.40.3.14.2
    optixPatchPkgInstallActionOption OBJECT-TYPE
        SYNTAX INTEGER
        {
            delbackpkg(1),
            keepbackpkg(2),
            mem(3),
            file(4),
            pkg(5),
            idle(6),
            null(7)
        }
        MAX-ACCESS read-write
        STATUS current
        DESCRIPTION
            "optixPatchPkgInstallActionOption"
        ::= { optixPatchPkgInstall 2 }

    -- 1.3.6.1.4.1.2011.2.25.3.40.3.15
    optixPatchPkgDel OBJECT IDENTIFIER ::= { optixGlobalSftm 15 }

    -- 1.3.6.1.4.1.2011.2.25.3.40.3.15.1
    optixPatchPkgDelVer OBJECT-TYPE
        SYNTAX OCTET STRING (SIZE(0..16))
        MAX-ACCESS read-write
        STATUS current
        DESCRIPTION
            "optixPatchPkgDelVer"
        ::= { optixPatchPkgDel 1 }

    -- 1.3.6.1.4.1.2011.2.25.3.40.3.15.2
    optixPatchPkgDelActionOption OBJECT-TYPE
        SYNTAX INTEGER
        {
            delbackpkg(1),
            keepbackpkg(2),
            mem(3),
            file(4),
            pkg(5),
            idle(6),
            null(7)
        }
        MAX-ACCESS read-write
        STATUS current
        DESCRIPTION
            "optixPatchPkgDelActionOption"
        ::= { optixPatchPkgDel 2 }

    -- 1.3.6.1.4.1.2011.2.25.3.40.3.16
    optixPatchPkgRollback OBJECT IDENTIFIER ::= { optixGlobalSftm 16 }

    -- 1.3.6.1.4.1.2011.2.25.3.40.3.16.1
    optixPatchPkgRollbackVer OBJECT-TYPE
        SYNTAX OCTET STRING (SIZE(0..16))
        MAX-ACCESS read-write
        STATUS current
        DESCRIPTION
            "optixPatchPkgRollbackVer"
        ::= { optixPatchPkgRollback 1 }

    -- 1.3.6.1.4.1.2011.2.25.3.40.3.16.2
    optixPatchRollbackActionOption OBJECT-TYPE
        SYNTAX INTEGER
        {
            delbackpkg(1),
            keepbackpkg(2),
            mem(3),
            file(4),
            pkg(5),
            idle(6),
            null(7)
        }
        MAX-ACCESS read-write
        STATUS current
        DESCRIPTION
            "optixPatchRollbackActionOption"
        ::= { optixPatchPkgRollback 2 }

    -- 1.3.6.1.4.1.2011.2.25.3.40.3.17
    optixSftmSignature OBJECT IDENTIFIER ::= { optixGlobalSftm 17 }

    -- 1.3.6.1.4.1.2011.2.25.3.40.3.17.1
    optixSftmSignatureSwitch OBJECT-TYPE
        SYNTAX INTEGER
        {
            disable(0),
            enable(1)
        }
        MAX-ACCESS read-write
        STATUS current
        DESCRIPTION
            "optixSignatureSwitch"
        ::= { optixSftmSignature 1 }

    -- 1.3.6.1.4.1.2011.2.25.3.40.3.18
    optixSftmRefresh OBJECT IDENTIFIER ::= { optixGlobalSftm 18 }

    -- 1.3.6.1.4.1.2011.2.25.3.40.3.18.1
    optixSftmRefreshCrl OBJECT-TYPE
        SYNTAX OCTET STRING (SIZE(0..16))
        MAX-ACCESS read-write
        STATUS current
        DESCRIPTION
            "optixRefreshCrl"
        ::= { optixSftmRefresh 1 }

    -- 1.3.6.1.4.1.2011.2.25.3.40.3.19
    optixSftmCfcard OBJECT IDENTIFIER ::= { optixGlobalSftm 19 }

    -- 1.3.6.1.4.1.2011.2.25.3.40.3.19.1
    optixSftmCfcardSign OBJECT-TYPE
        SYNTAX INTEGER
        {
            disable(0),
            enable(1)
        }
        MAX-ACCESS read-write
        STATUS current
        DESCRIPTION
            "optixSftmCfcardSign"
        ::= { optixSftmCfcard 1 }

    -- 1.3.6.1.4.1.2011.2.25.3.40.3.20
    optixSftmCRLInfo OBJECT IDENTIFIER ::= { optixGlobalSftm 20 }

    -- 1.3.6.1.4.1.2011.2.25.3.40.3.20.1
    optixSftmCRLInfoTable OBJECT-TYPE
        SYNTAX SEQUENCE OF OptixSftmCRLInfoEntry
        MAX-ACCESS not-accessible
        STATUS current
        DESCRIPTION
            "optixSftmCRLInfoTable"
        ::= { optixSftmCRLInfo 1 }

    -- 1.3.6.1.4.1.2011.2.25.3.40.3.20.1.1
    optixSftmCRLInfoEntry OBJECT-TYPE
        SYNTAX OptixSftmCRLInfoEntry
        MAX-ACCESS not-accessible
        STATUS current
        DESCRIPTION
            "optixSftmCRLInfoEntry"
        INDEX{ optixSftmCRLInfoType }
        ::= { optixSftmCRLInfoTable 1 }

    OptixSftmCRLInfoEntry ::=
        SEQUENCE {
            optixSftmCRLInfoType
                INTEGER,
            optixSftmCRLInfoResult
                OCTET STRING
        }

    -- 1.3.6.1.4.1.2011.2.25.3.40.3.20.1.1.1
    optixSftmCRLInfoType OBJECT-TYPE
        SYNTAX INTEGER
        {
            all(0),
            newest(1)
        }
        MAX-ACCESS not-accessible
        STATUS current
        DESCRIPTION
            "optixSftmCRLInfoType"
        ::= { optixSftmCRLInfoEntry 1 }

    -- 1.3.6.1.4.1.2011.2.25.3.40.3.20.1.1.2
    optixSftmCRLInfoResult OBJECT-TYPE
        SYNTAX OCTET STRING (SIZE(0..4620))
        MAX-ACCESS read-only
        STATUS current
        DESCRIPTION
            "optixSftmCRLInfoResult"
        ::= { optixSftmCRLInfoEntry 2 }

END
