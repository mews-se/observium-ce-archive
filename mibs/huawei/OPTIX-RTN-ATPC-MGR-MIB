-- OPTIX-RTN-ATPC-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-ATPC-MGR-MIB DEFINITIONS ::= BEGIN
    IMPORTS
        OBJECT-GROUP,MODULE-COMPLIANCE
            FROM SNMPv2-CONF
        Integer32,Unsigned32,OBJECT-TYPE,MODULE-IDENTITY
            FROM SNMPv2-SMI
        optixProvisionRtn
            FROM OPTIX-OID-MIB
        OPTIXRtnEnableStateType
            FROM OPTIX-RTN-GENNERAL-MIB
        optixRtnBoardID,optixRtnSubCardID,optixRtnPortID
            FROM OPTIX-RTN-IFBOARD-ATTRIB-MIB
        ;

    optixRtnATPCMgr MODULE-IDENTITY
        LAST-UPDATED "201204160000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query parameters for the ATPC function of IF boards, including the ATPC status, step, and threshold."
        REVISION "201204160000Z"
        DESCRIPTION
            "The initial revision of this MIB module1."
        ::={ optixProvisionRtn 1 }

    -- 1.3.6.1.4.1.2011.2.25.4.40.1.10
    optixISBoardATPCParameter OBJECT IDENTIFIER ::= { optixRtnATPCMgr 10 }

    -- 1.3.6.1.4.1.2011.2.25.4.40.1.10.1
    optixRtnIFATPCParameterTable OBJECT-TYPE
        SYNTAX SEQUENCE OF OptixRtnIFATPCParameterEntry
        MAX-ACCESS not-accessible
        STATUS current
        DESCRIPTION
            "Describes the ATPC attributes of an IF board, including the ATPC adjustment step and thresholds."
        ::= { optixISBoardATPCParameter 1 }

    -- 1.3.6.1.4.1.2011.2.25.4.40.1.10.1.1
    optixRtnIFATPCParameterEntry OBJECT-TYPE
        SYNTAX OptixRtnIFATPCParameterEntry
        MAX-ACCESS not-accessible
        STATUS current
        DESCRIPTION
            "Indicates the ATPC attribute entry for an IF board."
        INDEX{ optixRtnBoardID,optixRtnSubCardID,optixRtnPortID }
        ::= { optixRtnIFATPCParameterTable 1 }

    OptixRtnIFATPCParameterEntry ::=
        SEQUENCE {
            optixRtnIFATPCEnableState
                OPTIXRtnEnableStateType,
            optixRtnIFATPCStep
                Unsigned32,
            optixRtnIFATPCHighThreshold
                Integer32,
            optixRtnIFATPCLowThreshold
                Integer32,
            optixRtnIFATPCAutoThEnableState
                OPTIXRtnEnableStateType,
            optixRtnIFATPCCurrHighThreshold
                Integer32,
            optixRtnIFATPCCurrLowThreshold
                Integer32,
	    optixRtnIFATPCAutoThInfo
	    	OCTET STRING
        }

    -- 1.3.6.1.4.1.2011.2.25.4.40.1.10.1.1.1
    optixRtnIFATPCEnableState OBJECT-TYPE
        SYNTAX OPTIXRtnEnableStateType
        MAX-ACCESS read-write
        STATUS current
        DESCRIPTION
            "Indicates whether the ATPC function is enabled. Values: 0: disabled 1: enabled"
        DEFVAL{ 0 }
        ::= { optixRtnIFATPCParameterEntry 1 }

    -- 1.3.6.1.4.1.2011.2.25.4.40.1.10.1.1.2
    optixRtnIFATPCStep OBJECT-TYPE
        SYNTAX Unsigned32
        MAX-ACCESS read-write
        STATUS current
        DESCRIPTION
            "Indicates the ATPC adjustment step. The parameter refers to every increase or decrease in the ODU transmit power. Value range: 10 to 50"
        DEFVAL{ 20 }
        ::= { optixRtnIFATPCParameterEntry 2 }

    -- 1.3.6.1.4.1.2011.2.25.4.40.1.10.1.1.3
    optixRtnIFATPCHighThreshold OBJECT-TYPE
        SYNTAX Integer32
        MAX-ACCESS read-write
        STATUS current
        DESCRIPTION
            "Indicates the ATPC adjustment upper threshold. When the received signal level (RSL) exceeds the upper threshold, the transmitter automatically adjusts its transmit power. Signed type Value range: -850 to -200 Unit: 0.1 dBm"
        DEFVAL{ -450 }
        ::= { optixRtnIFATPCParameterEntry 3 }

    -- 1.3.6.1.4.1.2011.2.25.4.40.1.10.1.1.4
    optixRtnIFATPCLowThreshold OBJECT-TYPE
        SYNTAX Integer32
        MAX-ACCESS read-write
        STATUS current
        DESCRIPTION
            "Indicates the ATPC adjustment lower threshold. When the RSL is less than the lower threshold, the transmitter automatically adjusts its transmit power. Signed int type Value range: -900.0 to -250.0 Unit: 0.1 dBm"
        DEFVAL{ -700 }
        ::= { optixRtnIFATPCParameterEntry 4 }

    -- 1.3.6.1.4.1.2011.2.25.4.40.1.10.1.1.5
    optixRtnIFATPCAutoThEnableState OBJECT-TYPE
        SYNTAX OPTIXRtnEnableStateType
        MAX-ACCESS read-write
        STATUS current
        DESCRIPTION
            "Indicates whether ATPC automatic threshold configuration is enabled. The ATPC function enables the transmit power of a transmitter to automatically trace the change of the RSL at the receive end within the ATPC control range. When the function is enabled, the manually set ATPC upper and lower thresholds are invalid. The equipment automatically uses the preset ATPC upper and lower thresholds based on the working mode of the IF board. When the function is disabled, the manually set ATPC upper and lower thresholds are used. Values: 0: disabled 1: enabled"
        DEFVAL{ 0 }
        ::= { optixRtnIFATPCParameterEntry 5 }

    -- 1.3.6.1.4.1.2011.2.25.4.40.1.10.1.1.6
    optixRtnIFATPCCurrHighThreshold OBJECT-TYPE
        SYNTAX Integer32
        MAX-ACCESS read-only
        STATUS current
        DESCRIPTION
            "Indicates the ATPC automatic upper threshold. Signed int type Value range: -900.0 to -250.0 Unit: 0.1 dBm"
        ::= { optixRtnIFATPCParameterEntry 6 }

    -- 1.3.6.1.4.1.2011.2.25.4.40.1.10.1.1.7
    optixRtnIFATPCCurrLowThreshold OBJECT-TYPE
        SYNTAX Integer32
        MAX-ACCESS read-only
        STATUS current
        DESCRIPTION
            "Indicates the ATPC automatic lower threshold. Signed int type Value range: -900.0 to -250.0 Unit: 0.1 dBm"
        ::= { optixRtnIFATPCParameterEntry 7 }

    -- 1.3.6.1.4.1.2011.2.25.4.40.1.10.1.1.8
    optixRtnIFATPCAutoThInfo OBJECT-TYPE
        SYNTAX OCTET STRING
        MAX-ACCESS read-only
        STATUS current
        DESCRIPTION
            "Indicates cascading port information of ATPC Auto Threshold"
        ::= { optixRtnIFATPCParameterEntry 8 }

    -- 1.3.6.1.4.1.2011.2.25.4.40.1.10.2
    optixRtnIFATPCHistoryParameterTable OBJECT-TYPE
        SYNTAX SEQUENCE OF OptixRtnIFATPCHistoryParameterEntry
        MAX-ACCESS not-accessible
        STATUS current
        DESCRIPTION
            "Describes the ATPC attributes of an IF board, including the ATPC adjustment step and thresholds."
        ::= { optixISBoardATPCParameter 2 }

    -- 1.3.6.1.4.1.2011.2.25.4.40.1.10.2.1
    optixRtnIFATPCHistoryParameterEntry OBJECT-TYPE
        SYNTAX OptixRtnIFATPCHistoryParameterEntry
        MAX-ACCESS not-accessible
        STATUS current
        DESCRIPTION
            "Indicates the ATPC attribute entry for an IF board."
        INDEX{ optixRtnBoardID,optixRtnSubCardID,optixRtnPortID }
        ::= { optixRtnIFATPCHistoryParameterTable 1 }

    OptixRtnIFATPCHistoryParameterEntry ::=
        SEQUENCE {
            optixRtnIFATPCHistoryEventId
                Unsigned32,
            optixRtnIFATPCHistoryTime
                OCTET STRING,
            optixRtnIFATPCHistoryDirection
                INTEGER,
            optixRtnIFATPCHistoryType
                INTEGER,
            optixRtnIFATPCHistoryTxPower
                Integer32,
            optixRtnIFATPCHistoryRxPower
                Integer32
        }

    -- 1.3.6.1.4.1.2011.2.25.4.40.1.10.2.1.4
    optixRtnIFATPCHistoryEventId OBJECT-TYPE
        SYNTAX Unsigned32
        MAX-ACCESS not-accessible
        STATUS current
        DESCRIPTION
            "Indicates whether the ATPC function is enabled. Values: 0: disabled 1: enabled"
        DEFVAL{ 0 }
        ::= { optixRtnIFATPCHistoryParameterEntry 4 }

    -- 1.3.6.1.4.1.2011.2.25.4.40.1.10.2.1.5
    optixRtnIFATPCHistoryTime OBJECT-TYPE
        SYNTAX OCTET STRING
        MAX-ACCESS read-only
        STATUS current
        DESCRIPTION
            "Indicates the ATPC adjustment history"
        ::= { optixRtnIFATPCHistoryParameterEntry 5 }

    -- 1.3.6.1.4.1.2011.2.25.4.40.1.10.2.1.6
    optixRtnIFATPCHistoryDirection OBJECT-TYPE
        SYNTAX INTEGER
        {
            positive(0),
            negative(1)
        }
        MAX-ACCESS read-only
        STATUS current
        DESCRIPTION
            "Indicates the ATPC adjustment direction. Values: 0-increment, 1-decrement"
        DEFVAL{ 7 }
        ::= { optixRtnIFATPCHistoryParameterEntry 6 }

    -- 1.3.6.1.4.1.2011.2.25.4.40.1.10.2.1.7
    optixRtnIFATPCHistoryType OBJECT-TYPE
        SYNTAX INTEGER
        {
            require(1),
            response(2)
        }
        MAX-ACCESS read-only
        STATUS current
        DESCRIPTION
            "Indicates the ATPC adjustment action. Values: 1-request, 2-respond"
        DEFVAL{ 8 }
        ::= { optixRtnIFATPCHistoryParameterEntry 7 }

    -- 1.3.6.1.4.1.2011.2.25.4.40.1.10.2.1.8
    optixRtnIFATPCHistoryTxPower OBJECT-TYPE
        SYNTAX Integer32
        MAX-ACCESS read-only
        STATUS current
        DESCRIPTION
            "Indicates the ATPC transmit power (a signed number in the unit of 0.1 dBm)."
        DEFVAL{ 9 }
        ::= { optixRtnIFATPCHistoryParameterEntry 8 }

    -- 1.3.6.1.4.1.2011.2.25.4.40.1.10.2.1.9
    optixRtnIFATPCHistoryRxPower OBJECT-TYPE
        SYNTAX Integer32
        MAX-ACCESS read-only
        STATUS current
        DESCRIPTION
            "Indicates the ATPC receive power."
        DEFVAL{ 10 }
        ::= { optixRtnIFATPCHistoryParameterEntry 9 }

END
