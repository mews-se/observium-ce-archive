-- OPTIX-L2-IGMP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-L2-IGMP-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,IpAddress,NOTIFICATION-TYPE,Counter64
            FROM SNMPv2-SMI
        RowStatus,MacAddress,DateAndTime
            FROM SNMPv2-TC
        ;

    optixL2Igmp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the IGMP configuration information of device"
        REVISION "201204200000Z"
        DESCRIPTION
            "The initial revision of this MIB module1."
        ::={ optixProvisionPtn 38 }

    -- 1.3.6.1.4.1.2011.2.25.4.50.38.1
    optixL2IgmpGroup OBJECT IDENTIFIER ::= { optixL2Igmp 1 }

    -- 1.3.6.1.4.1.2011.2.25.4.50.38.1.1
    optixL2IgmpTable OBJECT-TYPE
        SYNTAX SEQUENCE OF OptixL2IgmpEntry
        MAX-ACCESS not-accessible
        STATUS current
        DESCRIPTION
            "This table describes the basic IGMP configurations."
        ::= { optixL2IgmpGroup 1 }

    -- 1.3.6.1.4.1.2011.2.25.4.50.38.1.1.1
    optixL2IgmpEntry OBJECT-TYPE
        SYNTAX OptixL2IgmpEntry
        MAX-ACCESS not-accessible
        STATUS current
        DESCRIPTION
            "This entry describes the basic IGMP configurations."
        INDEX{ optixL2IgmpServiceIndex }
        ::= { optixL2IgmpTable 1 }

    OptixL2IgmpEntry ::=
        SEQUENCE {
            optixL2IgmpServiceIndex
                Unsigned32,
            optixL2IgmpEnableState
                INTEGER,
            optixL2IgmpRouterAgeTime
                Unsigned32,
            optixL2IgmpMemberNoResponseTimes
                Unsigned32,
            optixL2IgmpMaxGroupNum
                Unsigned32,
            optixL2IgmpMaxMemberNum
                Unsigned32,
            optixL2IgmpRealGroupNum
                Unsigned32,
            optixL2IgmpRealMemberNum
                Unsigned32,
            optixL2IgmpAlmThMin
                Unsigned32,
            optixL2IgmpAlmThMax
                Unsigned32
        }

    -- 1.3.6.1.4.1.2011.2.25.4.50.38.1.1.1.1
    optixL2IgmpServiceIndex OBJECT-TYPE
        SYNTAX Unsigned32
        MAX-ACCESS read-only
        STATUS current
        DESCRIPTION
            "This object indicates the IGMP service index. Value range: 1 to 4294967294."
        ::= { optixL2IgmpEntry 1 }

    -- 1.3.6.1.4.1.2011.2.25.4.50.38.1.1.1.2
    optixL2IgmpEnableState OBJECT-TYPE
        SYNTAX INTEGER
        {
            disable(0),
            enable(1)
        }
        MAX-ACCESS read-write
        STATUS current
        DESCRIPTION
            "This object indicates the enable status of the IGMP snooping function. 0: disable, 1: enable"
        ::= { optixL2IgmpEntry 2 }

    -- 1.3.6.1.4.1.2011.2.25.4.50.38.1.1.1.3
    optixL2IgmpRouterAgeTime OBJECT-TYPE
        SYNTAX Unsigned32
        MAX-ACCESS read-write
        STATUS current
        DESCRIPTION
            "This object indicates the aging time of the multicast router port. Value range: 1 to 120 (unit: minute). The default value is 8."
        ::= { optixL2IgmpEntry 3 }

    -- 1.3.6.1.4.1.2011.2.25.4.50.38.1.1.1.4
    optixL2IgmpMemberNoResponseTimes OBJECT-TYPE
        SYNTAX Unsigned32
        MAX-ACCESS read-write
        STATUS current
        DESCRIPTION
            "This object indicates the maximum no response times of the multicast member. Value range: 1 to 4. The default value is 3."
        ::= { optixL2IgmpEntry 4 }

    -- 1.3.6.1.4.1.2011.2.25.4.50.38.1.1.1.5
    optixL2IgmpMaxGroupNum OBJECT-TYPE
        SYNTAX Unsigned32
        MAX-ACCESS read-write
        STATUS current
        DESCRIPTION
            "This object indicates the maximum number of available multicast groups. Value range for RTN equipment: 0 to 512."
        ::= { optixL2IgmpEntry 5 }

    -- 1.3.6.1.4.1.2011.2.25.4.50.38.1.1.1.6
    optixL2IgmpMaxMemberNum OBJECT-TYPE
        SYNTAX Unsigned32
        MAX-ACCESS read-write
        STATUS current
        DESCRIPTION
            "This object indicates the maximum number of available multicast members. Value range for RTN equipment: 0 to 1024."
        ::= { optixL2IgmpEntry 6 }

    -- 1.3.6.1.4.1.2011.2.25.4.50.38.1.1.1.7
    optixL2IgmpRealGroupNum OBJECT-TYPE
        SYNTAX Unsigned32
        MAX-ACCESS read-only
        STATUS current
        DESCRIPTION
            "This object indicates the number of actually used multicast groups. Value range for RTN equipment: 0 to 512."
        ::= { optixL2IgmpEntry 7 }

    -- 1.3.6.1.4.1.2011.2.25.4.50.38.1.1.1.8
    optixL2IgmpRealMemberNum OBJECT-TYPE
        SYNTAX Unsigned32
        MAX-ACCESS read-only
        STATUS current
        DESCRIPTION
            "This object indicates the number of actually used multicast members. Value range for RTN equipment: 0 to 1024."
        ::= { optixL2IgmpEntry 8 }

    -- 1.3.6.1.4.1.2011.2.25.4.50.38.1.1.1.9
    optixL2IgmpAlmThMin OBJECT-TYPE
        SYNTAX Unsigned32
        MAX-ACCESS read-write
        STATUS current
        DESCRIPTION
            "This parameter indicates the lower threshold for IGMP service alarms. The lower threshold must be smaller than the upper one. Value range: 60-100; default value: 80; unit: %"
        ::= { optixL2IgmpEntry 9 }

    -- 1.3.6.1.4.1.2011.2.25.4.50.38.1.1.1.10
    optixL2IgmpAlmThMax OBJECT-TYPE
        SYNTAX Unsigned32
        MAX-ACCESS read-write
        STATUS current
        DESCRIPTION
            "This parameter indicates the upper threshold for IGMP service alarms. Value range: 80-100; default value: 100; unit: %"
        ::= { optixL2IgmpEntry 10 }

    -- 1.3.6.1.4.1.2011.2.25.4.50.38.1.2
    optixL2IgmpRouterPortTable OBJECT-TYPE
        SYNTAX SEQUENCE OF OptixL2IgmpRouterPortEntry
        MAX-ACCESS not-accessible
        STATUS current
        DESCRIPTION
            "This table describes the basic configurations of the actual multicast router port."
        ::= { optixL2IgmpGroup 2 }

    -- 1.3.6.1.4.1.2011.2.25.4.50.38.1.2.1
    optixL2IgmpRouterPortEntry OBJECT-TYPE
        SYNTAX OptixL2IgmpRouterPortEntry
        MAX-ACCESS not-accessible
        STATUS current
        DESCRIPTION
            "This entry describes the basic configurations of the actual multicast router port."
        INDEX{ optixL2IgmpServiceIndex,optixL2IgmpVlanId,optixL2IgmpRouterPortType,optixL2IgmpRouterPortId }
        ::= { optixL2IgmpRouterPortTable 1 }

    OptixL2IgmpRouterPortEntry ::=
        SEQUENCE {
            optixL2IgmpVlanId
                Unsigned32,
            optixL2IgmpRouterPortType
                INTEGER,
            optixL2IgmpRouterPortId
                Unsigned32,
            optixL2IgmpRouterPortNum
                Unsigned32,
            optixL2IgmpRouterPortState
                INTEGER,
            optixL2IgmpRouterCreateTime
                DateAndTime,
            optixL2IgmpRouterCentSec
                Unsigned32,
            optixL2IgmpRouterRemainTime
                Unsigned32,
            optixL2IgmpRouterRowStatus
                RowStatus
        }

    -- 1.3.6.1.4.1.2011.2.25.4.50.38.1.2.1.1
    optixL2IgmpVlanId OBJECT-TYPE
        SYNTAX Unsigned32
        MAX-ACCESS not-accessible
        STATUS current
        DESCRIPTION
            "This object indicates the VLAN ID. Value range: 0 to 4094."
        ::= { optixL2IgmpRouterPortEntry 1 }

    -- 1.3.6.1.4.1.2011.2.25.4.50.38.1.2.1.2
    optixL2IgmpRouterPortType OBJECT-TYPE
        SYNTAX INTEGER
        {
            vuni(1),
            vnni(2)
        }
        MAX-ACCESS not-accessible
        STATUS current
        DESCRIPTION
            "This object indicates the multicast router port type. 1: V-UNI, 2: V-NNI"
        ::= { optixL2IgmpRouterPortEntry 2 }

    -- 1.3.6.1.4.1.2011.2.25.4.50.38.1.2.1.3
    optixL2IgmpRouterPortId OBJECT-TYPE
        SYNTAX Unsigned32
        MAX-ACCESS not-accessible
        STATUS current
        DESCRIPTION
            "This object indicates the multicast router port ID. Value range: 0 to 65535."
        ::= { optixL2IgmpRouterPortEntry 3 }

    -- 1.3.6.1.4.1.2011.2.25.4.50.38.1.2.1.4
    optixL2IgmpRouterPortNum OBJECT-TYPE
        SYNTAX Unsigned32
        MAX-ACCESS read-only
        STATUS current
        DESCRIPTION
            "This object indicates the number of multicast router ports. Value range: 0 to 65534."
        ::= { optixL2IgmpRouterPortEntry 4 }

    -- 1.3.6.1.4.1.2011.2.25.4.50.38.1.2.1.5
    optixL2IgmpRouterPortState OBJECT-TYPE
        SYNTAX INTEGER
        {
            dynamic(0),
            static(1)
        }
        MAX-ACCESS read-only
        STATUS current
        DESCRIPTION
            "This object indicates the multicast router port status. 0: dynamic, 1: static"
        ::= { optixL2IgmpRouterPortEntry 5 }

    -- 1.3.6.1.4.1.2011.2.25.4.50.38.1.2.1.6
    optixL2IgmpRouterCreateTime OBJECT-TYPE
        SYNTAX DateAndTime
        MAX-ACCESS read-only
        STATUS current
        DESCRIPTION
            "This object indicates the creation time of the multicast router port."
        ::= { optixL2IgmpRouterPortEntry 6 }

    -- 1.3.6.1.4.1.2011.2.25.4.50.38.1.2.1.7
    optixL2IgmpRouterCentSec OBJECT-TYPE
        SYNTAX Unsigned32
        MAX-ACCESS read-only
        STATUS current
        DESCRIPTION
            "This object indicates the multicast router port centisecond."
        ::= { optixL2IgmpRouterPortEntry 7 }

    -- 1.3.6.1.4.1.2011.2.25.4.50.38.1.2.1.8
    optixL2IgmpRouterRemainTime OBJECT-TYPE
        SYNTAX Unsigned32
        MAX-ACCESS read-only
        STATUS current
        DESCRIPTION
            "This object indicates the remaining aging time of the multicast router port. Value range: 1 to 120 (unit: minute)."
        ::= { optixL2IgmpRouterPortEntry 8 }

    -- 1.3.6.1.4.1.2011.2.25.4.50.38.1.2.1.255
    optixL2IgmpRouterRowStatus OBJECT-TYPE
        SYNTAX RowStatus
        MAX-ACCESS read-create
        STATUS current
        DESCRIPTION
            "This object indicates the row status of the multicast router port."
        ::= { optixL2IgmpRouterPortEntry 255 }

    -- 1.3.6.1.4.1.2011.2.25.4.50.38.1.3
    optixL2IgmpMemPortTable OBJECT-TYPE
        SYNTAX SEQUENCE OF OptixL2IgmpMemPortEntry
        MAX-ACCESS not-accessible
        STATUS current
        DESCRIPTION
            "This table describes the basic configurations of actual multicast member ports."
        ::= { optixL2IgmpGroup 3 }

    -- 1.3.6.1.4.1.2011.2.25.4.50.38.1.3.1
    optixL2IgmpMemPortEntry OBJECT-TYPE
        SYNTAX OptixL2IgmpMemPortEntry
        MAX-ACCESS not-accessible
        STATUS current
        DESCRIPTION
            "This entry describes the basic configurations of actual multicast member ports."
        INDEX{ optixL2IgmpServiceIndex,optixL2IgmpVlanId,optixL2IgmpMemPortId,optixL2IgmpMemPortType,optixL2IgmpMacAddress }
        ::= { optixL2IgmpMemPortTable 1 }

    OptixL2IgmpMemPortEntry ::=
        SEQUENCE {
            optixL2IgmpMemPortId
                Unsigned32,
            optixL2IgmpMemPortType
                INTEGER,
            optixL2IgmpMacAddress
                MacAddress,
            optixL2IgmpGroupType
                INTEGER,
            optixL2IgmpMemCreateTime
                DateAndTime,
            optixL2IgmpMemCentSec
                Unsigned32,
            optixL2IgmpMemRemainTime
                Unsigned32,
            optixL2IgmpMemGroupNum
                Unsigned32,
            optixL2IgmpMemGroupCreateTime
                DateAndTime,
            optixL2IgmpMemGroupCentSec
                Unsigned32,
            optixL2IgmpMemPortNum
                Unsigned32,
            optixL2IgmpMemPortRowStatus
                RowStatus
        }

    -- 1.3.6.1.4.1.2011.2.25.4.50.38.1.3.1.1
    optixL2IgmpMemPortId OBJECT-TYPE
        SYNTAX Unsigned32
        MAX-ACCESS not-accessible
        STATUS current
        DESCRIPTION
            "This object indicates the multicast member port number. Value range: 0 to 65535."
        ::= { optixL2IgmpMemPortEntry 1 }

    -- 1.3.6.1.4.1.2011.2.25.4.50.38.1.3.1.2
    optixL2IgmpMemPortType OBJECT-TYPE
        SYNTAX INTEGER
        {
            alltype(0),
            vuni(1),
            vnni(2)
        }
        MAX-ACCESS not-accessible
        STATUS current
        DESCRIPTION
            "This object indicates the multicast member port type. 1: V-UNI, 2: V-NNI"
        ::= { optixL2IgmpMemPortEntry 2 }

    -- 1.3.6.1.4.1.2011.2.25.4.50.38.1.3.1.3
    optixL2IgmpMacAddress OBJECT-TYPE
        SYNTAX MacAddress
        MAX-ACCESS not-accessible
        STATUS current
        DESCRIPTION
            "This object indicates the MAC address of the multicast member port."
        ::= { optixL2IgmpMemPortEntry 3 }

    -- 1.3.6.1.4.1.2011.2.25.4.50.38.1.3.1.4
    optixL2IgmpGroupType OBJECT-TYPE
        SYNTAX INTEGER
        {
            dynamic(0),
            static(1)
        }
        MAX-ACCESS read-only
        STATUS current
        DESCRIPTION
            "This object indicates the multicast group type. 0: dynamic, 1: static"
        ::= { optixL2IgmpMemPortEntry 4 }

    -- 1.3.6.1.4.1.2011.2.25.4.50.38.1.3.1.6
    optixL2IgmpMemCreateTime OBJECT-TYPE
        SYNTAX DateAndTime
        MAX-ACCESS read-only
        STATUS current
        DESCRIPTION
            "This object indicates the creation time of the multicast member port."
        ::= { optixL2IgmpMemPortEntry 6 }

    -- 1.3.6.1.4.1.2011.2.25.4.50.38.1.3.1.7
    optixL2IgmpMemCentSec OBJECT-TYPE
        SYNTAX Unsigned32
        MAX-ACCESS read-only
        STATUS current
        DESCRIPTION
            "This object indicates the multicast member port centisecond."
        ::= { optixL2IgmpMemPortEntry 7 }

    -- 1.3.6.1.4.1.2011.2.25.4.50.38.1.3.1.8
    optixL2IgmpMemRemainTime OBJECT-TYPE
        SYNTAX Unsigned32
        MAX-ACCESS read-only
        STATUS current
        DESCRIPTION
            "This object indicates the remaining aging time of the multicast member port. Value range: 1 to 120 (unit: minute)."
        ::= { optixL2IgmpMemPortEntry 8 }

    -- 1.3.6.1.4.1.2011.2.25.4.50.38.1.3.1.9
    optixL2IgmpMemGroupNum OBJECT-TYPE
        SYNTAX Unsigned32
        MAX-ACCESS read-only
        STATUS current
        DESCRIPTION
            "This object indicates the number of multicast groups. Value range for RTN equipment: 0 to 512."
        ::= { optixL2IgmpMemPortEntry 9 }

    -- 1.3.6.1.4.1.2011.2.25.4.50.38.1.3.1.10
    optixL2IgmpMemGroupCreateTime OBJECT-TYPE
        SYNTAX DateAndTime
        MAX-ACCESS read-only
        STATUS current
        DESCRIPTION
            "This object indicates the creation time of the group."
        ::= { optixL2IgmpMemPortEntry 10 }

    -- 1.3.6.1.4.1.2011.2.25.4.50.38.1.3.1.11
    optixL2IgmpMemGroupCentSec OBJECT-TYPE
        SYNTAX Unsigned32
        MAX-ACCESS read-only
        STATUS current
        DESCRIPTION
            "This object indicates the creation millisecond of the group."
        ::= { optixL2IgmpMemPortEntry 11 }

    -- 1.3.6.1.4.1.2011.2.25.4.50.38.1.3.1.12
    optixL2IgmpMemPortNum OBJECT-TYPE
        SYNTAX Unsigned32
        MAX-ACCESS read-only
        STATUS current
        DESCRIPTION
            "This object indicates the port number of multicast groups. Value range for RTN equipment: 0 to 1024."
        ::= { optixL2IgmpMemPortEntry 12 }

    -- 1.3.6.1.4.1.2011.2.25.4.50.38.1.3.1.255
    optixL2IgmpMemPortRowStatus OBJECT-TYPE
        SYNTAX RowStatus
        MAX-ACCESS read-create
        STATUS current
        DESCRIPTION
            "This object indicates the row status ofthe multicast member port."
        ::= { optixL2IgmpMemPortEntry 255 }

    -- 1.3.6.1.4.1.2011.2.25.4.50.38.1.4
    optixL2IgmpMessageTable OBJECT-TYPE
        SYNTAX SEQUENCE OF OptixL2IgmpMessageEntry
        MAX-ACCESS not-accessible
        STATUS current
        DESCRIPTION
            "This table describes the basic configurations of IGMP protocol packets."
        ::= { optixL2IgmpGroup 4 }

    -- 1.3.6.1.4.1.2011.2.25.4.50.38.1.4.1
    optixL2IgmpMessageEntry OBJECT-TYPE
        SYNTAX OptixL2IgmpMessageEntry
        MAX-ACCESS not-accessible
        STATUS current
        DESCRIPTION
            "This entry describes the basic configurations of IGMP protocol packets."
        INDEX{ optixL2IgmpServiceIndex,optixL2IgmpVlanId,opitxL2IgmpPortType,optixL2IgmpPortId }
        ::= { optixL2IgmpMessageTable 1 }

    OptixL2IgmpMessageEntry ::=
        SEQUENCE {
            opitxL2IgmpPortType
                INTEGER,
            optixL2IgmpPortId
                Unsigned32,
            optixL2IgmpquicklvEnableState
                INTEGER,
            optixL2IgmpMessageState
                INTEGER,
            optixL2IgmpV1ReportNum
                Counter64,
            optixL2IgmpV2ReportNum
                Counter64,
            optixL2IgmpV3ReportNum
                Counter64,
            optixL2IgmpLeaveMessageNum
                Counter64,
            optixL2IgmpV1QueryNume
                Counter64,
            optixL2IgmpV2QueryNume
                Counter64,
            optixL2IgmpV3QueryNume
                Counter64,
            optixL2IgmpUnknowNum
                Counter64,
            optixL2IgmpLostNum
                Counter64
        }

    -- 1.3.6.1.4.1.2011.2.25.4.50.38.1.4.1.1
    opitxL2IgmpPortType OBJECT-TYPE
        SYNTAX INTEGER
        {
            vuni(1),
            vnni(2)
        }
        MAX-ACCESS not-accessible
        STATUS current
        DESCRIPTION
            "This object indicates the port type. 1:V-UNI 2:V-NNI"
        ::= { optixL2IgmpMessageEntry 1 }

    -- 1.3.6.1.4.1.2011.2.25.4.50.38.1.4.1.2
    optixL2IgmpPortId OBJECT-TYPE
        SYNTAX Unsigned32
        MAX-ACCESS not-accessible
        STATUS current
        DESCRIPTION
            "This object indicates the port number. Value range: 0 to 65535."
        ::= { optixL2IgmpMessageEntry 2 }

    -- 1.3.6.1.4.1.2011.2.25.4.50.38.1.4.1.3
    optixL2IgmpquicklvEnableState OBJECT-TYPE
        SYNTAX INTEGER
        {
            disable(0),
            enable(1)
        }
        MAX-ACCESS read-write
        STATUS current
        DESCRIPTION
            "This object indicates the enable status of the quick leave attribute of the multicast group member port. Value range: 0 to 65535."
        ::= { optixL2IgmpMessageEntry 3 }

    -- 1.3.6.1.4.1.2011.2.25.4.50.38.1.4.1.4
    optixL2IgmpMessageState OBJECT-TYPE
        SYNTAX INTEGER
        {
            clear(0),
            start(1),
            stop(2)
        }
        MAX-ACCESS read-write
        STATUS current
        DESCRIPTION
            "This object indicates the statistic status of received IGMPv1 member packets. 0: clear, 1: start, 2: stop"
        ::= { optixL2IgmpMessageEntry 4 }

    -- 1.3.6.1.4.1.2011.2.25.4.50.38.1.4.1.5
    optixL2IgmpV1ReportNum OBJECT-TYPE
        SYNTAX Counter64
        MAX-ACCESS read-only
        STATUS current
        DESCRIPTION
            "This object indicates the number of received IGMPv1 member report packets (64-bit)."
        ::= { optixL2IgmpMessageEntry 5 }

    -- 1.3.6.1.4.1.2011.2.25.4.50.38.1.4.1.6
    optixL2IgmpV2ReportNum OBJECT-TYPE
        SYNTAX Counter64
        MAX-ACCESS read-only
        STATUS current
        DESCRIPTION
            "This object indicates the number of received IGMPv2 member report packets (64-bit)."
        ::= { optixL2IgmpMessageEntry 6 }

    -- 1.3.6.1.4.1.2011.2.25.4.50.38.1.4.1.7
    optixL2IgmpV3ReportNum OBJECT-TYPE
        SYNTAX Counter64
        MAX-ACCESS read-only
        STATUS current
        DESCRIPTION
            "This object indicates the number of received IGMPv3 member report packets (64-bit)."
        ::= { optixL2IgmpMessageEntry 7 }

    -- 1.3.6.1.4.1.2011.2.25.4.50.38.1.4.1.8
    optixL2IgmpLeaveMessageNum OBJECT-TYPE
        SYNTAX Counter64
        MAX-ACCESS read-only
        STATUS current
        DESCRIPTION
            "This object indicates the number of received IGMP leave multicast grouppackets (64-bit)."
        ::= { optixL2IgmpMessageEntry 8 }

    -- 1.3.6.1.4.1.2011.2.25.4.50.38.1.4.1.9
    optixL2IgmpV1QueryNume OBJECT-TYPE
        SYNTAX Counter64
        MAX-ACCESS read-only
        STATUS current
        DESCRIPTION
            "This object indicates the number of received IGMPv1 query packets (64-bit)."
        ::= { optixL2IgmpMessageEntry 9 }

    -- 1.3.6.1.4.1.2011.2.25.4.50.38.1.4.1.10
    optixL2IgmpV2QueryNume OBJECT-TYPE
        SYNTAX Counter64
        MAX-ACCESS read-only
        STATUS current
        DESCRIPTION
            "This object indicates the number of received IGMPv2 query packets (64-bit)."
        ::= { optixL2IgmpMessageEntry 10 }

    -- 1.3.6.1.4.1.2011.2.25.4.50.38.1.4.1.11
    optixL2IgmpV3QueryNume OBJECT-TYPE
        SYNTAX Counter64
        MAX-ACCESS read-only
        STATUS current
        DESCRIPTION
            "This object indicates the number of received IGMP V3 query packets (64-bit)."
        ::= { optixL2IgmpMessageEntry 11 }

    -- 1.3.6.1.4.1.2011.2.25.4.50.38.1.4.1.12
    optixL2IgmpUnknowNum OBJECT-TYPE
        SYNTAX Counter64
        MAX-ACCESS read-only
        STATUS current
        DESCRIPTION
            "This object indicates the number of unknown IGMP packets (64-bit)."
        ::= { optixL2IgmpMessageEntry 12 }

    -- 1.3.6.1.4.1.2011.2.25.4.50.38.1.4.1.13
    optixL2IgmpLostNum OBJECT-TYPE
        SYNTAX Counter64
        MAX-ACCESS read-only
        STATUS current
        DESCRIPTION
            "This object indicates the dropped error IGMP packets (64-bit)."
        ::= { optixL2IgmpMessageEntry 13 }

    -- 1.3.6.1.4.1.2011.2.25.4.50.38.1.5
    optixL2IgmpGrpinfoTable OBJECT-TYPE
        SYNTAX SEQUENCE OF OptixL2IgmpGrpinfoEntry
        MAX-ACCESS not-accessible
        STATUS current
        DESCRIPTION
            "This table describes basic configurations of the specified multicast group."
        ::= { optixL2IgmpGroup 5 }

    -- 1.3.6.1.4.1.2011.2.25.4.50.38.1.5.1
    optixL2IgmpGrpinfoEntry OBJECT-TYPE
        SYNTAX OptixL2IgmpGrpinfoEntry
        MAX-ACCESS not-accessible
        STATUS current
        DESCRIPTION
            "This entry describes basic configurations of the specified multicast group."
        INDEX{ optixL2IgmpServiceIndex,optixL2IgmpVlanId,optixL2IgmpGrpinfoMacAddress,optixL2IgmpGrpinfoPortType,optixL2IgmpGrpinfoPortID,optixL2IgmpGrpinfoIgmpPortType }
        ::= { optixL2IgmpGrpinfoTable 1 }

    OptixL2IgmpGrpinfoEntry ::=
        SEQUENCE {
            optixL2IgmpGrpinfoMacAddress
                MacAddress,
            optixL2IgmpGrpinfoPortType
                INTEGER,
            optixL2IgmpGrpinfoPortID
                Unsigned32,
            optixL2IgmpGrpinfoIgmpPortType
                INTEGER,
            optixL2IgmpGrpinfoGroupType
                INTEGER,
            optixL2IgmpGrpinfoCreateTime
                DateAndTime,
            optixL2IgmpGrpinfoCentSec
                Unsigned32,
            optixL2IgmpGrpinfoPortNum
                Unsigned32,
            optixL2IgmpGrpinfoPortRemainTime
                Unsigned32
        }

    -- 1.3.6.1.4.1.2011.2.25.4.50.38.1.5.1.1
    optixL2IgmpGrpinfoMacAddress OBJECT-TYPE
        SYNTAX MacAddress
        MAX-ACCESS not-accessible
        STATUS current
        DESCRIPTION
            "This object indicates theMAC addressof the multicast group."
        ::= { optixL2IgmpGrpinfoEntry 1 }

    -- 1.3.6.1.4.1.2011.2.25.4.50.38.1.5.1.2
    optixL2IgmpGrpinfoPortType OBJECT-TYPE
        SYNTAX INTEGER
        {
            alltype(0),
            vuni(1),
            vnni(2)
        }
        MAX-ACCESS not-accessible
        STATUS current
        DESCRIPTION
            "This object indicates the port type. 1:V-UNI 2:V-NNI"
        ::= { optixL2IgmpGrpinfoEntry 2 }

    -- 1.3.6.1.4.1.2011.2.25.4.50.38.1.5.1.3
    optixL2IgmpGrpinfoPortID OBJECT-TYPE
        SYNTAX Unsigned32
        MAX-ACCESS not-accessible
        STATUS current
        DESCRIPTION
            "This object indicates the port number. Value range: 0 to 65535."
        ::= { optixL2IgmpGrpinfoEntry 3 }

    -- 1.3.6.1.4.1.2011.2.25.4.50.38.1.5.1.4
    optixL2IgmpGrpinfoIgmpPortType OBJECT-TYPE
        SYNTAX INTEGER
        {
            routeport(0),
            hostport(1)
        }
        MAX-ACCESS not-accessible
        STATUS current
        DESCRIPTION
            "This object indicates the port type of the multicast group. 0: routeport, 1: hostport"
        ::= { optixL2IgmpGrpinfoEntry 4 }

    -- 1.3.6.1.4.1.2011.2.25.4.50.38.1.5.1.5
    optixL2IgmpGrpinfoGroupType OBJECT-TYPE
        SYNTAX INTEGER
        {
            dynamic(0),
            static(1)
        }
        MAX-ACCESS read-only
        STATUS current
        DESCRIPTION
            "This object indicates the multicast group type. 0: dynamic, 1: static"
        ::= { optixL2IgmpGrpinfoEntry 5 }

    -- 1.3.6.1.4.1.2011.2.25.4.50.38.1.5.1.6
    optixL2IgmpGrpinfoCreateTime OBJECT-TYPE
        SYNTAX DateAndTime
        MAX-ACCESS read-only
        STATUS current
        DESCRIPTION
            "This object indicates the creation time of the multicast group."
        ::= { optixL2IgmpGrpinfoEntry 6 }

    -- 1.3.6.1.4.1.2011.2.25.4.50.38.1.5.1.7
    optixL2IgmpGrpinfoCentSec OBJECT-TYPE
        SYNTAX Unsigned32
        MAX-ACCESS read-only
        STATUS current
        DESCRIPTION
            "This object indicates the multicast group centisecond."
        ::= { optixL2IgmpGrpinfoEntry 7 }

    -- 1.3.6.1.4.1.2011.2.25.4.50.38.1.5.1.8
    optixL2IgmpGrpinfoPortNum OBJECT-TYPE
        SYNTAX Unsigned32
        MAX-ACCESS read-only
        STATUS current
        DESCRIPTION
            "This object indicates the number of multicast groups. Value range for RTN equipment: 0 to 512."
        ::= { optixL2IgmpGrpinfoEntry 8 }

    -- 1.3.6.1.4.1.2011.2.25.4.50.38.1.5.1.9
    optixL2IgmpGrpinfoPortRemainTime OBJECT-TYPE
        SYNTAX Unsigned32
        MAX-ACCESS read-only
        STATUS current
        DESCRIPTION
            "This object indicates theremaining agingtime of the multicast group. Value range: 1 to 120 (unit: minute)."
        ::= { optixL2IgmpGrpinfoEntry 9 }

    -- 1.3.6.1.4.1.2011.2.25.4.50.38.1.6
    optixL2IgmpMacAddresEvent OBJECT IDENTIFIER ::= { optixL2IgmpGroup 6 }

    -- 1.3.6.1.4.1.2011.2.25.4.50.38.1.6.1
    optixL2IgmpMacAddressUseOut NOTIFICATION-TYPE
        OBJECTS{ optixL2IgmpServiceIndex,optixL2IgmpRealGroupNum }
        STATUS current
        DESCRIPTION
            "This object is used to report the exhaustation event of multicast MAC address tables."
        ::= { optixL2IgmpMacAddresEvent 1 }

    -- 1.3.6.1.4.1.2011.2.25.4.50.38.1.6.2
    optixL2IgmpMacMemberUseOut NOTIFICATION-TYPE
        OBJECTS{ optixL2IgmpServiceIndex,optixL2IgmpRealMemberNum }
        STATUS current
        DESCRIPTION
            "This object is used to report the exhaustation event of multicast member tables."
        ::= { optixL2IgmpMacAddresEvent 2 }

    -- 1.3.6.1.4.1.2011.2.25.4.50.38.1.7
    optixL2IgmpRouterPortExTable OBJECT-TYPE
        SYNTAX SEQUENCE OF OptixL2IgmpRouterPortExEntry
        MAX-ACCESS not-accessible
        STATUS current
        DESCRIPTION
            "This table describes the basic configurations of the actual multicast router port."
        ::= { optixL2IgmpGroup 7 }

    -- 1.3.6.1.4.1.2011.2.25.4.50.38.1.7.1
    optixL2IgmpRouterPortExEntry OBJECT-TYPE
        SYNTAX OptixL2IgmpRouterPortExEntry
        MAX-ACCESS not-accessible
        STATUS current
        DESCRIPTION
            "This entry describes the basic configurations of the actual multicast router port."
        INDEX{ optixL2IgmpServiceIndex,optixL2IgmpVlanId,optixL2IgmpPortListNum }
        ::= { optixL2IgmpRouterPortExTable 1 }

    OptixL2IgmpRouterPortExEntry ::=
        SEQUENCE {
            optixL2IgmpPortListNum
                Unsigned32,
            optixL2IgmpRouterPortNumEx
                Unsigned32,
            optixL2IgmpRouterPortTypeEx
                INTEGER,
            optixL2IgmpRouterPortIdEx
                Unsigned32,
            optixL2IgmpRouterPortStateEx
                INTEGER,
            optixL2IgmpRouterCreateTimeEx
                DateAndTime,
            optixL2IgmpRouterCentSecEx
                Unsigned32,
            optixL2IgmpRouterRemainTimeEx
                Unsigned32,
            optixL2IgmpRouterExRowStatus
                RowStatus
        }

    -- 1.3.6.1.4.1.2011.2.25.4.50.38.1.7.1.1
    optixL2IgmpPortListNum OBJECT-TYPE
        SYNTAX Unsigned32
        MAX-ACCESS not-accessible
        STATUS current
        DESCRIPTION
            "This object indicates the Slave Port List Number."
        ::= { optixL2IgmpRouterPortExEntry 1 }

    -- 1.3.6.1.4.1.2011.2.25.4.50.38.1.7.1.2
    optixL2IgmpRouterPortNumEx OBJECT-TYPE
        SYNTAX Unsigned32
        MAX-ACCESS read-only
        STATUS current
        DESCRIPTION
            "This object indicates the number of multicast router ports. Value range for RTN equipment: 0 to 1024."
        ::= { optixL2IgmpRouterPortExEntry 2 }

    -- 1.3.6.1.4.1.2011.2.25.4.50.38.1.7.1.3
    optixL2IgmpRouterPortTypeEx OBJECT-TYPE
        SYNTAX INTEGER
        {
            vuni(1),
            vnni(2)
        }
        MAX-ACCESS read-only
        STATUS current
        DESCRIPTION
            "This object indicates the multicast router port type. 1:V-UNI 2:V-NNI"
        ::= { optixL2IgmpRouterPortExEntry 3 }

    -- 1.3.6.1.4.1.2011.2.25.4.50.38.1.7.1.4
    optixL2IgmpRouterPortIdEx OBJECT-TYPE
        SYNTAX Unsigned32
        MAX-ACCESS read-only
        STATUS current
        DESCRIPTION
            "This object indicates the multicast router port number. Value range: 0 to 65535."
        ::= { optixL2IgmpRouterPortExEntry 4 }

    -- 1.3.6.1.4.1.2011.2.25.4.50.38.1.7.1.5
    optixL2IgmpRouterPortStateEx OBJECT-TYPE
        SYNTAX INTEGER
        {
            dynamic(0),
            static(1)
        }
        MAX-ACCESS read-only
        STATUS current
        DESCRIPTION
            "This object indicates the multicast router port status. 0: dynamic, 1: static"
        ::= { optixL2IgmpRouterPortExEntry 5 }

    -- 1.3.6.1.4.1.2011.2.25.4.50.38.1.7.1.6
    optixL2IgmpRouterCreateTimeEx OBJECT-TYPE
        SYNTAX DateAndTime
        MAX-ACCESS read-only
        STATUS current
        DESCRIPTION
            "This object indicates the creation time of the multicast router port."
        ::= { optixL2IgmpRouterPortExEntry 6 }

    -- 1.3.6.1.4.1.2011.2.25.4.50.38.1.7.1.7
    optixL2IgmpRouterCentSecEx OBJECT-TYPE
        SYNTAX Unsigned32
        MAX-ACCESS read-only
        STATUS current
        DESCRIPTION
            "This object indicates the multicast router port centisecond."
        ::= { optixL2IgmpRouterPortExEntry 7 }

    -- 1.3.6.1.4.1.2011.2.25.4.50.38.1.7.1.8
    optixL2IgmpRouterRemainTimeEx OBJECT-TYPE
        SYNTAX Unsigned32
        MAX-ACCESS read-only
        STATUS current
        DESCRIPTION
            "This object indicates theremaining aging time of the multicast router port. Value range: 1 to 120 (unit: minute)."
        ::= { optixL2IgmpRouterPortExEntry 8 }

    -- 1.3.6.1.4.1.2011.2.25.4.50.38.1.7.1.255
    optixL2IgmpRouterExRowStatus OBJECT-TYPE
        SYNTAX RowStatus
        MAX-ACCESS read-only
        STATUS current
        DESCRIPTION
            "This object indicates the row status of the multicast router port."
        ::= { optixL2IgmpRouterPortExEntry 255 }

    -- 1.3.6.1.4.1.2011.2.25.4.50.38.1.8
    optixL2IgmpVlanTable OBJECT-TYPE
        SYNTAX SEQUENCE OF OptixL2IgmpVlanEntry
        MAX-ACCESS not-accessible
        STATUS current
        DESCRIPTION
            "This table describes the basic configurations of add or delete router port ."
        ::= { optixL2IgmpGroup 8 }

    -- 1.3.6.1.4.1.2011.2.25.4.50.38.1.8.1
    optixL2IgmpVlanEntry OBJECT-TYPE
        SYNTAX OptixL2IgmpVlanEntry
        MAX-ACCESS not-accessible
        STATUS current
        DESCRIPTION
            "This entry describes the basic configurations of add or delete router port ."
        INDEX{ optixL2IgmpServiceIndex,optixL2IgmpVlanId }
        ::= { optixL2IgmpVlanTable 1 }

    OptixL2IgmpVlanEntry ::=
        SEQUENCE {
            optixL2IgmpVlanPortNum
                Unsigned32,
            optixL2IgmpVlanPortType
                OCTET STRING,
            optixL2IgmpVlanPortID
                OCTET STRING,
            optixL2IgmpVlanAction
                INTEGER,
            optixL2IgmpVlanRowStatus
                RowStatus
        }

    -- 1.3.6.1.4.1.2011.2.25.4.50.38.1.8.1.1
    optixL2IgmpVlanPortNum OBJECT-TYPE
        SYNTAX Unsigned32
        MAX-ACCESS read-create
        STATUS current
        DESCRIPTION
            "Router port number. Value range for RTN equipment: 0 to 1024."
        ::= { optixL2IgmpVlanEntry 1 }

    -- 1.3.6.1.4.1.2011.2.25.4.50.38.1.8.1.2
    optixL2IgmpVlanPortType OBJECT-TYPE
        SYNTAX OCTET STRING
        MAX-ACCESS read-create
        STATUS current
        DESCRIPTION
            "Router port type. Input format: V-UNI or V-NNI. &amp;amp; is used to separte multiple formats. For example, V-UNI &amp;amp; V-UNI."
        ::= { optixL2IgmpVlanEntry 2 }

    -- 1.3.6.1.4.1.2011.2.25.4.50.38.1.8.1.3
    optixL2IgmpVlanPortID OBJECT-TYPE
        SYNTAX OCTET STRING
        MAX-ACCESS read-create
        STATUS current
        DESCRIPTION
            "Router port ID. &amp;amp; is used to separate multiple port IDs. For example, 1 &amp;amp; 2."
        ::= { optixL2IgmpVlanEntry 3 }

    -- 1.3.6.1.4.1.2011.2.25.4.50.38.1.8.1.4
    optixL2IgmpVlanAction OBJECT-TYPE
        SYNTAX INTEGER
        {
            add(1),
            delete(2)
        }
        MAX-ACCESS read-create
        STATUS current
        DESCRIPTION
            "The action of add or delete port,query invalid"
        ::= { optixL2IgmpVlanEntry 4 }

    -- 1.3.6.1.4.1.2011.2.25.4.50.38.1.8.1.255
    optixL2IgmpVlanRowStatus OBJECT-TYPE
        SYNTAX RowStatus
        MAX-ACCESS read-create
        STATUS current
        DESCRIPTION
            "Row Status"
        ::= { optixL2IgmpVlanEntry 255 }

    -- 1.3.6.1.4.1.2011.2.25.4.50.38.1.9
    optixL2IgmpVlanMacTable OBJECT-TYPE
        SYNTAX SEQUENCE OF OptixL2IgmpVlanMacEntry
        MAX-ACCESS not-accessible
        STATUS current
        DESCRIPTION
            "This table describes the basic configurations of add or delete static group port ."
        ::= { optixL2IgmpGroup 9 }

    -- 1.3.6.1.4.1.2011.2.25.4.50.38.1.9.1
    optixL2IgmpVlanMacEntry OBJECT-TYPE
        SYNTAX OptixL2IgmpVlanMacEntry
        MAX-ACCESS not-accessible
        STATUS current
        DESCRIPTION
            "This entry describes the basic configurations of add or delete static group port ."
        INDEX{ optixL2IgmpServiceIndex,optixL2IgmpVlanId,optixL2IgmpMacAddress }
        ::= { optixL2IgmpVlanMacTable 1 }

    OptixL2IgmpVlanMacEntry ::=
        SEQUENCE {
            optixL2IgmpVlanMacPortNum
                Unsigned32,
            optixL2IgmpVlanMacPortType
                OCTET STRING,
            optixL2IgmpVlanMacPortID
                OCTET STRING,
            optixL2IgmpVlanMacAction
                INTEGER,
            optixL2IgmpVlanMacRowStatus
                RowStatus
        }

    -- 1.3.6.1.4.1.2011.2.25.4.50.38.1.9.1.1
    optixL2IgmpVlanMacPortNum OBJECT-TYPE
        SYNTAX Unsigned32
        MAX-ACCESS read-create
        STATUS current
        DESCRIPTION
            "Group port number. Value range for RTN equipment: 0 to 1024."
        ::= { optixL2IgmpVlanMacEntry 1 }

    -- 1.3.6.1.4.1.2011.2.25.4.50.38.1.9.1.2
    optixL2IgmpVlanMacPortType OBJECT-TYPE
        SYNTAX OCTET STRING
        MAX-ACCESS read-create
        STATUS current
        DESCRIPTION
            "Group port type. Input format: V-UNI or V-NNI. &amp;amp; is used to separte multiple formats. For example, V-UNI &amp;amp; V-UNI."
        ::= { optixL2IgmpVlanMacEntry 2 }

    -- 1.3.6.1.4.1.2011.2.25.4.50.38.1.9.1.3
    optixL2IgmpVlanMacPortID OBJECT-TYPE
        SYNTAX OCTET STRING
        MAX-ACCESS read-create
        STATUS current
        DESCRIPTION
            "Group port ID. &amp;amp; is used to separate multiple port IDs. For example, 1 &amp;amp; 2."
        ::= { optixL2IgmpVlanMacEntry 3 }

    -- 1.3.6.1.4.1.2011.2.25.4.50.38.1.9.1.4
    optixL2IgmpVlanMacAction OBJECT-TYPE
        SYNTAX INTEGER
        {
            add(1),
            delete(2)
        }
        MAX-ACCESS read-create
        STATUS current
        DESCRIPTION
            "The action of add or delete group port,query invalid"
        ::= { optixL2IgmpVlanMacEntry 4 }

    -- 1.3.6.1.4.1.2011.2.25.4.50.38.1.9.1.255
    optixL2IgmpVlanMacRowStatus OBJECT-TYPE
        SYNTAX RowStatus
        MAX-ACCESS read-create
        STATUS current
        DESCRIPTION
            "Row Status"
        ::= { optixL2IgmpVlanMacEntry 255 }

    -- 1.3.6.1.4.1.2011.2.25.4.50.38.1.10
    optixL2IgmpMultiStcPortTable OBJECT-TYPE
        SYNTAX SEQUENCE OF OptixL2IgmpMultiStcPortEntry
        MAX-ACCESS not-accessible
        STATUS current
        DESCRIPTION
            "This table contains configuration information for adding and deleting specific multicast ports"
        ::= { optixL2IgmpGroup 10 }

    -- 1.3.6.1.4.1.2011.2.25.4.50.38.1.10.1
    optixL2IgmpMultiStcPortEntry OBJECT-TYPE
        SYNTAX OptixL2IgmpMultiStcPortEntry
        MAX-ACCESS not-accessible
        STATUS current
        DESCRIPTION
            "This entry contains configuration information for adding and deleting specific multicast ports"
        INDEX{ optixL2IgmpServiceIndex,optixL2IgmpVlanId,optixL2IgmpMultiStcPortGropIp,optixL2IgmpMultiStcPortSrcIp,optixL2IgmpMultiStcPortType,optixL2IgmpMultiStcPortId }
        ::= { optixL2IgmpMultiStcPortTable 1 }

    OptixL2IgmpMultiStcPortEntry ::=
        SEQUENCE {
            optixL2IgmpMultiStcPortGropIp
                IpAddress,
            optixL2IgmpMultiStcPortSrcIp
                IpAddress,
            optixL2IgmpMultiStcPortType
                INTEGER,
            optixL2IgmpMultiStcPortId
                Unsigned32,
            optixL2IgmpMultiStcPortNum
                Unsigned32,
            optixL2IgmpMultiStcPortSrc
                INTEGER,
            optixL2IgmpMultiRemainTime
                Unsigned32,
            optixL2IgmpMultiGroupTime
                Unsigned32,
            optixL2IgmpMultiFiltMode
                INTEGER,
            optixL2IgmpMultiCompatMode
                INTEGER,
            optixL2IgmpMultiV1HostLiveTime
                Unsigned32,
            optixL2IgmpMultiV2HostLiveTime
                Unsigned32,
            optixL2IgmpMultiSrcipTimer
                Unsigned32,
            optixL2IgmpMultiSrcipSrc
                INTEGER,
            optixL2IgmpMultiIgmpPortType
                INTEGER
        }

    -- 1.3.6.1.4.1.2011.2.25.4.50.38.1.10.1.1
    optixL2IgmpMultiStcPortGropIp OBJECT-TYPE
        SYNTAX IpAddress
        MAX-ACCESS not-accessible
        STATUS current
        DESCRIPTION
            "Multicast IP address Value range: 224.0.1.0 ~ 239.255.255.255"
        ::= { optixL2IgmpMultiStcPortEntry 1 }

    -- 1.3.6.1.4.1.2011.2.25.4.50.38.1.10.1.2
    optixL2IgmpMultiStcPortSrcIp OBJECT-TYPE
        SYNTAX IpAddress
        MAX-ACCESS not-accessible
        STATUS current
        DESCRIPTION
            "Source IP address Value range is all class A, B, and C addresses"
        ::= { optixL2IgmpMultiStcPortEntry 2 }

    -- 1.3.6.1.4.1.2011.2.25.4.50.38.1.10.1.3
    optixL2IgmpMultiStcPortType OBJECT-TYPE
        SYNTAX INTEGER
        {
            vuni(1),
            vnni(2)
        }
        MAX-ACCESS not-accessible
        STATUS current
        DESCRIPTION
            "Port type vuni (1), vnni (2)"
        ::= { optixL2IgmpMultiStcPortEntry 3 }

    -- 1.3.6.1.4.1.2011.2.25.4.50.38.1.10.1.4
    optixL2IgmpMultiStcPortId OBJECT-TYPE
        SYNTAX Unsigned32 (1..65535)
        MAX-ACCESS not-accessible
        STATUS current
        DESCRIPTION
            "port id"
        ::= { optixL2IgmpMultiStcPortEntry 4 }

    -- 1.3.6.1.4.1.2011.2.25.4.50.38.1.10.1.5
    optixL2IgmpMultiStcPortNum OBJECT-TYPE
        SYNTAX Unsigned32
        MAX-ACCESS read-only
        STATUS current
        DESCRIPTION
            "port num"
        ::= { optixL2IgmpMultiStcPortEntry 5 }

    -- 1.3.6.1.4.1.2011.2.25.4.50.38.1.10.1.6
    optixL2IgmpMultiStcPortSrc OBJECT-TYPE
        SYNTAX INTEGER
        {
            static(1),
            dynamic(2),
            stcdyn(3),
            ssmmap(4),
            stcssm(5),
            dynssm(6),
            stcdynssm(7),
            protocol(8)
        }
        MAX-ACCESS read-only
        STATUS current
        DESCRIPTION
            "Port dynamic and static types static (1), dynamic (2), stcdyn (3), ssmmap (4), stcssm (5), dynssm (6), stcdynssm (7), protocol (8)"
        ::= { optixL2IgmpMultiStcPortEntry 6 }

    -- 1.3.6.1.4.1.2011.2.25.4.50.38.1.10.1.7
    optixL2IgmpMultiRemainTime OBJECT-TYPE
        SYNTAX Unsigned32
        MAX-ACCESS read-only
        STATUS current
        DESCRIPTION
            "Number of remaining unresponsive ports"
        ::= { optixL2IgmpMultiStcPortEntry 7 }

    -- 1.3.6.1.4.1.2011.2.25.4.50.38.1.10.1.8
    optixL2IgmpMultiGroupTime OBJECT-TYPE
        SYNTAX Unsigned32
        MAX-ACCESS read-only
        STATUS current
        DESCRIPTION
            "Group timer for port"
        ::= { optixL2IgmpMultiStcPortEntry 8 }

    -- 1.3.6.1.4.1.2011.2.25.4.50.38.1.10.1.9
    optixL2IgmpMultiFiltMode OBJECT-TYPE
        SYNTAX INTEGER
        {
            include(1),
            exclude(2)
        }
        MAX-ACCESS read-only
        STATUS current
        DESCRIPTION
            "Port filtering mode include(1),exclude(2)"
        ::= { optixL2IgmpMultiStcPortEntry 9 }

    -- 1.3.6.1.4.1.2011.2.25.4.50.38.1.10.1.10
    optixL2IgmpMultiCompatMode OBJECT-TYPE
        SYNTAX INTEGER
        {
            v1(1),
            v2(2),
            v3(3)
        }
        MAX-ACCESS read-only
        STATUS current
        DESCRIPTION
            "Compatibility mode v1(1),v2(2),v3(3)"
        ::= { optixL2IgmpMultiStcPortEntry 10 }

    -- 1.3.6.1.4.1.2011.2.25.4.50.38.1.10.1.11
    optixL2IgmpMultiV1HostLiveTime OBJECT-TYPE
        SYNTAX Unsigned32
        MAX-ACCESS read-only
        STATUS current
        DESCRIPTION
            "V1 host port remaining time (Unit of second)"
        ::= { optixL2IgmpMultiStcPortEntry 11 }

    -- 1.3.6.1.4.1.2011.2.25.4.50.38.1.10.1.12
    optixL2IgmpMultiV2HostLiveTime OBJECT-TYPE
        SYNTAX Unsigned32
        MAX-ACCESS read-only
        STATUS current
        DESCRIPTION
            "V2 host port remaining time (in seconds)"
        ::= { optixL2IgmpMultiStcPortEntry 12 }

    -- 1.3.6.1.4.1.2011.2.25.4.50.38.1.10.1.13
    optixL2IgmpMultiSrcipTimer OBJECT-TYPE
        SYNTAX Unsigned32
        MAX-ACCESS read-only
        STATUS current
        DESCRIPTION
            "Source IP timer (in seconds)"
        ::= { optixL2IgmpMultiStcPortEntry 13 }

    -- 1.3.6.1.4.1.2011.2.25.4.50.38.1.10.1.14
    optixL2IgmpMultiSrcipSrc OBJECT-TYPE
        SYNTAX INTEGER
        {
            static(1),
            dynamic(2),
            stcdyn(3),
            ssmmap(4),
            stcssm(5),
            dynssm(6),
            stcdynssm(7),
            protocol(8)
        }
        MAX-ACCESS read-only
        STATUS current
        DESCRIPTION
            "Source IP source: static (1), dynamic (2), stcdyn (3), ssmmap (4), stcssm (5), dynssm (6), stcdynssm (7), protocol (8)"
        ::= { optixL2IgmpMultiStcPortEntry 14 }

    -- 1.3.6.1.4.1.2011.2.25.4.50.38.1.10.1.15
    optixL2IgmpMultiIgmpPortType OBJECT-TYPE
        SYNTAX INTEGER
        {
            routeport(0),
            hostport(1),
            routehost(2)
        }
        MAX-ACCESS read-only
        STATUS current
        DESCRIPTION
            "Multicast port type: routeport (0), hostport (1), routehost (2)"
        ::= { optixL2IgmpMultiStcPortEntry 15 }

    -- 1.3.6.1.4.1.2011.2.25.4.50.38.1.11
    optixL2IgmpMultiGroupTable OBJECT-TYPE
        SYNTAX SEQUENCE OF OptixL2IgmpMultiGroupEntry
        MAX-ACCESS not-accessible
        STATUS current
        DESCRIPTION
            "This table contains configuration information for multicast groups."
        ::= { optixL2IgmpGroup 11 }

    -- 1.3.6.1.4.1.2011.2.25.4.50.38.1.11.1
    optixL2IgmpMultiGroupEntry OBJECT-TYPE
        SYNTAX OptixL2IgmpMultiGroupEntry
        MAX-ACCESS not-accessible
        STATUS current
        DESCRIPTION
            "This entry contains the configuration information for the multicast group"
        INDEX{ optixL2IgmpServiceIndex,optixL2IgmpVlanId,optixL2IgmpMultiStcPortGropIp,optixL2IgmpMultiStcPortSrcIp }
        ::= { optixL2IgmpMultiGroupTable 1 }

    OptixL2IgmpMultiGroupEntry ::=
        SEQUENCE {
            optixL2IgmpMultiGroupPortNum
                Unsigned32,
            optixL2IgmpMultiGroupPortList
                OCTET STRING,
            optixL2IgmpMultiStcPortOperFlag
                INTEGER,
            optixL2IgmpMultiGroupCrtTime
                DateAndTime,
            optixL2IgmpMultiGroupRowStatus
                RowStatus
        }

    -- 1.3.6.1.4.1.2011.2.25.4.50.38.1.11.1.1
    optixL2IgmpMultiGroupPortNum OBJECT-TYPE
        SYNTAX Unsigned32
        MAX-ACCESS read-create
        STATUS current
        DESCRIPTION
            "Number of multicast groups"
        ::= { optixL2IgmpMultiGroupEntry 1 }

    -- 1.3.6.1.4.1.2011.2.25.4.50.38.1.11.1.2
    optixL2IgmpMultiGroupPortList OBJECT-TYPE
        SYNTAX OCTET STRING
        MAX-ACCESS read-create
        STATUS current
        DESCRIPTION
            "Multicast group port list Input format is type and port id If multiple connections are used, such as: vuni&1,vnni&2"
        ::= { optixL2IgmpMultiGroupEntry 2 }

    -- 1.3.6.1.4.1.2011.2.25.4.50.38.1.11.1.3
    optixL2IgmpMultiStcPortOperFlag OBJECT-TYPE
        SYNTAX INTEGER
        {
            add(1),
            set(2),
            invalid(255)
        }
        MAX-ACCESS read-create
        STATUS current
        DESCRIPTION
            "Add setting mode for specific multicast port add(1),set(2),invalid(255)"
        ::= { optixL2IgmpMultiGroupEntry 3 }

    -- 1.3.6.1.4.1.2011.2.25.4.50.38.1.11.1.4
    optixL2IgmpMultiGroupCrtTime OBJECT-TYPE
        SYNTAX DateAndTime
        MAX-ACCESS read-only
        STATUS current
        DESCRIPTION
            "Multicast group establishment time"
        ::= { optixL2IgmpMultiGroupEntry 4 }

    -- 1.3.6.1.4.1.2011.2.25.4.50.38.1.11.1.255
    optixL2IgmpMultiGroupRowStatus OBJECT-TYPE
        SYNTAX RowStatus
        MAX-ACCESS read-create
        STATUS current
        DESCRIPTION
            "Add or delete row status of a multicast group"
        ::= { optixL2IgmpMultiGroupEntry 255 }

    -- 1.3.6.1.4.1.2011.2.25.4.50.38.1.12
    optixL2IgmpClrDynGroupTable OBJECT-TYPE
        SYNTAX SEQUENCE OF OptixL2IgmpClrDynGroupEntry
        MAX-ACCESS not-accessible
        STATUS current
        DESCRIPTION
            "This table contains configuration information for multicast groups."
        ::= { optixL2IgmpGroup 12 }

    -- 1.3.6.1.4.1.2011.2.25.4.50.38.1.12.1
    optixL2IgmpClrDynGroupEntry OBJECT-TYPE
        SYNTAX OptixL2IgmpClrDynGroupEntry
        MAX-ACCESS not-accessible
        STATUS current
        DESCRIPTION
            "This entry contains configuration information to delete IGMP dynamic school performance"
        INDEX{ optixL2IgmpServiceIndex,optixL2IgmpVlanId }
        ::= { optixL2IgmpClrDynGroupTable 1 }

    OptixL2IgmpClrDynGroupEntry ::=
        SEQUENCE {
            optixL2IgmpClrDynGroupOperFlag
                INTEGER
        }

    -- 1.3.6.1.4.1.2011.2.25.4.50.38.1.12.1.1
    optixL2IgmpClrDynGroupOperFlag OBJECT-TYPE
        SYNTAX INTEGER
        {
            clear(0)
        }
        MAX-ACCESS read-write
        STATUS current
        DESCRIPTION
            "Clear flag clear (0)"
        ::= { optixL2IgmpClrDynGroupEntry 1 }

    -- 1.3.6.1.4.1.2011.2.25.4.50.38.1.13
    optixL2IgmpV3AttrTable OBJECT-TYPE
        SYNTAX SEQUENCE OF OptixL2IgmpV3AttrEntry
        MAX-ACCESS not-accessible
        STATUS current
        DESCRIPTION
            "This table contains the configuration attributes of the IGMPV3 protocol."
        ::= { optixL2IgmpGroup 13 }

    -- 1.3.6.1.4.1.2011.2.25.4.50.38.1.13.1
    optixL2IgmpV3AttrEntry OBJECT-TYPE
        SYNTAX OptixL2IgmpV3AttrEntry
        MAX-ACCESS not-accessible
        STATUS current
        DESCRIPTION
            "This entry contains the configuration attributes of the IGMPV3 protocol."
        INDEX{ optixL2IgmpV3AttrSrvIndex }
        ::= { optixL2IgmpV3AttrTable 1 }

    OptixL2IgmpV3AttrEntry ::=
        SEQUENCE {
            optixL2IgmpV3AttrSrvIndex
                Unsigned32,
            optixL2IgmpV3AttrVer
                INTEGER,
            optixL2IgmpV3AttrRobust
                Unsigned32,
            optixL2IgmpV3AttrQueryInterval
                Unsigned32,
            optixL2IgmpV3AttrRspInterval
                Unsigned32,
            optixL2IgmpV3AttrSSMEnable
                INTEGER
        }

    -- 1.3.6.1.4.1.2011.2.25.4.50.38.1.13.1.1
    optixL2IgmpV3AttrSrvIndex OBJECT-TYPE
        SYNTAX Unsigned32
        MAX-ACCESS not-accessible
        STATUS current
        DESCRIPTION
            "the service index"
        ::= { optixL2IgmpV3AttrEntry 1 }

    -- 1.3.6.1.4.1.2011.2.25.4.50.38.1.13.1.2
    optixL2IgmpV3AttrVer OBJECT-TYPE
        SYNTAX INTEGER
        {
            v1(1),
            v2(2),
            v3(3)
        }
        MAX-ACCESS read-write
        STATUS current
        DESCRIPTION
            "protocol version, v1(1), v2(2),v3(3)"
        ::= { optixL2IgmpV3AttrEntry 2 }

    -- 1.3.6.1.4.1.2011.2.25.4.50.38.1.13.1.3
    optixL2IgmpV3AttrRobust OBJECT-TYPE
        SYNTAX Unsigned32
        MAX-ACCESS read-write
        STATUS current
        DESCRIPTION
            "robustness variable"
        ::= { optixL2IgmpV3AttrEntry 3 }

    -- 1.3.6.1.4.1.2011.2.25.4.50.38.1.13.1.4
    optixL2IgmpV3AttrQueryInterval OBJECT-TYPE
        SYNTAX Unsigned32
        MAX-ACCESS read-write
        STATUS current
        DESCRIPTION
            "query Period"
        ::= { optixL2IgmpV3AttrEntry 4 }

    -- 1.3.6.1.4.1.2011.2.25.4.50.38.1.13.1.5
    optixL2IgmpV3AttrRspInterval OBJECT-TYPE
        SYNTAX Unsigned32
        MAX-ACCESS read-write
        STATUS current
        DESCRIPTION
            "query response period"
        ::= { optixL2IgmpV3AttrEntry 5 }

    -- 1.3.6.1.4.1.2011.2.25.4.50.38.1.13.1.6
    optixL2IgmpV3AttrSSMEnable OBJECT-TYPE
        SYNTAX INTEGER
        {
            enable(1),
            disable(0)
        }
        MAX-ACCESS read-write
        STATUS current
        DESCRIPTION
            "To enable the SSM mapping, run the enable(1),disable(0) command."
        ::= { optixL2IgmpV3AttrEntry 6 }

    -- 1.3.6.1.4.1.2011.2.25.4.50.38.1.14
    optixL2IgmpV3SSMMapTable OBJECT-TYPE
        SYNTAX SEQUENCE OF OptixL2IgmpV3SSMMapEntry
        MAX-ACCESS not-accessible
        STATUS current
        DESCRIPTION
            "This table describes the basic configurations of add or delete static group port ."
        ::= { optixL2IgmpGroup 14 }

    -- 1.3.6.1.4.1.2011.2.25.4.50.38.1.14.1
    optixL2IgmpV3SSMMapEntry OBJECT-TYPE
        SYNTAX OptixL2IgmpV3SSMMapEntry
        MAX-ACCESS not-accessible
        STATUS current
        DESCRIPTION
            "This entry describes the basic configurations of add or delete static group port ."
        INDEX{ optixL2IgmpV3SSMMapSrvIndex,optixL2IgmpV3SSMMapMulticastIp,optixL2IgmpV3SSMMapAddrMask }
        ::= { optixL2IgmpV3SSMMapTable 1 }

    OptixL2IgmpV3SSMMapEntry ::=
        SEQUENCE {
            optixL2IgmpV3SSMMapSrvIndex
                Unsigned32,
            optixL2IgmpV3SSMMapMulticastIp
                IpAddress,
            optixL2IgmpV3SSMMapAddrMask
                IpAddress,
            optixL2IgmpV3SSMMapSrcIPNum
                Unsigned32,
            optixL2IgmpV3SSMMapSrcIP
                OCTET STRING,
            optixL2IgmpV3SSMMapAction
                INTEGER,
            optixL2IgmpV3SSMMapRowStatus
                RowStatus
        }

    -- 1.3.6.1.4.1.2011.2.25.4.50.38.1.14.1.1
    optixL2IgmpV3SSMMapSrvIndex OBJECT-TYPE
        SYNTAX Unsigned32
        MAX-ACCESS read-create
        STATUS current
        DESCRIPTION
            "the service index"
        ::= { optixL2IgmpV3SSMMapEntry 1 }

    -- 1.3.6.1.4.1.2011.2.25.4.50.38.1.14.1.2
    optixL2IgmpV3SSMMapMulticastIp OBJECT-TYPE
        SYNTAX IpAddress
        MAX-ACCESS read-create
        STATUS current
        DESCRIPTION
            "multicast IP address"
        ::= { optixL2IgmpV3SSMMapEntry 2 }

    -- 1.3.6.1.4.1.2011.2.25.4.50.38.1.14.1.3
    optixL2IgmpV3SSMMapAddrMask OBJECT-TYPE
        SYNTAX IpAddress
        MAX-ACCESS read-create
        STATUS current
        DESCRIPTION
            "multicast address mask"
        ::= { optixL2IgmpV3SSMMapEntry 3 }

    -- 1.3.6.1.4.1.2011.2.25.4.50.38.1.14.1.4
    optixL2IgmpV3SSMMapSrcIPNum OBJECT-TYPE
        SYNTAX Unsigned32
        MAX-ACCESS read-create
        STATUS current
        DESCRIPTION
            "number of multicast sources"
        ::= { optixL2IgmpV3SSMMapEntry 4 }

    -- 1.3.6.1.4.1.2011.2.25.4.50.38.1.14.1.5
    optixL2IgmpV3SSMMapSrcIP OBJECT-TYPE
        SYNTAX OCTET STRING
        MAX-ACCESS read-create
        STATUS current
        DESCRIPTION
            "Multicast source IP, if there are multiple, connect with &, such as:192.168.10.3&192.168.10.5"
        ::= { optixL2IgmpV3SSMMapEntry 5 }

    -- 1.3.6.1.4.1.2011.2.25.4.50.38.1.14.1.6
    optixL2IgmpV3SSMMapAction OBJECT-TYPE
        SYNTAX INTEGER
        {
            add(1),
            set(2),
            invalid(255)
        }
        MAX-ACCESS read-create
        STATUS current
        DESCRIPTION
            "Add or set the mapping relationship .add(1) and set(2). Query invalid(255)."
        ::= { optixL2IgmpV3SSMMapEntry 6 }

    -- 1.3.6.1.4.1.2011.2.25.4.50.38.1.14.1.255
    optixL2IgmpV3SSMMapRowStatus OBJECT-TYPE
        SYNTAX RowStatus
        MAX-ACCESS read-create
        STATUS current
        DESCRIPTION
            "Add or delete the row status of the mapping relationship"
        ::= { optixL2IgmpV3SSMMapEntry 255 }

END
