-- OPTIX-SDH-SNCP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-SNCP-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY,NOTIFICATION-TYPE
            FROM SNMPv2-SMI
        optixSdhXcLevel,optixSdhXcEXTId
            FROM OPTIX-SDH-XC-MIB
        RowStatus
            FROM SNMPv2-TC
        ;

    optixSdhSncp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describesSNCP configurations."
        REVISION "201204200000Z"
        DESCRIPTION
            "The initial revision of this MIB module1."
        ::={ optixProvisionSdh 46 }

    -- 1.3.6.1.4.1.2011.2.25.4.10.46.1
    optixSdhSncpGroup OBJECT IDENTIFIER ::= { optixSdhSncp 1 }

    -- 1.3.6.1.4.1.2011.2.25.4.10.46.1.1
    optixSdhSncpReport OBJECT-TYPE
        SYNTAX INTEGER
        {
            disable(0),
            enable(1)
        }
        MAX-ACCESS read-create
        STATUS current
        DESCRIPTION
            "This object indicates the enable status of the auto-reporting function of the SNCP group."
        ::= { optixSdhSncpGroup 1 }

    -- 1.3.6.1.4.1.2011.2.25.4.10.46.1.2
    optixSdhSncpgTable OBJECT-TYPE
        SYNTAX SEQUENCE OF OptixSdhSncpgEntry
        MAX-ACCESS not-accessible
        STATUS current
        DESCRIPTION
            "This table describes the SNCP group configurations."
        ::= { optixSdhSncpGroup 2 }

    -- 1.3.6.1.4.1.2011.2.25.4.10.46.1.2.1
    optixSdhSncpgEntry OBJECT-TYPE
        SYNTAX OptixSdhSncpgEntry
        MAX-ACCESS not-accessible
        STATUS current
        DESCRIPTION
            "Thisentry describes the SNCP group configurations."
        INDEX{ optixSdhSncpToXcPGId }
        ::= { optixSdhSncpgTable 1 }

    OptixSdhSncpgEntry ::=
        SEQUENCE {
            optixSdhSncpToXcPGId
                Unsigned32,
            optixSdhSncpRevertMode
                INTEGER,
            optixSdhSncpActiveFlag
                INTEGER,
            optixSdhSncpWtrTime
                Unsigned32,
            optixSdhSncpWorkPath
                INTEGER,
            optixSdhSncpSwitchReq
                INTEGER,
            optixSdhSncpWorkState
                INTEGER,
            optixSdhSncpProtState
                INTEGER,
            optixSdhSncpWorkBid
                Unsigned32,
            optixSdhSncpWorkPid
                Unsigned32,
            optixSdhSncpWorkAu4id
                Unsigned32,
            optixSdhSncpWorkUnitState
                INTEGER,
            optixSdhSncpBackBid
                Unsigned32,
            optixSdhSncpBackPid
                Unsigned32,
            optixSdhSncpBackAu4id
                Unsigned32,
            optixSdhSncpBackState
                INTEGER,
            optixSdhSncpgRowStatus
                RowStatus
        }

    -- 1.3.6.1.4.1.2011.2.25.4.10.46.1.2.1.1
    optixSdhSncpToXcPGId OBJECT-TYPE
        SYNTAX Unsigned32
        MAX-ACCESS read-only
        STATUS current
        DESCRIPTION
            "This object indicates the SNCP group ID."
        ::= { optixSdhSncpgEntry 1 }

    -- 1.3.6.1.4.1.2011.2.25.4.10.46.1.2.1.2
    optixSdhSncpRevertMode OBJECT-TYPE
        SYNTAX INTEGER
        {
            rvt(1),
            norvt(0)
        }
        MAX-ACCESS read-only
        STATUS current
        DESCRIPTION
            "This object indicates the reversion mode of the SNCP group. 1: rvt, 0: norvt"
        ::= { optixSdhSncpgEntry 2 }

    -- 1.3.6.1.4.1.2011.2.25.4.10.46.1.2.1.3
    optixSdhSncpActiveFlag OBJECT-TYPE
        SYNTAX INTEGER
        {
            adding(1),
            deleting(2),
            active(3)
        }
        MAX-ACCESS read-only
        STATUS current
        DESCRIPTION
            "This object indicates the current activation flag of the SNCP group. 1: adding, 2: deleting, 3: active"
        ::= { optixSdhSncpgEntry 3 }

    -- 1.3.6.1.4.1.2011.2.25.4.10.46.1.2.1.4
    optixSdhSncpWtrTime OBJECT-TYPE
        SYNTAX Unsigned32
        MAX-ACCESS read-only
        STATUS current
        DESCRIPTION
            "This object indicates the WTR time of the SNCP group. Value range: 300 to 720 (unit: s). The default value is 600 (for revertive mode). This parameter takes effect when the revertive mode is used. If the non-revertive mode is used, this parameter takes an invalid value of 0x00."
        ::= { optixSdhSncpgEntry 4 }

    -- 1.3.6.1.4.1.2011.2.25.4.10.46.1.2.1.5
    optixSdhSncpWorkPath OBJECT-TYPE
        SYNTAX INTEGER
        {
            workPath(1),
            backupPath(0),
            delayStart(255)
        }
        MAX-ACCESS read-only
        STATUS current
        DESCRIPTION
            "This object indicates the working path of the SNCP group. 0x01: active channel, 0x00: standby channel, 0xff: delay startup state (This value is applicable only in case of delay due to power-off.)"
        ::= { optixSdhSncpgEntry 5 }

    -- 1.3.6.1.4.1.2011.2.25.4.10.46.1.2.1.6
    optixSdhSncpSwitchReq OBJECT-TYPE
        SYNTAX INTEGER
        {
            sncpLocked(15),
            sncpFs(14),
            sncpSf(12),
            sncpSd(9),
            sncpMs(7),
            sncpWtr(5),
            sncpIdle(0)
        }
        MAX-ACCESS read-only
        STATUS current
        DESCRIPTION
            "This object indicates the switching request of the SNCP group. Active channel status: 0: normal, 1: SD, 2: SF"
        ::= { optixSdhSncpgEntry 6 }

    -- 1.3.6.1.4.1.2011.2.25.4.10.46.1.2.1.7
    optixSdhSncpWorkState OBJECT-TYPE
        SYNTAX INTEGER
        {
            sncpNormal(0),
            sncpSd(1),
            sncpSf(2)
        }
        MAX-ACCESS read-only
        STATUS current
        DESCRIPTION
            "This object indicates the working channel status of the SNCP group. Active channel status: 0: normal, 1: SD, 2: SF"
        ::= { optixSdhSncpgEntry 7 }

    -- 1.3.6.1.4.1.2011.2.25.4.10.46.1.2.1.8
    optixSdhSncpProtState OBJECT-TYPE
        SYNTAX INTEGER
        {
            sncpNormal(0),
            sncpSd(1),
            sncpSf(2)
        }
        MAX-ACCESS read-only
        STATUS current
        DESCRIPTION
            "This object indicates theprotection channel status of the SNCP group. Standby channel status: 0: normal, 1: SD, 2: SF"
        ::= { optixSdhSncpgEntry 8 }

    -- 1.3.6.1.4.1.2011.2.25.4.10.46.1.2.1.9
    optixSdhSncpWorkBid OBJECT-TYPE
        SYNTAX Unsigned32
        MAX-ACCESS read-only
        STATUS current
        DESCRIPTION
            "This object indicates theworking slot ID of the SNCP group. Value range: 1 to 6."
        ::= { optixSdhSncpgEntry 9 }

    -- 1.3.6.1.4.1.2011.2.25.4.10.46.1.2.1.10
    optixSdhSncpWorkPid OBJECT-TYPE
        SYNTAX Unsigned32
        MAX-ACCESS read-only
        STATUS current
        DESCRIPTION
            "This object indicates theworking port number of the SNCP group. Value range when src-bid is Pdh: 1 to 63. Value range in other situations: 1 and 2."
        ::= { optixSdhSncpgEntry 10 }

    -- 1.3.6.1.4.1.2011.2.25.4.10.46.1.2.1.11
    optixSdhSncpWorkAu4id OBJECT-TYPE
        SYNTAX Unsigned32
        MAX-ACCESS read-only
        STATUS current
        DESCRIPTION
            "This object indicates the working channel ID of the SNCP group. Value range: 0 and 1."
        ::= { optixSdhSncpgEntry 11 }

    -- 1.3.6.1.4.1.2011.2.25.4.10.46.1.2.1.12
    optixSdhSncpWorkUnitState OBJECT-TYPE
        SYNTAX INTEGER
        {
            sncpNormal(0),
            sncpSd(1),
            sncpSf(2),
            sncpUnknown(3)
        }
        MAX-ACCESS read-only
        STATUS current
        DESCRIPTION
            "This object indicates the SNC monitoring point of the SNCP working unit. 0: sncpNormal, 1: sncpSd, 2: sncpSf, 3: sncpUnknown"
        ::= { optixSdhSncpgEntry 12 }

    -- 1.3.6.1.4.1.2011.2.25.4.10.46.1.2.1.13
    optixSdhSncpBackBid OBJECT-TYPE
        SYNTAX Unsigned32
        MAX-ACCESS read-only
        STATUS current
        DESCRIPTION
            "This object indicates theprotection slot ID of the SNCP group. Value range: 1 to 6."
        ::= { optixSdhSncpgEntry 13 }

    -- 1.3.6.1.4.1.2011.2.25.4.10.46.1.2.1.14
    optixSdhSncpBackPid OBJECT-TYPE
        SYNTAX Unsigned32
        MAX-ACCESS read-only
        STATUS current
        DESCRIPTION
            "This object indicates theprotection port number of the SNCP group. Value range when src-bid is Pdh: 1 to 63. Value range in other situations: 1 and 2."
        ::= { optixSdhSncpgEntry 14 }

    -- 1.3.6.1.4.1.2011.2.25.4.10.46.1.2.1.15
    optixSdhSncpBackAu4id OBJECT-TYPE
        SYNTAX Unsigned32
        MAX-ACCESS read-only
        STATUS current
        DESCRIPTION
            "This object indicates the protectionchannel ID of the SNCP group. Value range: 0 and 1."
        ::= { optixSdhSncpgEntry 15 }

    -- 1.3.6.1.4.1.2011.2.25.4.10.46.1.2.1.16
    optixSdhSncpBackState OBJECT-TYPE
        SYNTAX INTEGER
        {
            sncpNormal(0),
            sncpSd(1),
            sncpSf(2),
            sncpUnknown(3)
        }
        MAX-ACCESS read-only
        STATUS current
        DESCRIPTION
            "This object indicates the SNC monitoring point of the SNCPprotection unit. 0: sncpNormal, 1: sncpSd, 2: sncpSf, 3: sncpUnknown"
        ::= { optixSdhSncpgEntry 16 }

    -- 1.3.6.1.4.1.2011.2.25.4.10.46.1.2.1.255
    optixSdhSncpgRowStatus OBJECT-TYPE
        SYNTAX RowStatus
        MAX-ACCESS read-only
        STATUS current
        DESCRIPTION
            "This object indicates the row status of the SNCP group."
        ::= { optixSdhSncpgEntry 255 }

    -- 1.3.6.1.4.1.2011.2.25.4.10.46.1.3
    optixSdhSncpuTable OBJECT-TYPE
        SYNTAX SEQUENCE OF OptixSdhSncpuEntry
        MAX-ACCESS not-accessible
        STATUS current
        DESCRIPTION
            "This table describes the SNCPprotection unitconfigurations."
        ::= { optixSdhSncpGroup 3 }

    -- 1.3.6.1.4.1.2011.2.25.4.10.46.1.3.1
    optixSdhSncpuEntry OBJECT-TYPE
        SYNTAX OptixSdhSncpuEntry
        MAX-ACCESS not-accessible
        STATUS current
        DESCRIPTION
            "Thisentry describes the SNCP protection unit configurations."
        INDEX{ optixSdhSncpToXcPGId,optixSdhSncpToXcPUId }
        ::= { optixSdhSncpuTable 1 }

    OptixSdhSncpuEntry ::=
        SEQUENCE {
            optixSdhSncpToXcPUId
                Unsigned32,
            optixSdhSncpOPcond
                OCTET STRING,
            optixSdhSncpDelayTime
                Unsigned32,
            optixSdhSncpuRowStatus
                RowStatus
        }

    -- 1.3.6.1.4.1.2011.2.25.4.10.46.1.3.1.1
    optixSdhSncpToXcPUId OBJECT-TYPE
        SYNTAX Unsigned32
        MAX-ACCESS not-accessible
        STATUS current
        DESCRIPTION
            "This object indicates the SNCPprotection unitID. Value range: 1 to 2016."
        ::= { optixSdhSncpuEntry 1 }

    -- 1.3.6.1.4.1.2011.2.25.4.10.46.1.3.1.2
    optixSdhSncpOPcond OBJECT-TYPE
        SYNTAX OCTET STRING (SIZE(0..64))
        MAX-ACCESS read-create
        STATUS current
        DESCRIPTION
            "This object indicates the optional monitoring conditions of the SNCP protection unit."
        ::= { optixSdhSncpuEntry 2 }

    -- 1.3.6.1.4.1.2011.2.25.4.10.46.1.3.1.3
    optixSdhSncpDelayTime OBJECT-TYPE
        SYNTAX Unsigned32
        MAX-ACCESS read-create
        STATUS current
        DESCRIPTION
            "This object indicates the delay time of the SNCP protection unit. Value range: 0 to 100 (unit: 100 ms)."
        ::= { optixSdhSncpuEntry 3 }

    -- 1.3.6.1.4.1.2011.2.25.4.10.46.1.3.1.255
    optixSdhSncpuRowStatus OBJECT-TYPE
        SYNTAX RowStatus
        MAX-ACCESS read-create
        STATUS current
        DESCRIPTION
            "This object indicates the row status of the SNCP protection unit."
        ::= { optixSdhSncpuEntry 255 }

    -- 1.3.6.1.4.1.2011.2.25.4.10.46.1.4
    optixSncpSwitchEvent OBJECT IDENTIFIER ::= { optixSdhSncpGroup 4 }

    -- 1.3.6.1.4.1.2011.2.25.4.10.46.1.4.1
    optixSncpSwitchETrap NOTIFICATION-TYPE
        OBJECTS{ optixSdhSncpToXcPGId,optixSdhSncpWorkPath,optixSdhSncpSwitchReq,optixSdhSncpWorkState,optixSdhSncpProtState }
        STATUS current
        DESCRIPTION
            "This parameter specifie Sncp State change event"
        ::= { optixSncpSwitchEvent 1 }

    -- 1.3.6.1.4.1.2011.2.25.4.10.46.1.5
    optixSdhSncpgEXTTable OBJECT-TYPE
        SYNTAX SEQUENCE OF OptixSdhSncpgEXTEntry
        MAX-ACCESS not-accessible
        STATUS current
        DESCRIPTION
            "This table describes the SNCP group configurations."
        ::= { optixSdhSncpGroup 5 }

    -- 1.3.6.1.4.1.2011.2.25.4.10.46.1.5.1
    optixSdhSncpgEXTEntry OBJECT-TYPE
        SYNTAX OptixSdhSncpgEXTEntry
        MAX-ACCESS not-accessible
        STATUS current
        DESCRIPTION
            "This entry describes the SNCP group configurations."
        INDEX{ optixSdhSncpgEXTid }
        ::= { optixSdhSncpgEXTTable 1 }

    OptixSdhSncpgEXTEntry ::=
        SEQUENCE {
            optixSdhSncpgEXTid
                Unsigned32,
            optixSdhSncpEXTRevertMode
                INTEGER,
            optixSdhSncpEXTWtrTime
                Unsigned32,
            optixSdhSncpEXTWorkPuid
                INTEGER,
            optixSdhSncpEXTWorkBid
                Unsigned32,
            optixSdhSncpEXTWorkSubCardid
                Unsigned32,
            optixSdhSncpEXTWorkPid
                Unsigned32,
            optixSdhSncpEXTWorkAu4id
                Unsigned32,
            optixSdhSncpEXTWorkPathid
                Unsigned32,
            optixSdhSncpEXTBackupPuid
                INTEGER,
            optixSdhSncpEXTBackupBid
                Unsigned32,
            optixSdhSncpEXTBackupSubCardid
                Unsigned32,
            optixSdhSncpEXTBackupPid
                Unsigned32,
            optixSdhSncpEXTBackupAu4id
                Unsigned32,
            optixSdhSncpEXTBackupPathid
                Unsigned32,
            optixSdhSncpEXTDestBid
                Unsigned32,
            optixSdhSncpEXTDestSubCardid
                Unsigned32,
            optixSdhSncpEXTDestPid
                Unsigned32,
            optixSdhSncpEXTDestAu4id
                Unsigned32,
            optixSdhSncpEXTDestPathid
                Unsigned32,
            optixSdhSncpEXTXcLevel
                INTEGER,
            optixSdhSncpEXTSwitchReq
                INTEGER,
            optixSdhSncpEXTSwitchDir
                INTEGER,
            optixSdhSncpEXTActiveFlag
                INTEGER,
            optixSdhSncpEXTWorkPath
                INTEGER,
            optixSdhSncpEXTWorkState
                INTEGER,
            optixSdhSncpEXTProtState
                INTEGER,
            optixSdhSncpEXTWorkUnitState
                INTEGER,
            optixSdhSncpEXTBackupState
                INTEGER,
            optixSdhSncpgEXTRowStatus
                RowStatus
        }

    -- 1.3.6.1.4.1.2011.2.25.4.10.46.1.5.1.1
    optixSdhSncpgEXTid OBJECT-TYPE
        SYNTAX Unsigned32
        MAX-ACCESS not-accessible
        STATUS current
        DESCRIPTION
            "This object indicates the SNCP group ID."
        ::= { optixSdhSncpgEXTEntry 1 }

    -- 1.3.6.1.4.1.2011.2.25.4.10.46.1.5.1.2
    optixSdhSncpEXTRevertMode OBJECT-TYPE
        SYNTAX INTEGER
        {
            rvt(1),
            norvt(0)
        }
        MAX-ACCESS read-create
        STATUS current
        DESCRIPTION
            "This object indicates the revertive mode of the SNCP group."
        ::= { optixSdhSncpgEXTEntry 2 }

    -- 1.3.6.1.4.1.2011.2.25.4.10.46.1.5.1.3
    optixSdhSncpEXTWtrTime OBJECT-TYPE
        SYNTAX Unsigned32
        MAX-ACCESS read-create
        STATUS current
        DESCRIPTION
            "This object indicates the WTR time of the SNCP group."
        ::= { optixSdhSncpgEXTEntry 3 }

    -- 1.3.6.1.4.1.2011.2.25.4.10.46.1.5.1.4
    optixSdhSncpEXTWorkPuid OBJECT-TYPE
        SYNTAX INTEGER
        {
            work(1),
            backup(0)
        }
        MAX-ACCESS read-create
        STATUS current
        DESCRIPTION
            "This object indicates the unit ID of the SNCP work unit."
        ::= { optixSdhSncpgEXTEntry 4 }

    -- 1.3.6.1.4.1.2011.2.25.4.10.46.1.5.1.5
    optixSdhSncpEXTWorkBid OBJECT-TYPE
        SYNTAX Unsigned32
        MAX-ACCESS read-create
        STATUS current
        DESCRIPTION
            "This object indicates theworking slot IDof the SNCP group."
        ::= { optixSdhSncpgEXTEntry 5 }

    -- 1.3.6.1.4.1.2011.2.25.4.10.46.1.5.1.6
    optixSdhSncpEXTWorkSubCardid OBJECT-TYPE
        SYNTAX Unsigned32
        MAX-ACCESS read-create
        STATUS current
        DESCRIPTION
            "This object indicates the subcard ID of the SNCP work unit."
        ::= { optixSdhSncpgEXTEntry 6 }

    -- 1.3.6.1.4.1.2011.2.25.4.10.46.1.5.1.7
    optixSdhSncpEXTWorkPid OBJECT-TYPE
        SYNTAX Unsigned32
        MAX-ACCESS read-create
        STATUS current
        DESCRIPTION
            "This object indicates theworking port number of the SNCP group."
        ::= { optixSdhSncpgEXTEntry 7 }

    -- 1.3.6.1.4.1.2011.2.25.4.10.46.1.5.1.8
    optixSdhSncpEXTWorkAu4id OBJECT-TYPE
        SYNTAX Unsigned32
        MAX-ACCESS read-create
        STATUS current
        DESCRIPTION
            "This object indicates the working channel ID of the SNCP group."
        ::= { optixSdhSncpgEXTEntry 8 }

    -- 1.3.6.1.4.1.2011.2.25.4.10.46.1.5.1.9
    optixSdhSncpEXTWorkPathid OBJECT-TYPE
        SYNTAX Unsigned32
        MAX-ACCESS read-create
        STATUS current
        DESCRIPTION
            "This object indicates the source path ID of the SNCP work unit."
        ::= { optixSdhSncpgEXTEntry 9 }

    -- 1.3.6.1.4.1.2011.2.25.4.10.46.1.5.1.10
    optixSdhSncpEXTBackupPuid OBJECT-TYPE
        SYNTAX INTEGER
        {
            work(1),
            backup(0)
        }
        MAX-ACCESS read-create
        STATUS current
        DESCRIPTION
            "This object indicates the unit ID of the SNCP protection unit."
        ::= { optixSdhSncpgEXTEntry 10 }

    -- 1.3.6.1.4.1.2011.2.25.4.10.46.1.5.1.11
    optixSdhSncpEXTBackupBid OBJECT-TYPE
        SYNTAX Unsigned32
        MAX-ACCESS read-create
        STATUS current
        DESCRIPTION
            "This object indicates theprotection slot ID of the SNCP group."
        ::= { optixSdhSncpgEXTEntry 11 }

    -- 1.3.6.1.4.1.2011.2.25.4.10.46.1.5.1.12
    optixSdhSncpEXTBackupSubCardid OBJECT-TYPE
        SYNTAX Unsigned32
        MAX-ACCESS read-create
        STATUS current
        DESCRIPTION
            "This object indicates the subcard ID of the SNCP protection unit."
        ::= { optixSdhSncpgEXTEntry 12 }

    -- 1.3.6.1.4.1.2011.2.25.4.10.46.1.5.1.13
    optixSdhSncpEXTBackupPid OBJECT-TYPE
        SYNTAX Unsigned32
        MAX-ACCESS read-create
        STATUS current
        DESCRIPTION
            "This object indicates theprotection port number of the SNCP group."
        ::= { optixSdhSncpgEXTEntry 13 }

    -- 1.3.6.1.4.1.2011.2.25.4.10.46.1.5.1.14
    optixSdhSncpEXTBackupAu4id OBJECT-TYPE
        SYNTAX Unsigned32
        MAX-ACCESS read-create
        STATUS current
        DESCRIPTION
            "This object indicates the protectionchannel ID of the SNCP group."
        ::= { optixSdhSncpgEXTEntry 14 }

    -- 1.3.6.1.4.1.2011.2.25.4.10.46.1.5.1.15
    optixSdhSncpEXTBackupPathid OBJECT-TYPE
        SYNTAX Unsigned32
        MAX-ACCESS read-create
        STATUS current
        DESCRIPTION
            "This object indicates the path ID of the SNCP protection unit."
        ::= { optixSdhSncpgEXTEntry 15 }

    -- 1.3.6.1.4.1.2011.2.25.4.10.46.1.5.1.16
    optixSdhSncpEXTDestBid OBJECT-TYPE
        SYNTAX Unsigned32
        MAX-ACCESS read-create
        STATUS current
        DESCRIPTION
            "This object indicates the destination board ID of the SNCP."
        ::= { optixSdhSncpgEXTEntry 16 }

    -- 1.3.6.1.4.1.2011.2.25.4.10.46.1.5.1.17
    optixSdhSncpEXTDestSubCardid OBJECT-TYPE
        SYNTAX Unsigned32
        MAX-ACCESS read-create
        STATUS current
        DESCRIPTION
            "This object indicates the destination subcard ID of the SNCP."
        ::= { optixSdhSncpgEXTEntry 17 }

    -- 1.3.6.1.4.1.2011.2.25.4.10.46.1.5.1.18
    optixSdhSncpEXTDestPid OBJECT-TYPE
        SYNTAX Unsigned32
        MAX-ACCESS read-create
        STATUS current
        DESCRIPTION
            "This object indicates the destination port ID of the SNCP."
        ::= { optixSdhSncpgEXTEntry 18 }

    -- 1.3.6.1.4.1.2011.2.25.4.10.46.1.5.1.19
    optixSdhSncpEXTDestAu4id OBJECT-TYPE
        SYNTAX Unsigned32
        MAX-ACCESS read-create
        STATUS current
        DESCRIPTION
            "This object indicates the destination au4 ID of the SNCP."
        ::= { optixSdhSncpgEXTEntry 19 }

    -- 1.3.6.1.4.1.2011.2.25.4.10.46.1.5.1.20
    optixSdhSncpEXTDestPathid OBJECT-TYPE
        SYNTAX Unsigned32
        MAX-ACCESS read-create
        STATUS current
        DESCRIPTION
            "This object indicates the destination path ID of the SNCP."
        ::= { optixSdhSncpgEXTEntry 20 }

    -- 1.3.6.1.4.1.2011.2.25.4.10.46.1.5.1.21
    optixSdhSncpEXTXcLevel OBJECT-TYPE
        SYNTAX INTEGER
        {
            allLevel(0),
            vc12(6),
            vc3(7),
            vc4(1),
            au4V4c(2),
            au4V8c(3),
            au4V16c(4),
            au4V64c(5),
            au3(9)
        }
        MAX-ACCESS read-create
        STATUS current
        DESCRIPTION
            "This object indicates the XC level of the SNCP."
        ::= { optixSdhSncpgEXTEntry 21 }

    -- 1.3.6.1.4.1.2011.2.25.4.10.46.1.5.1.22
    optixSdhSncpEXTSwitchReq OBJECT-TYPE
        SYNTAX INTEGER
        {
            sncpclear(16),
            sncpLocked(15),
            sncpFs(14),
            sncpSf(12),
            ncpSd(9),
            sncpMs(7),
            sncpWtr(5),
            sncpIdle(0)
        }
        MAX-ACCESS read-create
        STATUS current
        DESCRIPTION
            "This object indicates the switching request of the SNCP group."
        ::= { optixSdhSncpgEXTEntry 22 }

    -- 1.3.6.1.4.1.2011.2.25.4.10.46.1.5.1.23
    optixSdhSncpEXTSwitchDir OBJECT-TYPE
        SYNTAX INTEGER
        {
            w2p(0),
            p2w(1),
            invalid(3)
        }
        MAX-ACCESS read-create
        STATUS current
        DESCRIPTION
            "This object indicates the switch direction of the SNCP."
        ::= { optixSdhSncpgEXTEntry 23 }

    -- 1.3.6.1.4.1.2011.2.25.4.10.46.1.5.1.24
    optixSdhSncpEXTActiveFlag OBJECT-TYPE
        SYNTAX INTEGER
        {
            adding(1),
            deleting(2),
            active(3)
        }
        MAX-ACCESS read-only
        STATUS current
        DESCRIPTION
            "This object indicates the current activation flag of the SNCP group."
        ::= { optixSdhSncpgEXTEntry 24 }

    -- 1.3.6.1.4.1.2011.2.25.4.10.46.1.5.1.25
    optixSdhSncpEXTWorkPath OBJECT-TYPE
        SYNTAX INTEGER
        {
            workPath(1),
            backupPath(0),
            delayStart(255)
        }
        MAX-ACCESS read-only
        STATUS current
        DESCRIPTION
            "This object indicates the working path of the SNCP group."
        ::= { optixSdhSncpgEXTEntry 25 }

    -- 1.3.6.1.4.1.2011.2.25.4.10.46.1.5.1.26
    optixSdhSncpEXTWorkState OBJECT-TYPE
        SYNTAX INTEGER
        {
            sncpNormal(0),
            sncpSd(1),
            sncpSf(2)
        }
        MAX-ACCESS read-only
        STATUS current
        DESCRIPTION
            "This object indicates the working channel status of the SNCP group."
        ::= { optixSdhSncpgEXTEntry 26 }

    -- 1.3.6.1.4.1.2011.2.25.4.10.46.1.5.1.27
    optixSdhSncpEXTProtState OBJECT-TYPE
        SYNTAX INTEGER
        {
            sncpNormal(0),
            sncpSd(1),
            sncpSf(2)
        }
        MAX-ACCESS read-only
        STATUS current
        DESCRIPTION
            "This object indicates the protection channel status of the SNCP group."
        ::= { optixSdhSncpgEXTEntry 27 }

    -- 1.3.6.1.4.1.2011.2.25.4.10.46.1.5.1.28
    optixSdhSncpEXTWorkUnitState OBJECT-TYPE
        SYNTAX INTEGER
        {
            sncpNormal(0),
            sncpSd(1),
            sncpSf(2),
            sncpUnknown(3)
        }
        MAX-ACCESS read-only
        STATUS current
        DESCRIPTION
            "This object indicates the SNC monitoring point of the SNCP working unit."
        ::= { optixSdhSncpgEXTEntry 28 }

    -- 1.3.6.1.4.1.2011.2.25.4.10.46.1.5.1.29
    optixSdhSncpEXTBackupState OBJECT-TYPE
        SYNTAX INTEGER
        {
            sncpNormal(0),
            sncpSd(1),
            sncpSf(2),
            sncpUnknown(3)
        }
        MAX-ACCESS read-only
        STATUS current
        DESCRIPTION
            "This object indicates the SNC monitoring point of the SNCP protection unit."
        ::= { optixSdhSncpgEXTEntry 29 }

    -- 1.3.6.1.4.1.2011.2.25.4.10.46.1.5.1.255
    optixSdhSncpgEXTRowStatus OBJECT-TYPE
        SYNTAX RowStatus
        MAX-ACCESS read-create
        STATUS current
        DESCRIPTION
            "This object indicates the row status of the SNCP group."
        ::= { optixSdhSncpgEXTEntry 255 }

    -- 1.3.6.1.4.1.2011.2.25.4.10.46.1.12
    optixSdhXcToSncpTable OBJECT-TYPE
        SYNTAX SEQUENCE OF OptixSdhXcToSncpEntry
        MAX-ACCESS not-accessible
        STATUS current
        DESCRIPTION
            "This table implements conversion from cross-connections to SNCPs."
        ::= { optixSdhSncpGroup 12 }

    -- 1.3.6.1.4.1.2011.2.25.4.10.46.1.12.1
    optixSdhXcToSncpEntry OBJECT-TYPE
        SYNTAX OptixSdhXcToSncpEntry
        MAX-ACCESS not-accessible
        STATUS current
        DESCRIPTION
            "This entry implements conversion from cross-connections to SNCPs."
        INDEX{ optixSdhXcEXTId,optixSdhSncpEXTWorkBid,optixSdhSncpEXTWorkSubCardid,optixSdhSncpEXTWorkPid,optixSdhSncpEXTWorkAu4id,optixSdhSncpEXTWorkPathid,optixSdhSncpEXTDestBid,optixSdhSncpEXTDestSubCardid,optixSdhSncpEXTDestPid,optixSdhSncpEXTDestAu4id,optixSdhSncpEXTDestPathid,optixSdhSncpEXTXcLevel,optixSdhSncpgEXTid,optixSdhSncpEXTBackupBid,optixSdhSncpEXTBackupSubCardid,optixSdhSncpEXTBackupPid,optixSdhSncpEXTBackupAu4id,optixSdhSncpEXTBackupPathid }
        ::= { optixSdhXcToSncpTable 1 }

    OptixSdhXcToSncpEntry ::=
        SEQUENCE {
            optixSdhXcToSncpConvert
                INTEGER
        }

    -- 1.3.6.1.4.1.2011.2.25.4.10.46.1.12.1.1
    optixSdhXcToSncpConvert OBJECT-TYPE
        SYNTAX INTEGER
        {
            convert(0)
        }
        MAX-ACCESS read-write
        STATUS current
        DESCRIPTION
            "This object is used to implement conversion from cross-connections to SNCPs. No query result is available."
        ::= { optixSdhXcToSncpEntry 1 }

END
