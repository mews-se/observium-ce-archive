-- OPTIX-TUNNEL-OAM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-TUNNEL-OAM-MIB DEFINITIONS ::= BEGIN
    IMPORTS
        OBJECT-GROUP,MODULE-COMPLIANCE
            FROM SNMPv2-CONF
        MODULE-IDENTITY,OBJECT-TYPE,Unsigned32,Integer32,IpAddress
            FROM SNMPv2-SMI
        RowStatus
            FROM SNMPv2-TC
        optixProvisionPtn
            FROM OPTIX-OID-MIB
        ;

    optixTunnelOamMod MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage the MPLStunnel OAM. Thetunnel OAM provides complete fault detection and identification mechanism and network performance monitoringat thetunnel layer. Based on the OAM check result, the equipment determines whether to trigger protection switching.The tunnel OAM enables quick fault detection and identification and service protection."
        REVISION "201204170000Z"
        DESCRIPTION
            "Initial version of this MIB module"
        ::={ optixProvisionPtn 10 }

    -- 1.3.6.1.4.1.2011.2.25.4.50.10.1
    optixTunnelOamObject OBJECT IDENTIFIER ::= { optixTunnelOamMod 1 }

    -- 1.3.6.1.4.1.2011.2.25.4.50.10.1.1
    optixTunnelOamFdiEnable OBJECT-TYPE
        SYNTAX INTEGER
        {
            disable(0),
            enable(1)
        }
        MAX-ACCESS read-write
        STATUS current
        DESCRIPTION
            "This object indicates the enable status of the FDI function on the device. 0: disable 1: enable"
        DEFVAL{ 1 }
        ::= { optixTunnelOamObject 1 }

    -- 1.3.6.1.4.1.2011.2.25.4.50.10.1.2
    optixTunnelOamTable OBJECT-TYPE
        SYNTAX SEQUENCE OF OptixTunnelOamEntry
        MAX-ACCESS not-accessible
        STATUS current
        DESCRIPTION
            "This table is used to configuretunnel OAM attributes, includingthe tunnel OAM enable status, detection mode, CC detection mode, SD/SF thresholds, and query the OAM status."
        ::= { optixTunnelOamObject 2 }

    -- 1.3.6.1.4.1.2011.2.25.4.50.10.1.2.1
    optixTunnelOamEntry OBJECT-TYPE
        SYNTAX OptixTunnelOamEntry
        MAX-ACCESS not-accessible
        STATUS current
        DESCRIPTION
            "This entry is used to manage tunnel OAM attributes and status."
        INDEX{ optixTunnelOamIndex }
        ::= { optixTunnelOamTable 1 }

    OptixTunnelOamEntry ::=
        SEQUENCE {
            optixTunnelOamIndex
                Unsigned32,
            optixTunnelOamEnable
                INTEGER,
            optixTunnelOamCheckWay
                INTEGER,
            optixTunnelOamCcType
                INTEGER,
            optixTunnelOamCcTime
                Unsigned32,
            optixTunnelOamCcSend
                INTEGER,
            optixTunnelOamSf
                Unsigned32,
            optixTunnelOamSd
                Unsigned32,
            optixTunnelOamRevTunnelindex
                Unsigned32,
            optixTunnelOamStandard
                INTEGER,
            optixTunnelOamRowStatus
                RowStatus
        }

    -- 1.3.6.1.4.1.2011.2.25.4.50.10.1.2.1.1
    optixTunnelOamIndex OBJECT-TYPE
        SYNTAX Unsigned32
        MAX-ACCESS not-accessible
        STATUS current
        DESCRIPTION
            "This object indicates the tunnel OAM index, ranging from 1 to 0x00ffffff."
        ::= { optixTunnelOamEntry 1 }

    -- 1.3.6.1.4.1.2011.2.25.4.50.10.1.2.1.2
    optixTunnelOamEnable OBJECT-TYPE
        SYNTAX INTEGER
        {
            disable(0),
            enable(1)
        }
        MAX-ACCESS read-write
        STATUS current
        DESCRIPTION
            "This object indicates whether the OAM is enabled. 1: enable 0: disable"
        DEFVAL{ 0 }
        ::= { optixTunnelOamEntry 2 }

    -- 1.3.6.1.4.1.2011.2.25.4.50.10.1.2.1.3
    optixTunnelOamCheckWay OBJECT-TYPE
        SYNTAX INTEGER
        {
            self(1),
            manu(2),
            invalid(255)
        }
        MAX-ACCESS read-write
        STATUS current
        DESCRIPTION
            "This object indicates the OAM detection mode. 1: self 2: manu 255: invalid detection mode This parameter is unconfigurable when the tunnel is a unidirectional ingress tunnel.The queried value is invalid."
        DEFVAL{ 1 }
        ::= { optixTunnelOamEntry 3 }

    -- 1.3.6.1.4.1.2011.2.25.4.50.10.1.2.1.4
    optixTunnelOamCcType OBJECT-TYPE
        SYNTAX INTEGER
        {
            cv(1),
            ffd(2)
        }
        MAX-ACCESS read-write
        STATUS current
        DESCRIPTION
            "This object indicates the CC detection packet type. 1: cv (default value) 2: ffd"
        DEFVAL{ 1 }
        ::= { optixTunnelOamEntry 4 }

    -- 1.3.6.1.4.1.2011.2.25.4.50.10.1.2.1.5
    optixTunnelOamCcTime OBJECT-TYPE
        SYNTAX Unsigned32(1..7|255)
        MAX-ACCESS read-write
        STATUS current
        DESCRIPTION
            "This object indicates the CC detection packet frequency. When the packet type is cv, the frequency is an invalid value, 0xff. When the packet type is ffd, the valid value of the frequency is as follows: 1: 3.3 ms 2: 10 ms 3: 20 ms 4: 50 ms 5: 100 ms 6: 200 ms 7: 500 ms"
        DEFVAL{ 255 }
        ::= { optixTunnelOamEntry 5 }

    -- 1.3.6.1.4.1.2011.2.25.4.50.10.1.2.1.6
    optixTunnelOamCcSend OBJECT-TYPE
        SYNTAX INTEGER
        {
            disable(0),
            enable(1),
            invalid(255)
        }
        MAX-ACCESS read-write
        STATUS current
        DESCRIPTION
            "This object indicates the CC start/stop status. 0: disable1: enable 255: invalid This parameter is unconfigurable when the tunnel is a unidirectional egress node. The quried value is invalid."
        DEFVAL{ 1 }
        ::= { optixTunnelOamEntry 6 }

    -- 1.3.6.1.4.1.2011.2.25.4.50.10.1.2.1.7
    optixTunnelOamSf OBJECT-TYPE
        SYNTAX Unsigned32(0..255)
        MAX-ACCESS read-write
        STATUS current
        DESCRIPTION
            "This object indicates the SF threshold (packet loss rate). Valid values range from 0 to 100."
        DEFVAL{ 0 }
        ::= { optixTunnelOamEntry 7 }

    -- 1.3.6.1.4.1.2011.2.25.4.50.10.1.2.1.8
    optixTunnelOamSd OBJECT-TYPE
        SYNTAX Unsigned32(0..255)
        MAX-ACCESS read-write
        STATUS current
        DESCRIPTION
            "This object indicates the SD threshold (packet loss rate). Valid values range from 0 to 100."
        DEFVAL{ 0 }
        ::= { optixTunnelOamEntry 8 }

    -- 1.3.6.1.4.1.2011.2.25.4.50.10.1.2.1.9
    optixTunnelOamRevTunnelindex OBJECT-TYPE
        SYNTAX Unsigned32
        MAX-ACCESS read-write
        STATUS current
        DESCRIPTION
            "This object indicates the reverse tunnel index. This parameter is applicable to only when the tunnel serves as an egress node. When the value is 0xffffffff, the reverse tunnel index is not configured."
        DEFVAL{ 4294967295 }
        ::= { optixTunnelOamEntry 9 }

    -- 1.3.6.1.4.1.2011.2.25.4.50.10.1.2.1.10
    optixTunnelOamStandard OBJECT-TYPE
        SYNTAX INTEGER
        {
            y1711(1),
            y1731(2)
        }
        MAX-ACCESS read-write
        STATUS current
        DESCRIPTION
            "This object indicates the OAM protocol standard&amp;nbsp; 1: 1711 2: 1731"
        DEFVAL{ 1 }
        ::= { optixTunnelOamEntry 10 }

    -- 1.3.6.1.4.1.2011.2.25.4.50.10.1.2.1.255
    optixTunnelOamRowStatus OBJECT-TYPE
        SYNTAX RowStatus
        MAX-ACCESS read-write
        STATUS current
        DESCRIPTION
            "This object indicates the row status. 1: active 6: destroy,destroy indicates clearing the instance's configure.createAndGo is not supported"
        ::= { optixTunnelOamEntry 255 }

    -- 1.3.6.1.4.1.2011.2.25.4.50.10.1.3
    optixTunnelOamStateTable OBJECT-TYPE
        SYNTAX SEQUENCE OF OptixTunnelOamStateEntry
        MAX-ACCESS not-accessible
        STATUS current
        DESCRIPTION
            "This table is used to query thetunnel OAM status."
        ::= { optixTunnelOamObject 3 }

    -- 1.3.6.1.4.1.2011.2.25.4.50.10.1.3.1
    optixTunnelOamStateEntry OBJECT-TYPE
        SYNTAX OptixTunnelOamStateEntry
        MAX-ACCESS not-accessible
        STATUS current
        DESCRIPTION
            "This entry is used tomanage the tunnel OAM status."
        INDEX{ optixTunnelOamIndex,optixTunnelOamDirection }
        ::= { optixTunnelOamStateTable 1 }

    OptixTunnelOamStateEntry ::=
        SEQUENCE {
            optixTunnelOamDirection
                INTEGER,
            optixTunnelOamState
                INTEGER,
            optixTunnelOamDefectType
                INTEGER,
            optixTunnelOamUnavailableTime
                Unsigned32,
            optixTunnelOamDefectPosition
                IpAddress
        }

    -- 1.3.6.1.4.1.2011.2.25.4.50.10.1.3.1.1
    optixTunnelOamDirection OBJECT-TYPE
        SYNTAX INTEGER
        {
            farend(0),
            nearend(1)
        }
        MAX-ACCESS not-accessible
        STATUS current
        DESCRIPTION
            "For bidirectional tunnels, the status query is performaned in two directions, local and remote ends. This object indicates the direction of thetunnel OAM, localor remote end. For unidirectional ingress tunnels, only the local query result is returned. While forunidirectional egress tunnels, only the remote query result is returned."
        ::= { optixTunnelOamStateEntry 1 }

    -- 1.3.6.1.4.1.2011.2.25.4.50.10.1.3.1.2
    optixTunnelOamState OBJECT-TYPE
        SYNTAX INTEGER
        {
            initialstate(0),
            nearendavailable(1),
            nearenddefectavailable(2),
            nearenddefectunavailable(3),
            nearendunavailable(4),
            farendavailable(5),
            farenddefectavailable(6),
            farenddefectunavailable(7),
            farendunavailable(8)
        }
        MAX-ACCESS read-only
        STATUS current
        DESCRIPTION
            "This object indicates the tunnel OAM status. 0: initialstate, 1: nearendavailable, 2: nearenddefectavailable, 3: nearenddefectunavailable, 4: nearendunavailable, 5: farendavailable, 6: farenddefectavailable, 7: farenddefectunavailable, 8: farendunavailable"
        ::= { optixTunnelOamStateEntry 2 }

    -- 1.3.6.1.4.1.2011.2.25.4.50.10.1.3.1.3
    optixTunnelOamDefectType OBJECT-TYPE
        SYNTAX INTEGER
        {
            dserver(1),
            dpeerme(2),
            dlocv(3),
            dttsimismatch(4),
            dttsimismerge(5),
            dexcess(6),
            dunknown(7),
            invalid(255)
        }
        MAX-ACCESS read-only
        STATUS current
        DESCRIPTION
            "This object indicates the defect type of the tunnel OAM. 1: dserver, 2: dpeerme, 3: dlocv, 4: dttsimismatch, 5: dttsimismerge, 6: dexcess, 7: dunknown, 255: invalid"
        ::= { optixTunnelOamStateEntry 3 }

    -- 1.3.6.1.4.1.2011.2.25.4.50.10.1.3.1.4
    optixTunnelOamUnavailableTime OBJECT-TYPE
        SYNTAX Unsigned32
        MAX-ACCESS read-only
        STATUS current
        DESCRIPTION
            "This object indicates the unavailable time of the tunnel. The time ranges from 0 to 300,000 ms. 4294967295: invalid"
        ::= { optixTunnelOamStateEntry 4 }

    -- 1.3.6.1.4.1.2011.2.25.4.50.10.1.3.1.5
    optixTunnelOamDefectPosition OBJECT-TYPE
        SYNTAX IpAddress
        MAX-ACCESS read-only
        STATUS current
        DESCRIPTION
            "This object indicates the position of the tunnel defect: a node identified by IP address."
        ::= { optixTunnelOamStateEntry 5 }

END
