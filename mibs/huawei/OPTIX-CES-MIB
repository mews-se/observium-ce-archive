-- OPTIX-CES-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-CES-MIB DEFINITIONS ::= BEGIN
    IMPORTS
        OBJECT-GROUP,MODULE-COMPLIANCE
            FROM SNMPv2-CONF
        MODULE-IDENTITY,OBJECT-TYPE,Unsigned32,Integer32,IpAddress,Counter64
            FROM SNMPv2-SMI
        RowStatus
            FROM SNMPv2-TC
        optixProvisionPtn
            FROM OPTIX-OID-MIB
        ;

    optixCesMod MODULE-IDENTITY
        LAST-UPDATED "201204120000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to manage configurations of the circuit emulation service (CES). The CES service adopts the PWE3 emulation technology. The PWE3 packet header carries TDM service stream information, including alarm, signaling, and timing synchronization information. The PW packets are encapsulated andtransmitted through the MPLS tunnel on the PSN network. After reaching the PW output port, the PW packets are decapsulated for rebuilding the TDM circuit switching service stream."
        REVISION "201204120000Z"
        DESCRIPTION
            "Initial version of this MIB module"
        ::={ optixProvisionPtn 2 }

    -- 1.3.6.1.4.1.2011.2.25.4.50.2.1
    optixCesObject OBJECT IDENTIFIER ::= { optixCesMod 1 }

    -- 1.3.6.1.4.1.2011.2.25.4.50.2.1.1
    optixUnitoUniCesTable OBJECT-TYPE
        SYNTAX SEQUENCE OF OptixUnitoUniCesEntry
        MAX-ACCESS not-accessible
        STATUS current
        DESCRIPTION
            "This table implements the configurations of the local private UNI-UNI CES service. These configurations include the service index, service ID, service name, and UNI information (such as the slot ID, subboard ID, port number, and high-/lower-order channel ID)."
        ::= { optixCesObject 1 }

    -- 1.3.6.1.4.1.2011.2.25.4.50.2.1.1.1
    optixUnitoUniCesEntry OBJECT-TYPE
        SYNTAX OptixUnitoUniCesEntry
        MAX-ACCESS not-accessible
        STATUS current
        DESCRIPTION
            "This entry indicates the local CES parameter table."
        INDEX{ optixUnitoUniCesIndex,optixUnitoUniCesFirstUniId,optixUnitoUniCesSecondUniId }
        ::= { optixUnitoUniCesTable 1 }

    OptixUnitoUniCesEntry ::=
        SEQUENCE {
            optixUnitoUniCesIndex
                Unsigned32,
            optixUnitoUniCesFirstUniId
                Unsigned32,
            optixUnitoUniCesSecondUniId
                Unsigned32,
            optixUnitoUniCesId
                Unsigned32,
            optixUnitoUniCesName
                OCTET STRING,
            optixUnitoUniCesFirstUniBid
                Unsigned32,
            optixUnitoUniCesFirstUniSubBid
                Unsigned32,
            optixUnitoUniCesFirstUniPortId
                Unsigned32,
            optixUnitoUniCesFirstUniHpPath
                Unsigned32,
            optixUnitoUniCesFirstUniLpPath
                Unsigned32,
            optixUnitoUniCesFirstUniLevel
                INTEGER,
            optixUnitoUniCesFirstUnislotNum
                Unsigned32,
            optixUnitoUniCesFirstUnislotList
                OCTET STRING,
            optixUnitoUniCesSecondUniBid
                Unsigned32,
            optixUnitoUniCesSecondUniSubBid
                Unsigned32,
            optixUnitoUniCesSecondUniPortId
                Unsigned32,
            optixUnitoUniCesSecondUniHpPath
                Unsigned32,
            optixUnitoUniCesSecondUniLpPath
                Unsigned32,
            optixUnitoUniCesSecondUniLevel
                INTEGER,
            optixUnitoUniCesSecondUnislotNum
                Unsigned32,
            optixUnitoUniCesSecondUnislotList
                OCTET STRING,
            optixUnitoUniCesRowStatus
                RowStatus
        }

    -- 1.3.6.1.4.1.2011.2.25.4.50.2.1.1.1.1
    optixUnitoUniCesIndex OBJECT-TYPE
        SYNTAX Unsigned32
        MAX-ACCESS not-accessible
        STATUS current
        DESCRIPTION
            "This object indicates the service index."
        ::= { optixUnitoUniCesEntry 1 }

    -- 1.3.6.1.4.1.2011.2.25.4.50.2.1.1.1.2
    optixUnitoUniCesFirstUniId OBJECT-TYPE
        SYNTAX Unsigned32(1..65535)
        MAX-ACCESS not-accessible
        STATUS current
        DESCRIPTION
            "This object indicates the first V-UNI ID of the service. Value range: 1 to 65535"
        ::= { optixUnitoUniCesEntry 2 }

    -- 1.3.6.1.4.1.2011.2.25.4.50.2.1.1.1.3
    optixUnitoUniCesSecondUniId OBJECT-TYPE
        SYNTAX Unsigned32(1..65535)
        MAX-ACCESS not-accessible
        STATUS current
        DESCRIPTION
            "This object indicates the second V-UNI ID of the service. Value range: 1 to 65535"
        ::= { optixUnitoUniCesEntry 3 }

    -- 1.3.6.1.4.1.2011.2.25.4.50.2.1.1.1.4
    optixUnitoUniCesId OBJECT-TYPE
        SYNTAX Unsigned32
        MAX-ACCESS read-create
        STATUS current
        DESCRIPTION
            "This object indicates the CES service ID."
        ::= { optixUnitoUniCesEntry 4 }

    -- 1.3.6.1.4.1.2011.2.25.4.50.2.1.1.1.5
    optixUnitoUniCesName OBJECT-TYPE
        SYNTAX OCTET STRING(SIZE(0..64))
        MAX-ACCESS read-create
        STATUS current
        DESCRIPTION
            "This object indicates the service name, which is a character stringcontaining 64 bytes."
        DEFVAL{ "" }
        ::= { optixUnitoUniCesEntry 5 }

    -- 1.3.6.1.4.1.2011.2.25.4.50.2.1.1.1.6
    optixUnitoUniCesFirstUniBid OBJECT-TYPE
        SYNTAX Unsigned32(1..65535)
        MAX-ACCESS read-create
        STATUS current
        DESCRIPTION
            "This object indicates the first V-UNI slot ID of the service. Value range: 1 to 65535"
        ::= { optixUnitoUniCesEntry 6 }

    -- 1.3.6.1.4.1.2011.2.25.4.50.2.1.1.1.7
    optixUnitoUniCesFirstUniSubBid OBJECT-TYPE
        SYNTAX Unsigned32(1..255)
        MAX-ACCESS read-create
        STATUS current
        DESCRIPTION
            "This object indicates the first V-UNI subboard ID of the service. Value range: 1 to 255"
        ::= { optixUnitoUniCesEntry 7 }

    -- 1.3.6.1.4.1.2011.2.25.4.50.2.1.1.1.8
    optixUnitoUniCesFirstUniPortId OBJECT-TYPE
        SYNTAX Unsigned32(1..65535)
        MAX-ACCESS read-create
        STATUS current
        DESCRIPTION
            "This object indicates the first V-UNI port number of the service. Value range: 1 to 65535"
        ::= { optixUnitoUniCesEntry 8 }

    -- 1.3.6.1.4.1.2011.2.25.4.50.2.1.1.1.9
    optixUnitoUniCesFirstUniHpPath OBJECT-TYPE
        SYNTAX Unsigned32(1..65535)
        MAX-ACCESS read-create
        STATUS current
        DESCRIPTION
            "This object indicates the first V-UNI high-order channel ID of the service. The high-order channel ID is compatible with other STM-N services. When the service is carried through E1 ports, the high-/low-order channel ID is unavailable and the value is an invalid value, 0xffff. When VC4 and 3xVC3 emulation services are provided, the VC4 and 3xVC3 channel IDs must be 1."
        ::= { optixUnitoUniCesEntry 9 }

    -- 1.3.6.1.4.1.2011.2.25.4.50.2.1.1.1.10
    optixUnitoUniCesFirstUniLpPath OBJECT-TYPE
        SYNTAX Unsigned32(1..65535)
        MAX-ACCESS read-create
        STATUS current
        DESCRIPTION
            "This object indicates the first V-UNI low-order channel ID of the service. The low-order channel ID is compatible with other STM-N services. When the service is carried through E1 ports, the high/low order channel ID is unavailable and the value is an invalid value, 0xffff. When VC4 and 3xVC3 emulation services are provided, the VC4 and 3xVC3 channel IDs must be 0xffff."
        ::= { optixUnitoUniCesEntry 10 }

    -- 1.3.6.1.4.1.2011.2.25.4.50.2.1.1.1.11
    optixUnitoUniCesFirstUniLevel OBJECT-TYPE
        SYNTAX INTEGER
        {
            vc12(1),
            vc3(2),
            vc11(3),
            vc4(4),
            triplicatevc3(5),
            invalid(255)
        }
        MAX-ACCESS read-create
        STATUS current
        DESCRIPTION
            "This object indicates the first V-UNI channel level of the service. 1: VC12 2: VC3 3: VC11 4: VC4 5: triplicatevc3 255:invalid"
        DEFVAL{ 1 }
        ::= { optixUnitoUniCesEntry 11 }

    -- 1.3.6.1.4.1.2011.2.25.4.50.2.1.1.1.12
    optixUnitoUniCesFirstUnislotNum OBJECT-TYPE
        SYNTAX Unsigned32(0..32)
        MAX-ACCESS read-create
        STATUS current
        DESCRIPTION
            "This object indicates the number of valid timeslots of the first V-UNI. 0: all timeslots"
        ::= { optixUnitoUniCesEntry 12 }

    -- 1.3.6.1.4.1.2011.2.25.4.50.2.1.1.1.13
    optixUnitoUniCesFirstUnislotList OBJECT-TYPE
        SYNTAX OCTET STRING(SIZE(0..64))
        MAX-ACCESS read-create
        STATUS current
        DESCRIPTION
            "This object indicates the valid timeslot list of the first service V-UNI. Each timeslot of the channel occupies two bytes."
        ::= { optixUnitoUniCesEntry 13 }

    -- 1.3.6.1.4.1.2011.2.25.4.50.2.1.1.1.14
    optixUnitoUniCesSecondUniBid OBJECT-TYPE
        SYNTAX Unsigned32(1..65535)
        MAX-ACCESS read-create
        STATUS current
        DESCRIPTION
            "This object indicates the second V-UNI slot ID of the service. Value range: 1 to 65535"
        ::= { optixUnitoUniCesEntry 14 }

    -- 1.3.6.1.4.1.2011.2.25.4.50.2.1.1.1.15
    optixUnitoUniCesSecondUniSubBid OBJECT-TYPE
        SYNTAX Unsigned32(1..255)
        MAX-ACCESS read-create
        STATUS current
        DESCRIPTION
            "This object indicates the second V-UNI subboard ID of the service. Value range: 1 to 255"
        ::= { optixUnitoUniCesEntry 15 }

    -- 1.3.6.1.4.1.2011.2.25.4.50.2.1.1.1.16
    optixUnitoUniCesSecondUniPortId OBJECT-TYPE
        SYNTAX Unsigned32(1..65535)
        MAX-ACCESS read-create
        STATUS current
        DESCRIPTION
            "This object indicates the second V-UNI port number of the service. Value range: 1 to 65535"
        ::= { optixUnitoUniCesEntry 16 }

    -- 1.3.6.1.4.1.2011.2.25.4.50.2.1.1.1.17
    optixUnitoUniCesSecondUniHpPath OBJECT-TYPE
        SYNTAX Unsigned32(1..65535)
        MAX-ACCESS read-create
        STATUS current
        DESCRIPTION
            "This object indicates the second V-UNI high-order channel ID of the service. The high-order channel ID is compatible with other STM-N services. When the service is carried through E1 ports, the high/low order channel ID is unavailable and the value is an invalid value, 0xffff. When VC4 and 3xVC3 emulation services are provided, the VC4 and 3xVC3 channel IDs must be 1."
        ::= { optixUnitoUniCesEntry 17 }

    -- 1.3.6.1.4.1.2011.2.25.4.50.2.1.1.1.18
    optixUnitoUniCesSecondUniLpPath OBJECT-TYPE
        SYNTAX Unsigned32(1..65535)
        MAX-ACCESS read-create
        STATUS current
        DESCRIPTION
            "This object indicates the second V-UNI low-order channel ID of the service. The low-order channel ID is compatible with other STM-N services. When the service is carried through E1 ports, the high/low order channel ID is unavailable and the value is an invalid value, 0xffff. When VC4 and 3xVC3 emulation services are provided, the VC4 and 3xVC3 channel IDs must be 0xffff."
        ::= { optixUnitoUniCesEntry 18 }

    -- 1.3.6.1.4.1.2011.2.25.4.50.2.1.1.1.19
    optixUnitoUniCesSecondUniLevel OBJECT-TYPE
        SYNTAX INTEGER
        {
            vc12(1),
            vc3(2),
            vc11(3),
            vc4(4),
            triplicatevc3(5),
            invalid(255)
        }
        MAX-ACCESS read-create
        STATUS current
        DESCRIPTION
            "This object indicates the second V-UNI channel level of the service. 1: VC12 2: VC3 3: VC11 4: VC4 5: triplicatevc3 255:invalid"
        DEFVAL{ 1 }
        ::= { optixUnitoUniCesEntry 19 }

    -- 1.3.6.1.4.1.2011.2.25.4.50.2.1.1.1.20
    optixUnitoUniCesSecondUnislotNum OBJECT-TYPE
        SYNTAX Unsigned32(0..32)
        MAX-ACCESS read-create
        STATUS current
        DESCRIPTION
            "This object indicates the number of valid timeslots of the second V-UNI. 0: all timeslots"
        ::= { optixUnitoUniCesEntry 20 }

    -- 1.3.6.1.4.1.2011.2.25.4.50.2.1.1.1.21
    optixUnitoUniCesSecondUnislotList OBJECT-TYPE
        SYNTAX OCTET STRING(SIZE(0..64))
        MAX-ACCESS read-create
        STATUS current
        DESCRIPTION
            "This object indicates the valid timeslot list of the second service V-UNI. Each timeslot of the channel occupies two bytes."
        ::= { optixUnitoUniCesEntry 21 }

    -- 1.3.6.1.4.1.2011.2.25.4.50.2.1.1.1.255
    optixUnitoUniCesRowStatus OBJECT-TYPE
        SYNTAX RowStatus
        MAX-ACCESS read-create
        STATUS current
        DESCRIPTION
            "Thisobject indicates the row status. 1: active 4: createAndGo 6: destroy"
        ::= { optixUnitoUniCesEntry 255 }

    -- 1.3.6.1.4.1.2011.2.25.4.50.2.1.2
    optixUnitoNniCesTable OBJECT-TYPE
        SYNTAX SEQUENCE OF OptixUnitoNniCesEntry
        MAX-ACCESS not-accessible
        STATUS current
        DESCRIPTION
            "This table implements the configurations of the remote private UNI-UNI CES service. These configurations include the service index, service ID, service name, UNI information (such as the slot ID, subboard ID, port number, and high-/lower-order channel ID), and PW index carried by NNIs."
        ::= { optixCesObject 2 }

    -- 1.3.6.1.4.1.2011.2.25.4.50.2.1.2.1
    optixUnitoNniCesEntry OBJECT-TYPE
        SYNTAX OptixUnitoNniCesEntry
        MAX-ACCESS not-accessible
        STATUS current
        DESCRIPTION
            "This entry indicates the remote CES parameter table."
        INDEX{ optixUnitoNniCesIndex,optixUnitoNniCesUniId,optixUnitoNniCesNniId }
        ::= { optixUnitoNniCesTable 1 }

    OptixUnitoNniCesEntry ::=
        SEQUENCE {
            optixUnitoNniCesIndex
                Unsigned32,
            optixUnitoNniCesUniId
                Unsigned32,
            optixUnitoNniCesNniId
                Unsigned32,
            optixUnitoNniCesId
                Unsigned32,
            optixUnitoNniCesName
                OCTET STRING,
            optixUnitoNniCesUniBid
                Unsigned32,
            optixUnitoNniCesUniSubBid
                Unsigned32,
            optixUnitoNniCesUniPortId
                Unsigned32,
            optixUnitoNniCesUniHpPath
                Unsigned32,
            optixUnitoNniCesUniLpPath
                Unsigned32,
            optixUnitoNniCesUniLevel
                INTEGER,
            optixUnitoNniCesUnislotNum
                Unsigned32,
            optixUnitoNniCesUnislotList
                OCTET STRING,
            optixUnitoNniCesUniPri
                INTEGER,
            optixUnitoNniCesNniPwIndex
                Unsigned32,
            optixUnitoNniCesRowStatus
                RowStatus
        }

    -- 1.3.6.1.4.1.2011.2.25.4.50.2.1.2.1.1
    optixUnitoNniCesIndex OBJECT-TYPE
        SYNTAX Unsigned32
        MAX-ACCESS not-accessible
        STATUS current
        DESCRIPTION
            "This object indicates the service index."
        ::= { optixUnitoNniCesEntry 1 }

    -- 1.3.6.1.4.1.2011.2.25.4.50.2.1.2.1.2
    optixUnitoNniCesUniId OBJECT-TYPE
        SYNTAX Unsigned32(1..65535)
        MAX-ACCESS not-accessible
        STATUS current
        DESCRIPTION
            "This object indicates the service V-UNI ID. Value range: 1 to 65535"
        ::= { optixUnitoNniCesEntry 2 }

    -- 1.3.6.1.4.1.2011.2.25.4.50.2.1.2.1.3
    optixUnitoNniCesNniId OBJECT-TYPE
        SYNTAX Unsigned32(1..65535)
        MAX-ACCESS not-accessible
        STATUS current
        DESCRIPTION
            "This object indicates the service V-NNI ID. Value range: 1 to 65535"
        ::= { optixUnitoNniCesEntry 3 }

    -- 1.3.6.1.4.1.2011.2.25.4.50.2.1.2.1.4
    optixUnitoNniCesId OBJECT-TYPE
        SYNTAX Unsigned32
        MAX-ACCESS read-create
        STATUS current
        DESCRIPTION
            "This object indicates the CES service ID."
        ::= { optixUnitoNniCesEntry 4 }

    -- 1.3.6.1.4.1.2011.2.25.4.50.2.1.2.1.5
    optixUnitoNniCesName OBJECT-TYPE
        SYNTAX OCTET STRING(SIZE(0..64))
        MAX-ACCESS read-create
        STATUS current
        DESCRIPTION
            "This object indicates the service name, which is a character string containing 64 bytes."
        DEFVAL{ "" }
        ::= { optixUnitoNniCesEntry 5 }

    -- 1.3.6.1.4.1.2011.2.25.4.50.2.1.2.1.6
    optixUnitoNniCesUniBid OBJECT-TYPE
        SYNTAX Unsigned32(1..65535)
        MAX-ACCESS read-create
        STATUS current
        DESCRIPTION
            "This object indicates the slot ID of the service V-UNI. Value range: 1 to 65535"
        ::= { optixUnitoNniCesEntry 6 }

    -- 1.3.6.1.4.1.2011.2.25.4.50.2.1.2.1.7
    optixUnitoNniCesUniSubBid OBJECT-TYPE
        SYNTAX Unsigned32(1..255)
        MAX-ACCESS read-create
        STATUS current
        DESCRIPTION
            "This object indicates the subboard ID of the service V-UNI. Value range: 1 to 65535"
        ::= { optixUnitoNniCesEntry 7 }

    -- 1.3.6.1.4.1.2011.2.25.4.50.2.1.2.1.8
    optixUnitoNniCesUniPortId OBJECT-TYPE
        SYNTAX Unsigned32(1..65535)
        MAX-ACCESS read-create
        STATUS current
        DESCRIPTION
            "This object indicates the port number of the service V-UNI. Value range: 1 to 65535"
        ::= { optixUnitoNniCesEntry 8 }

    -- 1.3.6.1.4.1.2011.2.25.4.50.2.1.2.1.9
    optixUnitoNniCesUniHpPath OBJECT-TYPE
        SYNTAX Unsigned32(1..65535)
        MAX-ACCESS read-create
        STATUS current
        DESCRIPTION
            "This object indicates the high-order channel ID of the service V-UNI. The high-order channel ID is compatible with other STM-N services. When the service is carried through E1 ports, the high/low order channel ID is unavailable and the value is an invalid value, 0xffff. When VC4 and 3xVC3 emulation services are provided, the VC4 and 3xVC3 channel IDs must be 1."
        ::= { optixUnitoNniCesEntry 9 }

    -- 1.3.6.1.4.1.2011.2.25.4.50.2.1.2.1.10
    optixUnitoNniCesUniLpPath OBJECT-TYPE
        SYNTAX Unsigned32(1..65535)
        MAX-ACCESS read-create
        STATUS current
        DESCRIPTION
            "This object indicates the low-order channel ID of the service V-UNI. The low-order channel ID is compatible with other STM-N services. When the service is carried through E1 ports, the high/low order channel ID is unavailable and the value is an invalid value, 0xffff. When VC4 and 3xVC3 emulation services are provided, the VC4 and 3xVC3 channel IDs must be 0xffff."
        ::= { optixUnitoNniCesEntry 10 }

    -- 1.3.6.1.4.1.2011.2.25.4.50.2.1.2.1.11
    optixUnitoNniCesUniLevel OBJECT-TYPE
        SYNTAX INTEGER
        {
            vc12(1),
            vc3(2),
            vc11(3),
            vc4(4),
            triplicatevc3(5)
        }
        MAX-ACCESS read-create
        STATUS current
        DESCRIPTION
            "This object indicates the V-UNI channel level of the service. 1: VC12 2: VC3 3: VC11 4: VC4 5: triplicatevc3"
        DEFVAL{ 1 }
        ::= { optixUnitoNniCesEntry 11 }

    -- 1.3.6.1.4.1.2011.2.25.4.50.2.1.2.1.12
    optixUnitoNniCesUnislotNum OBJECT-TYPE
        SYNTAX Unsigned32(0..32)
        MAX-ACCESS read-create
        STATUS current
        DESCRIPTION
            "This object indicates the number of valid timeslots of theservice V-UNI. 0: all timeslots"
        ::= { optixUnitoNniCesEntry 12 }

    -- 1.3.6.1.4.1.2011.2.25.4.50.2.1.2.1.13
    optixUnitoNniCesUnislotList OBJECT-TYPE
        SYNTAX OCTET STRING(SIZE(0..64))
        MAX-ACCESS read-create
        STATUS current
        DESCRIPTION
            "This object indicates the valid timeslot list of the service V-UNI. Each timeslot of the channel occupies two bytes."
        ::= { optixUnitoNniCesEntry 13 }

    -- 1.3.6.1.4.1.2011.2.25.4.50.2.1.2.1.14
    optixUnitoNniCesUniPri OBJECT-TYPE
        SYNTAX INTEGER
        {
            cs7(1),
            cs6(2),
            ef(3),
            af4(4),
            af3(5),
            af2(6),
            af1(7),
            be(8)
        }
        MAX-ACCESS read-create
        STATUS current
        DESCRIPTION
            "This object indicates the CES service priority of the service V-UNI. The value ranges from 1 to 8. Valid values: 1: CS7 2: CS6 3: EF 4: AF4 5: AF3 6: AF2 7: AF1 8: BE"
        DEFVAL{ 3 }
        ::= { optixUnitoNniCesEntry 14 }

    -- 1.3.6.1.4.1.2011.2.25.4.50.2.1.2.1.15
    optixUnitoNniCesNniPwIndex OBJECT-TYPE
        SYNTAX Unsigned32
        MAX-ACCESS read-create
        STATUS current
        DESCRIPTION
            "This object indicates the index to the PW carried by the NNI."
        ::= { optixUnitoNniCesEntry 15 }

    -- 1.3.6.1.4.1.2011.2.25.4.50.2.1.2.1.255
    optixUnitoNniCesRowStatus OBJECT-TYPE
        SYNTAX RowStatus
        MAX-ACCESS read-create
        STATUS current
        DESCRIPTION
            "This object indicates the row status. 1: active 4: createAndGo 6: destroy"
        ::= { optixUnitoNniCesEntry 255 }

    -- 1.3.6.1.4.1.2011.2.25.4.50.2.1.3
    optixSohThoroughCesTable OBJECT-TYPE
        SYNTAX SEQUENCE OF OptixSohThoroughCesEntry
        MAX-ACCESS not-accessible
        STATUS current
        DESCRIPTION
            "This table implements the configurations of transparent transmission of CES services with section overheads (including MS and RS overheads)and ensures the transmission of SDH overheads from both ends of the service. The supported attributes include UNI-UNI service attributes and especially the SDH overheads for transparent transmission."
        ::= { optixCesObject 3 }

    -- 1.3.6.1.4.1.2011.2.25.4.50.2.1.3.1
    optixSohThoroughCesEntry OBJECT-TYPE
        SYNTAX OptixSohThoroughCesEntry
        MAX-ACCESS not-accessible
        STATUS current
        DESCRIPTION
            "This entry indicates the remote CES parameter table supporting transparent transmission of port section overheads."
        INDEX{ optixSohThoroughCesIndex,optixSohThoroughCesUniId,optixSohThoroughCesNniId }
        ::= { optixSohThoroughCesTable 1 }

    OptixSohThoroughCesEntry ::=
        SEQUENCE {
            optixSohThoroughCesIndex
                Unsigned32,
            optixSohThoroughCesUniId
                Unsigned32,
            optixSohThoroughCesNniId
                Unsigned32,
            optixSohThoroughCesId
                Unsigned32,
            optixSohThoroughCesName
                OCTET STRING,
            optixSohThoroughCesSohNum
                Unsigned32,
            optixSohThoroughCesSohList
                OCTET STRING,
            optixSohThoroughCesUniBid
                Unsigned32,
            optixSohThoroughCesUniSubBid
                Unsigned32,
            optixSohThoroughCesUniPortId
                Unsigned32,
            optixSohThoroughCesUniHpPath
                Unsigned32,
            optixSohThoroughCesUniLpPath
                Unsigned32,
            optixSohThoroughCesUniLevel
                INTEGER,
            optixSohThoroughCesUnislotNum
                Unsigned32,
            optixSohThoroughCesUnislotList
                OCTET STRING,
            optixSohThoroughCesUniPri
                INTEGER,
            optixSohThoroughCesNniPwIndex
                Unsigned32,
            optixSohThoroughCesRowStatus
                RowStatus
        }

    -- 1.3.6.1.4.1.2011.2.25.4.50.2.1.3.1.1
    optixSohThoroughCesIndex OBJECT-TYPE
        SYNTAX Unsigned32
        MAX-ACCESS not-accessible
        STATUS current
        DESCRIPTION
            "This object indicates the service index."
        ::= { optixSohThoroughCesEntry 1 }

    -- 1.3.6.1.4.1.2011.2.25.4.50.2.1.3.1.2
    optixSohThoroughCesUniId OBJECT-TYPE
        SYNTAX Unsigned32(1..65535)
        MAX-ACCESS not-accessible
        STATUS current
        DESCRIPTION
            "This object indicates the service V-UNI ID. Value range: 1 to 65535"
        ::= { optixSohThoroughCesEntry 2 }

    -- 1.3.6.1.4.1.2011.2.25.4.50.2.1.3.1.3
    optixSohThoroughCesNniId OBJECT-TYPE
        SYNTAX Unsigned32(1..65535)
        MAX-ACCESS not-accessible
        STATUS current
        DESCRIPTION
            "This object indicates the service V-NNI ID. Value range: 1 to 65535"
        ::= { optixSohThoroughCesEntry 3 }

    -- 1.3.6.1.4.1.2011.2.25.4.50.2.1.3.1.4
    optixSohThoroughCesId OBJECT-TYPE
        SYNTAX Unsigned32
        MAX-ACCESS read-create
        STATUS current
        DESCRIPTION
            "This object indicates the CES service ID."
        ::= { optixSohThoroughCesEntry 4 }

    -- 1.3.6.1.4.1.2011.2.25.4.50.2.1.3.1.5
    optixSohThoroughCesName OBJECT-TYPE
        SYNTAX OCTET STRING(SIZE(0..64))
        MAX-ACCESS read-create
        STATUS current
        DESCRIPTION
            "This object indicates the service name, which is a character string containing 64 bytes."
        DEFVAL{ "" }
        ::= { optixSohThoroughCesEntry 5 }

    -- 1.3.6.1.4.1.2011.2.25.4.50.2.1.3.1.6
    optixSohThoroughCesSohNum OBJECT-TYPE
        SYNTAX Unsigned32(0..255)
        MAX-ACCESS read-create
        STATUS current
        DESCRIPTION
            "This object indicates the number of transparently transmitted overheads. The number ranges from 0 to 255. 0: All overheads are not transparently transmitted."
        DEFVAL{ 0 }
        ::= { optixSohThoroughCesEntry 6 }

    -- 1.3.6.1.4.1.2011.2.25.4.50.2.1.3.1.7
    optixSohThoroughCesSohList OBJECT-TYPE
        SYNTAX OCTET STRING(SIZE(0..255))
        MAX-ACCESS read-create
        STATUS current
        DESCRIPTION
            "This object indicates the list of transparently transmitted overheads. Each overhead occupies one byte.If the number of transparently transmitted overheads is 0, the parameter value is 0xff. The value corresponding to each overhead is as follows: E1: 0, F1: 1, D1: 2, D2: 3, D3: 4, X1: 5, X2: 6, K1: 7, K2: 8, D4: 9, X4: 10, D5: 11, D6: 12, D7: 13, D8: 14, D9: 15, D10: 16, D11: 17, D12: 18, X3: 19, E2: 20 0xff: invalid value, indicating the overhead is deleted."
        ::= { optixSohThoroughCesEntry 7 }

    -- 1.3.6.1.4.1.2011.2.25.4.50.2.1.3.1.8
    optixSohThoroughCesUniBid OBJECT-TYPE
        SYNTAX Unsigned32(1..65535)
        MAX-ACCESS read-create
        STATUS current
        DESCRIPTION
            "This object indicates the slot ID of the service V-UNI. Value range: 1 to 65535"
        ::= { optixSohThoroughCesEntry 8 }

    -- 1.3.6.1.4.1.2011.2.25.4.50.2.1.3.1.9
    optixSohThoroughCesUniSubBid OBJECT-TYPE
        SYNTAX Unsigned32(1..255)
        MAX-ACCESS read-create
        STATUS current
        DESCRIPTION
            "This object indicates the subboard ID of the service V-UNI. Value range: 1 to 65535"
        ::= { optixSohThoroughCesEntry 9 }

    -- 1.3.6.1.4.1.2011.2.25.4.50.2.1.3.1.10
    optixSohThoroughCesUniPortId OBJECT-TYPE
        SYNTAX Unsigned32(1..65535)
        MAX-ACCESS read-create
        STATUS current
        DESCRIPTION
            "This object indicates the port number of the service V-UNI. Value range: 1 to 65535"
        ::= { optixSohThoroughCesEntry 10 }

    -- 1.3.6.1.4.1.2011.2.25.4.50.2.1.3.1.11
    optixSohThoroughCesUniHpPath OBJECT-TYPE
        SYNTAX Unsigned32(1..65535)
        MAX-ACCESS read-create
        STATUS current
        DESCRIPTION
            "This object indicates the high-order channel ID of the service V-UNI. The high-order channel ID is compatible with other STM-N services. When the service is carried through E1 ports, the high/low-order channel ID is unavailable and the value is an invalid value, 0xffff. When VC4/3 x VC3 emulation services are provided, the VC4/3 x VC3 channel ID must be 1."
        ::= { optixSohThoroughCesEntry 11 }

    -- 1.3.6.1.4.1.2011.2.25.4.50.2.1.3.1.12
    optixSohThoroughCesUniLpPath OBJECT-TYPE
        SYNTAX Unsigned32(1..65535)
        MAX-ACCESS read-create
        STATUS current
        DESCRIPTION
            "This object indicates the low-order channel ID of the service V-UNI. The low-order channel ID is compatible with other STM-N services. When the service is carried through E1 ports, the high/low order channel ID is unavailable and the value is an invalid value, 0xffff. When VC4 and 3xVC3 emulation services are provided, the VC4 and 3xVC3 channel IDs must be 0xffff."
        ::= { optixSohThoroughCesEntry 12 }

    -- 1.3.6.1.4.1.2011.2.25.4.50.2.1.3.1.13
    optixSohThoroughCesUniLevel OBJECT-TYPE
        SYNTAX INTEGER
        {
            vc12(1),
            vc3(2),
            vc11(3),
            vc4(4),
            triplicatevc3(5)
        }
        MAX-ACCESS read-create
        STATUS current
        DESCRIPTION
            "This object indicates the V-UNI channel level of the service. 1: VC12 2: VC3 3: VC11 4: VC4 5: triplicatevc3"
        DEFVAL{ 1 }
        ::= { optixSohThoroughCesEntry 13 }

    -- 1.3.6.1.4.1.2011.2.25.4.50.2.1.3.1.14
    optixSohThoroughCesUnislotNum OBJECT-TYPE
        SYNTAX Unsigned32(0..32)
        MAX-ACCESS read-create
        STATUS current
        DESCRIPTION
            "This object indicates the number of valid timeslots of the service V-UNI. 0: all timeslots"
        ::= { optixSohThoroughCesEntry 14 }

    -- 1.3.6.1.4.1.2011.2.25.4.50.2.1.3.1.15
    optixSohThoroughCesUnislotList OBJECT-TYPE
        SYNTAX OCTET STRING(SIZE(0..64))
        MAX-ACCESS read-create
        STATUS current
        DESCRIPTION
            "This object indicates the valid timeslot list of the service V-UNI. Each timeslot of the channel occupies two bytes."
        ::= { optixSohThoroughCesEntry 15 }

    -- 1.3.6.1.4.1.2011.2.25.4.50.2.1.3.1.16
    optixSohThoroughCesUniPri OBJECT-TYPE
        SYNTAX INTEGER
        {
            cs7(1),
            cs6(2),
            ef(3),
            af4(4),
            af3(5),
            af2(6),
            af1(7),
            be(8)
        }
        MAX-ACCESS read-create
        STATUS current
        DESCRIPTION
            "This object indicates the CES service priority of the service V-UNI.The value ranges from 1 to 8. Valid values: 1: CS7 2: CS6 3: EF 4: AF4 5: AF3 6: AF2 7: AF1 8: BE"
        DEFVAL{ 3 }
        ::= { optixSohThoroughCesEntry 16 }

    -- 1.3.6.1.4.1.2011.2.25.4.50.2.1.3.1.17
    optixSohThoroughCesNniPwIndex OBJECT-TYPE
        SYNTAX Unsigned32
        MAX-ACCESS read-create
        STATUS current
        DESCRIPTION
            "This object indicates the index to the PW carried by the NNI."
        ::= { optixSohThoroughCesEntry 17 }

    -- 1.3.6.1.4.1.2011.2.25.4.50.2.1.3.1.255
    optixSohThoroughCesRowStatus OBJECT-TYPE
        SYNTAX RowStatus
        MAX-ACCESS read-create
        STATUS current
        DESCRIPTION
            "This object indicates the row status. 1: active 4: createAndGo 6: destroy"
        ::= { optixSohThoroughCesEntry 255 }

    -- 1.3.6.1.4.1.2011.2.25.4.50.2.1.4
    optixCesIdletsValueTable OBJECT-TYPE
        SYNTAX SEQUENCE OF OptixCesIdletsValueEntry
        MAX-ACCESS not-accessible
        STATUS current
        DESCRIPTION
            "This table implements the configurations of the recovery value of the idle CES timeslot by board and subboard."
        ::= { optixCesObject 4 }

    -- 1.3.6.1.4.1.2011.2.25.4.50.2.1.4.1
    optixCesIdletsValueEntry OBJECT-TYPE
        SYNTAX OptixCesIdletsValueEntry
        MAX-ACCESS not-accessible
        STATUS current
        DESCRIPTION
            "This object indicates the parameter table for CES idle timeslot values."
        INDEX{ optixCesIdletsValueBid,optixCesIdletsValueSubBid }
        ::= { optixCesIdletsValueTable 1 }

    OptixCesIdletsValueEntry ::=
        SEQUENCE {
            optixCesIdletsValueBid
                Unsigned32,
            optixCesIdletsValueSubBid
                Unsigned32,
            optixCesIdletsValue
                Unsigned32
        }

    -- 1.3.6.1.4.1.2011.2.25.4.50.2.1.4.1.1
    optixCesIdletsValueBid OBJECT-TYPE
        SYNTAX Unsigned32(1..65535)
        MAX-ACCESS not-accessible
        STATUS current
        DESCRIPTION
            "This object indicates the slot ID. Value range: 1 to 65535"
        ::= { optixCesIdletsValueEntry 1 }

    -- 1.3.6.1.4.1.2011.2.25.4.50.2.1.4.1.2
    optixCesIdletsValueSubBid OBJECT-TYPE
        SYNTAX Unsigned32(1..255)
        MAX-ACCESS not-accessible
        STATUS current
        DESCRIPTION
            "This object indicates the subboard ID. Value range: 1 to 255"
        ::= { optixCesIdletsValueEntry 2 }

    -- 1.3.6.1.4.1.2011.2.25.4.50.2.1.4.1.3
    optixCesIdletsValue OBJECT-TYPE
        SYNTAX Unsigned32 (0..255)
        MAX-ACCESS read-write
        STATUS current
        DESCRIPTION
            "This object indicates the recovery value of the idle CES timeslot. Value range: 1 to 255"
        ::= { optixCesIdletsValueEntry 3 }

    -- 1.3.6.1.4.1.2011.2.25.4.50.2.1.5
    optixCesbandwidthTable OBJECT-TYPE
        SYNTAX SEQUENCE OF OptixCesbandwidthEntry
        MAX-ACCESS not-accessible
        STATUS current
        DESCRIPTION
            "This table implements the query of CES PW bandwidth based on CES service parameters."
        ::= { optixCesObject 5 }

    -- 1.3.6.1.4.1.2011.2.25.4.50.2.1.5.1
    optixCesbandwidthEntry OBJECT-TYPE
        SYNTAX OptixCesbandwidthEntry
        MAX-ACCESS not-accessible
        STATUS current
        DESCRIPTION
            "This object implements the query of CES PW bandwidth based on CES service parameters."
        INDEX{ optixCesbandwidthPwType,optixCesbandwidthCesLevel,optixCesbandwidthPathNum,optixCesbandwidthRtpEn,optixCesbandwidthLoadTime,optixCesbandwidthMspwFlag,optixCesbandwidthCesOhEn,optixCesbandwidthFrameNum }
        ::= { optixCesbandwidthTable 1 }

    OptixCesbandwidthEntry ::=
        SEQUENCE {
            optixCesbandwidthPwType
                INTEGER,
            optixCesbandwidthCesLevel
                INTEGER,
            optixCesbandwidthPathNum
                Unsigned32,
            optixCesbandwidthRtpEn
                INTEGER,
            optixCesbandwidthLoadTime
                Unsigned32,
            optixCesbandwidthMspwFlag
                INTEGER,
            optixCesbandwidthCesOhEn
                INTEGER,
            optixCesbandwidthFrameNum
                Unsigned32,
            optixCesbandwidth
                Unsigned32
        }

    -- 1.3.6.1.4.1.2011.2.25.4.50.2.1.5.1.1
    optixCesbandwidthPwType OBJECT-TYPE
        SYNTAX INTEGER
        {
            ethraw(5),
            ethtag(4),
            atmtrans(3),
            atmnto1vcc(9),
            atmnto1vpc(10),
            atm1to1vcc(12),
            atm1to1vpc(13),
            satope1(17),
            cesopsnbas(21)
        }
        MAX-ACCESS not-accessible
        STATUS current
        DESCRIPTION
            "This object indicates the PW type."
        ::= { optixCesbandwidthEntry 1 }

    -- 1.3.6.1.4.1.2011.2.25.4.50.2.1.5.1.2
    optixCesbandwidthCesLevel OBJECT-TYPE
        SYNTAX INTEGER
        {
            vc12(1),
            vc3(2),
            invalid(255)
        }
        MAX-ACCESS not-accessible
        STATUS current
        DESCRIPTION
            "This object indicates the CES level."
        ::= { optixCesbandwidthEntry 2 }

    -- 1.3.6.1.4.1.2011.2.25.4.50.2.1.5.1.3
    optixCesbandwidthPathNum OBJECT-TYPE
        SYNTAX Unsigned32
        MAX-ACCESS not-accessible
        STATUS current
        DESCRIPTION
            "This object indicates the path number."
        ::= { optixCesbandwidthEntry 3 }

    -- 1.3.6.1.4.1.2011.2.25.4.50.2.1.5.1.4
    optixCesbandwidthRtpEn OBJECT-TYPE
        SYNTAX INTEGER
        {
            disable(0),
            enablehwrtp(1),
            enablestdrtp(2)
        }
        MAX-ACCESS not-accessible
        STATUS current
        DESCRIPTION
            "This object indicates the RTP header encapsulation enable status."
        ::= { optixCesbandwidthEntry 4 }

    -- 1.3.6.1.4.1.2011.2.25.4.50.2.1.5.1.5
    optixCesbandwidthLoadTime OBJECT-TYPE
        SYNTAX Unsigned32
        MAX-ACCESS not-accessible
        STATUS current
        DESCRIPTION
            "This object indicates the packet loading time."
        ::= { optixCesbandwidthEntry 5 }

    -- 1.3.6.1.4.1.2011.2.25.4.50.2.1.5.1.6
    optixCesbandwidthMspwFlag OBJECT-TYPE
        SYNTAX INTEGER
        {
            disable(0),
            enable(1)
        }
        MAX-ACCESS not-accessible
        STATUS current
        DESCRIPTION
            "This object indicates the MSPW flag."
        ::= { optixCesbandwidthEntry 6 }

    -- 1.3.6.1.4.1.2011.2.25.4.50.2.1.5.1.7
    optixCesbandwidthCesOhEn OBJECT-TYPE
        SYNTAX INTEGER
        {
            disable(0),
            enable(1)
        }
        MAX-ACCESS not-accessible
        STATUS current
        DESCRIPTION
            "This object indicates the enable status of transparent transmission for segment overhead."
        ::= { optixCesbandwidthEntry 7 }

    -- 1.3.6.1.4.1.2011.2.25.4.50.2.1.5.1.8
    optixCesbandwidthFrameNum OBJECT-TYPE
        SYNTAX Unsigned32
        MAX-ACCESS not-accessible
        STATUS current
        DESCRIPTION
            "This object indicates the number of frames."
        ::= { optixCesbandwidthEntry 8 }

    -- 1.3.6.1.4.1.2011.2.25.4.50.2.1.5.1.9
    optixCesbandwidth OBJECT-TYPE
        SYNTAX Unsigned32
        MAX-ACCESS read-only
        STATUS current
        DESCRIPTION
            "This object indicates the CES PW bandwidth."
        ::= { optixCesbandwidthEntry 9 }

    -- 1.3.6.1.4.1.2011.2.25.4.50.2.1.6
    optixCesDropCheckTable OBJECT-TYPE
        SYNTAX SEQUENCE OF OptixCesDropCheckEntry
        MAX-ACCESS not-accessible
        STATUS current
        DESCRIPTION
            "This table implements the function of checking CES packet loss."
        ::= { optixCesObject 6 }

    -- 1.3.6.1.4.1.2011.2.25.4.50.2.1.6.1
    optixCesDropCheckEntry OBJECT-TYPE
        SYNTAX OptixCesDropCheckEntry
        MAX-ACCESS not-accessible
        STATUS current
        DESCRIPTION
            "This entry indicates the function of checking CES packet loss. SNMP walking is not supported. Users must manually deliver indexes."
        INDEX{ optixCesDropCheckMplsType,optixCesDropCheckTnlIndex,optixCesDropCheckPwInLabel,optixCesDropCheckTnlDir }
        ::= { optixCesDropCheckTable 1 }

    OptixCesDropCheckEntry ::=
        SEQUENCE {
            optixCesDropCheckMplsType
                INTEGER,
            optixCesDropCheckTnlIndex
                Unsigned32,
            optixCesDropCheckPwInLabel
                Unsigned32,
            optixCesDropCheckTnlDir
                INTEGER,
            optixCesDropCheckCesSnMode
                INTEGER,
            optixCesDropCheckEnable
                INTEGER,
            optixCesDropCheckHighTh
                Unsigned32,
            optixCesDropCheckLowTh
                Unsigned32,
            optixCesDropCheckMisorderCut
                Counter64
        }

    -- 1.3.6.1.4.1.2011.2.25.4.50.2.1.6.1.1
    optixCesDropCheckMplsType OBJECT-TYPE
        SYNTAX INTEGER
        {
            transitTunnel(0),
            msPw(1)
        }
        MAX-ACCESS not-accessible
        STATUS current
        DESCRIPTION
            "This object indicates the MPLS type. 0:Transit Tunnel;1:MSPW"
        ::= { optixCesDropCheckEntry 1 }

    -- 1.3.6.1.4.1.2011.2.25.4.50.2.1.6.1.2
    optixCesDropCheckTnlIndex OBJECT-TYPE
        SYNTAX Unsigned32
        MAX-ACCESS not-accessible
        STATUS current
        DESCRIPTION
            "This object indicates the tunnel index.Value range:1 to 4294967295"
        ::= { optixCesDropCheckEntry 2 }

    -- 1.3.6.1.4.1.2011.2.25.4.50.2.1.6.1.3
    optixCesDropCheckPwInLabel OBJECT-TYPE
        SYNTAX Unsigned32
        MAX-ACCESS not-accessible
        STATUS current
        DESCRIPTION
            "This object indicates the PW ingress lable.Value range: 0x10 to 0xfffff"
        ::= { optixCesDropCheckEntry 3 }

    -- 1.3.6.1.4.1.2011.2.25.4.50.2.1.6.1.4
    optixCesDropCheckTnlDir OBJECT-TYPE
        SYNTAX INTEGER
        {
            forward(0),
            reverse(1)
        }
        MAX-ACCESS not-accessible
        STATUS current
        DESCRIPTION
            "This object indicates the tunnel direction.Value range 0:forward 1:reverse. Default value: forward"
        ::= { optixCesDropCheckEntry 4 }

    -- 1.3.6.1.4.1.2011.2.25.4.50.2.1.6.1.5
    optixCesDropCheckCesSnMode OBJECT-TYPE
        SYNTAX INTEGER
        {
            stdmode(0),
            hwmode(1)
        }
        MAX-ACCESS read-write
        STATUS current
        DESCRIPTION
            "This object indicates the mode of the CES serial number. Value range: 0: standard mode 1:huawei mode. Default value:huawei mode"
        ::= { optixCesDropCheckEntry 5 }

    -- 1.3.6.1.4.1.2011.2.25.4.50.2.1.6.1.6
    optixCesDropCheckEnable OBJECT-TYPE
        SYNTAX INTEGER
        {
            disable(0),
            enable(1)
        }
        MAX-ACCESS read-write
        STATUS current
        DESCRIPTION
            "This object indicates the statue of the function  of checking CES packet loss. Value range: 0:disable 1:enable .default: disable"
        ::= { optixCesDropCheckEntry 6 }

    -- 1.3.6.1.4.1.2011.2.25.4.50.2.1.6.1.7
    optixCesDropCheckHighTh OBJECT-TYPE
        SYNTAX Unsigned32 (0..1000)
        MAX-ACCESS read-write
        STATUS current
        DESCRIPTION
            "This object indicates the upper threshold of checking CES packet loss. Value range: 0 to 1000. Default value: 5"
        ::= { optixCesDropCheckEntry 7 }

    -- 1.3.6.1.4.1.2011.2.25.4.50.2.1.6.1.8
    optixCesDropCheckLowTh OBJECT-TYPE
        SYNTAX Unsigned32 (0..1000)
        MAX-ACCESS read-write
        STATUS current
        DESCRIPTION
            "This object indicates the lower threshold of checking CES packet loss. Value range: 0 to 1000. Default value: 0"
        ::= { optixCesDropCheckEntry 8 }

    -- 1.3.6.1.4.1.2011.2.25.4.50.2.1.6.1.9
    optixCesDropCheckMisorderCut OBJECT-TYPE
        SYNTAX Counter64
        MAX-ACCESS read-only
        STATUS current
        DESCRIPTION
            "This object indicates the disordered count of the function of checking CES packet loss."
        ::= { optixCesDropCheckEntry 9 }

END
