-- OPTIX-PW-APS-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PW-APS-MIB DEFINITIONS ::= BEGIN
    IMPORTS
        OBJECT-GROUP,MODULE-COMPLIANCE
            FROM SNMPv2-CONF
        MODULE-IDENTITY,OBJECT-TYPE,Unsigned32,Integer32,IpAddress,NOTIFICATION-TYPE
            FROM SNMPv2-SMI
        RowStatus
            FROM SNMPv2-TC
        optixProvisionPtn
            FROM OPTIX-OID-MIB
        ;

    optixPWApsMod MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage the MPLS PW APS. The PW APS is a protection mechanism. When the working PW is faulty, the service carried on the working PW will be switched to the protection PW to protect the service. The more the PW APS groups are, the more network and device resources are occupied.To reduce resource consumption, multiple PW APS protection switchings are handled by one APS state machine. Multiple PWs share one APS state machine. Thisis called PW APS binding."
        REVISION "201204170000Z"
        DESCRIPTION
            "Initial version of this MIB module"
        ::={ optixProvisionPtn 5 }

    -- 1.3.6.1.4.1.2011.2.25.4.50.5.1
    optixPWApsObject OBJECT IDENTIFIER ::= { optixPWApsMod 1 }

    -- 1.3.6.1.4.1.2011.2.25.4.50.5.1.1
    optixPWApsTable OBJECT-TYPE
        SYNTAX SEQUENCE OF OptixPWApsEntry
        MAX-ACCESS not-accessible
        STATUS current
        DESCRIPTION
            "This table implements the configurations and status management of thePW APS. These configurations include APS protection members, the enable status, revertive mode, single-ended or dual-ended, recovery time, delay time, and APS switching status."
        ::= { optixPWApsObject 1 }

    -- 1.3.6.1.4.1.2011.2.25.4.50.5.1.1.1
    optixPWApsEntry OBJECT-TYPE
        SYNTAX OptixPWApsEntry
        MAX-ACCESS not-accessible
        STATUS current
        DESCRIPTION
            "This entry indicates the PW APS parameter table."
        INDEX{ optixPWApsId }
        ::= { optixPWApsTable 1 }

    OptixPWApsEntry ::=
        SEQUENCE {
            optixPWApsId
                Unsigned32,
            optixPWApsType
                INTEGER,
            optixPWApsSwitchMode
                INTEGER,
            optixPWApsRevertiveMode
                INTEGER,
            optixPWApsRevertiveTime
                Unsigned32,
            optixPWApsHoldoffTime
                Unsigned32,
            optixPWApsWorkOutPWIndex
                Unsigned32,
            optixPWApsProtectOutPWIndex
                Unsigned32,
            optixPWApsEnable
                INTEGER,
            optixPWApsGroupState
                INTEGER,
            optixPWApsProtoolState
                INTEGER,
            optixPWApsWorkState
                INTEGER,
            optixPWApsProtectState
                INTEGER,
            optixPWApsClrPair
                INTEGER,
            optixPWApsExcSwitch
                INTEGER,
            optixPWApsRowStatus
                RowStatus
        }

    -- 1.3.6.1.4.1.2011.2.25.4.50.5.1.1.1.1
    optixPWApsId OBJECT-TYPE
        SYNTAX Unsigned32
        MAX-ACCESS not-accessible
        STATUS current
        DESCRIPTION
            "This object indicates the APS protection group ID."
        ::= { optixPWApsEntry 1 }

    -- 1.3.6.1.4.1.2011.2.25.4.50.5.1.1.1.2
    optixPWApsType OBJECT-TYPE
        SYNTAX INTEGER
        {
            snmp1j1(0),
            snmp1p1(1),
            pwfps(2)
        }
        MAX-ACCESS read-create
        STATUS current
        DESCRIPTION
            "This object indicates the APS prtoection group type. 0: 1 + 1,1: 1:1,2:fps(PW FRR)"
        ::= { optixPWApsEntry 2 }

    -- 1.3.6.1.4.1.2011.2.25.4.50.5.1.1.1.3
    optixPWApsSwitchMode OBJECT-TYPE
        SYNTAX INTEGER
        {
            uni(0),
            bi(1)
        }
        MAX-ACCESS read-create
        STATUS current
        DESCRIPTION
            "This object indicates the switching mode of the APS protection group. 0: uni 1: bi"
        DEFVAL{ 1 }
        ::= { optixPWApsEntry 3 }

    -- 1.3.6.1.4.1.2011.2.25.4.50.5.1.1.1.4
    optixPWApsRevertiveMode OBJECT-TYPE
        SYNTAX INTEGER
        {
            norevertive(0),
            revertive(1)
        }
        MAX-ACCESS read-create
        STATUS current
        DESCRIPTION
            "This object indicates the revertive mode of the APS protection group. 0: no-revertive 1: revertive"
        DEFVAL{ 1 }
        ::= { optixPWApsEntry 4 }

    -- 1.3.6.1.4.1.2011.2.25.4.50.5.1.1.1.5
    optixPWApsRevertiveTime OBJECT-TYPE
        SYNTAX Unsigned32(0..12)
        MAX-ACCESS read-create
        STATUS current
        DESCRIPTION
            "This object indicates the recovery time of the APS protection group. Value range: 0 to 12 (unit: s)."
        DEFVAL{ 1 }
        ::= { optixPWApsEntry 5 }

    -- 1.3.6.1.4.1.2011.2.25.4.50.5.1.1.1.6
    optixPWApsHoldoffTime OBJECT-TYPE
        SYNTAX Unsigned32(0..100)
        MAX-ACCESS read-create
        STATUS current
        DESCRIPTION
            "This object indicates the switching delay time of the APS protection group. Value range: 0 to 100 (unit: 100 ms)."
        DEFVAL{ 0 }
        ::= { optixPWApsEntry 6 }

    -- 1.3.6.1.4.1.2011.2.25.4.50.5.1.1.1.7
    optixPWApsWorkOutPWIndex OBJECT-TYPE
        SYNTAX Unsigned32
        MAX-ACCESS read-create
        STATUS current
        DESCRIPTION
            "This object indicates the working PW index of the APS protection group. Value range: 1 to 4294967295."
        DEFVAL{ 0 }
        ::= { optixPWApsEntry 7 }

    -- 1.3.6.1.4.1.2011.2.25.4.50.5.1.1.1.8
    optixPWApsProtectOutPWIndex OBJECT-TYPE
        SYNTAX Unsigned32
        MAX-ACCESS read-create
        STATUS current
        DESCRIPTION
            "This object indicates the protection PW index of the APS protection group. Value range: 1 to 4294967295."
        DEFVAL{ 0 }
        ::= { optixPWApsEntry 8 }

    -- 1.3.6.1.4.1.2011.2.25.4.50.5.1.1.1.9
    optixPWApsEnable OBJECT-TYPE
        SYNTAX INTEGER
        {
            disable(0),
            enable(1)
        }
        MAX-ACCESS read-create
        STATUS current
        DESCRIPTION
            "This object indicates the enable status of the APS protection protocol. 1: enable 0: disable"
        DEFVAL{ 0 }
        ::= { optixPWApsEntry 9 }

    -- 1.3.6.1.4.1.2011.2.25.4.50.5.1.1.1.10
    optixPWApsGroupState OBJECT-TYPE
        SYNTAX INTEGER
        {
            inprotect(0),
            inwork(1)
        }
        MAX-ACCESS read-only
        STATUS current
        DESCRIPTION
            "This object indicates the switching mode of the APS protection group. 1: in-work 0: in-protect"
        ::= { optixPWApsEntry 10 }

    -- 1.3.6.1.4.1.2011.2.25.4.50.5.1.1.1.11
    optixPWApsProtoolState OBJECT-TYPE
        SYNTAX INTEGER
        {
            nrw(0),
            nrp(1),
            lo(2),
            fs(3),
            sfw(4),
            sfp(5),
            sdp(6),
            sdw(7),
            msw(8),
            msp(9),
            wtr(10),
            dnr(11),
            exerw(12),
            exerp(13),
            rrw(14),
            rrp(15)
        }
        MAX-ACCESS read-only
        STATUS current
        DESCRIPTION
            "This object indicates the status of the APS protection protocol."
        ::= { optixPWApsEntry 11 }

    -- 1.3.6.1.4.1.2011.2.25.4.50.5.1.1.1.12
    optixPWApsWorkState OBJECT-TYPE
        SYNTAX INTEGER
        {
            invalid(0),
            valid(1)
        }
        MAX-ACCESS read-only
        STATUS current
        DESCRIPTION
            "This object indicates the working channel status of the APS protection group. 1: valid 0: invalid"
        ::= { optixPWApsEntry 12 }

    -- 1.3.6.1.4.1.2011.2.25.4.50.5.1.1.1.13
    optixPWApsProtectState OBJECT-TYPE
        SYNTAX INTEGER
        {
            invalid(0),
            valid(1)
        }
        MAX-ACCESS read-only
        STATUS current
        DESCRIPTION
            "This object indicates the protection channel status of the APS protection group. 1: valid 0: invalid"
        ::= { optixPWApsEntry 13 }

    -- 1.3.6.1.4.1.2011.2.25.4.50.5.1.1.1.14
    optixPWApsClrPair OBJECT-TYPE
        SYNTAX INTEGER
        {
            clr(1)
        }
        MAX-ACCESS read-create
        STATUS current
        DESCRIPTION
            "This object indicates that PW APS pairs are to be deleted."
        ::= { optixPWApsEntry 14 }

    -- 1.3.6.1.4.1.2011.2.25.4.50.5.1.1.1.15
    optixPWApsExcSwitch OBJECT-TYPE
        SYNTAX INTEGER
        {
            clear(0),
            lock(1),
            force(2),
            manualtowork(3),
            manualtoprotect(4),
            exercise(5)
        }
        MAX-ACCESS read-create
        STATUS current
        DESCRIPTION
            "This object indicates the switching mode of the APS protection group."
        ::= { optixPWApsEntry 15 }

    -- 1.3.6.1.4.1.2011.2.25.4.50.5.1.1.1.255
    optixPWApsRowStatus OBJECT-TYPE
        SYNTAX RowStatus
        MAX-ACCESS read-create
        STATUS current
        DESCRIPTION
            "This object indicates the row status. 1: active 4: createAndGo 6: destroy"
        ::= { optixPWApsEntry 255 }

    -- 1.3.6.1.4.1.2011.2.25.4.50.5.1.2
    optixPWApsPairTable OBJECT-TYPE
        SYNTAX SEQUENCE OF OptixPWApsPairEntry
        MAX-ACCESS not-accessible
        STATUS current
        DESCRIPTION
            "This table implements the configurations and management of the PW APS pair. Pairs belonging to one protection group share the same state machine with the PW APS protection group. When the working PW in the PW APS protection group is faulty, protection switching occurs on the PW APS protection group as well as on all its slave protection pairs. In this manner, switching efficiency is improved."
        ::= { optixPWApsObject 2 }

    -- 1.3.6.1.4.1.2011.2.25.4.50.5.1.2.1
    optixPWApsPairEntry OBJECT-TYPE
        SYNTAX OptixPWApsPairEntry
        MAX-ACCESS not-accessible
        STATUS current
        DESCRIPTION
            "This entry indicates the parameter table for the slave PW APS pairs."
        INDEX{ optixPWApsPairId,optixPWApsPairWorkOutPWIndex,optixPWApsPairProtectOutPWIndex }
        ::= { optixPWApsPairTable 1 }

    OptixPWApsPairEntry ::=
        SEQUENCE {
            optixPWApsPairId
                Unsigned32,
            optixPWApsPairWorkOutPWIndex
                Unsigned32,
            optixPWApsPairProtectOutPWIndex
                Unsigned32,
            optixPWApsPairExtPara
                Unsigned32,
            optixPWApsPairRowStatus
                RowStatus
        }

    -- 1.3.6.1.4.1.2011.2.25.4.50.5.1.2.1.1
    optixPWApsPairId OBJECT-TYPE
        SYNTAX Unsigned32
        MAX-ACCESS not-accessible
        STATUS current
        DESCRIPTION
            "This object indicates the APS protection group ID."
        ::= { optixPWApsPairEntry 1 }

    -- 1.3.6.1.4.1.2011.2.25.4.50.5.1.2.1.2
    optixPWApsPairWorkOutPWIndex OBJECT-TYPE
        SYNTAX Unsigned32
        MAX-ACCESS not-accessible
        STATUS current
        DESCRIPTION
            "This object indicates the working PW index of the slave PW APS pairs. Value range: 1 to 4294967295."
        ::= { optixPWApsPairEntry 2 }

    -- 1.3.6.1.4.1.2011.2.25.4.50.5.1.2.1.3
    optixPWApsPairProtectOutPWIndex OBJECT-TYPE
        SYNTAX Unsigned32
        MAX-ACCESS not-accessible
        STATUS current
        DESCRIPTION
            "This object indicates theprotection PW index of the slave PW APS pairs. Value range: 1 to 4294967295."
        ::= { optixPWApsPairEntry 3 }

    -- 1.3.6.1.4.1.2011.2.25.4.50.5.1.2.1.4
    optixPWApsPairExtPara OBJECT-TYPE
        SYNTAX Unsigned32
        MAX-ACCESS read-only
        STATUS current
        DESCRIPTION
            "This object indicates the ext para of the APS protection group pair."
        ::= { optixPWApsPairEntry 4 }

    -- 1.3.6.1.4.1.2011.2.25.4.50.5.1.2.1.255
    optixPWApsPairRowStatus OBJECT-TYPE
        SYNTAX RowStatus
        MAX-ACCESS read-create
        STATUS current
        DESCRIPTION
            "This object indicates the row status. 1: active 4: createAndGo 6: destroy"
        ::= { optixPWApsPairEntry 255 }

    -- 1.3.6.1.4.1.2011.2.25.4.50.5.2
    optixPWApsTrap OBJECT IDENTIFIER ::= { optixPWApsMod 2 }

    -- 1.3.6.1.4.1.2011.2.25.4.50.5.2.1
    optixPWApsTrapMember OBJECT IDENTIFIER ::= { optixPWApsTrap 1 }

    -- 1.3.6.1.4.1.2011.2.25.4.50.5.2.1.1
    optixPWApsTrapGrouppId OBJECT-TYPE
        SYNTAX Unsigned32
        MAX-ACCESS accessible-for-notify
        STATUS current
        DESCRIPTION
            "This object indicates the APS protection group ID."
        ::= { optixPWApsTrapMember 1 }

    -- 1.3.6.1.4.1.2011.2.25.4.50.5.2.1.2
    optixPWApsTrapGroupState OBJECT-TYPE
        SYNTAX INTEGER
        {
            inprotect(0),
            inwork(1)
        }
        MAX-ACCESS accessible-for-notify
        STATUS current
        DESCRIPTION
            "This object indicates the switching mode of the APS protection group. 1: in-work 0: in-protect"
        ::= { optixPWApsTrapMember 2 }

    -- 1.3.6.1.4.1.2011.2.25.4.50.5.2.1.3
    optixPWApsTrapProtoolState OBJECT-TYPE
        SYNTAX INTEGER
        {
            nrw(0),
            nrp(1),
            lo(2),
            fs(3),
            sfw(4),
            sfp(5),
            sdp(6),
            sdw(7),
            msw(8),
            msp(9),
            wtr(10),
            dnr(11),
            exerw(12),
            exerp(13),
            rrw(14),
            rrp(15)
        }
        MAX-ACCESS accessible-for-notify
        STATUS current
        DESCRIPTION
            "This object indicates the status of the APS protection protocol. 0: nrw, 1: nrp, 2: lo, 3: fs, 4: sfw, 5: sfp, 6: sdp, 7: sdw, 8: msw, 9: msp, 10: wtr, 11: dnr, 12: exerw, 13: exerp, 14: rrw, 15: rrp"
        ::= { optixPWApsTrapMember 3 }

    -- 1.3.6.1.4.1.2011.2.25.4.50.5.2.1.4
    optixPWApsTrapWorkState OBJECT-TYPE
        SYNTAX INTEGER
        {
            invalid(0),
            valid(1)
        }
        MAX-ACCESS accessible-for-notify
        STATUS current
        DESCRIPTION
            "This object indicates the working channel status of the APS protection group. 1: valid 0: invalid"
        ::= { optixPWApsTrapMember 4 }

    -- 1.3.6.1.4.1.2011.2.25.4.50.5.2.1.5
    optixPWApsTrapProtectState OBJECT-TYPE
        SYNTAX INTEGER
        {
            invalid(0),
            valid(1)
        }
        MAX-ACCESS accessible-for-notify
        STATUS current
        DESCRIPTION
            "This object indicates the protection channel status of the APS protection group. 1: valid 0: invalid"
        ::= { optixPWApsTrapMember 5 }

    -- 1.3.6.1.4.1.2011.2.25.4.50.5.2.2
    optixPWApsTrapReport OBJECT IDENTIFIER ::= { optixPWApsTrap 2 }

    -- 1.3.6.1.4.1.2011.2.25.4.50.5.2.2.1
    optixPWApsSwitchTrap NOTIFICATION-TYPE
        OBJECTS{ optixPWApsTrapGrouppId,optixPWApsTrapGroupState,optixPWApsTrapProtoolState,optixPWApsTrapWorkState,optixPWApsTrapProtectState }
        STATUS current
        DESCRIPTION
            "This object is used to report PW APS status change events. When the APS protection switching occurs, the status change event must be reported."
        ::= { optixPWApsTrapReport 1 }

END
