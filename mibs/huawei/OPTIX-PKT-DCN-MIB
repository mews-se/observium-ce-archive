-- OPTIX-PKT-DCN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-DCN-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,IpAddress,Integer32
            FROM SNMPv2-SMI
        optixLogBoardId,optixLogSubCardId
            FROM OPTIX-BOARD-MANAGE-MIB
        ;

    optixPktDcn MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes DCN configurations."
        REVISION "201204200000Z"
        DESCRIPTION
            "The initial revision of this MIB module1."
        ::={ optixProvisionPtn 11 }

    -- 1.3.6.1.4.1.2011.2.25.4.50.11.1
    optixPktDcnGroup OBJECT IDENTIFIER ::= { optixPktDcn 1 }

    -- 1.3.6.1.4.1.2011.2.25.4.50.11.1.1
    optixDcnBandAdminVlan OBJECT-TYPE
        SYNTAX Unsigned32
        MAX-ACCESS read-write
        STATUS current
        DESCRIPTION
            "This object indicates the DCN bandwidth."
        ::= { optixPktDcnGroup 1 }

    -- 1.3.6.1.4.1.2011.2.25.4.50.11.1.2
    optixDcnBandWidthTable OBJECT-TYPE
        SYNTAX SEQUENCE OF OptixDcnBandWidthEntry
        MAX-ACCESS not-accessible
        STATUS current
        DESCRIPTION
            "This table describes various DCN bandwidth types."
        ::= { optixPktDcnGroup 2 }

    -- 1.3.6.1.4.1.2011.2.25.4.50.11.1.2.1
    optixDcnBandWidthEntry OBJECT-TYPE
        SYNTAX OptixDcnBandWidthEntry
        MAX-ACCESS not-accessible
        STATUS current
        DESCRIPTION
            "This entry describes various DCN bandwidth types."
        INDEX{ optixDcnBandType }
        ::= { optixDcnBandWidthTable 1 }

    OptixDcnBandWidthEntry ::=
        SEQUENCE {
            optixDcnBandType
                INTEGER,
            optixDcnBandWidth
                Unsigned32
        }

    -- 1.3.6.1.4.1.2011.2.25.4.50.11.1.2.1.1
    optixDcnBandType OBJECT-TYPE
        SYNTAX INTEGER
        {
            eth(16),
            e1(32),
            mw(96)
        }
        MAX-ACCESS not-accessible
        STATUS current
        DESCRIPTION
            "This object indicates the DCN bandwidthtype. 16: ETH, 32: E1, 48: POS, 96: MW"
        ::= { optixDcnBandWidthEntry 1 }

    -- 1.3.6.1.4.1.2011.2.25.4.50.11.1.2.1.2
    optixDcnBandWidth OBJECT-TYPE
        SYNTAX Unsigned32
        MAX-ACCESS read-write
        STATUS current
        DESCRIPTION
            "This object indicates the DCN bandwidth."
        ::= { optixDcnBandWidthEntry 2 }

    -- 1.3.6.1.4.1.2011.2.25.4.50.11.1.3
    optixDcnTable OBJECT-TYPE
        SYNTAX SEQUENCE OF OptixDcnEntry
        MAX-ACCESS not-accessible
        STATUS current
        DESCRIPTION
            "This table describes DCN function configurations."
        ::= { optixPktDcnGroup 3 }

    -- 1.3.6.1.4.1.2011.2.25.4.50.11.1.3.1
    optixDcnEntry OBJECT-TYPE
        SYNTAX OptixDcnEntry
        MAX-ACCESS not-accessible
        STATUS current
        DESCRIPTION
            "This entry describes DCN function configurations."
        INDEX{ optixLogBoardId,optixLogSubCardId,optixDcnPortId,optixDcnPathId,optixDcnInferType }
        ::= { optixDcnTable 1 }

    OptixDcnEntry ::=
        SEQUENCE {
            optixDcnPortId
                Unsigned32,
            optixDcnPathId
                Unsigned32,
            optixDcnInferType
                INTEGER,
            optixDcnInferEnable
                INTEGER,
            optixDcnNSInIp
                IpAddress,
            optixDcnNSInMask
                IpAddress,
            optixDcnOSPFEnable
                INTEGER,
            optixDcnOPQLSAEnable
                INTEGER
        }

    -- 1.3.6.1.4.1.2011.2.25.4.50.11.1.3.1.1
    optixDcnPortId OBJECT-TYPE
        SYNTAX Unsigned32
        MAX-ACCESS not-accessible
        STATUS current
        DESCRIPTION
            "This node describes the ID of a port configured with the independent DCN function."
        ::= { optixDcnEntry 1 }

    -- 1.3.6.1.4.1.2011.2.25.4.50.11.1.3.1.2
    optixDcnPathId OBJECT-TYPE
        SYNTAX Unsigned32
        MAX-ACCESS not-accessible
        STATUS current
        DESCRIPTION
            "This object indicates the DCN channel ID. If the DCN type is not CSTM-1 DCNIF, this parameter takes a fixed value of 0. If the DCN type is CSTM-1 DCNIF and VC-11s are configured on the port, the value ranges from 1 to 28. If VC-12s are configured on the port, the value ranges from 1 to 63 except for RTN 905E (1 to 46)."
        ::= { optixDcnEntry 2 }

    -- 1.3.6.1.4.1.2011.2.25.4.50.11.1.3.1.3
    optixDcnInferType OBJECT-TYPE
        SYNTAX INTEGER
        {
            ethdcnif(17),
            ethnmsif(18),
            e1dcnif(33),
            null(0),
            cstmdcnif(65),
            posdcnif(49),
            mwdcnif(97),
            localdcnif(113)
        }
        MAX-ACCESS not-accessible
        STATUS current
        DESCRIPTION
            "This object indicates the interface type. 17: ethdcnif, 18: ethnmsif, 33: e1dcnif, 49: posdcnif, 97: mwdcnif, 0: null, 65: cstmdcnif, 113: localdcnif"
        ::= { optixDcnEntry 3 }

    -- 1.3.6.1.4.1.2011.2.25.4.50.11.1.3.1.4
    optixDcnInferEnable OBJECT-TYPE
        SYNTAX INTEGER
        {
            enable(1),
            disable(0)
        }
        MAX-ACCESS read-write
        STATUS current
        DESCRIPTION
            "This object indicates the interface enable status. 0: disable, 1: enable"
        ::= { optixDcnEntry 4 }

    -- 1.3.6.1.4.1.2011.2.25.4.50.11.1.3.1.5
    optixDcnNSInIp OBJECT-TYPE
        SYNTAX IpAddress
        MAX-ACCESS read-write
        STATUS current
        DESCRIPTION
            "This object indicates the access IP address of the NMS. Value range in dotted decimal notation: 0.0.0.0 to 255.255.255.255."
        ::= { optixDcnEntry 5 }

    -- 1.3.6.1.4.1.2011.2.25.4.50.11.1.3.1.6
    optixDcnNSInMask OBJECT-TYPE
        SYNTAX IpAddress
        MAX-ACCESS read-write
        STATUS current
        DESCRIPTION
            "This object indicates the access mask of the NMS. Value range in dotted decimal notation: 0.0.0.0 to 255.255.255.255."
        ::= { optixDcnEntry 6 }

    -- 1.3.6.1.4.1.2011.2.25.4.50.11.1.3.1.7
    optixDcnOSPFEnable OBJECT-TYPE
        SYNTAX INTEGER
        {
            enable(1),
            disable(0)
        }
        MAX-ACCESS read-write
        STATUS current
        DESCRIPTION
            "This object indicates the OSPF enable status. 0: disable, 1: enable"
        ::= { optixDcnEntry 7 }

    -- 1.3.6.1.4.1.2011.2.25.4.50.11.1.3.1.8
    optixDcnOPQLSAEnable OBJECT-TYPE
        SYNTAX INTEGER
        {
            enable(1),
            disable(0)
        }
        MAX-ACCESS read-write
        STATUS current
        DESCRIPTION
            "This object indicates the enable status of OPQLSA. 0: disable, 1: enable"
        ::= { optixDcnEntry 8 }

    -- 1.3.6.1.4.1.2011.2.25.4.50.11.1.4
    optixDcnProTable OBJECT-TYPE
        SYNTAX SEQUENCE OF OptixDcnProEntry
        MAX-ACCESS not-accessible
        STATUS current
        DESCRIPTION
            "This table describes DCN function configurations."
        ::= { optixPktDcnGroup 4 }

    -- 1.3.6.1.4.1.2011.2.25.4.50.11.1.4.1
    optixDcnProEntry OBJECT-TYPE
        SYNTAX OptixDcnProEntry
        MAX-ACCESS not-accessible
        STATUS current
        DESCRIPTION
            "This entry describes DCN function configurations."
        INDEX{ optixLogBoardId,optixLogSubCardId,optixDcnPortId,optixDcnPathId }
        ::= { optixDcnProTable 1 }

    OptixDcnProEntry ::=
        SEQUENCE {
            optixDcnProMode
                INTEGER,
            optixDcnType
                INTEGER,
            optixSwitchDcnProMode
                INTEGER,
            optixSwitchDcnType
                INTEGER
        }

    -- 1.3.6.1.4.1.2011.2.25.4.50.11.1.4.1.1
    optixDcnProMode OBJECT-TYPE
        SYNTAX INTEGER
        {
            ip(1),
            hwecc(3),
            l2dcn(8),
            noTagL2dcn(11),
            sl2dcn(12),
            wifi(13),
            mixl2dcn(14),
            superl2dcn(15),
            notagmixl2dcn(16)
        }
        MAX-ACCESS read-write
        STATUS current
        DESCRIPTION
            "This object indicates the protocol type. 1: IP, 3: HWECC, 8: L2DCN, 11: NoTagL2DCN, 12: SL2DCN, 13: WiFi, 14: Mixed L2DCN, 15: SuperL2DCN, 16: NoTagMixL2DCN"
        ::= { optixDcnProEntry 1 }

    -- 1.3.6.1.4.1.2011.2.25.4.50.11.1.4.1.2
    optixDcnType OBJECT-TYPE
        SYNTAX INTEGER
        {
            ethdcnif(17),
            ethnmsif(18),
            e1dcnif(33),
            posdcnif(49),
            mwdcnif(97),
            null(0),
            cstmdcnif(65),
            ethlocalif(113)
        }
        MAX-ACCESS read-write
        STATUS current
        DESCRIPTION
            "This object indicates the DCN type. 17: ethdcnif, 18: ethnmsif, 33: e1dcnif, 49: posdcnif, 97: mwdcnif, 0: null, 65: cstmdcnif, 113: ethlocalif"
        ::= { optixDcnProEntry 2 }

    -- 1.3.6.1.4.1.2011.2.25.4.50.11.1.4.1.3
    optixSwitchDcnProMode OBJECT-TYPE
        SYNTAX INTEGER
        {
            l2dcn(8)
        }
        MAX-ACCESS read-write
        STATUS current
        DESCRIPTION
            "This object indicates the protocol type. 8: l2dcn"
        ::= { optixDcnProEntry 3 }

    -- 1.3.6.1.4.1.2011.2.25.4.50.11.1.4.1.4
    optixSwitchDcnType OBJECT-TYPE
        SYNTAX INTEGER
        {
            ethdcnif(17)
        }
        MAX-ACCESS read-write
        STATUS current
        DESCRIPTION
            "This object indicates the DCN type. 17: ethdcnif"
        ::= { optixDcnProEntry 4 }

    -- 1.3.6.1.4.1.2011.2.25.4.50.11.1.9
    optixDcnPublicTable OBJECT-TYPE
        SYNTAX SEQUENCE OF OptixDcnPublicEntry
        MAX-ACCESS not-accessible
        STATUS current
        DESCRIPTION
            "This table describes the ATN compatibility mode of a DCN port."
        ::= { optixPktDcnGroup 9 }

    -- 1.3.6.1.4.1.2011.2.25.4.50.11.1.9.1
    optixDcnPublicEntry OBJECT-TYPE
        SYNTAX OptixDcnPublicEntry
        MAX-ACCESS not-accessible
        STATUS current
        DESCRIPTION
            "This entry describes the ATN compatibility mode of a DCN port."
        INDEX{ optixLogBoardId,optixLogSubCardId,optixDcnPortId }
        ::= { optixDcnPublicTable 1 }

    OptixDcnPublicEntry ::=
        SEQUENCE {
            optixDcnPublicATNEnable
                INTEGER,
            optixDcnPublicVlanID
                Unsigned32,
            optixDcnMixL2dcnVlanID
                Unsigned32
        }

    -- 1.3.6.1.4.1.2011.2.25.4.50.11.1.9.1.1
    optixDcnPublicATNEnable OBJECT-TYPE
        SYNTAX INTEGER
        {
            disable(0),
            enable(1)
        }
        MAX-ACCESS read-write
        STATUS current
        DESCRIPTION
            "This table describes the ATN compatibility mode of a DCN configured on a port."
        ::= { optixDcnPublicEntry 1 }

    -- 1.3.6.1.4.1.2011.2.25.4.50.11.1.9.1.2
    optixDcnPublicVlanID OBJECT-TYPE
        SYNTAX Unsigned32 (1..4094)
        MAX-ACCESS read-write
        STATUS current
        DESCRIPTION
            "This object specifies the VLAN ID of an independent DCN configured on a port."
        ::= { optixDcnPublicEntry 2 }

    -- 1.3.6.1.4.1.2011.2.25.4.50.11.1.9.1.3
    optixDcnMixL2dcnVlanID OBJECT-TYPE
        SYNTAX Unsigned32 (1..4094)
        MAX-ACCESS read-write
        STATUS current
        DESCRIPTION
            "This object specifies the VLAN ID of the mixed L2 DCN configured on a port."
        ::= { optixDcnPublicEntry 3 }

    -- 1.3.6.1.4.1.2011.2.25.4.50.11.1.10
    optixDcnPortTable OBJECT-TYPE
        SYNTAX SEQUENCE OF OptixDcnPortEntry
        MAX-ACCESS not-accessible
        STATUS current
        DESCRIPTION
            "This table implements the configuration of independent DCN for ports."
        ::= { optixPktDcnGroup 10 }

    -- 1.3.6.1.4.1.2011.2.25.4.50.11.1.10.1
    optixDcnPortEntry OBJECT-TYPE
        SYNTAX OptixDcnPortEntry
        MAX-ACCESS not-accessible
        STATUS current
        DESCRIPTION
            "This node describes an entity of the independent DCN parameter table."
        INDEX{ optixDcnPortID }
        ::= { optixDcnPortTable 1 }

    OptixDcnPortEntry ::=
        SEQUENCE {
            optixDcnPortID
                INTEGER
        }

    -- 1.3.6.1.4.1.2011.2.25.4.50.11.1.10.1.1
    optixDcnPortID OBJECT-TYPE
        SYNTAX INTEGER (1..4094)
        MAX-ACCESS not-accessible
        STATUS current
        DESCRIPTION
            "This node describes the ID of a port configured with an independent DCN VLAN."
        ::= { optixDcnPortEntry 1 }

    -- 1.3.6.1.4.1.2011.2.25.4.50.11.1.11
    optixDcnOSPFTable OBJECT-TYPE
        SYNTAX SEQUENCE OF OptixDcnOSPFEntry
        MAX-ACCESS not-accessible
        STATUS current
        DESCRIPTION
            "This table implements configuring an OSPF subnet on an inband DCN port."
        ::= { optixPktDcnGroup 11 }

    -- 1.3.6.1.4.1.2011.2.25.4.50.11.1.11.1
    optixDcnOSPFEntry OBJECT-TYPE
        SYNTAX OptixDcnOSPFEntry
        MAX-ACCESS not-accessible
        STATUS current
        DESCRIPTION
            "This node describes an entity of the function that configures an OSPF subnet on an inband DCN port."
        INDEX{ optixDcnOSPFTunnelID }
        ::= { optixDcnOSPFTable 1 }

    OptixDcnOSPFEntry ::=
        SEQUENCE {
            optixDcnOSPFTunnelID
                Unsigned32,
            optixDcnOSPFID
                Integer32
        }

    -- 1.3.6.1.4.1.2011.2.25.4.50.11.1.11.1.1
    optixDcnOSPFTunnelID OBJECT-TYPE
        SYNTAX Unsigned32
        MAX-ACCESS not-accessible
        STATUS current
        DESCRIPTION
            "This object indicates the ID of the tunnel configured on an inband DCN port."
        ::= { optixDcnOSPFEntry 1 }

    -- 1.3.6.1.4.1.2011.2.25.4.50.11.1.11.1.2
    optixDcnOSPFID OBJECT-TYPE
        SYNTAX Integer32 (1..4)
        MAX-ACCESS read-write
        STATUS current
        DESCRIPTION
            "This object indicates the subnet ID of the OSPF configured on an inband DCN port."
        ::= { optixDcnOSPFEntry 2 }

    -- 1.3.6.1.4.1.2011.2.25.4.50.11.2
    optixPktDcnNEGroup OBJECT IDENTIFIER ::= { optixPktDcn 2 }

    -- 1.3.6.1.4.1.2011.2.25.4.50.11.2.1
    optixDcnUserVlan OBJECT-TYPE
        SYNTAX Unsigned32
        MAX-ACCESS read-write
        STATUS current
        DESCRIPTION
            "This object indicates the vlanid of DCN user connect. Value range: 1 to 4096."
        ::= { optixPktDcnNEGroup 1 }

    -- 1.3.6.1.4.1.2011.2.25.4.50.11.2.2
    optixL2DcnRstpState OBJECT-TYPE
        SYNTAX INTEGER
        {
            disable(0),
            enable(1),
            auto(2)
        }
        MAX-ACCESS read-write
        STATUS current
        DESCRIPTION
            "This object indicates the L2DCN rstp protocol state. 0: disable, 1: enable, 2: auto"
        ::= { optixPktDcnNEGroup 2 }

    -- 1.3.6.1.4.1.2011.2.25.4.50.11.2.3
    optixL2DcnRstpRealState OBJECT-TYPE
        SYNTAX INTEGER
        {
            disable(0),
            enable(1),
            auto(2)
        }
        MAX-ACCESS read-only
        STATUS current
        DESCRIPTION
            "This object indicates the L2DCN rstp protocol real state. 0: disable, 1: enable, 2: auto"
        ::= { optixPktDcnNEGroup 3 }

    -- 1.3.6.1.4.1.2011.2.25.4.50.11.2.4
    optixDcnAllPortOnOffState OBJECT-TYPE
        SYNTAX INTEGER
        {
            invalid(0),
            close(1),
            open(2)
        }
        MAX-ACCESS read-write
        STATUS current
        DESCRIPTION
            "This object indicates the DCN control all ports."
        ::= { optixPktDcnNEGroup 4 }

END
