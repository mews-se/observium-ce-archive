-- OPTIX-GLOBAL-PER-TRAPS-RTN-MIB
-- MIB generated by ExcelToMIB tool 1.0
-- 
-- =================================================================
--  Copyright (C) 2012 by HUAWEI TECHNOLOGIES. All rights reserved
--  
--  Description:This MIB describes the DataPmformance interface of Huawei macrowave transmit
--  Reference:
--  Version: V1.00
--  History:
--  <author>,<date>,<contents>
-- =================================================================
--
OPTIX-GLOBAL-PER-TRAPS-RTN-MIB DEFINITIONS ::= BEGIN
    IMPORTS
        optixCommonGlobal
            FROM OPTIX-OID-MIB
        PerformanceEventType,ValidflagType,ObjType,AlarmEventType,AlmDataSrvEffType,AlmDataNtfcnCdeType,DataPmEventType
            FROM OPTIX-GLOBAL-TC-MIB
        OBJECT-GROUP,MODULE-COMPLIANCE
            FROM SNMPv2-CONF
        optixGlobalTrap,rptEvtPeriod,rptEvtValue,rptEvtVldty,rptEvtDateTime,rptEvtObjType,rptEvtParaLen,rptEvtPara
            FROM OPTIX-GLOBAL-TRAPS-MIB
        Integer32,Unsigned32,OBJECT-TYPE,MODULE-IDENTITY,NOTIFICATION-TYPE
            FROM SNMPv2-SMI
        DateAndTime,DisplayString
            FROM SNMPv2-TC
        ;

    -- 1.3.6.1.4.1.2011.2.25.3.40.40.30
    optixTrapsPER OBJECT IDENTIFIER ::= { optixGlobalTrap 30 }

    -- 1.3.6.1.4.1.2011.2.25.3.40.40.30.1
    pmRsBbe NOTIFICATION-TYPE
        OBJECTS{ rptEvtPeriod,rptEvtValue,rptEvtVldty,rptEvtDateTime,rptEvtObjType,rptEvtParaLen,rptEvtPara }
        STATUS current
        DESCRIPTION
            "Trap of Event:RS Background block error."
        ::= { optixTrapsPER 1 }

    -- 1.3.6.1.4.1.2011.2.25.3.40.40.30.2
    pmRsEs NOTIFICATION-TYPE
        OBJECTS{ rptEvtPeriod,rptEvtValue,rptEvtVldty,rptEvtDateTime,rptEvtObjType,rptEvtParaLen,rptEvtPara }
        STATUS current
        DESCRIPTION
            "Trap of Event:RS Errored Second."
        ::= { optixTrapsPER 2 }

    -- 1.3.6.1.4.1.2011.2.25.3.40.40.30.3
    pmRsSes NOTIFICATION-TYPE
        OBJECTS{ rptEvtPeriod,rptEvtValue,rptEvtVldty,rptEvtDateTime,rptEvtObjType,rptEvtParaLen,rptEvtPara }
        STATUS current
        DESCRIPTION
            "Trap of Event:RS Severely errored second."
        ::= { optixTrapsPER 3 }

    -- 1.3.6.1.4.1.2011.2.25.3.40.40.30.4
    pmRsOof NOTIFICATION-TYPE
        OBJECTS{ rptEvtPeriod,rptEvtValue,rptEvtVldty,rptEvtDateTime,rptEvtObjType,rptEvtParaLen,rptEvtPara }
        STATUS current
        DESCRIPTION
            "Trap of Event:RS Out of frame."
        ::= { optixTrapsPER 4 }

    -- 1.3.6.1.4.1.2011.2.25.3.40.40.30.5
    pmRsOfs NOTIFICATION-TYPE
        OBJECTS{ rptEvtPeriod,rptEvtValue,rptEvtVldty,rptEvtDateTime,rptEvtObjType,rptEvtParaLen,rptEvtPara }
        STATUS current
        DESCRIPTION
            "Trap of Event:RS Out-of-frame second."
        ::= { optixTrapsPER 5 }

    -- 1.3.6.1.4.1.2011.2.25.3.40.40.30.6
    pmRsUas NOTIFICATION-TYPE
        OBJECTS{ rptEvtPeriod,rptEvtValue,rptEvtVldty,rptEvtDateTime,rptEvtObjType,rptEvtParaLen,rptEvtPara }
        STATUS current
        DESCRIPTION
            "Trap of Event:RS Unavailable second."
        ::= { optixTrapsPER 6 }

    -- 1.3.6.1.4.1.2011.2.25.3.40.40.30.7
    pmRsCses NOTIFICATION-TYPE
        OBJECTS{ rptEvtPeriod,rptEvtValue,rptEvtVldty,rptEvtDateTime,rptEvtObjType,rptEvtParaLen,rptEvtPara }
        STATUS current
        DESCRIPTION
            "Trap of Event:RS Consecutive severely errored second."
        ::= { optixTrapsPER 7 }

    -- 1.3.6.1.4.1.2011.2.25.3.40.40.30.12
    pmE1LcvSdh NOTIFICATION-TYPE
        OBJECTS{ rptEvtPeriod,rptEvtValue,rptEvtVldty,rptEvtDateTime,rptEvtObjType,rptEvtParaLen,rptEvtPara }
        STATUS current
        DESCRIPTION
            "Trap of Event:E1 LCV."
        ::= { optixTrapsPER 12 }

    -- 1.3.6.1.4.1.2011.2.25.3.40.40.30.13
    pmE1LesSdh NOTIFICATION-TYPE
        OBJECTS{ rptEvtPeriod,rptEvtValue,rptEvtVldty,rptEvtDateTime,rptEvtObjType,rptEvtParaLen,rptEvtPara }
        STATUS current
        DESCRIPTION
            "Trap of Event:E1 LLosS."
        ::= { optixTrapsPER 13 }

    -- 1.3.6.1.4.1.2011.2.25.3.40.40.30.14
    pmE1LsesSdh NOTIFICATION-TYPE
        OBJECTS{ rptEvtPeriod,rptEvtValue,rptEvtVldty,rptEvtDateTime,rptEvtObjType,rptEvtParaLen,rptEvtPara }
        STATUS current
        DESCRIPTION
            "Trap of Event:E1 LSES."
        ::= { optixTrapsPER 14 }

    -- 1.3.6.1.4.1.2011.2.25.3.40.40.30.15
    pmE1LLossSdh NOTIFICATION-TYPE
        OBJECTS{ rptEvtPeriod,rptEvtValue,rptEvtVldty,rptEvtDateTime,rptEvtObjType,rptEvtParaLen,rptEvtPara }
        STATUS current
        DESCRIPTION
            "Trap of Event:E1 LLOSS."
        ::= { optixTrapsPER 15 }

    -- 1.3.6.1.4.1.2011.2.25.3.40.40.30.16
    pmMsBbe NOTIFICATION-TYPE
        OBJECTS{ rptEvtPeriod,rptEvtValue,rptEvtVldty,rptEvtDateTime,rptEvtObjType,rptEvtParaLen,rptEvtPara }
        STATUS current
        DESCRIPTION
            "Trap of Event:MS Background block error."
        ::= { optixTrapsPER 16 }

    -- 1.3.6.1.4.1.2011.2.25.3.40.40.30.17
    pmMsEs NOTIFICATION-TYPE
        OBJECTS{ rptEvtPeriod,rptEvtValue,rptEvtVldty,rptEvtDateTime,rptEvtObjType,rptEvtParaLen,rptEvtPara }
        STATUS current
        DESCRIPTION
            "Trap of Event:MS Errored Second."
        ::= { optixTrapsPER 17 }

    -- 1.3.6.1.4.1.2011.2.25.3.40.40.30.18
    pmMsSes NOTIFICATION-TYPE
        OBJECTS{ rptEvtPeriod,rptEvtValue,rptEvtVldty,rptEvtDateTime,rptEvtObjType,rptEvtParaLen,rptEvtPara }
        STATUS current
        DESCRIPTION
            "Trap of Event:MS Severely errored second."
        ::= { optixTrapsPER 18 }

    -- 1.3.6.1.4.1.2011.2.25.3.40.40.30.19
    pmMsFeBbe NOTIFICATION-TYPE
        OBJECTS{ rptEvtPeriod,rptEvtValue,rptEvtVldty,rptEvtDateTime,rptEvtObjType,rptEvtParaLen,rptEvtPara }
        STATUS current
        DESCRIPTION
            "Trap of Event:MS Far end background block error."
        ::= { optixTrapsPER 19 }

    -- 1.3.6.1.4.1.2011.2.25.3.40.40.30.20
    pmMsFeEs NOTIFICATION-TYPE
        OBJECTS{ rptEvtPeriod,rptEvtValue,rptEvtVldty,rptEvtDateTime,rptEvtObjType,rptEvtParaLen,rptEvtPara }
        STATUS current
        DESCRIPTION
            "Trap of Event:MS Far end errored second."
        ::= { optixTrapsPER 20 }

    -- 1.3.6.1.4.1.2011.2.25.3.40.40.30.21
    pmMsFeSes NOTIFICATION-TYPE
        OBJECTS{ rptEvtPeriod,rptEvtValue,rptEvtVldty,rptEvtDateTime,rptEvtObjType,rptEvtParaLen,rptEvtPara }
        STATUS current
        DESCRIPTION
            "Trap of Event:MS Far end severely errored second."
        ::= { optixTrapsPER 21 }

    -- 1.3.6.1.4.1.2011.2.25.3.40.40.30.22
    pmMsUas NOTIFICATION-TYPE
        OBJECTS{ rptEvtPeriod,rptEvtValue,rptEvtVldty,rptEvtDateTime,rptEvtObjType,rptEvtParaLen,rptEvtPara }
        STATUS current
        DESCRIPTION
            "Trap of Event:MS Unavailable second."
        ::= { optixTrapsPER 22 }

    -- 1.3.6.1.4.1.2011.2.25.3.40.40.30.23
    pmMsCses NOTIFICATION-TYPE
        OBJECTS{ rptEvtPeriod,rptEvtValue,rptEvtVldty,rptEvtDateTime,rptEvtObjType,rptEvtParaLen,rptEvtPara }
        STATUS current
        DESCRIPTION
            "Trap of Event:MS Consecutive severely errored second."
        ::= { optixTrapsPER 23 }

    -- 1.3.6.1.4.1.2011.2.25.3.40.40.30.24
    pmMsFeCses NOTIFICATION-TYPE
        OBJECTS{ rptEvtPeriod,rptEvtValue,rptEvtVldty,rptEvtDateTime,rptEvtObjType,rptEvtParaLen,rptEvtPara }
        STATUS current
        DESCRIPTION
            "Trap of Event:MS Far end Consecutive severely errored second."
        ::= { optixTrapsPER 24 }

    -- 1.3.6.1.4.1.2011.2.25.3.40.40.30.33
    pmMsFeUas NOTIFICATION-TYPE
        OBJECTS{ rptEvtPeriod,rptEvtValue,rptEvtVldty,rptEvtDateTime,rptEvtObjType,rptEvtParaLen,rptEvtPara }
        STATUS current
        DESCRIPTION
            "Trap of Event:MS Far end Unavailable second."
        ::= { optixTrapsPER 33 }

    -- 1.3.6.1.4.1.2011.2.25.3.40.40.30.42
    pmAupjcHigh NOTIFICATION-TYPE
        OBJECTS{ rptEvtPeriod,rptEvtValue,rptEvtVldty,rptEvtDateTime,rptEvtObjType,rptEvtParaLen,rptEvtPara }
        STATUS current
        DESCRIPTION
            "Trap of Event:Administrative Unit Pointer justification count HIGH."
        ::= { optixTrapsPER 42 }

    -- 1.3.6.1.4.1.2011.2.25.3.40.40.30.43
    pmAupjcLow NOTIFICATION-TYPE
        OBJECTS{ rptEvtPeriod,rptEvtValue,rptEvtVldty,rptEvtDateTime,rptEvtObjType,rptEvtParaLen,rptEvtPara }
        STATUS current
        DESCRIPTION
            "Trap of Event:Administrative Unit Pointer justification count LOW."
        ::= { optixTrapsPER 43 }

    -- 1.3.6.1.4.1.2011.2.25.3.40.40.30.44
    pmAupjcNew NOTIFICATION-TYPE
        OBJECTS{ rptEvtPeriod,rptEvtValue,rptEvtVldty,rptEvtDateTime,rptEvtObjType,rptEvtParaLen,rptEvtPara }
        STATUS current
        DESCRIPTION
            "Trap of Event:Administrative Unit Pointer justification count NEW."
        ::= { optixTrapsPER 44 }

    -- 1.3.6.1.4.1.2011.2.25.3.40.40.30.48
    pmHpBbe NOTIFICATION-TYPE
        OBJECTS{ rptEvtPeriod,rptEvtValue,rptEvtVldty,rptEvtDateTime,rptEvtObjType,rptEvtParaLen,rptEvtPara }
        STATUS current
        DESCRIPTION
            "Trap of Event:HP Background block error."
        ::= { optixTrapsPER 48 }

    -- 1.3.6.1.4.1.2011.2.25.3.40.40.30.49
    pmHpEs NOTIFICATION-TYPE
        OBJECTS{ rptEvtPeriod,rptEvtValue,rptEvtVldty,rptEvtDateTime,rptEvtObjType,rptEvtParaLen,rptEvtPara }
        STATUS current
        DESCRIPTION
            "Trap of Event:HP Errored Second."
        ::= { optixTrapsPER 49 }

    -- 1.3.6.1.4.1.2011.2.25.3.40.40.30.50
    pmHpSes NOTIFICATION-TYPE
        OBJECTS{ rptEvtPeriod,rptEvtValue,rptEvtVldty,rptEvtDateTime,rptEvtObjType,rptEvtParaLen,rptEvtPara }
        STATUS current
        DESCRIPTION
            "Trap of Event:HP Severely errored second."
        ::= { optixTrapsPER 50 }

    -- 1.3.6.1.4.1.2011.2.25.3.40.40.30.51
    pmHpFeBbe NOTIFICATION-TYPE
        OBJECTS{ rptEvtPeriod,rptEvtValue,rptEvtVldty,rptEvtDateTime,rptEvtObjType,rptEvtParaLen,rptEvtPara }
        STATUS current
        DESCRIPTION
            "Trap of Event:HP Far end background block error."
        ::= { optixTrapsPER 51 }

    -- 1.3.6.1.4.1.2011.2.25.3.40.40.30.52
    pmHpFeEs NOTIFICATION-TYPE
        OBJECTS{ rptEvtPeriod,rptEvtValue,rptEvtVldty,rptEvtDateTime,rptEvtObjType,rptEvtParaLen,rptEvtPara }
        STATUS current
        DESCRIPTION
            "Trap of Event:HP Far end errored second."
        ::= { optixTrapsPER 52 }

    -- 1.3.6.1.4.1.2011.2.25.3.40.40.30.53
    pmHpFeSes NOTIFICATION-TYPE
        OBJECTS{ rptEvtPeriod,rptEvtValue,rptEvtVldty,rptEvtDateTime,rptEvtObjType,rptEvtParaLen,rptEvtPara }
        STATUS current
        DESCRIPTION
            "Trap of Event:HP Far end severely errored second."
        ::= { optixTrapsPER 53 }

    -- 1.3.6.1.4.1.2011.2.25.3.40.40.30.54
    pmHpUas NOTIFICATION-TYPE
        OBJECTS{ rptEvtPeriod,rptEvtValue,rptEvtVldty,rptEvtDateTime,rptEvtObjType,rptEvtParaLen,rptEvtPara }
        STATUS current
        DESCRIPTION
            "Trap of Event:HP Unavailable second."
        ::= { optixTrapsPER 54 }

    -- 1.3.6.1.4.1.2011.2.25.3.40.40.30.55
    pmHpCses NOTIFICATION-TYPE
        OBJECTS{ rptEvtPeriod,rptEvtValue,rptEvtVldty,rptEvtDateTime,rptEvtObjType,rptEvtParaLen,rptEvtPara }
        STATUS current
        DESCRIPTION
            "Trap of Event:HP Consecutive severely errored second."
        ::= { optixTrapsPER 55 }

    -- 1.3.6.1.4.1.2011.2.25.3.40.40.30.56
    pmHpFeCses NOTIFICATION-TYPE
        OBJECTS{ rptEvtPeriod,rptEvtValue,rptEvtVldty,rptEvtDateTime,rptEvtObjType,rptEvtParaLen,rptEvtPara }
        STATUS current
        DESCRIPTION
            "Trap of Event:HP Far end Consecutive severely errored second."
        ::= { optixTrapsPER 56 }

    -- 1.3.6.1.4.1.2011.2.25.3.40.40.30.76
    pmHpFeUas NOTIFICATION-TYPE
        OBJECTS{ rptEvtPeriod,rptEvtValue,rptEvtVldty,rptEvtDateTime,rptEvtObjType,rptEvtParaLen,rptEvtPara }
        STATUS current
        DESCRIPTION
            "Trap of Event:HP Far end Unavailable second."
        ::= { optixTrapsPER 76 }

    -- 1.3.6.1.4.1.2011.2.25.3.40.40.30.96
    pmTlbMax NOTIFICATION-TYPE
        OBJECTS{ rptEvtPeriod,rptEvtValue,rptEvtVldty,rptEvtDateTime,rptEvtObjType,rptEvtParaLen,rptEvtPara }
        STATUS current
        DESCRIPTION
            "Trap of Event:Laser Transmission Power Level Maximum."
        ::= { optixTrapsPER 96 }

    -- 1.3.6.1.4.1.2011.2.25.3.40.40.30.97
    pmTlbMin NOTIFICATION-TYPE
        OBJECTS{ rptEvtPeriod,rptEvtValue,rptEvtVldty,rptEvtDateTime,rptEvtObjType,rptEvtParaLen,rptEvtPara }
        STATUS current
        DESCRIPTION
            "Trap of Event:Transmission Laser bias Current Minimum."
        ::= { optixTrapsPER 97 }

    -- 1.3.6.1.4.1.2011.2.25.3.40.40.30.98
    pmTlbCur NOTIFICATION-TYPE
        OBJECTS{ rptEvtPeriod,rptEvtValue,rptEvtVldty,rptEvtDateTime,rptEvtObjType,rptEvtParaLen,rptEvtPara }
        STATUS current
        DESCRIPTION
            "Trap of Event:Transmission Laser bias Current Cur-Value."
        ::= { optixTrapsPER 98 }

    -- 1.3.6.1.4.1.2011.2.25.3.40.40.30.102
    pmTplMax NOTIFICATION-TYPE
        OBJECTS{ rptEvtPeriod,rptEvtValue,rptEvtVldty,rptEvtDateTime,rptEvtObjType,rptEvtParaLen,rptEvtPara }
        STATUS current
        DESCRIPTION
            "Trap of Event:Laser Transmission Power Level Maximum."
        ::= { optixTrapsPER 102 }

    -- 1.3.6.1.4.1.2011.2.25.3.40.40.30.103
    pmTplMin NOTIFICATION-TYPE
        OBJECTS{ rptEvtPeriod,rptEvtValue,rptEvtVldty,rptEvtDateTime,rptEvtObjType,rptEvtParaLen,rptEvtPara }
        STATUS current
        DESCRIPTION
            "Trap of Event:Laser Transmission Power Level Minimum."
        ::= { optixTrapsPER 103 }

    -- 1.3.6.1.4.1.2011.2.25.3.40.40.30.104
    pmTplCur NOTIFICATION-TYPE
        OBJECTS{ rptEvtPeriod,rptEvtValue,rptEvtVldty,rptEvtDateTime,rptEvtObjType,rptEvtParaLen,rptEvtPara }
        STATUS current
        DESCRIPTION
            "Trap of Event:Laser Transmission Power Level Cur-Value."
        ::= { optixTrapsPER 104 }

    -- 1.3.6.1.4.1.2011.2.25.3.40.40.30.105
    pmRplMax NOTIFICATION-TYPE
        OBJECTS{ rptEvtPeriod,rptEvtValue,rptEvtVldty,rptEvtDateTime,rptEvtObjType,rptEvtParaLen,rptEvtPara }
        STATUS current
        DESCRIPTION
            "Trap of Event:Laser Receiving Power level Maximum."
        ::= { optixTrapsPER 105 }

    -- 1.3.6.1.4.1.2011.2.25.3.40.40.30.106
    pmRplMin NOTIFICATION-TYPE
        OBJECTS{ rptEvtPeriod,rptEvtValue,rptEvtVldty,rptEvtDateTime,rptEvtObjType,rptEvtParaLen,rptEvtPara }
        STATUS current
        DESCRIPTION
            "Trap of Event:Laser Receiving Power level Minimum."
        ::= { optixTrapsPER 106 }

    -- 1.3.6.1.4.1.2011.2.25.3.40.40.30.107
    pmRplCur NOTIFICATION-TYPE
        OBJECTS{ rptEvtPeriod,rptEvtValue,rptEvtVldty,rptEvtDateTime,rptEvtObjType,rptEvtParaLen,rptEvtPara }
        STATUS current
        DESCRIPTION
            "Trap of Event:Laser Receiving Power level current."
        ::= { optixTrapsPER 107 }

    -- 1.3.6.1.4.1.2011.2.25.3.40.40.30.108
    pmOspiTmpMax NOTIFICATION-TYPE
        OBJECTS{ rptEvtPeriod,rptEvtValue,rptEvtVldty,rptEvtDateTime,rptEvtObjType,rptEvtParaLen,rptEvtPara }
        STATUS current
        DESCRIPTION
            "Trap of Event:Laser Temperature Maximums."
        ::= { optixTrapsPER 108 }

    -- 1.3.6.1.4.1.2011.2.25.3.40.40.30.109
    pmOspiTmpMin NOTIFICATION-TYPE
        OBJECTS{ rptEvtPeriod,rptEvtValue,rptEvtVldty,rptEvtDateTime,rptEvtObjType,rptEvtParaLen,rptEvtPara }
        STATUS current
        DESCRIPTION
            "Trap of Event:Laser Temperature Minimum."
        ::= { optixTrapsPER 109 }

    -- 1.3.6.1.4.1.2011.2.25.3.40.40.30.110
    pmOspiTmpCur NOTIFICATION-TYPE
        OBJECTS{ rptEvtPeriod,rptEvtValue,rptEvtVldty,rptEvtDateTime,rptEvtObjType,rptEvtParaLen,rptEvtPara }
        STATUS current
        DESCRIPTION
            "Trap of Event:Laser Temperature Cur-Valuet."
        ::= { optixTrapsPER 110 }

    -- 1.3.6.1.4.1.2011.2.25.3.40.40.30.135
    pmFecCorByteCnt NOTIFICATION-TYPE
        OBJECTS{ rptEvtPeriod,rptEvtValue,rptEvtVldty,rptEvtDateTime,rptEvtObjType,rptEvtParaLen,rptEvtPara }
        STATUS current
        DESCRIPTION
            "Forward Error Correction - Corrected Byte Count"
        ::= { optixTrapsPER 135 }

    -- 1.3.6.1.4.1.2011.2.25.3.40.40.30.136
    pmFecUncorBlockCnt NOTIFICATION-TYPE
        OBJECTS{ rptEvtPeriod,rptEvtValue,rptEvtVldty,rptEvtDateTime,rptEvtObjType,rptEvtParaLen,rptEvtPara }
        STATUS current
        DESCRIPTION
            "Forward Error Correction - UnCorrected Block Count"
        ::= { optixTrapsPER 136 }

    -- 1.3.6.1.4.1.2011.2.25.3.40.40.30.142
    pmLpFeUas NOTIFICATION-TYPE
        OBJECTS{ rptEvtPeriod,rptEvtValue,rptEvtVldty,rptEvtDateTime,rptEvtObjType,rptEvtParaLen,rptEvtPara }
        STATUS current
        DESCRIPTION
            "Trap of Event:lp Far end Unavailable Second"
        ::= { optixTrapsPER 142 }

    -- 1.3.6.1.4.1.2011.2.25.3.40.40.30.144
    pmLpBbe NOTIFICATION-TYPE
        OBJECTS{ rptEvtPeriod,rptEvtValue,rptEvtVldty,rptEvtDateTime,rptEvtObjType,rptEvtParaLen,rptEvtPara }
        STATUS current
        DESCRIPTION
            "Trap of Event:LP Background block error"
        ::= { optixTrapsPER 144 }

    -- 1.3.6.1.4.1.2011.2.25.3.40.40.30.145
    pmLpEs NOTIFICATION-TYPE
        OBJECTS{ rptEvtPeriod,rptEvtValue,rptEvtVldty,rptEvtDateTime,rptEvtObjType,rptEvtParaLen,rptEvtPara }
        STATUS current
        DESCRIPTION
            "Trap of Event:LP Error Second"
        ::= { optixTrapsPER 145 }

    -- 1.3.6.1.4.1.2011.2.25.3.40.40.30.146
    pmLpSes NOTIFICATION-TYPE
        OBJECTS{ rptEvtPeriod,rptEvtValue,rptEvtVldty,rptEvtDateTime,rptEvtObjType,rptEvtParaLen,rptEvtPara }
        STATUS current
        DESCRIPTION
            "Trap of Event:LP Severely errored second"
        ::= { optixTrapsPER 146 }

    -- 1.3.6.1.4.1.2011.2.25.3.40.40.30.147
    pmLpFeBbe NOTIFICATION-TYPE
        OBJECTS{ rptEvtPeriod,rptEvtValue,rptEvtVldty,rptEvtDateTime,rptEvtObjType,rptEvtParaLen,rptEvtPara }
        STATUS current
        DESCRIPTION
            "Trap of Event:LP Far end background block error"
        ::= { optixTrapsPER 147 }

    -- 1.3.6.1.4.1.2011.2.25.3.40.40.30.148
    pmLpFeEs NOTIFICATION-TYPE
        OBJECTS{ rptEvtPeriod,rptEvtValue,rptEvtVldty,rptEvtDateTime,rptEvtObjType,rptEvtParaLen,rptEvtPara }
        STATUS current
        DESCRIPTION
            "Trap of Event:LP Far end errored second"
        ::= { optixTrapsPER 148 }

    -- 1.3.6.1.4.1.2011.2.25.3.40.40.30.149
    pmLpFeSes NOTIFICATION-TYPE
        OBJECTS{ rptEvtPeriod,rptEvtValue,rptEvtVldty,rptEvtDateTime,rptEvtObjType,rptEvtParaLen,rptEvtPara }
        STATUS current
        DESCRIPTION
            "Trap of Event:LP Far end severely errored second"
        ::= { optixTrapsPER 149 }

    -- 1.3.6.1.4.1.2011.2.25.3.40.40.30.150
    pmLpUas NOTIFICATION-TYPE
        OBJECTS{ rptEvtPeriod,rptEvtValue,rptEvtVldty,rptEvtDateTime,rptEvtObjType,rptEvtParaLen,rptEvtPara }
        STATUS current
        DESCRIPTION
            "Trap of Event:LP Unavailable second"
        ::= { optixTrapsPER 150 }

    -- 1.3.6.1.4.1.2011.2.25.3.40.40.30.151
    pmLpCses NOTIFICATION-TYPE
        OBJECTS{ rptEvtPeriod,rptEvtValue,rptEvtVldty,rptEvtDateTime,rptEvtObjType,rptEvtParaLen,rptEvtPara }
        STATUS current
        DESCRIPTION
            "Trap of Event:LP Consecutive severely errored second"
        ::= { optixTrapsPER 151 }

    -- 1.3.6.1.4.1.2011.2.25.3.40.40.30.152
    pmLpFeCses NOTIFICATION-TYPE
        OBJECTS{ rptEvtPeriod,rptEvtValue,rptEvtVldty,rptEvtDateTime,rptEvtObjType,rptEvtParaLen,rptEvtPara }
        STATUS current
        DESCRIPTION
            "Trap of Event:LP Far end Consecutive severely errored second"
        ::= { optixTrapsPER 152 }

    -- 1.3.6.1.4.1.2011.2.25.3.40.40.30.164
    pmT1LcvSdh NOTIFICATION-TYPE
        OBJECTS{ rptEvtPeriod,rptEvtValue,rptEvtVldty,rptEvtDateTime,rptEvtObjType,rptEvtParaLen,rptEvtPara }
        STATUS current
        DESCRIPTION
            "Trap of Event:T1 LCV."
        ::= { optixTrapsPER 164 }

    -- 1.3.6.1.4.1.2011.2.25.3.40.40.30.165
    pmT1LesSdh NOTIFICATION-TYPE
        OBJECTS{ rptEvtPeriod,rptEvtValue,rptEvtVldty,rptEvtDateTime,rptEvtObjType,rptEvtParaLen,rptEvtPara }
        STATUS current
        DESCRIPTION
            "Trap of Event:T1 LES."
        ::= { optixTrapsPER 165 }

    -- 1.3.6.1.4.1.2011.2.25.3.40.40.30.166
    pmT1LsesSdh NOTIFICATION-TYPE
        OBJECTS{ rptEvtPeriod,rptEvtValue,rptEvtVldty,rptEvtDateTime,rptEvtObjType,rptEvtParaLen,rptEvtPara }
        STATUS current
        DESCRIPTION
            "Trap of Event:T1 LSES."
        ::= { optixTrapsPER 166 }

    -- 1.3.6.1.4.1.2011.2.25.3.40.40.30.170
    pmTupjcHigh NOTIFICATION-TYPE
        OBJECTS{ rptEvtPeriod,rptEvtValue,rptEvtVldty,rptEvtDateTime,rptEvtObjType,rptEvtParaLen,rptEvtPara }
        STATUS current
        DESCRIPTION
            "Trap of Event:Tributary Unit Pointer justification count HIGH"
        ::= { optixTrapsPER 170 }

    -- 1.3.6.1.4.1.2011.2.25.3.40.40.30.171
    pmTupjcLow NOTIFICATION-TYPE
        OBJECTS{ rptEvtPeriod,rptEvtValue,rptEvtVldty,rptEvtDateTime,rptEvtObjType,rptEvtParaLen,rptEvtPara }
        STATUS current
        DESCRIPTION
            "Trap of Event:Tributary Unit Pointer justification count LOW"
        ::= { optixTrapsPER 171 }

    -- 1.3.6.1.4.1.2011.2.25.3.40.40.30.172
    pmTupjcNew NOTIFICATION-TYPE
        OBJECTS{ rptEvtPeriod,rptEvtValue,rptEvtVldty,rptEvtDateTime,rptEvtObjType,rptEvtParaLen,rptEvtPara }
        STATUS current
        DESCRIPTION
            "Trap of Event:Tributary Unit Pointer justification count NEW"
        ::= { optixTrapsPER 172 }

    -- 1.3.6.1.4.1.2011.2.25.3.40.40.30.252
    pmFecBefCorEr NOTIFICATION-TYPE
        OBJECTS{ rptEvtPeriod,rptEvtValue,rptEvtVldty,rptEvtDateTime,rptEvtObjType,rptEvtParaLen,rptEvtPara }
        STATUS current
        DESCRIPTION
            "Trap of Event:Before FEC Correct Error Ratio"
        ::= { optixTrapsPER 252 }

    -- 1.3.6.1.4.1.2011.2.25.3.40.40.30.8606
    pmRslMax NOTIFICATION-TYPE
        OBJECTS{ rptEvtPeriod,rptEvtValue,rptEvtVldty,rptEvtDateTime,rptEvtObjType,rptEvtParaLen,rptEvtPara }
        STATUS current
        DESCRIPTION
            "Trap of Event:Max Receive Signal Level"
        ::= { optixTrapsPER 8606 }

    -- 1.3.6.1.4.1.2011.2.25.3.40.40.30.8607
    pmRslMin NOTIFICATION-TYPE
        OBJECTS{ rptEvtPeriod,rptEvtValue,rptEvtVldty,rptEvtDateTime,rptEvtObjType,rptEvtParaLen,rptEvtPara }
        STATUS current
        DESCRIPTION
            "Trap of Event:Min Receive Signal Level"
        ::= { optixTrapsPER 8607 }

    -- 1.3.6.1.4.1.2011.2.25.3.40.40.30.8608
    pmRslCur NOTIFICATION-TYPE
        OBJECTS{ rptEvtPeriod,rptEvtValue,rptEvtVldty,rptEvtDateTime,rptEvtObjType,rptEvtParaLen,rptEvtPara }
        STATUS current
        DESCRIPTION
            "Trap of Event:Current Receive Signal Level"
        ::= { optixTrapsPER 8608 }

    -- 1.3.6.1.4.1.2011.2.25.3.40.40.30.8609
    pmTslMax NOTIFICATION-TYPE
        OBJECTS{ rptEvtPeriod,rptEvtValue,rptEvtVldty,rptEvtDateTime,rptEvtObjType,rptEvtParaLen,rptEvtPara }
        STATUS current
        DESCRIPTION
            "Trap of Event:Max Transmission Signal Level"
        ::= { optixTrapsPER 8609 }

    -- 1.3.6.1.4.1.2011.2.25.3.40.40.30.8610
    pmTslMin NOTIFICATION-TYPE
        OBJECTS{ rptEvtPeriod,rptEvtValue,rptEvtVldty,rptEvtDateTime,rptEvtObjType,rptEvtParaLen,rptEvtPara }
        STATUS current
        DESCRIPTION
            "Trap of Event:Minimum Transmission Signal Level"
        ::= { optixTrapsPER 8610 }

    -- 1.3.6.1.4.1.2011.2.25.3.40.40.30.8611
    pmTslCur NOTIFICATION-TYPE
        OBJECTS{ rptEvtPeriod,rptEvtValue,rptEvtVldty,rptEvtDateTime,rptEvtObjType,rptEvtParaLen,rptEvtPara }
        STATUS current
        DESCRIPTION
            "Trap of Event:Current Transmission Signal Level"
        ::= { optixTrapsPER 8611 }

    -- 1.3.6.1.4.1.2011.2.25.3.40.40.30.14915
    pmCpTelDownCount NOTIFICATION-TYPE
        OBJECTS{ rptEvtPeriod,rptEvtValue,rptEvtVldty,rptEvtDateTime,rptEvtObjType,rptEvtParaLen,rptEvtPara }
        STATUS current
        DESCRIPTION
            "Trap of Event:TE Link Down Count"
        ::= { optixTrapsPER 14915 }

    -- 1.3.6.1.4.1.2011.2.25.3.40.40.30.14916
    pmCpTelDownTime NOTIFICATION-TYPE
        OBJECTS{ rptEvtPeriod,rptEvtValue,rptEvtVldty,rptEvtDateTime,rptEvtObjType,rptEvtParaLen,rptEvtPara }
        STATUS current
        DESCRIPTION
            "Trap of Event:TE Link Down Time"
        ::= { optixTrapsPER 14916 }

    -- 1.3.6.1.4.1.2011.2.25.3.40.40.30.14917
    pmCpCcDownCount NOTIFICATION-TYPE
        OBJECTS{ rptEvtPeriod,rptEvtValue,rptEvtVldty,rptEvtDateTime,rptEvtObjType,rptEvtParaLen,rptEvtPara }
        STATUS current
        DESCRIPTION
            "Trap of Event:Control Channel Down Count"
        ::= { optixTrapsPER 14917 }

    -- 1.3.6.1.4.1.2011.2.25.3.40.40.30.14918
    pmCpCcDownTime NOTIFICATION-TYPE
        OBJECTS{ rptEvtPeriod,rptEvtValue,rptEvtVldty,rptEvtDateTime,rptEvtObjType,rptEvtParaLen,rptEvtPara }
        STATUS current
        DESCRIPTION
            "Trap of Event:Control Channel Down Time"
        ::= { optixTrapsPER 14918 }

    -- 1.3.6.1.4.1.2011.2.25.3.40.40.30.14919
    pmCpuUsageMax NOTIFICATION-TYPE
        OBJECTS{ rptEvtPeriod,rptEvtValue,rptEvtVldty,rptEvtDateTime,rptEvtObjType,rptEvtParaLen,rptEvtPara }
        STATUS current
        DESCRIPTION
            "Trap of Event:Max value of CPU usage"
        ::= { optixTrapsPER 14919 }

    -- 1.3.6.1.4.1.2011.2.25.3.40.40.30.14920
    pmCpuUsageMin NOTIFICATION-TYPE
        OBJECTS{ rptEvtPeriod,rptEvtValue,rptEvtVldty,rptEvtDateTime,rptEvtObjType,rptEvtParaLen,rptEvtPara }
        STATUS current
        DESCRIPTION
            "Trap of Event:Min value of CPU usage"
        ::= { optixTrapsPER 14920 }

    -- 1.3.6.1.4.1.2011.2.25.3.40.40.30.14921
    pmCpuUsageCur NOTIFICATION-TYPE
        OBJECTS{ rptEvtPeriod,rptEvtValue,rptEvtVldty,rptEvtDateTime,rptEvtObjType,rptEvtParaLen,rptEvtPara }
        STATUS current
        DESCRIPTION
            "Trap of Event:Current value of CPU usage"
        ::= { optixTrapsPER 14921 }

    -- 1.3.6.1.4.1.2011.2.25.3.40.40.30.14922
    pmMemUsageMax NOTIFICATION-TYPE
        OBJECTS{ rptEvtPeriod,rptEvtValue,rptEvtVldty,rptEvtDateTime,rptEvtObjType,rptEvtParaLen,rptEvtPara }
        STATUS current
        DESCRIPTION
            "Trap of Event:Maximum value of memory usage"
        ::= { optixTrapsPER 14922 }

    -- 1.3.6.1.4.1.2011.2.25.3.40.40.30.14923
    pmMemUsageMin NOTIFICATION-TYPE
        OBJECTS{ rptEvtPeriod,rptEvtValue,rptEvtVldty,rptEvtDateTime,rptEvtObjType,rptEvtParaLen,rptEvtPara }
        STATUS current
        DESCRIPTION
            "Trap of Event:Minimum value of memory usage"
        ::= { optixTrapsPER 14923 }

    -- 1.3.6.1.4.1.2011.2.25.3.40.40.30.14924
    pmMemUsageCur NOTIFICATION-TYPE
        OBJECTS{ rptEvtPeriod,rptEvtValue,rptEvtVldty,rptEvtDateTime,rptEvtObjType,rptEvtParaLen,rptEvtPara }
        STATUS current
        DESCRIPTION
            "Trap of Event:Current value of memory usage"
        ::= { optixTrapsPER 14924 }

    -- 1.3.6.1.4.1.2011.2.25.3.40.40.30.14933
    pmMplsTunnelLs NOTIFICATION-TYPE
        OBJECTS{ rptEvtPeriod,rptEvtValue,rptEvtVldty,rptEvtDateTime,rptEvtObjType,rptEvtParaLen,rptEvtPara }
        STATUS current
        DESCRIPTION
            "MPLS service packet loss second"
        ::= { optixTrapsPER 14933 }

    -- 1.3.6.1.4.1.2011.2.25.3.40.40.30.14934
    pmMplsTunnelSls NOTIFICATION-TYPE
        OBJECTS{ rptEvtPeriod,rptEvtValue,rptEvtVldty,rptEvtDateTime,rptEvtObjType,rptEvtParaLen,rptEvtPara }
        STATUS current
        DESCRIPTION
            "MPLS service severe packet loss second"
        ::= { optixTrapsPER 14934 }

    -- 1.3.6.1.4.1.2011.2.25.3.40.40.30.14935
    pmMplsTunnelCsls NOTIFICATION-TYPE
        OBJECTS{ rptEvtPeriod,rptEvtValue,rptEvtVldty,rptEvtDateTime,rptEvtObjType,rptEvtParaLen,rptEvtPara }
        STATUS current
        DESCRIPTION
            "MPLS service consecutive severe packet loss second"
        ::= { optixTrapsPER 14935 }

    -- 1.3.6.1.4.1.2011.2.25.3.40.40.30.14936
    pmMplsTunnelUas NOTIFICATION-TYPE
        OBJECTS{ rptEvtPeriod,rptEvtValue,rptEvtVldty,rptEvtDateTime,rptEvtObjType,rptEvtParaLen,rptEvtPara }
        STATUS current
        DESCRIPTION
            "MPLS service unavailable second"
        ::= { optixTrapsPER 14936 }

    -- 1.3.6.1.4.1.2011.2.25.3.40.40.30.14937
    pmEthCfmLs NOTIFICATION-TYPE
        OBJECTS{ rptEvtPeriod,rptEvtValue,rptEvtVldty,rptEvtDateTime,rptEvtObjType,rptEvtParaLen,rptEvtPara }
        STATUS current
        DESCRIPTION
            "Packet loss second (SDH like)"
        ::= { optixTrapsPER 14937 }

    -- 1.3.6.1.4.1.2011.2.25.3.40.40.30.14938
    pmEthCfmSls NOTIFICATION-TYPE
        OBJECTS{ rptEvtPeriod,rptEvtValue,rptEvtVldty,rptEvtDateTime,rptEvtObjType,rptEvtParaLen,rptEvtPara }
        STATUS current
        DESCRIPTION
            "Severe packet loss second (SDH like)"
        ::= { optixTrapsPER 14938 }

    -- 1.3.6.1.4.1.2011.2.25.3.40.40.30.14939
    pmEthCfmCsls NOTIFICATION-TYPE
        OBJECTS{ rptEvtPeriod,rptEvtValue,rptEvtVldty,rptEvtDateTime,rptEvtObjType,rptEvtParaLen,rptEvtPara }
        STATUS current
        DESCRIPTION
            "Severely errored seconds(SDH Like)"
        ::= { optixTrapsPER 14939 }

    -- 1.3.6.1.4.1.2011.2.25.3.40.40.30.14940
    pmEthCfmUas NOTIFICATION-TYPE
        OBJECTS{ rptEvtPeriod,rptEvtValue,rptEvtVldty,rptEvtDateTime,rptEvtObjType,rptEvtParaLen,rptEvtPara }
        STATUS current
        DESCRIPTION
            "Unavailable Seconds(SDH Like)"
        ::= { optixTrapsPER 14940 }

    -- 1.3.6.1.4.1.2011.2.25.3.40.40.30.14941
    pmIfBbe NOTIFICATION-TYPE
        OBJECTS{ rptEvtPeriod,rptEvtValue,rptEvtVldty,rptEvtDateTime,rptEvtObjType,rptEvtParaLen,rptEvtPara }
        STATUS current
        DESCRIPTION
            "Trap of Event:Intermediate frequency Background Block Error"
        ::= { optixTrapsPER 14941 }

    -- 1.3.6.1.4.1.2011.2.25.3.40.40.30.14942
    pmIfEs NOTIFICATION-TYPE
        OBJECTS{ rptEvtPeriod,rptEvtValue,rptEvtVldty,rptEvtDateTime,rptEvtObjType,rptEvtParaLen,rptEvtPara }
        STATUS current
        DESCRIPTION
            "Trap of Event:Intermediate frequency Errored Second"
        ::= { optixTrapsPER 14942 }

    -- 1.3.6.1.4.1.2011.2.25.3.40.40.30.14943
    pmIfSes NOTIFICATION-TYPE
        OBJECTS{ rptEvtPeriod,rptEvtValue,rptEvtVldty,rptEvtDateTime,rptEvtObjType,rptEvtParaLen,rptEvtPara }
        STATUS current
        DESCRIPTION
            "Trap of Event:Intermediate frequency Severely Errored Second"
        ::= { optixTrapsPER 14943 }

    -- 1.3.6.1.4.1.2011.2.25.3.40.40.30.14944
    pmIfUas NOTIFICATION-TYPE
        OBJECTS{ rptEvtPeriod,rptEvtValue,rptEvtVldty,rptEvtDateTime,rptEvtObjType,rptEvtParaLen,rptEvtPara }
        STATUS current
        DESCRIPTION
            "Trap of Event:Intermediate Frequency Unavailable Second"
        ::= { optixTrapsPER 14944 }

    -- 1.3.6.1.4.1.2011.2.25.3.40.40.30.14945
    pmIfCses NOTIFICATION-TYPE
        OBJECTS{ rptEvtPeriod,rptEvtValue,rptEvtVldty,rptEvtDateTime,rptEvtObjType,rptEvtParaLen,rptEvtPara }
        STATUS current
        DESCRIPTION
            "Trap of Event:Intermediate Frequency Consecutive Severely Errored Second"
        ::= { optixTrapsPER 14945 }

    -- 1.3.6.1.4.1.2011.2.25.3.40.40.30.14991
    pmBdTempMax NOTIFICATION-TYPE
        OBJECTS{ rptEvtPeriod,rptEvtValue,rptEvtVldty,rptEvtDateTime,rptEvtObjType,rptEvtParaLen,rptEvtPara }
        STATUS current
        DESCRIPTION
            "Trap of Event:Maximum value of board temperature"
        ::= { optixTrapsPER 14991 }

    -- 1.3.6.1.4.1.2011.2.25.3.40.40.30.14992
    pmBdTempMin NOTIFICATION-TYPE
        OBJECTS{ rptEvtPeriod,rptEvtValue,rptEvtVldty,rptEvtDateTime,rptEvtObjType,rptEvtParaLen,rptEvtPara }
        STATUS current
        DESCRIPTION
            "Trap of Event:Minimum value of board temperature"
        ::= { optixTrapsPER 14992 }

    -- 1.3.6.1.4.1.2011.2.25.3.40.40.30.14993
    pmBdTempCur NOTIFICATION-TYPE
        OBJECTS{ rptEvtPeriod,rptEvtValue,rptEvtVldty,rptEvtDateTime,rptEvtObjType,rptEvtParaLen,rptEvtPara }
        STATUS current
        DESCRIPTION
            "Trap of Event:Current value of board temperature"
        ::= { optixTrapsPER 14993 }

    -- 1.3.6.1.4.1.2011.2.25.3.40.40.30.15033
    pmQPSKWS NOTIFICATION-TYPE
        OBJECTS{ rptEvtPeriod,rptEvtValue,rptEvtVldty,rptEvtDateTime,rptEvtObjType,rptEvtParaLen,rptEvtPara }
        STATUS current
        DESCRIPTION
            "Trap of Event:QPSK Work Second"
        ::= { optixTrapsPER 15033 }

    -- 1.3.6.1.4.1.2011.2.25.3.40.40.30.15034
    pmQAMWS16 NOTIFICATION-TYPE
        OBJECTS{ rptEvtPeriod,rptEvtValue,rptEvtVldty,rptEvtDateTime,rptEvtObjType,rptEvtParaLen,rptEvtPara }
        STATUS current
        DESCRIPTION
            "Trap of Event:16QAM Work Second"
        ::= { optixTrapsPER 15034 }

    -- 1.3.6.1.4.1.2011.2.25.3.40.40.30.15035
    pmQAMWS32 NOTIFICATION-TYPE
        OBJECTS{ rptEvtPeriod,rptEvtValue,rptEvtVldty,rptEvtDateTime,rptEvtObjType,rptEvtParaLen,rptEvtPara }
        STATUS current
        DESCRIPTION
            "Trap of Event:32QAM Work Second"
        ::= { optixTrapsPER 15035 }

    -- 1.3.6.1.4.1.2011.2.25.3.40.40.30.15036
    pmQAMWS64 NOTIFICATION-TYPE
        OBJECTS{ rptEvtPeriod,rptEvtValue,rptEvtVldty,rptEvtDateTime,rptEvtObjType,rptEvtParaLen,rptEvtPara }
        STATUS current
        DESCRIPTION
            "Trap of Event:64QAM Work Second"
        ::= { optixTrapsPER 15036 }

    -- 1.3.6.1.4.1.2011.2.25.3.40.40.30.15037
    pmQAMWS128 NOTIFICATION-TYPE
        OBJECTS{ rptEvtPeriod,rptEvtValue,rptEvtVldty,rptEvtDateTime,rptEvtObjType,rptEvtParaLen,rptEvtPara }
        STATUS current
        DESCRIPTION
            "Trap of Event:128QAM Work Second"
        ::= { optixTrapsPER 15037 }

    -- 1.3.6.1.4.1.2011.2.25.3.40.40.30.15038
    pmQAMWS256 NOTIFICATION-TYPE
        OBJECTS{ rptEvtPeriod,rptEvtValue,rptEvtVldty,rptEvtDateTime,rptEvtObjType,rptEvtParaLen,rptEvtPara }
        STATUS current
        DESCRIPTION
            "Trap of Event:256QAM Work Second"
        ::= { optixTrapsPER 15038 }

    -- 1.3.6.1.4.1.2011.2.25.3.40.40.30.15039
    pmCpuUsageAvg NOTIFICATION-TYPE
        OBJECTS{ rptEvtPeriod,rptEvtValue,rptEvtVldty,rptEvtDateTime,rptEvtObjType,rptEvtParaLen,rptEvtPara }
        STATUS current
        DESCRIPTION
            "Trap of Event: The average value of CPU usage."
        ::= { optixTrapsPER 15039 }

    -- 1.3.6.1.4.1.2011.2.25.3.40.40.30.15040
    pmMemUsageAvg NOTIFICATION-TYPE
        OBJECTS{ rptEvtPeriod,rptEvtValue,rptEvtVldty,rptEvtDateTime,rptEvtObjType,rptEvtParaLen,rptEvtPara }
        STATUS current
        DESCRIPTION
            "Trap of Event: Average value of memory usage."
        ::= { optixTrapsPER 15040 }

    -- 1.3.6.1.4.1.2011.2.25.3.40.40.30.15041
    pmATPCPAdjust NOTIFICATION-TYPE
        OBJECTS{ rptEvtPeriod,rptEvtValue,rptEvtVldty,rptEvtDateTime,rptEvtObjType,rptEvtParaLen,rptEvtPara }
        STATUS current
        DESCRIPTION
            "Trap of Event:ATPC Positive Adjust"
        ::= { optixTrapsPER 15041 }

    -- 1.3.6.1.4.1.2011.2.25.3.40.40.30.15042
    pmATPCNAdjust NOTIFICATION-TYPE
        OBJECTS{ rptEvtPeriod,rptEvtValue,rptEvtVldty,rptEvtDateTime,rptEvtObjType,rptEvtParaLen,rptEvtPara }
        STATUS current
        DESCRIPTION
            "Trap of Event:ATPC Negative Adjust"
        ::= { optixTrapsPER 15042 }

    -- 1.3.6.1.4.1.2011.2.25.3.40.40.30.15043
    pmRslAvg NOTIFICATION-TYPE
        OBJECTS{ rptEvtPeriod,rptEvtValue,rptEvtVldty,rptEvtDateTime,rptEvtObjType,rptEvtParaLen,rptEvtPara }
        STATUS current
        DESCRIPTION
            "Trap of Event:RSL Average"
        ::= { optixTrapsPER 15043 }

    -- 1.3.6.1.4.1.2011.2.25.3.40.40.30.15047
    pmTslAvg NOTIFICATION-TYPE
        OBJECTS{ rptEvtPeriod,rptEvtValue,rptEvtVldty,rptEvtDateTime,rptEvtObjType,rptEvtParaLen,rptEvtPara }
        STATUS current
        DESCRIPTION
            "Trap of Event:ODU Tx level average value"
        ::= { optixTrapsPER 15047 }

    -- 1.3.6.1.4.1.2011.2.25.3.40.40.30.15048
    pmAMDownCnt NOTIFICATION-TYPE
        OBJECTS{ rptEvtPeriod,rptEvtValue,rptEvtVldty,rptEvtDateTime,rptEvtObjType,rptEvtParaLen,rptEvtPara }
        STATUS current
        DESCRIPTION
            "Trap of Event: AM downshift count"
        ::= { optixTrapsPER 15048 }

    -- 1.3.6.1.4.1.2011.2.25.3.40.40.30.15049
    pmAMUpCnt NOTIFICATION-TYPE
        OBJECTS{ rptEvtPeriod,rptEvtValue,rptEvtVldty,rptEvtDateTime,rptEvtObjType,rptEvtParaLen,rptEvtPara }
        STATUS current
        DESCRIPTION
            "Trap of Event: AM upshift count"
        ::= { optixTrapsPER 15049 }

    -- 1.3.6.1.4.1.2011.2.25.3.40.40.30.15050
    pmTLHTT NOTIFICATION-TYPE
        OBJECTS{ rptEvtPeriod,rptEvtValue,rptEvtVldty,rptEvtDateTime,rptEvtObjType,rptEvtParaLen,rptEvtPara }
        STATUS current
        DESCRIPTION
            "Trap of Event:Transmitted Level High Threshold Time"
        ::= { optixTrapsPER 15050 }

    -- 1.3.6.1.4.1.2011.2.25.3.40.40.30.15051
    pmTLLTT NOTIFICATION-TYPE
        OBJECTS{ rptEvtPeriod,rptEvtValue,rptEvtVldty,rptEvtDateTime,rptEvtObjType,rptEvtParaLen,rptEvtPara }
        STATUS current
        DESCRIPTION
            "Trap of Event:Transmitted Level Low Threshold Time"
        ::= { optixTrapsPER 15051 }

    -- 1.3.6.1.4.1.2011.2.25.3.40.40.30.15052
    pmRLHTT NOTIFICATION-TYPE
        OBJECTS{ rptEvtPeriod,rptEvtValue,rptEvtVldty,rptEvtDateTime,rptEvtObjType,rptEvtParaLen,rptEvtPara }
        STATUS current
        DESCRIPTION
            "Trap of Event:Received Level High Threshold Time"
        ::= { optixTrapsPER 15052 }

    -- 1.3.6.1.4.1.2011.2.25.3.40.40.30.15053
    pmRLLTT NOTIFICATION-TYPE
        OBJECTS{ rptEvtPeriod,rptEvtValue,rptEvtVldty,rptEvtDateTime,rptEvtObjType,rptEvtParaLen,rptEvtPara }
        STATUS current
        DESCRIPTION
            "Trap of Event:Received Level Low Threshold Time"
        ::= { optixTrapsPER 15053 }

    -- 1.3.6.1.4.1.2011.2.25.3.40.40.30.15066
    pmMPLSPWLS NOTIFICATION-TYPE
        OBJECTS{ rptEvtPeriod,rptEvtValue,rptEvtVldty,rptEvtDateTime,rptEvtObjType,rptEvtParaLen,rptEvtPara }
        STATUS current
        DESCRIPTION
            "Indicates the packet loss second (SDH like)."
        ::= { optixTrapsPER 15066 }

    -- 1.3.6.1.4.1.2011.2.25.3.40.40.30.15067
    pmMPLSPWSLS NOTIFICATION-TYPE
        OBJECTS{ rptEvtPeriod,rptEvtValue,rptEvtVldty,rptEvtDateTime,rptEvtObjType,rptEvtParaLen,rptEvtPara }
        STATUS current
        DESCRIPTION
            "Indicates the severe packet loss second (SDH like)."
        ::= { optixTrapsPER 15067 }

    -- 1.3.6.1.4.1.2011.2.25.3.40.40.30.15068
    pmMPLSPWCSLS NOTIFICATION-TYPE
        OBJECTS{ rptEvtPeriod,rptEvtValue,rptEvtVldty,rptEvtDateTime,rptEvtObjType,rptEvtParaLen,rptEvtPara }
        STATUS current
        DESCRIPTION
            "Indicates the severely errored second (SDH like)."
        ::= { optixTrapsPER 15068 }

    -- 1.3.6.1.4.1.2011.2.25.3.40.40.30.15069
    pmMPLSPWUAS NOTIFICATION-TYPE
        OBJECTS{ rptEvtPeriod,rptEvtValue,rptEvtVldty,rptEvtDateTime,rptEvtObjType,rptEvtParaLen,rptEvtPara }
        STATUS current
        DESCRIPTION
            "Indicates the unavailable second (SDH like)."
        ::= { optixTrapsPER 15069 }

    -- 1.3.6.1.4.1.2011.2.25.3.40.40.30.15088
    pmMAXFREQDEV NOTIFICATION-TYPE
        OBJECTS{ rptEvtPeriod,rptEvtValue,rptEvtVldty,rptEvtDateTime,rptEvtObjType,rptEvtParaLen,rptEvtPara }
        STATUS current
        DESCRIPTION
            "Trap of Event:max value of frequent offset"
        ::= { optixTrapsPER 15088 }

    -- 1.3.6.1.4.1.2011.2.25.3.40.40.30.15089
    pmMINFREQDEV NOTIFICATION-TYPE
        OBJECTS{ rptEvtPeriod,rptEvtValue,rptEvtVldty,rptEvtDateTime,rptEvtObjType,rptEvtParaLen,rptEvtPara }
        STATUS current
        DESCRIPTION
            "Trap of Event:min value of frequent offset"
        ::= { optixTrapsPER 15089 }

    -- 1.3.6.1.4.1.2011.2.25.3.40.40.30.15090
    pmAVGFREQDEV NOTIFICATION-TYPE
        OBJECTS{ rptEvtPeriod,rptEvtValue,rptEvtVldty,rptEvtDateTime,rptEvtObjType,rptEvtParaLen,rptEvtPara }
        STATUS current
        DESCRIPTION
            "Trap of Event:average value of frequent offset"
        ::= { optixTrapsPER 15090 }

    -- 1.3.6.1.4.1.2011.2.25.3.40.40.30.15091
    pmMAXPHASEOFFSET NOTIFICATION-TYPE
        OBJECTS{ rptEvtPeriod,rptEvtValue,rptEvtVldty,rptEvtDateTime,rptEvtObjType,rptEvtParaLen,rptEvtPara }
        STATUS current
        DESCRIPTION
            "Trap of Event:max value of phase offset"
        ::= { optixTrapsPER 15091 }

    -- 1.3.6.1.4.1.2011.2.25.3.40.40.30.15092
    pmMINPHASEOFFSET NOTIFICATION-TYPE
        OBJECTS{ rptEvtPeriod,rptEvtValue,rptEvtVldty,rptEvtDateTime,rptEvtObjType,rptEvtParaLen,rptEvtPara }
        STATUS current
        DESCRIPTION
            "Trap of Event:min value of phase offset"
        ::= { optixTrapsPER 15092 }

    -- 1.3.6.1.4.1.2011.2.25.3.40.40.30.15093
    pmAVGPHASEOFFSET NOTIFICATION-TYPE
        OBJECTS{ rptEvtPeriod,rptEvtValue,rptEvtVldty,rptEvtDateTime,rptEvtObjType,rptEvtParaLen,rptEvtPara }
        STATUS current
        DESCRIPTION
            "Trap of Event:average value of phase offset"
        ::= { optixTrapsPER 15093 }

    -- 1.3.6.1.4.1.2011.2.25.3.40.40.30.15094
    pmMAXMEANPATHDELAY NOTIFICATION-TYPE
        OBJECTS{ rptEvtPeriod,rptEvtValue,rptEvtVldty,rptEvtDateTime,rptEvtObjType,rptEvtParaLen,rptEvtPara }
        STATUS current
        DESCRIPTION
            "Trap of Event:max value of path delay"
        ::= { optixTrapsPER 15094 }

    -- 1.3.6.1.4.1.2011.2.25.3.40.40.30.15095
    pmMINMEANPATHDELAY NOTIFICATION-TYPE
        OBJECTS{ rptEvtPeriod,rptEvtValue,rptEvtVldty,rptEvtDateTime,rptEvtObjType,rptEvtParaLen,rptEvtPara }
        STATUS current
        DESCRIPTION
            "Trap of Event:min value of path delay"
        ::= { optixTrapsPER 15095 }

    -- 1.3.6.1.4.1.2011.2.25.3.40.40.30.15096
    pmAVGMEANPATHDELAY NOTIFICATION-TYPE
        OBJECTS{ rptEvtPeriod,rptEvtValue,rptEvtVldty,rptEvtDateTime,rptEvtObjType,rptEvtParaLen,rptEvtPara }
        STATUS current
        DESCRIPTION
            "Trap of Event:average value of path delay"
        ::= { optixTrapsPER 15096 }

    -- 1.3.6.1.4.1.2011.2.25.3.40.40.30.15103
    pmMAXPOSITIVEDELAY NOTIFICATION-TYPE
        OBJECTS{ rptEvtPeriod,rptEvtValue,rptEvtVldty,rptEvtDateTime,rptEvtObjType,rptEvtParaLen,rptEvtPara }
        STATUS current
        DESCRIPTION
            "Trap of Event:max value of positive delay"
        ::= { optixTrapsPER 15103 }

    -- 1.3.6.1.4.1.2011.2.25.3.40.40.30.15104
    pmMINPOSITIVEDELAY NOTIFICATION-TYPE
        OBJECTS{ rptEvtPeriod,rptEvtValue,rptEvtVldty,rptEvtDateTime,rptEvtObjType,rptEvtParaLen,rptEvtPara }
        STATUS current
        DESCRIPTION
            "Trap of Event:min value of positive delay"
        ::= { optixTrapsPER 15104 }

    -- 1.3.6.1.4.1.2011.2.25.3.40.40.30.15105
    pmAVGPOSITIVEDELAY NOTIFICATION-TYPE
        OBJECTS{ rptEvtPeriod,rptEvtValue,rptEvtVldty,rptEvtDateTime,rptEvtObjType,rptEvtParaLen,rptEvtPara }
        STATUS current
        DESCRIPTION
            "Trap of Event:average value of positive delay"
        ::= { optixTrapsPER 15105 }

    -- 1.3.6.1.4.1.2011.2.25.3.40.40.30.15106
    pmMAXNEGATIVEDELAY NOTIFICATION-TYPE
        OBJECTS{ rptEvtPeriod,rptEvtValue,rptEvtVldty,rptEvtDateTime,rptEvtObjType,rptEvtParaLen,rptEvtPara }
        STATUS current
        DESCRIPTION
            "Trap of Event:Maximum negative delay between the master clock and slave clock"
        ::= { optixTrapsPER 15106 }

    -- 1.3.6.1.4.1.2011.2.25.3.40.40.30.15107
    pmMINNEGATIVEDELAY NOTIFICATION-TYPE
        OBJECTS{ rptEvtPeriod,rptEvtValue,rptEvtVldty,rptEvtDateTime,rptEvtObjType,rptEvtParaLen,rptEvtPara }
        STATUS current
        DESCRIPTION
            "Trap of Event:Minimum negative delay between the master clock and slave clock"
        ::= { optixTrapsPER 15107 }

    -- 1.3.6.1.4.1.2011.2.25.3.40.40.30.15108
    pmAVGNEGATIVEDELAY NOTIFICATION-TYPE
        OBJECTS{ rptEvtPeriod,rptEvtValue,rptEvtVldty,rptEvtDateTime,rptEvtObjType,rptEvtParaLen,rptEvtPara }
        STATUS current
        DESCRIPTION
            "Trap of Event:Average negative delay between the master clock and slave clock"
        ::= { optixTrapsPER 15108 }

    -- 1.3.6.1.4.1.2011.2.25.3.40.40.30.15418
    pmCURNEGATIVEPDV NOTIFICATION-TYPE
        OBJECTS{ rptEvtPeriod,rptEvtValue,rptEvtVldty,rptEvtDateTime,rptEvtObjType,rptEvtParaLen,rptEvtPara }
        STATUS current
        DESCRIPTION
            "Trap of Event:Current Negative PDV Value"
        ::= { optixTrapsPER 15418 }

    -- 1.3.6.1.4.1.2011.2.25.3.40.40.30.15121
    pmOtu4Fesesr NOTIFICATION-TYPE
        OBJECTS{ rptEvtPeriod,rptEvtValue,rptEvtVldty,rptEvtDateTime,rptEvtObjType,rptEvtParaLen,rptEvtPara }
        STATUS current
        DESCRIPTION
            "Trap of Event:OTUk SM  Section Ratio of Far End Severely Errored Second"
        ::= { optixTrapsPER 15121 }

    -- 1.3.6.1.4.1.2011.2.25.3.40.40.30.15233
    pmXpicXpdValue NOTIFICATION-TYPE
        OBJECTS{ rptEvtPeriod,rptEvtValue,rptEvtVldty,rptEvtDateTime,rptEvtObjType,rptEvtParaLen,rptEvtPara }
        STATUS current
        DESCRIPTION
            "Trap of Event:XPD value of the XPIC measured with an interval of one second"
        ::= { optixTrapsPER 15233 }

    -- 1.3.6.1.4.1.2011.2.25.3.40.40.30.15234
    pmOduSsvTh NOTIFICATION-TYPE
        OBJECTS{ rptEvtPeriod,rptEvtValue,rptEvtVldty,rptEvtDateTime,rptEvtObjType,rptEvtParaLen,rptEvtPara }
        STATUS current
        DESCRIPTION
            "Trap of Event:Count of seconds when ODU rsl is below sensitivity threshold"
        ::= { optixTrapsPER 15234 }

    -- 1.3.6.1.4.1.2011.2.25.3.40.40.30.15363
    pmXpdMax NOTIFICATION-TYPE
        OBJECTS{ rptEvtPeriod,rptEvtValue,rptEvtVldty,rptEvtDateTime,rptEvtObjType,rptEvtParaLen,rptEvtPara }
        STATUS current
        DESCRIPTION
            "The XPD Maximum value"
        ::= { optixTrapsPER 15363 }

    -- 1.3.6.1.4.1.2011.2.25.3.40.40.30.15364
    pmXpdMin NOTIFICATION-TYPE
        OBJECTS{ rptEvtPeriod,rptEvtValue,rptEvtVldty,rptEvtDateTime,rptEvtObjType,rptEvtParaLen,rptEvtPara }
        STATUS current
        DESCRIPTION
            "The XPD minimum value"
        ::= { optixTrapsPER 15364 }

    -- 1.3.6.1.4.1.2011.2.25.3.40.40.30.15365
    pmE1Bbe NOTIFICATION-TYPE
        OBJECTS{ rptEvtPeriod,rptEvtValue,rptEvtVldty,rptEvtDateTime,rptEvtObjType,rptEvtParaLen,rptEvtPara }
        STATUS current
        DESCRIPTION
            "Trap of Event:E1 Background Block Error"
        ::= { optixTrapsPER 15365 }

    -- 1.3.6.1.4.1.2011.2.25.3.40.40.30.15366
    pmE1Es NOTIFICATION-TYPE
        OBJECTS{ rptEvtPeriod,rptEvtValue,rptEvtVldty,rptEvtDateTime,rptEvtObjType,rptEvtParaLen,rptEvtPara }
        STATUS current
        DESCRIPTION
            "Trap of Event:E1 Errored Second"
        ::= { optixTrapsPER 15366 }

    -- 1.3.6.1.4.1.2011.2.25.3.40.40.30.15367
    pmE1Ses NOTIFICATION-TYPE
        OBJECTS{ rptEvtPeriod,rptEvtValue,rptEvtVldty,rptEvtDateTime,rptEvtObjType,rptEvtParaLen,rptEvtPara }
        STATUS current
        DESCRIPTION
            "Trap of Event:E1 Severely Errored Second"
        ::= { optixTrapsPER 15367 }

    -- 1.3.6.1.4.1.2011.2.25.3.40.40.30.15368
    pmE1Cses NOTIFICATION-TYPE
        OBJECTS{ rptEvtPeriod,rptEvtValue,rptEvtVldty,rptEvtDateTime,rptEvtObjType,rptEvtParaLen,rptEvtPara }
        STATUS current
        DESCRIPTION
            "Trap of Event:E1 Consecutive Severely Errored Second"
        ::= { optixTrapsPER 15368 }

    -- 1.3.6.1.4.1.2011.2.25.3.40.40.30.15369
    pmE1Uas NOTIFICATION-TYPE
        OBJECTS{ rptEvtPeriod,rptEvtValue,rptEvtVldty,rptEvtDateTime,rptEvtObjType,rptEvtParaLen,rptEvtPara }
        STATUS current
        DESCRIPTION
            "Trap of Event:E1 Unavailable Second"
        ::= { optixTrapsPER 15369 }

    -- 1.3.6.1.4.1.2011.2.25.3.40.40.30.15370
    pmPgIfBbe NOTIFICATION-TYPE
        OBJECTS{ rptEvtPeriod,rptEvtValue,rptEvtVldty,rptEvtDateTime,rptEvtObjType,rptEvtParaLen,rptEvtPara }
        STATUS current
        DESCRIPTION
            "Trap of Event:Protection Group Background Block Error"
        ::= { optixTrapsPER 15370 }

    -- 1.3.6.1.4.1.2011.2.25.3.40.40.30.15371
    pmPgIfEs NOTIFICATION-TYPE
        OBJECTS{ rptEvtPeriod,rptEvtValue,rptEvtVldty,rptEvtDateTime,rptEvtObjType,rptEvtParaLen,rptEvtPara }
        STATUS current
        DESCRIPTION
            "Trap of Event:Protection Group Errored Second"
        ::= { optixTrapsPER 15371 }

    -- 1.3.6.1.4.1.2011.2.25.3.40.40.30.15372
    pmPgIfSes NOTIFICATION-TYPE
        OBJECTS{ rptEvtPeriod,rptEvtValue,rptEvtVldty,rptEvtDateTime,rptEvtObjType,rptEvtParaLen,rptEvtPara }
        STATUS current
        DESCRIPTION
            "Trap of Event:Protection Group Severely Errored Second"
        ::= { optixTrapsPER 15372 }

    -- 1.3.6.1.4.1.2011.2.25.3.40.40.30.15373
    pmPgIfCses NOTIFICATION-TYPE
        OBJECTS{ rptEvtPeriod,rptEvtValue,rptEvtVldty,rptEvtDateTime,rptEvtObjType,rptEvtParaLen,rptEvtPara }
        STATUS current
        DESCRIPTION
            "Trap of Event:Protection Group Consecutive Severely Errored Second"
        ::= { optixTrapsPER 15373 }

    -- 1.3.6.1.4.1.2011.2.25.3.40.40.30.15374
    pmPgIfUas NOTIFICATION-TYPE
        OBJECTS{ rptEvtPeriod,rptEvtValue,rptEvtVldty,rptEvtDateTime,rptEvtObjType,rptEvtParaLen,rptEvtPara }
        STATUS current
        DESCRIPTION
            "Trap of Event:Protection Group Unavailable Second"
        ::= { optixTrapsPER 15374 }

    -- 1.3.6.1.4.1.2011.2.25.3.40.40.30.15375
    pmIfSnrMax NOTIFICATION-TYPE
        OBJECTS{ rptEvtPeriod,rptEvtValue,rptEvtVldty,rptEvtDateTime,rptEvtObjType,rptEvtParaLen,rptEvtPara }
        STATUS current
        DESCRIPTION
            "Trap of Event:Maximum Signal-Noise Ratio"
        ::= { optixTrapsPER 15375 }

    -- 1.3.6.1.4.1.2011.2.25.3.40.40.30.15376
    pmIfSnrMin NOTIFICATION-TYPE
        OBJECTS{ rptEvtPeriod,rptEvtValue,rptEvtVldty,rptEvtDateTime,rptEvtObjType,rptEvtParaLen,rptEvtPara }
        STATUS current
        DESCRIPTION
            "Trap of Event:Minimum Signal-Noise Ratio"
        ::= { optixTrapsPER 15376 }

    -- 1.3.6.1.4.1.2011.2.25.3.40.40.30.15377
    pmIfSnrAvg NOTIFICATION-TYPE
        OBJECTS{ rptEvtPeriod,rptEvtValue,rptEvtVldty,rptEvtDateTime,rptEvtObjType,rptEvtParaLen,rptEvtPara }
        STATUS current
        DESCRIPTION
            "Trap of Event:Average Signal-Noise Ratio"
        ::= { optixTrapsPER 15377 }

    -- 1.3.6.1.4.1.2011.2.25.3.40.40.30.15411
    pmQAMWS512 NOTIFICATION-TYPE
        OBJECTS{ rptEvtPeriod,rptEvtValue,rptEvtVldty,rptEvtDateTime,rptEvtObjType,rptEvtParaLen,rptEvtPara }
        STATUS current
        DESCRIPTION
            "Trap of Event:512QAM Work Second"
        ::= { optixTrapsPER 15411 }

    -- 1.3.6.1.4.1.2011.2.25.3.40.40.30.15412
    pmQAMWS1024 NOTIFICATION-TYPE
        OBJECTS{ rptEvtPeriod,rptEvtValue,rptEvtVldty,rptEvtDateTime,rptEvtObjType,rptEvtParaLen,rptEvtPara }
        STATUS current
        DESCRIPTION
            "Trap of Event:1024QAM Work Second"
        ::= { optixTrapsPER 15412 }

    -- 1.3.6.1.4.1.2011.2.25.3.40.40.30.15413
    pmPaTempMax NOTIFICATION-TYPE
        OBJECTS{ rptEvtPeriod,rptEvtValue,rptEvtVldty,rptEvtDateTime,rptEvtObjType,rptEvtParaLen,rptEvtPara }
        STATUS current
        DESCRIPTION
            "Trap of Event: Maximum temperature for a power amplifier within a specified period (unit: C)."
        ::= { optixTrapsPER 15413 }

    -- 1.3.6.1.4.1.2011.2.25.3.40.40.30.15414
    pmPaTempMin NOTIFICATION-TYPE
        OBJECTS{ rptEvtPeriod,rptEvtValue,rptEvtVldty,rptEvtDateTime,rptEvtObjType,rptEvtParaLen,rptEvtPara }
        STATUS current
        DESCRIPTION
            "Trap of Event: Minimum temperature for a power amplifier within a specified period (unit: C)."
        ::= { optixTrapsPER 15414 }

    -- 1.3.6.1.4.1.2011.2.25.3.40.40.30.15415
    pmPaTempCur NOTIFICATION-TYPE
        OBJECTS{ rptEvtPeriod,rptEvtValue,rptEvtVldty,rptEvtDateTime,rptEvtObjType,rptEvtParaLen,rptEvtPara }
        STATUS current
        DESCRIPTION
            "Trap of Event: Current temperature for a power amplifier within a specified period (unit: C)."
        ::= { optixTrapsPER 15415 }

    -- 1.3.6.1.4.1.2011.2.25.3.40.40.30.15417
    pmCURPOSITIVEPDV NOTIFICATION-TYPE
        OBJECTS{ rptEvtPeriod,rptEvtValue,rptEvtVldty,rptEvtDateTime,rptEvtObjType,rptEvtParaLen,rptEvtPara }
        STATUS current
        DESCRIPTION
            "Trap of Event:current value of positive PDV"
        ::= { optixTrapsPER 15417 }

    -- 1.3.6.1.4.1.2011.2.25.3.40.40.30.15419
    pmQpskSWS NOTIFICATION-TYPE
        OBJECTS{ rptEvtPeriod,rptEvtValue,rptEvtVldty,rptEvtDateTime,rptEvtObjType,rptEvtParaLen,rptEvtPara }
        STATUS current
        DESCRIPTION
            "Trap of Event:QPSKSTRONG Working Second"
        ::= { optixTrapsPER 15419 }

    -- 1.3.6.1.4.1.2011.2.25.3.40.40.30.15420
    pmQamSWS16 NOTIFICATION-TYPE
        OBJECTS{ rptEvtPeriod,rptEvtValue,rptEvtVldty,rptEvtDateTime,rptEvtObjType,rptEvtParaLen,rptEvtPara }
        STATUS current
        DESCRIPTION
            "Trap of Event:16QAMSTRONG Working Second"
        ::= { optixTrapsPER 15420 }

    -- 1.3.6.1.4.1.2011.2.25.3.40.40.30.15421
    pmQamLWS512 NOTIFICATION-TYPE
        OBJECTS{ rptEvtPeriod,rptEvtValue,rptEvtVldty,rptEvtDateTime,rptEvtObjType,rptEvtParaLen,rptEvtPara }
        STATUS current
        DESCRIPTION
            "Trap of Event:512QAMLIGHT Working Second"
        ::= { optixTrapsPER 15421 }

    -- 1.3.6.1.4.1.2011.2.25.3.40.40.30.15422
    pmQamLWs1024 NOTIFICATION-TYPE
        OBJECTS{ rptEvtPeriod,rptEvtValue,rptEvtVldty,rptEvtDateTime,rptEvtObjType,rptEvtParaLen,rptEvtPara }
        STATUS current
        DESCRIPTION
            "Trap of Event:1024QAMLIGHT Working Second"
        ::= { optixTrapsPER 15422 }

    -- 1.3.6.1.4.1.2011.2.25.3.40.40.30.15479
    pmIfBer NOTIFICATION-TYPE
        OBJECTS{ rptEvtPeriod,rptEvtValue,rptEvtVldty,rptEvtDateTime,rptEvtObjType,rptEvtParaLen,rptEvtPara }
        STATUS current
        DESCRIPTION
            "Trap of Event:The current overall value of the Bit-Error-Rate"
        ::= { optixTrapsPER 15479 }

    -- 1.3.6.1.4.1.2011.2.25.3.40.40.30.15480
    pmQAMWS2048 NOTIFICATION-TYPE
        OBJECTS{ rptEvtPeriod,rptEvtValue,rptEvtVldty,rptEvtDateTime,rptEvtObjType,rptEvtParaLen,rptEvtPara }
        STATUS current
        DESCRIPTION
            "Trap of Event:2048QAM Working Second"
        ::= { optixTrapsPER 15480 }

    -- 1.3.6.1.4.1.2011.2.25.3.40.40.30.15481
    pmQPSKS250MWS NOTIFICATION-TYPE
        OBJECTS{ rptEvtPeriod, rptEvtValue, rptEvtVldty, rptEvtDateTime, rptEvtObjType, rptEvtParaLen, rptEvtPara }
        STATUS current
        DESCRIPTION
            "Trap of Event:250M, QPSKSTRONG Working Second"
        ::= { optixTrapsPER 15481 }

    -- 1.3.6.1.4.1.2011.2.25.3.40.40.30.15482
    pmQPSKS500MWS NOTIFICATION-TYPE
        OBJECTS{ rptEvtPeriod, rptEvtValue, rptEvtVldty, rptEvtDateTime, rptEvtObjType, rptEvtParaLen, rptEvtPara }
        STATUS current
        DESCRIPTION
            "Trap of Event:500M, QPSKSTRONG Working Second"
        ::= { optixTrapsPER 15482 }

    -- 1.3.6.1.4.1.2011.2.25.3.40.40.30.15507
    pmIfMseAvg NOTIFICATION-TYPE
        OBJECTS{ rptEvtPeriod,rptEvtValue,rptEvtVldty,rptEvtDateTime,rptEvtObjType,rptEvtParaLen,rptEvtPara }
        STATUS current
        DESCRIPTION
            "Trap of Event:The Average MSE of IF Board"
        ::= { optixTrapsPER 15507 }

    -- 1.3.6.1.4.1.2011.2.25.3.40.40.30.15508
    pmIfMseMax NOTIFICATION-TYPE
        OBJECTS{ rptEvtPeriod,rptEvtValue,rptEvtVldty,rptEvtDateTime,rptEvtObjType,rptEvtParaLen,rptEvtPara }
        STATUS current
        DESCRIPTION
            "Trap of Event:The Max MSE of IF Board"
        ::= { optixTrapsPER 15508 }

    -- 1.3.6.1.4.1.2011.2.25.3.40.40.30.15509
    pmIfMseMin NOTIFICATION-TYPE
        OBJECTS{ rptEvtPeriod,rptEvtValue,rptEvtVldty,rptEvtDateTime,rptEvtObjType,rptEvtParaLen,rptEvtPara }
        STATUS current
        DESCRIPTION
            "Trap of Event:The Min MSE of IF Board"
        ::= { optixTrapsPER 15509 }

    -- 1.3.6.1.4.1.2011.2.25.3.40.40.30.15510
    pmIfMseCur NOTIFICATION-TYPE
        OBJECTS{ rptEvtPeriod,rptEvtValue,rptEvtVldty,rptEvtDateTime,rptEvtObjType,rptEvtParaLen,rptEvtPara }
        STATUS current
        DESCRIPTION
            "Trap of Event:The Cur MSE of IF Board"
        ::= { optixTrapsPER 15510 }

    -- 1.3.6.1.4.1.2011.2.25.3.40.40.30.15607
    pmMplsPwLsN NOTIFICATION-TYPE
        OBJECTS{ rptEvtPeriod,rptEvtValue,rptEvtVldty,rptEvtDateTime,rptEvtObjType,rptEvtParaLen,rptEvtPara }
        STATUS current
        DESCRIPTION
            "PW service near-end packet loss second"
        ::= { optixTrapsPER 15607 }

    -- 1.3.6.1.4.1.2011.2.25.3.40.40.30.15608
    pmMplsPwUasN NOTIFICATION-TYPE
        OBJECTS{ rptEvtPeriod,rptEvtValue,rptEvtVldty,rptEvtDateTime,rptEvtObjType,rptEvtParaLen,rptEvtPara }
        STATUS current
        DESCRIPTION
            "PW service near-end unavailable second"
        ::= { optixTrapsPER 15608 }

    -- 1.3.6.1.4.1.2011.2.25.3.40.40.30.15609
    pmMplsPwCslsN NOTIFICATION-TYPE
        OBJECTS{ rptEvtPeriod,rptEvtValue,rptEvtVldty,rptEvtDateTime,rptEvtObjType,rptEvtParaLen,rptEvtPara }
        STATUS current
        DESCRIPTION
            "Severe packet loss second (SDH like)  on the near end"
        ::= { optixTrapsPER 15609 }

    -- 1.3.6.1.4.1.2011.2.25.3.40.40.30.15610
    pmMplsPwSlsN NOTIFICATION-TYPE
        OBJECTS{ rptEvtPeriod,rptEvtValue,rptEvtVldty,rptEvtDateTime,rptEvtObjType,rptEvtParaLen,rptEvtPara }
        STATUS current
        DESCRIPTION
            "PW service near-end severe packet loss second"
        ::= { optixTrapsPER 15610 }

    -- 1.3.6.1.4.1.2011.2.25.3.40.40.30.15611
    pmMplsTunnelSlsN NOTIFICATION-TYPE
        OBJECTS{ rptEvtPeriod,rptEvtValue,rptEvtVldty,rptEvtDateTime,rptEvtObjType,rptEvtParaLen,rptEvtPara }
        STATUS current
        DESCRIPTION
            "MPLS service near-end severe packet loss second"
        ::= { optixTrapsPER 15611 }

    -- 1.3.6.1.4.1.2011.2.25.3.40.40.30.15612
    pmMplsTunnelLsN NOTIFICATION-TYPE
        OBJECTS{ rptEvtPeriod,rptEvtValue,rptEvtVldty,rptEvtDateTime,rptEvtObjType,rptEvtParaLen,rptEvtPara }
        STATUS current
        DESCRIPTION
            "MPLS service near-end packet loss second"
        ::= { optixTrapsPER 15612 }

    -- 1.3.6.1.4.1.2011.2.25.3.40.40.30.15613
    pmMplsTunnelCslsN NOTIFICATION-TYPE
        OBJECTS{ rptEvtPeriod,rptEvtValue,rptEvtVldty,rptEvtDateTime,rptEvtObjType,rptEvtParaLen,rptEvtPara }
        STATUS current
        DESCRIPTION
            "MPLS service near-end consecutive severe packet loss second"
        ::= { optixTrapsPER 15613 }

    -- 1.3.6.1.4.1.2011.2.25.3.40.40.30.15614
    pmMplsTunnelUasN NOTIFICATION-TYPE
        OBJECTS{ rptEvtPeriod,rptEvtValue,rptEvtVldty,rptEvtDateTime,rptEvtObjType,rptEvtParaLen,rptEvtPara }
        STATUS current
        DESCRIPTION
            "Unavailable Seconds on the near end"
        ::= { optixTrapsPER 15614 }

    -- 1.3.6.1.4.1.2011.2.25.3.40.40.30.15615
    pmQPSKS62P5MWS NOTIFICATION-TYPE
        OBJECTS{ rptEvtPeriod, rptEvtValue, rptEvtVldty, rptEvtDateTime, rptEvtObjType, rptEvtParaLen, rptEvtPara }
        STATUS current
        DESCRIPTION
            "Trap of Event:62.5M, QPSKSTRONG Working Second"
        ::= { optixTrapsPER 15615 }

    -- 1.3.6.1.4.1.2011.2.25.3.40.40.30.15616
    pmQPSKS125MWS NOTIFICATION-TYPE
        OBJECTS{ rptEvtPeriod, rptEvtValue, rptEvtVldty, rptEvtDateTime, rptEvtObjType, rptEvtParaLen, rptEvtPara }
        STATUS current
        DESCRIPTION
            "Trap of Event:125M, QPSKSTRONG Working Second"
        ::= { optixTrapsPER 15616 }

    -- 1.3.6.1.4.1.2011.2.25.3.40.40.30.15617
    pmQPSKS750MWS NOTIFICATION-TYPE
        OBJECTS{ rptEvtPeriod, rptEvtValue, rptEvtVldty, rptEvtDateTime, rptEvtObjType, rptEvtParaLen, rptEvtPara }
        STATUS current
        DESCRIPTION
            "Trap of Event:750M, QPSKSTRONG Working Second"
        ::= { optixTrapsPER 15617 }

    -- 1.3.6.1.4.1.2011.2.25.3.40.40.30.15740
    pmPortBerCnt NOTIFICATION-TYPE
        OBJECTS{ rptEvtPeriod, rptEvtValue, rptEvtVldty, rptEvtDateTime, rptEvtObjType, rptEvtParaLen, rptEvtPara }
        STATUS current
        DESCRIPTION
            "Trap of Event:The counts of port bit error"
        ::= { optixTrapsPER 15740 }

    -- 1.3.6.1.4.1.2011.2.25.3.40.40.30.15856
    pmBpsk250MWS NOTIFICATION-TYPE
        OBJECTS{ rptEvtPeriod,rptEvtValue,rptEvtVldty,rptEvtDateTime,rptEvtObjType,rptEvtParaLen,rptEvtPara }
        STATUS current
        DESCRIPTION
            "Trap of Event:BPSK Working Second in 250M"
        ::= { optixTrapsPER 15856 }

    -- 1.3.6.1.4.1.2011.2.25.3.40.40.30.15857
    pmBpsk500MWS NOTIFICATION-TYPE
        OBJECTS{ rptEvtPeriod,rptEvtValue,rptEvtVldty,rptEvtDateTime,rptEvtObjType,rptEvtParaLen,rptEvtPara }
        STATUS current
        DESCRIPTION
            "Trap of Event:BPSK Working Second in 500M"
        ::= { optixTrapsPER 15857 }

    -- 1.3.6.1.4.1.2011.2.25.3.40.40.30.15858
    pmBpsk750MWS NOTIFICATION-TYPE
        OBJECTS{ rptEvtPeriod, rptEvtValue, rptEvtVldty, rptEvtDateTime, rptEvtObjType, rptEvtParaLen, rptEvtPara }
        STATUS current
        DESCRIPTION
            "Trap of Event:BPSK Working Second in 750M"
        ::= { optixTrapsPER 15858 }

    -- 1.3.6.1.4.1.2011.2.25.3.40.40.30.15859
    pmBpsk1000MWS NOTIFICATION-TYPE
        OBJECTS{ rptEvtPeriod, rptEvtValue, rptEvtVldty, rptEvtDateTime, rptEvtObjType, rptEvtParaLen, rptEvtPara }
        STATUS current
        DESCRIPTION
            "Trap of Event:BPSK Working Second in 1000M"
        ::= { optixTrapsPER 15859 }

    -- 1.3.6.1.4.1.2011.2.25.3.40.40.30.15860
    pmBpsk1500MWS NOTIFICATION-TYPE
        OBJECTS{ rptEvtPeriod, rptEvtValue, rptEvtVldty, rptEvtDateTime, rptEvtObjType, rptEvtParaLen, rptEvtPara }
        STATUS current
        DESCRIPTION
            "Trap of Event:BPSK Working Second in 1500M"
        ::= { optixTrapsPER 15860 }
	
    -- 1.3.6.1.4.1.2011.2.25.3.40.40.30.15861
    pmBpsk2000MWS NOTIFICATION-TYPE
        OBJECTS{ rptEvtPeriod, rptEvtValue, rptEvtVldty, rptEvtDateTime, rptEvtObjType, rptEvtParaLen, rptEvtPara }
        STATUS current
        DESCRIPTION
            "Trap of Event:BPSK Working Second in 2000M"
        ::= { optixTrapsPER 15861 }

    -- 1.3.6.1.4.1.2011.2.25.3.40.40.30.15976
    pmRsciMin NOTIFICATION-TYPE
        OBJECTS{ rptEvtPeriod,rptEvtValue,rptEvtVldty,rptEvtDateTime,rptEvtObjType,rptEvtParaLen,rptEvtPara }
        STATUS current
        DESCRIPTION
            "Trap of Event: Minimum value of RSCI."
        ::= { optixTrapsPER 15976 }

    -- 1.3.6.1.4.1.2011.2.25.3.40.40.30.15977
    pmRsciMax NOTIFICATION-TYPE
        OBJECTS{ rptEvtPeriod,rptEvtValue,rptEvtVldty,rptEvtDateTime,rptEvtObjType,rptEvtParaLen,rptEvtPara }
        STATUS current
        DESCRIPTION
            "Trap of Event: Maximum value of RSCI."
        ::= { optixTrapsPER 15977 }

    -- 1.3.6.1.4.1.2011.2.25.3.40.40.30.15978
    pmRsciCurr NOTIFICATION-TYPE
        OBJECTS{ rptEvtPeriod,rptEvtValue,rptEvtVldty,rptEvtDateTime,rptEvtObjType,rptEvtParaLen,rptEvtPara }
        STATUS current
        DESCRIPTION
            "Trap of Event: Current value of RSCI."
        ::= { optixTrapsPER 15978 }

    -- 1.3.6.1.4.1.2011.2.25.3.40.40.30.15979
    pmRsciAvg NOTIFICATION-TYPE
        OBJECTS{ rptEvtPeriod,rptEvtValue,rptEvtVldty,rptEvtDateTime,rptEvtObjType,rptEvtParaLen,rptEvtPara }
        STATUS current
        DESCRIPTION
            "Trap of Event: Average value of RSCI."
        ::= { optixTrapsPER 15979 }

    -- 1.3.6.1.4.1.2011.2.25.3.40.40.30.15926
    pmMcs0RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS0."
        ::= { optixTrapsPER 15926 }

    -- 1.3.6.1.4.1.2011.2.25.3.40.40.30.15927
    pmMcs1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS1."
        ::= { optixTrapsPER 15927 }

    -- 1.3.6.1.4.1.2011.2.25.3.40.40.30.15928
    pmMcs2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS2."
        ::= { optixTrapsPER 15928 }

    -- 1.3.6.1.4.1.2011.2.25.3.40.40.30.15929
    pmMcs3RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS3."
        ::= { optixTrapsPER 15929 }

    -- 1.3.6.1.4.1.2011.2.25.3.40.40.30.15930
    pmMcs4RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS4."
        ::= { optixTrapsPER 15930 }

    -- 1.3.6.1.4.1.2011.2.25.3.40.40.30.15931
    pmMcs5RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS5."
        ::= { optixTrapsPER 15931 }

    -- 1.3.6.1.4.1.2011.2.25.3.40.40.30.15932
    pmMcs6RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS6."
        ::= { optixTrapsPER 15932 }

    -- 1.3.6.1.4.1.2011.2.25.3.40.40.30.15933
    pmMcs7RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS7."
        ::= { optixTrapsPER 15933 }

    -- 1.3.6.1.4.1.2011.2.25.3.40.40.30.15934
    pmMcs8RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under MCS8."
        ::= { optixTrapsPER 15934 }

    -- 1.3.6.1.4.1.2011.2.25.3.40.40.30.15975
    pmChannelOccuptRate NOTIFICATION-TYPE
        OBJECTS{ rptEvtPeriod,rptEvtValue,rptEvtVldty,rptEvtDateTime,rptEvtObjType,rptEvtParaLen,rptEvtPara }
        STATUS current
        DESCRIPTION
            "Trap of Event: Channel occupancy rate."
        ::= { optixTrapsPER 15975 }

    -- 1.3.6.1.4.1.2011.2.25.3.40.40.30.15935
    pmMcs0nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs0nss1."
        ::= { optixTrapsPER 15935 }

    -- 1.3.6.1.4.1.2011.2.25.3.40.40.30.15936
    pmMcs1nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs1nss1."
        ::= { optixTrapsPER 15936 }

    -- 1.3.6.1.4.1.2011.2.25.3.40.40.30.15937
    pmMcs2nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs2nss1."
        ::= { optixTrapsPER 15937 }

    -- 1.3.6.1.4.1.2011.2.25.3.40.40.30.15938
    pmMcs3nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs3nss1."
        ::= { optixTrapsPER 15938 }

    -- 1.3.6.1.4.1.2011.2.25.3.40.40.30.15939
    pmMcs4nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs4nss1."
        ::= { optixTrapsPER 15939 }

    -- 1.3.6.1.4.1.2011.2.25.3.40.40.30.15940
    pmMcs5nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs5nss1."
        ::= { optixTrapsPER 15940 }

    -- 1.3.6.1.4.1.2011.2.25.3.40.40.30.15941
    pmMcs6nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs6nss1."
        ::= { optixTrapsPER 15941 }

    -- 1.3.6.1.4.1.2011.2.25.3.40.40.30.15942
    pmMcs7nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs7nss1."
        ::= { optixTrapsPER 15942 }

    -- 1.3.6.1.4.1.2011.2.25.3.40.40.30.15943
    pmMcs8nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs8nss1."
        ::= { optixTrapsPER 15943 }

    -- 1.3.6.1.4.1.2011.2.25.3.40.40.30.15944
    pmMcs9nss1RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs9nss1."
        ::= { optixTrapsPER 15944 }

    -- 1.3.6.1.4.1.2011.2.25.3.40.40.30.15945
    pmMcs0nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs0nss2."
        ::= { optixTrapsPER 15945 }

    -- 1.3.6.1.4.1.2011.2.25.3.40.40.30.15946
    pmMcs1nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs1nss2."
        ::= { optixTrapsPER 15946 }

    -- 1.3.6.1.4.1.2011.2.25.3.40.40.30.15947
    pmMcs2nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs2nss2."
        ::= { optixTrapsPER 15947 }

    -- 1.3.6.1.4.1.2011.2.25.3.40.40.30.15948
    pmMcs3nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs3nss2."
        ::= { optixTrapsPER 15948 }

    -- 1.3.6.1.4.1.2011.2.25.3.40.40.30.15949
    pmMcs4nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs4nss2."
        ::= { optixTrapsPER 15949 }

    -- 1.3.6.1.4.1.2011.2.25.3.40.40.30.15950
    pmMcs5nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs5nss2."
        ::= { optixTrapsPER 15950 }

    -- 1.3.6.1.4.1.2011.2.25.3.40.40.30.15951
    pmMcs6nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs6nss2."
        ::= { optixTrapsPER 15951 }

    -- 1.3.6.1.4.1.2011.2.25.3.40.40.30.15952
    pmMcs7nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs7nss2."
        ::= { optixTrapsPER 15952 }

    -- 1.3.6.1.4.1.2011.2.25.3.40.40.30.15953
    pmMcs8nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs8nss2."
        ::= { optixTrapsPER 15953 }

    -- 1.3.6.1.4.1.2011.2.25.3.40.40.30.15954
    pmMcs9nss2RxPkt NOTIFICATION-TYPE
        OBJECTS{ rptEvtPeriod,rptEvtValue,rptEvtVldty,rptEvtDateTime,rptEvtObjType,rptEvtParaLen,rptEvtPara }
        STATUS current
        DESCRIPTION
            "Trap of Event: The number of packets received under mcs9nss2."
        ::= { optixTrapsPER 15954 }

    -- 1.3.6.1.4.1.2011.2.25.3.40.40.30.15955
    pmMcs0nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs0nss1."
        ::= { optixTrapsPER 15955 }

    -- 1.3.6.1.4.1.2011.2.25.3.40.40.30.15956
    pmMcs1nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs1nss1."
        ::= { optixTrapsPER 15956 }

    -- 1.3.6.1.4.1.2011.2.25.3.40.40.30.15957
    pmMcs2nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs2nss1."
        ::= { optixTrapsPER 15957 }

    -- 1.3.6.1.4.1.2011.2.25.3.40.40.30.15958
    pmMcs3nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs3nss1."
        ::= { optixTrapsPER 15958 }

    -- 1.3.6.1.4.1.2011.2.25.3.40.40.30.15959
    pmMcs4nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs4nss1."
        ::= { optixTrapsPER 15959 }

    -- 1.3.6.1.4.1.2011.2.25.3.40.40.30.15960
    pmMcs5nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs5nss1."
        ::= { optixTrapsPER 15960 }

    -- 1.3.6.1.4.1.2011.2.25.3.40.40.30.15961
    pmMcs6nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs6nss1."
        ::= { optixTrapsPER 15961 }

    -- 1.3.6.1.4.1.2011.2.25.3.40.40.30.15962
    pmMcs7nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs7nss1."
        ::= { optixTrapsPER 15962 }

    -- 1.3.6.1.4.1.2011.2.25.3.40.40.30.15963
    pmMcs8nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs8nss1."
        ::= { optixTrapsPER 15963 }

    -- 1.3.6.1.4.1.2011.2.25.3.40.40.30.15964
    pmMcs9nss1TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs9nss1."
        ::= { optixTrapsPER 15964 }

    -- 1.3.6.1.4.1.2011.2.25.3.40.40.30.15965
    pmMcs0nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs0nss2."
        ::= { optixTrapsPER 15965 }

    -- 1.3.6.1.4.1.2011.2.25.3.40.40.30.15966
    pmMcs1nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs1nss2."
        ::= { optixTrapsPER 15966 }

    -- 1.3.6.1.4.1.2011.2.25.3.40.40.30.15967
    pmMcs2nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs2nss2."
        ::= { optixTrapsPER 15967 }

    -- 1.3.6.1.4.1.2011.2.25.3.40.40.30.15968
    pmMcs3nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs3nss2."
        ::= { optixTrapsPER 15968 }

    -- 1.3.6.1.4.1.2011.2.25.3.40.40.30.15969
    pmMcs4nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs4nss2."
        ::= { optixTrapsPER 15969 }

    -- 1.3.6.1.4.1.2011.2.25.3.40.40.30.15970
    pmMcs5nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs5nss2."
        ::= { optixTrapsPER 15970 }

    -- 1.3.6.1.4.1.2011.2.25.3.40.40.30.15971
    pmMcs6nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs6nss2."
        ::= { optixTrapsPER 15971 }

    -- 1.3.6.1.4.1.2011.2.25.3.40.40.30.15972
    pmMcs7nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs7nss2."
        ::= { optixTrapsPER 15972 }

    -- 1.3.6.1.4.1.2011.2.25.3.40.40.30.15973
    pmMcs8nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs8nss2."
        ::= { optixTrapsPER 15973 }

    -- 1.3.6.1.4.1.2011.2.25.3.40.40.30.15974
    pmMcs9nss2TxPkt NOTIFICATION-TYPE
        OBJECTS{ rptEvtPeriod,rptEvtValue,rptEvtVldty,rptEvtDateTime,rptEvtObjType,rptEvtParaLen,rptEvtPara }
        STATUS current
        DESCRIPTION
            "Trap of Event: The number of packets send under mcs9nss2."
        ::= { optixTrapsPER 15974 }
	
    -- 1.3.6.1.4.1.2011.2.25.3.40.40.30.16094
    pmMAXCLKDA NOTIFICATION-TYPE
        OBJECTS{ rptEvtPeriod,rptEvtValue,rptEvtVldty,rptEvtDateTime,rptEvtObjType,rptEvtParaLen,rptEvtPara }
        STATUS current
        DESCRIPTION
            "Trap of Event:Maximum clock DA of the clock source"
        ::= { optixTrapsPER 16094 }

    -- 1.3.6.1.4.1.2011.2.25.3.40.40.30.16095
    pmMINCLKDA NOTIFICATION-TYPE
        OBJECTS{ rptEvtPeriod,rptEvtValue,rptEvtVldty,rptEvtDateTime,rptEvtObjType,rptEvtParaLen,rptEvtPara }
        STATUS current
        DESCRIPTION
            "Trap of Event:Minimum clock DA of the clock source"
        ::= { optixTrapsPER 16095 }

    -- 1.3.6.1.4.1.2011.2.25.3.40.40.30.16096
    pmAVGCLKDA NOTIFICATION-TYPE
        OBJECTS{ rptEvtPeriod,rptEvtValue,rptEvtVldty,rptEvtDateTime,rptEvtObjType,rptEvtParaLen,rptEvtPara }
        STATUS current
        DESCRIPTION
            "Trap of Event:Average clock DA of the clock source"
        ::= { optixTrapsPER 16096 }		
		
    -- 1.3.6.1.4.1.2011.2.25.3.40.40.30.37
    pmE3LcvSdh NOTIFICATION-TYPE
        OBJECTS{ rptEvtPeriod,rptEvtValue,rptEvtVldty,rptEvtDateTime,rptEvtObjType,rptEvtParaLen,rptEvtPara }
        STATUS current
        DESCRIPTION
            "Trap of Event:E3 line side code violation count"
        ::= { optixTrapsPER 37 }

    -- 1.3.6.1.4.1.2011.2.25.3.40.40.30.38
    pmE3LesSdh NOTIFICATION-TYPE
        OBJECTS{ rptEvtPeriod,rptEvtValue,rptEvtVldty,rptEvtDateTime,rptEvtObjType,rptEvtParaLen,rptEvtPara }
        STATUS current
        DESCRIPTION
            "Trap of Event:E3 line side code violation errored second"
        ::= { optixTrapsPER 38 }

    -- 1.3.6.1.4.1.2011.2.25.3.40.40.30.39
    pmE3LsesSdh NOTIFICATION-TYPE
        OBJECTS{ rptEvtPeriod,rptEvtValue,rptEvtVldty,rptEvtDateTime,rptEvtObjType,rptEvtParaLen,rptEvtPara }
        STATUS current
        DESCRIPTION
            "Trap of Event:E3 line side code violation severely errored second"
        ::= { optixTrapsPER 39 }

    -- 1.3.6.1.4.1.2011.2.25.3.40.40.30.45
    pmTcbbe NOTIFICATION-TYPE
        OBJECTS{ rptEvtPeriod,rptEvtValue,rptEvtVldty,rptEvtDateTime,rptEvtObjType,rptEvtParaLen,rptEvtPara }
        STATUS current
        DESCRIPTION
            "Trap of Event:Tandem Connection Background Block Error"
        ::= { optixTrapsPER 45 }

    -- 1.3.6.1.4.1.2011.2.25.3.40.40.30.46
    pmTcfebbe NOTIFICATION-TYPE
        OBJECTS{ rptEvtPeriod,rptEvtValue,rptEvtVldty,rptEvtDateTime,rptEvtObjType,rptEvtParaLen,rptEvtPara }
        STATUS current
        DESCRIPTION
            "Trap of Event:Tandem Connection Far End Background Block Error"
        ::= { optixTrapsPER 46 }

    -- 1.3.6.1.4.1.2011.2.25.3.40.40.30.47
    pmTcobbe NOTIFICATION-TYPE
        OBJECTS{ rptEvtPeriod,rptEvtValue,rptEvtVldty,rptEvtDateTime,rptEvtObjType,rptEvtParaLen,rptEvtPara }
        STATUS current
        DESCRIPTION
            "Trap of Event:Tandem Connection Outgoing Background Block Error"
        ::= { optixTrapsPER 47 }

    -- 1.3.6.1.4.1.2011.2.25.3.40.40.30.65
    pmEdfboxtmpmax NOTIFICATION-TYPE
        OBJECTS{ rptEvtPeriod,rptEvtValue,rptEvtVldty,rptEvtDateTime,rptEvtObjType,rptEvtParaLen,rptEvtPara }
        STATUS current
        DESCRIPTION
            "Trap of Event:EDFA Fiber Box Temperature - the Maximum value."
        ::= { optixTrapsPER 65 }

    -- 1.3.6.1.4.1.2011.2.25.3.40.40.30.66
    pmEdfboxtmpmin NOTIFICATION-TYPE
        OBJECTS{ rptEvtPeriod,rptEvtValue,rptEvtVldty,rptEvtDateTime,rptEvtObjType,rptEvtParaLen,rptEvtPara }
        STATUS current
        DESCRIPTION
            "Trap of Event:EDFA Fiber Box Temperature - the Minimum value."
        ::= { optixTrapsPER 66 }

    -- 1.3.6.1.4.1.2011.2.25.3.40.40.30.67
    pmEdfboxtmpcur NOTIFICATION-TYPE
        OBJECTS{ rptEvtPeriod,rptEvtValue,rptEvtVldty,rptEvtDateTime,rptEvtObjType,rptEvtParaLen,rptEvtPara }
        STATUS current
        DESCRIPTION
            "Trap of Event:EDFA Fiber Box Temperature - the Current value."
        ::= { optixTrapsPER 67 }

    -- 1.3.6.1.4.1.2011.2.25.3.40.40.30.80
    pmVc3bbe NOTIFICATION-TYPE
        OBJECTS{ rptEvtPeriod,rptEvtValue,rptEvtVldty,rptEvtDateTime,rptEvtObjType,rptEvtParaLen,rptEvtPara }
        STATUS current
        DESCRIPTION
            "Trap of Event:VC3 Background Block Error"
        ::= { optixTrapsPER 80 }

    -- 1.3.6.1.4.1.2011.2.25.3.40.40.30.81
    pmVc3es NOTIFICATION-TYPE
        OBJECTS{ rptEvtPeriod,rptEvtValue,rptEvtVldty,rptEvtDateTime,rptEvtObjType,rptEvtParaLen,rptEvtPara }
        STATUS current
        DESCRIPTION
            "Trap of Event:VC3Errored Second"
        ::= { optixTrapsPER 81 }

    -- 1.3.6.1.4.1.2011.2.25.3.40.40.30.82
    pmVc3ses NOTIFICATION-TYPE
        OBJECTS{ rptEvtPeriod,rptEvtValue,rptEvtVldty,rptEvtDateTime,rptEvtObjType,rptEvtParaLen,rptEvtPara }
        STATUS current
        DESCRIPTION
            "Trap of Event:VC3Serverly Errored Second"
        ::= { optixTrapsPER 82 }

    -- 1.3.6.1.4.1.2011.2.25.3.40.40.30.83
    pmVc3febbe NOTIFICATION-TYPE
        OBJECTS{ rptEvtPeriod,rptEvtValue,rptEvtVldty,rptEvtDateTime,rptEvtObjType,rptEvtParaLen,rptEvtPara }
        STATUS current
        DESCRIPTION
            "Trap of Event:VC3 FAR END Background Block Error"
        ::= { optixTrapsPER 83 }

    -- 1.3.6.1.4.1.2011.2.25.3.40.40.30.84
    pmVc3fees NOTIFICATION-TYPE
        OBJECTS{ rptEvtPeriod,rptEvtValue,rptEvtVldty,rptEvtDateTime,rptEvtObjType,rptEvtParaLen,rptEvtPara }
        STATUS current
        DESCRIPTION
            "Trap of Event:VC3 FAR END Errored Second"
        ::= { optixTrapsPER 84 }

    -- 1.3.6.1.4.1.2011.2.25.3.40.40.30.85
    pmVc3feses NOTIFICATION-TYPE
        OBJECTS{ rptEvtPeriod,rptEvtValue,rptEvtVldty,rptEvtDateTime,rptEvtObjType,rptEvtParaLen,rptEvtPara }
        STATUS current
        DESCRIPTION
            "Trap of Event:VC3 far end"
        ::= { optixTrapsPER 85 }

    -- 1.3.6.1.4.1.2011.2.25.3.40.40.30.86
    pmVc3uas NOTIFICATION-TYPE
        OBJECTS{ rptEvtPeriod,rptEvtValue,rptEvtVldty,rptEvtDateTime,rptEvtObjType,rptEvtParaLen,rptEvtPara }
        STATUS current
        DESCRIPTION
            "Trap of Event:VC3 Unavailable Second"
        ::= { optixTrapsPER 86 }

    -- 1.3.6.1.4.1.2011.2.25.3.40.40.30.87
    pmVc3cses NOTIFICATION-TYPE
        OBJECTS{ rptEvtPeriod,rptEvtValue,rptEvtVldty,rptEvtDateTime,rptEvtObjType,rptEvtParaLen,rptEvtPara }
        STATUS current
        DESCRIPTION
            "Trap of Event: VC3Consecutiv Serverly Eeeored Second"
        ::= { optixTrapsPER 87 }

    -- 1.3.6.1.4.1.2011.2.25.3.40.40.30.88
    pmVc3fecses NOTIFICATION-TYPE
        OBJECTS{ rptEvtPeriod,rptEvtValue,rptEvtVldty,rptEvtDateTime,rptEvtObjType,rptEvtParaLen,rptEvtPara }
        STATUS current
        DESCRIPTION
            "Trap of Event:VC3 far end Consecutiv Serverly Eeeored Second"
        ::= { optixTrapsPER 88 }

    -- 1.3.6.1.4.1.2011.2.25.3.40.40.30.89
    pmVc3feuas NOTIFICATION-TYPE
        OBJECTS{ rptEvtPeriod,rptEvtValue,rptEvtVldty,rptEvtDateTime,rptEvtObjType,rptEvtParaLen,rptEvtPara }
        STATUS current
        DESCRIPTION
            "Trap of Event:VC3 FarEndUnavailableSecond"
        ::= { optixTrapsPER 89 }

    -- 1.3.6.1.4.1.2011.2.25.3.40.40.30.99
    pmOspiccvmax NOTIFICATION-TYPE
        OBJECTS{ rptEvtPeriod,rptEvtValue,rptEvtVldty,rptEvtDateTime,rptEvtObjType,rptEvtParaLen,rptEvtPara }
        STATUS current
        DESCRIPTION
            "Trap of Event:Maximum value of laser cooling Current"
        ::= { optixTrapsPER 99 }

    -- 1.3.6.1.4.1.2011.2.25.3.40.40.30.100
    pmOspiccvmin NOTIFICATION-TYPE
        OBJECTS{ rptEvtPeriod,rptEvtValue,rptEvtVldty,rptEvtDateTime,rptEvtObjType,rptEvtParaLen,rptEvtPara }
        STATUS current
        DESCRIPTION
            "Trap of Event:Minimum value of laser cooling Current"
        ::= { optixTrapsPER 100 }

    -- 1.3.6.1.4.1.2011.2.25.3.40.40.30.101
    pmOspiccvcur NOTIFICATION-TYPE
        OBJECTS{ rptEvtPeriod,rptEvtValue,rptEvtVldty,rptEvtDateTime,rptEvtObjType,rptEvtParaLen,rptEvtPara }
        STATUS current
        DESCRIPTION
            "Trap of Event:Current value of laser cooling current"
        ::= { optixTrapsPER 101 }

    -- 1.3.6.1.4.1.2011.2.25.3.40.40.30.112
    pmWcvmax NOTIFICATION-TYPE
        OBJECTS{ rptEvtPeriod,rptEvtValue,rptEvtVldty,rptEvtDateTime,rptEvtObjType,rptEvtParaLen,rptEvtPara }
        STATUS current
        DESCRIPTION
            "Trap of Event:EDFA Working Current Value Maximum"
        ::= { optixTrapsPER 112 }

    -- 1.3.6.1.4.1.2011.2.25.3.40.40.30.113
    pmWcvmin NOTIFICATION-TYPE
        OBJECTS{ rptEvtPeriod,rptEvtValue,rptEvtVldty,rptEvtDateTime,rptEvtObjType,rptEvtParaLen,rptEvtPara }
        STATUS current
        DESCRIPTION
            "Trap of Event:EDFA Working Current Value Minimum"
        ::= { optixTrapsPER 113 }

    -- 1.3.6.1.4.1.2011.2.25.3.40.40.30.114
    pmWcvcur NOTIFICATION-TYPE
        OBJECTS{ rptEvtPeriod,rptEvtValue,rptEvtVldty,rptEvtDateTime,rptEvtObjType,rptEvtParaLen,rptEvtPara }
        STATUS current
        DESCRIPTION
            "Trap of Event:EDFA Working Current Value Avg-Value"
        ::= { optixTrapsPER 114 }

    -- 1.3.6.1.4.1.2011.2.25.3.40.40.30.115
    pmCcvmax NOTIFICATION-TYPE
        OBJECTS{ rptEvtPeriod,rptEvtValue,rptEvtVldty,rptEvtDateTime,rptEvtObjType,rptEvtParaLen,rptEvtPara }
        STATUS current
        DESCRIPTION
            "Trap of Event:EDFA Cooling Current Value Maximum"
        ::= { optixTrapsPER 115 }

    -- 1.3.6.1.4.1.2011.2.25.3.40.40.30.116
    pmCcvmin NOTIFICATION-TYPE
        OBJECTS{ rptEvtPeriod,rptEvtValue,rptEvtVldty,rptEvtDateTime,rptEvtObjType,rptEvtParaLen,rptEvtPara }
        STATUS current
        DESCRIPTION
            "Trap of Event:EDFA Cooling Current Value Minimum"
        ::= { optixTrapsPER 116 }

    -- 1.3.6.1.4.1.2011.2.25.3.40.40.30.117
    pmCcvcur NOTIFICATION-TYPE
        OBJECTS{ rptEvtPeriod,rptEvtValue,rptEvtVldty,rptEvtDateTime,rptEvtObjType,rptEvtParaLen,rptEvtPara }
        STATUS current
        DESCRIPTION
            "Trap of Event:EDFA Cooling Current Value Avg-Value"
        ::= { optixTrapsPER 117 }

    -- 1.3.6.1.4.1.2011.2.25.3.40.40.30.118
    pmBcvmax NOTIFICATION-TYPE
        OBJECTS{ rptEvtPeriod,rptEvtValue,rptEvtVldty,rptEvtDateTime,rptEvtObjType,rptEvtParaLen,rptEvtPara }
        STATUS current
        DESCRIPTION
            "Trap of Event:EDFA Back Current Value Maximum"
        ::= { optixTrapsPER 118 }

    -- 1.3.6.1.4.1.2011.2.25.3.40.40.30.119
    pmBcvmin NOTIFICATION-TYPE
        OBJECTS{ rptEvtPeriod,rptEvtValue,rptEvtVldty,rptEvtDateTime,rptEvtObjType,rptEvtParaLen,rptEvtPara }
        STATUS current
        DESCRIPTION
            "Trap of Event:EDFA Back Current Value Minimum"
        ::= { optixTrapsPER 119 }

    -- 1.3.6.1.4.1.2011.2.25.3.40.40.30.124
    pmEdrplmax NOTIFICATION-TYPE
        OBJECTS{ rptEvtPeriod,rptEvtValue,rptEvtVldty,rptEvtDateTime,rptEvtObjType,rptEvtParaLen,rptEvtPara }
        STATUS current
        DESCRIPTION
            "Trap of Event:Maximum value of EDFA receiving power"
        ::= { optixTrapsPER 124 }

    -- 1.3.6.1.4.1.2011.2.25.3.40.40.30.125
    pmEdrplmin NOTIFICATION-TYPE
        OBJECTS{ rptEvtPeriod,rptEvtValue,rptEvtVldty,rptEvtDateTime,rptEvtObjType,rptEvtParaLen,rptEvtPara }
        STATUS current
        DESCRIPTION
            "Trap of Event:Minimum value of EDFA receiving power"
        ::= { optixTrapsPER 125 }

    -- 1.3.6.1.4.1.2011.2.25.3.40.40.30.126
    pmEdrplcur NOTIFICATION-TYPE
        OBJECTS{ rptEvtPeriod,rptEvtValue,rptEvtVldty,rptEvtDateTime,rptEvtObjType,rptEvtParaLen,rptEvtPara }
        STATUS current
        DESCRIPTION
            "Trap of Event:Current value of laser transmitting power"
        ::= { optixTrapsPER 126 }

    -- 1.3.6.1.4.1.2011.2.25.3.40.40.30.127
    pmEdwcsmax NOTIFICATION-TYPE
        OBJECTS{ rptEvtPeriod,rptEvtValue,rptEvtVldty,rptEvtDateTime,rptEvtObjType,rptEvtParaLen,rptEvtPara }
        STATUS current
        DESCRIPTION
            "Trap of Event:Maximum value of EDFA working current setup"
        ::= { optixTrapsPER 127 }

    -- 1.3.6.1.4.1.2011.2.25.3.40.40.30.128
    pmEdwcsmin NOTIFICATION-TYPE
        OBJECTS{ rptEvtPeriod,rptEvtValue,rptEvtVldty,rptEvtDateTime,rptEvtObjType,rptEvtParaLen,rptEvtPara }
        STATUS current
        DESCRIPTION
            "Trap of Event:Minimum value of EDFA working current setup"
        ::= { optixTrapsPER 128 }

    -- 1.3.6.1.4.1.2011.2.25.3.40.40.30.129
    pmEdwcscur NOTIFICATION-TYPE
        OBJECTS{ rptEvtPeriod,rptEvtValue,rptEvtVldty,rptEvtDateTime,rptEvtObjType,rptEvtParaLen,rptEvtPara }
        STATUS current
        DESCRIPTION
            "Trap of Event:Current value of EDFA working current setup"
        ::= { optixTrapsPER 129 }

    -- 1.3.6.1.4.1.2011.2.25.3.40.40.30.130
    pmEdtmpmax NOTIFICATION-TYPE
        OBJECTS{ rptEvtPeriod,rptEvtValue,rptEvtVldty,rptEvtDateTime,rptEvtObjType,rptEvtParaLen,rptEvtPara }
        STATUS current
        DESCRIPTION
            "Trap of Event:EDFA Temperature Maximum"
        ::= { optixTrapsPER 130 }

    -- 1.3.6.1.4.1.2011.2.25.3.40.40.30.131
    pmEdtmpmin NOTIFICATION-TYPE
        OBJECTS{ rptEvtPeriod,rptEvtValue,rptEvtVldty,rptEvtDateTime,rptEvtObjType,rptEvtParaLen,rptEvtPara }
        STATUS current
        DESCRIPTION
            "Trap of Event:EDFA Temperature Minimum"
        ::= { optixTrapsPER 131 }

    -- 1.3.6.1.4.1.2011.2.25.3.40.40.30.132
    pmEdtmpcur NOTIFICATION-TYPE
        OBJECTS{ rptEvtPeriod,rptEvtValue,rptEvtVldty,rptEvtDateTime,rptEvtObjType,rptEvtParaLen,rptEvtPara }
        STATUS current
        DESCRIPTION
            "Trap of Event:EDFA Temperature Avg-Value"
        ::= { optixTrapsPER 132 }

    -- 1.3.6.1.4.1.2011.2.25.3.40.40.30.133
    pmFecCor0bitCnt NOTIFICATION-TYPE
        OBJECTS{ rptEvtPeriod,rptEvtValue,rptEvtVldty,rptEvtDateTime,rptEvtObjType,rptEvtParaLen,rptEvtPara }
        STATUS current
        DESCRIPTION
            "Trap of Event:Forward Error Correction - Corrected 0 Bit Count"
        ::= { optixTrapsPER 133 }

    -- 1.3.6.1.4.1.2011.2.25.3.40.40.30.134
    pmFecCor1bitCnt NOTIFICATION-TYPE
        OBJECTS{ rptEvtPeriod,rptEvtValue,rptEvtVldty,rptEvtDateTime,rptEvtObjType,rptEvtParaLen,rptEvtPara }
        STATUS current
        DESCRIPTION
            "Trap of Event:Forward Error Correction - Corrected 1 Bit Count"
        ::= { optixTrapsPER 134 }

    -- 1.3.6.1.4.1.2011.2.25.3.40.40.30.138
    pmEmuvolmax NOTIFICATION-TYPE
        OBJECTS{ rptEvtPeriod,rptEvtValue,rptEvtVldty,rptEvtDateTime,rptEvtObjType,rptEvtParaLen,rptEvtPara }
        STATUS current
        DESCRIPTION
            "Trap of Event:EMU Voltage max"
        ::= { optixTrapsPER 138 }

    -- 1.3.6.1.4.1.2011.2.25.3.40.40.30.139
    pmEmuvolmin NOTIFICATION-TYPE
        OBJECTS{ rptEvtPeriod,rptEvtValue,rptEvtVldty,rptEvtDateTime,rptEvtObjType,rptEvtParaLen,rptEvtPara }
        STATUS current
        DESCRIPTION
            "Trap of Event:EMU Voltage min"
        ::= { optixTrapsPER 139 }

    -- 1.3.6.1.4.1.2011.2.25.3.40.40.30.141
    pmEmuvolcur NOTIFICATION-TYPE
        OBJECTS{ rptEvtPeriod,rptEvtValue,rptEvtVldty,rptEvtDateTime,rptEvtObjType,rptEvtParaLen,rptEvtPara }
        STATUS current
        DESCRIPTION
            "Trap of Event:EMU Voltage current"
        ::= { optixTrapsPER 141 }

    -- 1.3.6.1.4.1.2011.2.25.3.40.40.30.160
    pmT3LcvSdh NOTIFICATION-TYPE
        OBJECTS{ rptEvtPeriod,rptEvtValue,rptEvtVldty,rptEvtDateTime,rptEvtObjType,rptEvtParaLen,rptEvtPara }
        STATUS current
        DESCRIPTION
            "Trap of Event:T3 line side code violation count"
        ::= { optixTrapsPER 160 }

    -- 1.3.6.1.4.1.2011.2.25.3.40.40.30.161
    pmT3LesSdh NOTIFICATION-TYPE
        OBJECTS{ rptEvtPeriod,rptEvtValue,rptEvtVldty,rptEvtDateTime,rptEvtObjType,rptEvtParaLen,rptEvtPara }
        STATUS current
        DESCRIPTION
            "Trap of Event:T3 line side code violation errored second"
        ::= { optixTrapsPER 161 }

    -- 1.3.6.1.4.1.2011.2.25.3.40.40.30.162
    pmT3LsesSdh NOTIFICATION-TYPE
        OBJECTS{ rptEvtPeriod,rptEvtValue,rptEvtVldty,rptEvtDateTime,rptEvtObjType,rptEvtParaLen,rptEvtPara }
        STATUS current
        DESCRIPTION
            "Trap of Event:T3 line side code violation severely errored second"
        ::= { optixTrapsPER 162 }

    -- 1.3.6.1.4.1.2011.2.25.3.40.40.30.167
    pmT1LlossSdh NOTIFICATION-TYPE
        OBJECTS{ rptEvtPeriod,rptEvtValue,rptEvtVldty,rptEvtDateTime,rptEvtObjType,rptEvtParaLen,rptEvtPara }
        STATUS current
        DESCRIPTION
            "Trap of Event:T1 line side code violation signal lossed second"
        ::= { optixTrapsPER 167 }

    -- 1.3.6.1.4.1.2011.2.25.3.40.40.30.185
    pmCrc4Err NOTIFICATION-TYPE
        OBJECTS{ rptEvtPeriod,rptEvtValue,rptEvtVldty,rptEvtDateTime,rptEvtObjType,rptEvtParaLen,rptEvtPara }
        STATUS current
        DESCRIPTION
            "Trap of Event:CRC4  error"
        ::= { optixTrapsPER 185 }

    -- 1.3.6.1.4.1.2011.2.25.3.40.40.30.186
    pmDdnCrc4Err NOTIFICATION-TYPE
        OBJECTS{ rptEvtPeriod,rptEvtValue,rptEvtVldty,rptEvtDateTime,rptEvtObjType,rptEvtParaLen,rptEvtPara }
        STATUS current
        DESCRIPTION
            "Trap of Event:CRC4  error on DDN side"
        ::= { optixTrapsPER 186 }

    -- 1.3.6.1.4.1.2011.2.25.3.40.40.30.188
    pmXcstmpmax NOTIFICATION-TYPE
        OBJECTS{ rptEvtPeriod,rptEvtValue,rptEvtVldty,rptEvtDateTime,rptEvtObjType,rptEvtParaLen,rptEvtPara }
        STATUS current
        DESCRIPTION
            "Trap of Event:Board Temperature Maximum"
        ::= { optixTrapsPER 188 }

    -- 1.3.6.1.4.1.2011.2.25.3.40.40.30.189
    pmXcstmpmin NOTIFICATION-TYPE
        OBJECTS{ rptEvtPeriod,rptEvtValue,rptEvtVldty,rptEvtDateTime,rptEvtObjType,rptEvtParaLen,rptEvtPara }
        STATUS current
        DESCRIPTION
            "Trap of Event:Board Temperature Minimum"
        ::= { optixTrapsPER 189 }

    -- 1.3.6.1.4.1.2011.2.25.3.40.40.30.190
    pmXcstmpcur NOTIFICATION-TYPE
        OBJECTS{ rptEvtPeriod,rptEvtValue,rptEvtVldty,rptEvtDateTime,rptEvtObjType,rptEvtParaLen,rptEvtPara }
        STATUS current
        DESCRIPTION
            "Trap of Event:Board Temperature Cur-Value"
        ::= { optixTrapsPER 190 }

    -- 1.3.6.1.4.1.2011.2.25.3.40.40.30.210
    pmSumiopmax NOTIFICATION-TYPE
        OBJECTS{ rptEvtPeriod,rptEvtValue,rptEvtVldty,rptEvtDateTime,rptEvtObjType,rptEvtParaLen,rptEvtPara }
        STATUS current
        DESCRIPTION
            "Trap of Event:Sum Laser Input Of Power Maximum"
        ::= { optixTrapsPER 210 }

    -- 1.3.6.1.4.1.2011.2.25.3.40.40.30.211
    pmSumiopmin NOTIFICATION-TYPE
        OBJECTS{ rptEvtPeriod,rptEvtValue,rptEvtVldty,rptEvtDateTime,rptEvtObjType,rptEvtParaLen,rptEvtPara }
        STATUS current
        DESCRIPTION
            "Trap of Event:Sum Laser Input Of Power Minimum"
        ::= { optixTrapsPER 211 }

    -- 1.3.6.1.4.1.2011.2.25.3.40.40.30.212
    pmSumiopcur NOTIFICATION-TYPE
        OBJECTS{ rptEvtPeriod,rptEvtValue,rptEvtVldty,rptEvtDateTime,rptEvtObjType,rptEvtParaLen,rptEvtPara }
        STATUS current
        DESCRIPTION
            "Trap of Event:Sum Laser Input Of Power Cur-Value"
        ::= { optixTrapsPER 212 }

    -- 1.3.6.1.4.1.2011.2.25.3.40.40.30.213
    pmSumoopmax NOTIFICATION-TYPE
        OBJECTS{ rptEvtPeriod,rptEvtValue,rptEvtVldty,rptEvtDateTime,rptEvtObjType,rptEvtParaLen,rptEvtPara }
        STATUS current
        DESCRIPTION
            "Trap of Event:Sum Laser Output Of Power Maximum"
        ::= { optixTrapsPER 213 }

    -- 1.3.6.1.4.1.2011.2.25.3.40.40.30.214
    pmSumoopmin NOTIFICATION-TYPE
        OBJECTS{ rptEvtPeriod,rptEvtValue,rptEvtVldty,rptEvtDateTime,rptEvtObjType,rptEvtParaLen,rptEvtPara }
        STATUS current
        DESCRIPTION
            "Trap of Event:Sum Laser Output Of Power Minimum"
        ::= { optixTrapsPER 214 }

    -- 1.3.6.1.4.1.2011.2.25.3.40.40.30.215
    pmSumoopcur NOTIFICATION-TYPE
        OBJECTS{ rptEvtPeriod,rptEvtValue,rptEvtVldty,rptEvtDateTime,rptEvtObjType,rptEvtParaLen,rptEvtPara }
        STATUS current
        DESCRIPTION
            "Trap of Event:Sum Laser Output Of Power Cur-Value"
        ::= { optixTrapsPER 215 }

    -- 1.3.6.1.4.1.2011.2.25.3.40.40.30.222
    pmEnvtmpmax NOTIFICATION-TYPE
        OBJECTS{ rptEvtPeriod,rptEvtValue,rptEvtVldty,rptEvtDateTime,rptEvtObjType,rptEvtParaLen,rptEvtPara }
        STATUS current
        DESCRIPTION
            "Trap of Event:Environment Temperature Maximum"
        ::= { optixTrapsPER 222 }

    -- 1.3.6.1.4.1.2011.2.25.3.40.40.30.223
    pmEnvtmpmin NOTIFICATION-TYPE
        OBJECTS{ rptEvtPeriod,rptEvtValue,rptEvtVldty,rptEvtDateTime,rptEvtObjType,rptEvtParaLen,rptEvtPara }
        STATUS current
        DESCRIPTION
            "Trap of Event:Environment Temperature Minimum"
        ::= { optixTrapsPER 223 }

    -- 1.3.6.1.4.1.2011.2.25.3.40.40.30.224
    pmEnvtmpcur NOTIFICATION-TYPE
        OBJECTS{ rptEvtPeriod,rptEvtValue,rptEvtVldty,rptEvtDateTime,rptEvtObjType,rptEvtParaLen,rptEvtPara }
        STATUS current
        DESCRIPTION
            "Trap of Event:Environment Temperature Cur-Value"
        ::= { optixTrapsPER 224 }

    -- 1.3.6.1.4.1.2011.2.25.3.40.40.30.225
    pmLsclcmax NOTIFICATION-TYPE
        OBJECTS{ rptEvtPeriod,rptEvtValue,rptEvtVldty,rptEvtDateTime,rptEvtObjType,rptEvtParaLen,rptEvtPara }
        STATUS current
        DESCRIPTION
            "Trap of Event:Laser Cooling Current Maximum"
        ::= { optixTrapsPER 225 }

    -- 1.3.6.1.4.1.2011.2.25.3.40.40.30.226
    pmLsclcmin NOTIFICATION-TYPE
        OBJECTS{ rptEvtPeriod,rptEvtValue,rptEvtVldty,rptEvtDateTime,rptEvtObjType,rptEvtParaLen,rptEvtPara }
        STATUS current
        DESCRIPTION
            "Trap of Event:Laser Cooling Current Minimum"
        ::= { optixTrapsPER 226 }

    -- 1.3.6.1.4.1.2011.2.25.3.40.40.30.227
    pmLsclccur NOTIFICATION-TYPE
        OBJECTS{ rptEvtPeriod,rptEvtValue,rptEvtVldty,rptEvtDateTime,rptEvtObjType,rptEvtParaLen,rptEvtPara }
        STATUS current
        DESCRIPTION
            "Trap of Event:Laser Cooling Current Cur-Value"
        ::= { optixTrapsPER 227 }

    -- 1.3.6.1.4.1.2011.2.25.3.40.40.30.228
    pmPclswlmax NOTIFICATION-TYPE
        OBJECTS{ rptEvtPeriod,rptEvtValue,rptEvtVldty,rptEvtDateTime,rptEvtObjType,rptEvtParaLen,rptEvtPara }
        STATUS current
        DESCRIPTION
            "Trap of Event:Per Channel Laser WaveLength Maximum"
        ::= { optixTrapsPER 228 }

    -- 1.3.6.1.4.1.2011.2.25.3.40.40.30.229
    pmPclswlmin NOTIFICATION-TYPE
        OBJECTS{ rptEvtPeriod,rptEvtValue,rptEvtVldty,rptEvtDateTime,rptEvtObjType,rptEvtParaLen,rptEvtPara }
        STATUS current
        DESCRIPTION
            "Trap of Event:Per Channel Laser WaveLength Minimum"
        ::= { optixTrapsPER 229 }

    -- 1.3.6.1.4.1.2011.2.25.3.40.40.30.230
    pmPclswlcur NOTIFICATION-TYPE
        OBJECTS{ rptEvtPeriod,rptEvtValue,rptEvtVldty,rptEvtDateTime,rptEvtObjType,rptEvtParaLen,rptEvtPara }
        STATUS current
        DESCRIPTION
            "Trap of Event:Per Channel Laser WaveLength Cur-Value"
        ::= { optixTrapsPER 230 }

    -- 1.3.6.1.4.1.2011.2.25.3.40.40.30.231
    pmPclswlomax NOTIFICATION-TYPE
        OBJECTS{ rptEvtPeriod,rptEvtValue,rptEvtVldty,rptEvtDateTime,rptEvtObjType,rptEvtParaLen,rptEvtPara }
        STATUS current
        DESCRIPTION
            "Trap of Event:Per Channel Laser WaveLength Offset Maximum"
        ::= { optixTrapsPER 231 }

    -- 1.3.6.1.4.1.2011.2.25.3.40.40.30.232
    pmPclswlomin NOTIFICATION-TYPE
        OBJECTS{ rptEvtPeriod,rptEvtValue,rptEvtVldty,rptEvtDateTime,rptEvtObjType,rptEvtParaLen,rptEvtPara }
        STATUS current
        DESCRIPTION
            "Trap of Event:Per Channel Laser WaveLength Offset Minimum"
        ::= { optixTrapsPER 232 }

    -- 1.3.6.1.4.1.2011.2.25.3.40.40.30.233
    pmPclswlocur NOTIFICATION-TYPE
        OBJECTS{ rptEvtPeriod,rptEvtValue,rptEvtVldty,rptEvtDateTime,rptEvtObjType,rptEvtParaLen,rptEvtPara }
        STATUS current
        DESCRIPTION
            "Trap of Event:Per Channel Laser WaveLength Offset Cur-Value"
        ::= { optixTrapsPER 233 }

    -- 1.3.6.1.4.1.2011.2.25.3.40.40.30.234
    pmPclsopmax NOTIFICATION-TYPE
        OBJECTS{ rptEvtPeriod,rptEvtValue,rptEvtVldty,rptEvtDateTime,rptEvtObjType,rptEvtParaLen,rptEvtPara }
        STATUS current
        DESCRIPTION
            "Trap of Event:Per Channel Laser Power Maximum"
        ::= { optixTrapsPER 234 }

    -- 1.3.6.1.4.1.2011.2.25.3.40.40.30.235
    pmPclsopmin NOTIFICATION-TYPE
        OBJECTS{ rptEvtPeriod,rptEvtValue,rptEvtVldty,rptEvtDateTime,rptEvtObjType,rptEvtParaLen,rptEvtPara }
        STATUS current
        DESCRIPTION
            "Trap of Event:Per Channel Laser Power Minimum"
        ::= { optixTrapsPER 235 }

    -- 1.3.6.1.4.1.2011.2.25.3.40.40.30.236
    pmPclsopcur NOTIFICATION-TYPE
        OBJECTS{ rptEvtPeriod,rptEvtValue,rptEvtVldty,rptEvtDateTime,rptEvtObjType,rptEvtParaLen,rptEvtPara }
        STATUS current
        DESCRIPTION
            "Trap of Event:Per Channel Laser Power Cur-Value"
        ::= { optixTrapsPER 236 }

    -- 1.3.6.1.4.1.2011.2.25.3.40.40.30.237
    pmPclssnmax NOTIFICATION-TYPE
        OBJECTS{ rptEvtPeriod,rptEvtValue,rptEvtVldty,rptEvtDateTime,rptEvtObjType,rptEvtParaLen,rptEvtPara }
        STATUS current
        DESCRIPTION
            "Trap of Event:Per Channel Laser Rate Of Singnal And Noise Maximum"
        ::= { optixTrapsPER 237 }

    -- 1.3.6.1.4.1.2011.2.25.3.40.40.30.238
    pmPclssnmin NOTIFICATION-TYPE
        OBJECTS{ rptEvtPeriod,rptEvtValue,rptEvtVldty,rptEvtDateTime,rptEvtObjType,rptEvtParaLen,rptEvtPara }
        STATUS current
        DESCRIPTION
            "Trap of Event:Per Channel Laser Rate Of Singnal And Noise Minimum"
        ::= { optixTrapsPER 238 }

    -- 1.3.6.1.4.1.2011.2.25.3.40.40.30.239
    pmPclssncur NOTIFICATION-TYPE
        OBJECTS{ rptEvtPeriod,rptEvtValue,rptEvtVldty,rptEvtDateTime,rptEvtObjType,rptEvtParaLen,rptEvtPara }
        STATUS current
        DESCRIPTION
            "Trap of Event:Per Channel Laser Rate Of Singnal And Noise Cur-Value"
        ::= { optixTrapsPER 239 }

    -- 1.3.6.1.4.1.2011.2.25.3.40.40.30.240
    pmCrc4bbe NOTIFICATION-TYPE
        OBJECTS{ rptEvtPeriod,rptEvtValue,rptEvtVldty,rptEvtDateTime,rptEvtObjType,rptEvtParaLen,rptEvtPara }
        STATUS current
        DESCRIPTION
            "Trap of Event:CRC4 Background block error"
        ::= { optixTrapsPER 240 }

    -- 1.3.6.1.4.1.2011.2.25.3.40.40.30.241
    pmCrc4es NOTIFICATION-TYPE
        OBJECTS{ rptEvtPeriod,rptEvtValue,rptEvtVldty,rptEvtDateTime,rptEvtObjType,rptEvtParaLen,rptEvtPara }
        STATUS current
        DESCRIPTION
            "Trap of Event:CRC4 Error Second"
        ::= { optixTrapsPER 241 }

    -- 1.3.6.1.4.1.2011.2.25.3.40.40.30.242
    pmCrc4ses NOTIFICATION-TYPE
        OBJECTS{ rptEvtPeriod,rptEvtValue,rptEvtVldty,rptEvtDateTime,rptEvtObjType,rptEvtParaLen,rptEvtPara }
        STATUS current
        DESCRIPTION
            "Trap of Event:CRC4 Severely errored second"
        ::= { optixTrapsPER 242 }

    -- 1.3.6.1.4.1.2011.2.25.3.40.40.30.243
    pmCrc4febbe NOTIFICATION-TYPE
        OBJECTS{ rptEvtPeriod,rptEvtValue,rptEvtVldty,rptEvtDateTime,rptEvtObjType,rptEvtParaLen,rptEvtPara }
        STATUS current
        DESCRIPTION
            "Trap of Event:CRC4 Far end background block error"
        ::= { optixTrapsPER 243 }

    -- 1.3.6.1.4.1.2011.2.25.3.40.40.30.244
    pmCrc4fees NOTIFICATION-TYPE
        OBJECTS{ rptEvtPeriod,rptEvtValue,rptEvtVldty,rptEvtDateTime,rptEvtObjType,rptEvtParaLen,rptEvtPara }
        STATUS current
        DESCRIPTION
            "Trap of Event:CRC4 Far end errored second"
        ::= { optixTrapsPER 244 }

    -- 1.3.6.1.4.1.2011.2.25.3.40.40.30.245
    pmCrc4feses NOTIFICATION-TYPE
        OBJECTS{ rptEvtPeriod,rptEvtValue,rptEvtVldty,rptEvtDateTime,rptEvtObjType,rptEvtParaLen,rptEvtPara }
        STATUS current
        DESCRIPTION
            "Trap of Event:CRC4 Far end severely errored second"
        ::= { optixTrapsPER 245 }

    -- 1.3.6.1.4.1.2011.2.25.3.40.40.30.246
    pmCrc4uas NOTIFICATION-TYPE
        OBJECTS{ rptEvtPeriod,rptEvtValue,rptEvtVldty,rptEvtDateTime,rptEvtObjType,rptEvtParaLen,rptEvtPara }
        STATUS current
        DESCRIPTION
            "Trap of Event:CRC4 Unavailable second"
        ::= { optixTrapsPER 246 }

    -- 1.3.6.1.4.1.2011.2.25.3.40.40.30.247
    pmCrc4cses NOTIFICATION-TYPE
        OBJECTS{ rptEvtPeriod,rptEvtValue,rptEvtVldty,rptEvtDateTime,rptEvtObjType,rptEvtParaLen,rptEvtPara }
        STATUS current
        DESCRIPTION
            "Trap of Event:CRC4 Consecutive severely errored second"
        ::= { optixTrapsPER 247 }

    -- 1.3.6.1.4.1.2011.2.25.3.40.40.30.248
    pmCrc4fecses NOTIFICATION-TYPE
        OBJECTS{ rptEvtPeriod,rptEvtValue,rptEvtVldty,rptEvtDateTime,rptEvtObjType,rptEvtParaLen,rptEvtPara }
        STATUS current
        DESCRIPTION
            "Trap of Event:CRC4 Far end Consecutive severely errored second"
        ::= { optixTrapsPER 248 }

    -- 1.3.6.1.4.1.2011.2.25.3.40.40.30.249
    pmIctmpmax NOTIFICATION-TYPE
        OBJECTS{ rptEvtPeriod,rptEvtValue,rptEvtVldty,rptEvtDateTime,rptEvtObjType,rptEvtParaLen,rptEvtPara }
        STATUS current
        DESCRIPTION
            "Trap of Event:Integrate Circuit Temperature Maximum"
        ::= { optixTrapsPER 249 }

    -- 1.3.6.1.4.1.2011.2.25.3.40.40.30.250
    pmIctmpmin NOTIFICATION-TYPE
        OBJECTS{ rptEvtPeriod,rptEvtValue,rptEvtVldty,rptEvtDateTime,rptEvtObjType,rptEvtParaLen,rptEvtPara }
        STATUS current
        DESCRIPTION
            "Trap of Event:Integrate Circuit Temperature Minimum"
        ::= { optixTrapsPER 250 }

    -- 1.3.6.1.4.1.2011.2.25.3.40.40.30.251
    pmIctmpcur NOTIFICATION-TYPE
        OBJECTS{ rptEvtPeriod,rptEvtValue,rptEvtVldty,rptEvtDateTime,rptEvtObjType,rptEvtParaLen,rptEvtPara }
        STATUS current
        DESCRIPTION
            "Trap of Event:Integrate Circuit Temperature Cur-Value"
        ::= { optixTrapsPER 251 }

    -- 1.3.6.1.4.1.2011.2.25.3.40.40.30.254
    pmCrc4feuas NOTIFICATION-TYPE
        OBJECTS{ rptEvtPeriod,rptEvtValue,rptEvtVldty,rptEvtDateTime,rptEvtObjType,rptEvtParaLen,rptEvtPara }
        STATUS current
        DESCRIPTION
            "Trap of Event:w32CRC4FarEndUnavailableSecond"
        ::= { optixTrapsPER 254 }

    -- 1.3.6.1.4.1.2011.2.25.3.40.40.30.4170
    pmOtu2smbip8 NOTIFICATION-TYPE
        OBJECTS{ rptEvtPeriod,rptEvtValue,rptEvtVldty,rptEvtDateTime,rptEvtObjType,rptEvtParaLen,rptEvtPara }
        STATUS current
        DESCRIPTION
            "Trap of Event:Optical transport section error"
        ::= { optixTrapsPER 4170 }

    -- 1.3.6.1.4.1.2011.2.25.3.40.40.30.4171
    pmOdu2pmbip8 NOTIFICATION-TYPE
        OBJECTS{ rptEvtPeriod,rptEvtValue,rptEvtVldty,rptEvtDateTime,rptEvtObjType,rptEvtParaLen,rptEvtPara }
        STATUS current
        DESCRIPTION
            "Trap of Event:Optical data section error"
        ::= { optixTrapsPER 4171 }

    -- 1.3.6.1.4.1.2011.2.25.3.40.40.30.4172
    pmIcclcmax NOTIFICATION-TYPE
        OBJECTS{ rptEvtPeriod,rptEvtValue,rptEvtVldty,rptEvtDateTime,rptEvtObjType,rptEvtParaLen,rptEvtPara }
        STATUS current
        DESCRIPTION
            "Trap of Event:MAX Module Cool Current"
        ::= { optixTrapsPER 4172 }

    -- 1.3.6.1.4.1.2011.2.25.3.40.40.30.4173
    pmIcclcmin NOTIFICATION-TYPE
        OBJECTS{ rptEvtPeriod,rptEvtValue,rptEvtVldty,rptEvtDateTime,rptEvtObjType,rptEvtParaLen,rptEvtPara }
        STATUS current
        DESCRIPTION
            "Trap of Event:MIN Module Cool Current"
        ::= { optixTrapsPER 4173 }

    -- 1.3.6.1.4.1.2011.2.25.3.40.40.30.4174
    pmIcclccur NOTIFICATION-TYPE
        OBJECTS{ rptEvtPeriod,rptEvtValue,rptEvtVldty,rptEvtDateTime,rptEvtObjType,rptEvtParaLen,rptEvtPara }
        STATUS current
        DESCRIPTION
            "Trap of Event:Current Module Cool Current"
        ::= { optixTrapsPER 4174 }

    -- 1.3.6.1.4.1.2011.2.25.3.40.40.30.15702
    pmQamws4096 NOTIFICATION-TYPE
        OBJECTS{ rptEvtPeriod,rptEvtValue,rptEvtVldty,rptEvtDateTime,rptEvtObjType,rptEvtParaLen,rptEvtPara }
        STATUS current
        DESCRIPTION
            "Trap of Event:4096QAM Working Second"
        ::= { optixTrapsPER 15702 }

    -- 1.3.6.1.4.1.2011.2.25.3.40.40.30.15855
    pmQamLWs2048 NOTIFICATION-TYPE
        OBJECTS{ rptEvtPeriod,rptEvtValue,rptEvtVldty,rptEvtDateTime,rptEvtObjType,rptEvtParaLen,rptEvtPara }
        STATUS current
        DESCRIPTION
            "Trap of Event:2048QAMLIGHT  Working Second"
        ::= { optixTrapsPER 15855 }

    -- 1.3.6.1.4.1.2011.2.25.3.40.40.30.40
    pmE3LlossSdh NOTIFICATION-TYPE
        OBJECTS{ rptEvtPeriod,rptEvtValue,rptEvtVldty,rptEvtDateTime,rptEvtObjType,rptEvtParaLen,rptEvtPara }
        STATUS current
        DESCRIPTION
            "Trap of Event:E3 line side  code violation signal lossed second"
        ::= { optixTrapsPER 40 }

    -- 1.3.6.1.4.1.2011.2.25.3.40.40.30.68
    pmLineOutPowermax NOTIFICATION-TYPE
        OBJECTS{ rptEvtPeriod,rptEvtValue,rptEvtVldty,rptEvtDateTime,rptEvtObjType,rptEvtParaLen,rptEvtPara }
        STATUS current
        DESCRIPTION
            "Trap of Event:Line output power max"
        ::= { optixTrapsPER 68 }

    -- 1.3.6.1.4.1.2011.2.25.3.40.40.30.69
    pmLineOutPowermin NOTIFICATION-TYPE
        OBJECTS{ rptEvtPeriod,rptEvtValue,rptEvtVldty,rptEvtDateTime,rptEvtObjType,rptEvtParaLen,rptEvtPara }
        STATUS current
        DESCRIPTION
            "Trap of Event:Line output power min"
        ::= { optixTrapsPER 69 }

    -- 1.3.6.1.4.1.2011.2.25.3.40.40.30.70
    pmLineOutPowercur NOTIFICATION-TYPE
        OBJECTS{ rptEvtPeriod,rptEvtValue,rptEvtVldty,rptEvtDateTime,rptEvtObjType,rptEvtParaLen,rptEvtPara }
        STATUS current
        DESCRIPTION
            "Trap of Event:Line output power current"
        ::= { optixTrapsPER 70 }

    -- 1.3.6.1.4.1.2011.2.25.3.40.40.30.163
    pmT3LlossSdh NOTIFICATION-TYPE
        OBJECTS{ rptEvtPeriod,rptEvtValue,rptEvtVldty,rptEvtDateTime,rptEvtObjType,rptEvtParaLen,rptEvtPara }
        STATUS current
        DESCRIPTION
            "Trap of Event:T3 line side code violation signal lossed second"
        ::= { optixTrapsPER 163 }

    -- 1.3.6.1.4.1.2011.2.25.3.40.40.30.176
    pmLppsc NOTIFICATION-TYPE
        OBJECTS{ rptEvtPeriod,rptEvtValue,rptEvtVldty,rptEvtDateTime,rptEvtObjType,rptEvtParaLen,rptEvtPara }
        STATUS current
        DESCRIPTION
            "Trap of Event:LP Protection switch count"
        ::= { optixTrapsPER 176 }

    -- 1.3.6.1.4.1.2011.2.25.3.40.40.30.177
    pmLppsd NOTIFICATION-TYPE
        OBJECTS{ rptEvtPeriod,rptEvtValue,rptEvtVldty,rptEvtDateTime,rptEvtObjType,rptEvtParaLen,rptEvtPara }
        STATUS current
        DESCRIPTION
            "Trap of Event:LP Protection switch duration"
        ::= { optixTrapsPER 177 }

    -- 1.3.6.1.4.1.2011.2.25.3.40.40.30.178
    pmDslCv NOTIFICATION-TYPE
        OBJECTS{ rptEvtPeriod,rptEvtValue,rptEvtVldty,rptEvtDateTime,rptEvtObjType,rptEvtParaLen,rptEvtPara }
        STATUS current
        DESCRIPTION
            "Trap of Event: DSL CRC ERR CNT (digital subscriber line CRC errors )"
        ::= { optixTrapsPER 178 }

    -- 1.3.6.1.4.1.2011.2.25.3.40.40.30.179
    pmDslLosws NOTIFICATION-TYPE
        OBJECTS{ rptEvtPeriod,rptEvtValue,rptEvtVldty,rptEvtDateTime,rptEvtObjType,rptEvtParaLen,rptEvtPara }
        STATUS current
        DESCRIPTION
            "Trap of Event: DSL  LOWS  CNT (digital subscriber line LOWS)"
        ::= { optixTrapsPER 179 }

    -- 1.3.6.1.4.1.2011.2.25.3.40.40.30.180
    pmDslEs NOTIFICATION-TYPE
        OBJECTS{ rptEvtPeriod,rptEvtValue,rptEvtVldty,rptEvtDateTime,rptEvtObjType,rptEvtParaLen,rptEvtPara }
        STATUS current
        DESCRIPTION
            "Trap of Event: DSL ES (digital subscriber line errors seconds)"
        ::= { optixTrapsPER 180 }

    -- 1.3.6.1.4.1.2011.2.25.3.40.40.30.181
    pmDslSes NOTIFICATION-TYPE
        OBJECTS{ rptEvtPeriod,rptEvtValue,rptEvtVldty,rptEvtDateTime,rptEvtObjType,rptEvtParaLen,rptEvtPara }
        STATUS current
        DESCRIPTION
            "Trap of Event: DSL SES (digital subscriber line severe  errors  seconds)"
        ::= { optixTrapsPER 181 }

    -- 1.3.6.1.4.1.2011.2.25.3.40.40.30.182
    pmDslUas NOTIFICATION-TYPE
        OBJECTS{ rptEvtPeriod,rptEvtValue,rptEvtVldty,rptEvtDateTime,rptEvtObjType,rptEvtParaLen,rptEvtPara }
        STATUS current
        DESCRIPTION
            "Trap of Event: DSL UAS  (digital subscriber line unuse  access  seconds)"
        ::= { optixTrapsPER 182 }

    -- 1.3.6.1.4.1.2011.2.25.3.40.40.30.183
    pmDslLpa NOTIFICATION-TYPE
        OBJECTS{ rptEvtPeriod,rptEvtValue,rptEvtVldty,rptEvtDateTime,rptEvtObjType,rptEvtParaLen,rptEvtPara }
        STATUS current
        DESCRIPTION
            "Trap of Event: DSL  current loop path attenuation"
        ::= { optixTrapsPER 183 }

    -- 1.3.6.1.4.1.2011.2.25.3.40.40.30.184
    pmDslSnr NOTIFICATION-TYPE
        OBJECTS{ rptEvtPeriod,rptEvtValue,rptEvtVldty,rptEvtDateTime,rptEvtObjType,rptEvtParaLen,rptEvtPara }
        STATUS current
        DESCRIPTION
            "Trap of Event: DSL  current  sigal noise rations"
        ::= { optixTrapsPER 184 }

    -- 1.3.6.1.4.1.2011.2.25.3.40.40.30.192
    pmPmutmpmax NOTIFICATION-TYPE
        OBJECTS{ rptEvtPeriod,rptEvtValue,rptEvtVldty,rptEvtDateTime,rptEvtObjType,rptEvtParaLen,rptEvtPara }
        STATUS current
        DESCRIPTION
            "Trap of Event:PMU Temperature Maximum"
        ::= { optixTrapsPER 192 }

    -- 1.3.6.1.4.1.2011.2.25.3.40.40.30.193
    pmPmutmpmin NOTIFICATION-TYPE
        OBJECTS{ rptEvtPeriod,rptEvtValue,rptEvtVldty,rptEvtDateTime,rptEvtObjType,rptEvtParaLen,rptEvtPara }
        STATUS current
        DESCRIPTION
            "Trap of Event:PMU Temperature Minimum"
        ::= { optixTrapsPER 193 }

    -- 1.3.6.1.4.1.2011.2.25.3.40.40.30.194
    pmPmutmpavg NOTIFICATION-TYPE
        OBJECTS{ rptEvtPeriod,rptEvtValue,rptEvtVldty,rptEvtDateTime,rptEvtObjType,rptEvtParaLen,rptEvtPara }
        STATUS current
        DESCRIPTION
            "Trap of Event:PMU Temperature Cur-Value"
        ::= { optixTrapsPER 194 }

    -- 1.3.6.1.4.1.2011.2.25.3.40.40.30.198
    pmLsOopMax NOTIFICATION-TYPE
        OBJECTS{ rptEvtPeriod,rptEvtValue,rptEvtVldty,rptEvtDateTime,rptEvtObjType,rptEvtParaLen,rptEvtPara }
        STATUS current
        DESCRIPTION
            "Trap of Event:Laser Output Of Power Maximum"
        ::= { optixTrapsPER 198 }

    -- 1.3.6.1.4.1.2011.2.25.3.40.40.30.199
    pmLsOopMin NOTIFICATION-TYPE
        OBJECTS{ rptEvtPeriod,rptEvtValue,rptEvtVldty,rptEvtDateTime,rptEvtObjType,rptEvtParaLen,rptEvtPara }
        STATUS current
        DESCRIPTION
            "Trap of Event:Laser Output Of Power Minimum"
        ::= { optixTrapsPER 199 }

    -- 1.3.6.1.4.1.2011.2.25.3.40.40.30.200
    pmLsOopCur NOTIFICATION-TYPE
        OBJECTS{ rptEvtPeriod,rptEvtValue,rptEvtVldty,rptEvtDateTime,rptEvtObjType,rptEvtParaLen,rptEvtPara }
        STATUS current
        DESCRIPTION
            "Trap of Event:Laser Output Of Power Cur-Value"
        ::= { optixTrapsPER 200 }

    -- 1.3.6.1.4.1.2011.2.25.3.40.40.30.201
    pmLsIopMax NOTIFICATION-TYPE
        OBJECTS{ rptEvtPeriod,rptEvtValue,rptEvtVldty,rptEvtDateTime,rptEvtObjType,rptEvtParaLen,rptEvtPara }
        STATUS current
        DESCRIPTION
            "Trap of Event:Laser Input Of Power Maximum"
        ::= { optixTrapsPER 201 }

    -- 1.3.6.1.4.1.2011.2.25.3.40.40.30.202
    pmLsIopMin NOTIFICATION-TYPE
        OBJECTS{ rptEvtPeriod,rptEvtValue,rptEvtVldty,rptEvtDateTime,rptEvtObjType,rptEvtParaLen,rptEvtPara }
        STATUS current
        DESCRIPTION
            "Trap of Event:Laser Input Of Power Minimum"
        ::= { optixTrapsPER 202 }

    -- 1.3.6.1.4.1.2011.2.25.3.40.40.30.203
    pmLsIopCur NOTIFICATION-TYPE
        OBJECTS{ rptEvtPeriod,rptEvtValue,rptEvtVldty,rptEvtDateTime,rptEvtObjType,rptEvtParaLen,rptEvtPara }
        STATUS current
        DESCRIPTION
            "Trap of Event:Laser Input Of Power Cur-Value"
        ::= { optixTrapsPER 203 }

    -- 1.3.6.1.4.1.2011.2.25.3.40.40.30.204
    pmLsTmpMax NOTIFICATION-TYPE
        OBJECTS{ rptEvtPeriod,rptEvtValue,rptEvtVldty,rptEvtDateTime,rptEvtObjType,rptEvtParaLen,rptEvtPara }
        STATUS current
        DESCRIPTION
            "Trap of Event:Laser Working Temperature Maximum"
        ::= { optixTrapsPER 204 }

    -- 1.3.6.1.4.1.2011.2.25.3.40.40.30.205
    pmLsTmpMin NOTIFICATION-TYPE
        OBJECTS{ rptEvtPeriod,rptEvtValue,rptEvtVldty,rptEvtDateTime,rptEvtObjType,rptEvtParaLen,rptEvtPara }
        STATUS current
        DESCRIPTION
            "Trap of Event:Laser Working Temperature Minimum"
        ::= { optixTrapsPER 205 }

    -- 1.3.6.1.4.1.2011.2.25.3.40.40.30.206
    pmLsTmpCur NOTIFICATION-TYPE
        OBJECTS{ rptEvtPeriod,rptEvtValue,rptEvtVldty,rptEvtDateTime,rptEvtObjType,rptEvtParaLen,rptEvtPara }
        STATUS current
        DESCRIPTION
            "Trap of Event:Laser Working Temperature Cur-Value"
        ::= { optixTrapsPER 206 }

    -- 1.3.6.1.4.1.2011.2.25.3.40.40.30.207
    pmLsBiasMax NOTIFICATION-TYPE
        OBJECTS{ rptEvtPeriod,rptEvtValue,rptEvtVldty,rptEvtDateTime,rptEvtObjType,rptEvtParaLen,rptEvtPara }
        STATUS current
        DESCRIPTION
            "Trap of Event:Laser bias Current Maximum"
        ::= { optixTrapsPER 207 }

    -- 1.3.6.1.4.1.2011.2.25.3.40.40.30.208
    pmLsBiasMin NOTIFICATION-TYPE
        OBJECTS{ rptEvtPeriod,rptEvtValue,rptEvtVldty,rptEvtDateTime,rptEvtObjType,rptEvtParaLen,rptEvtPara }
        STATUS current
        DESCRIPTION
            "Trap of Event:Laser bias Current Minimum"
        ::= { optixTrapsPER 208 }

    -- 1.3.6.1.4.1.2011.2.25.3.40.40.30.209
    pmLsBiasCur NOTIFICATION-TYPE
        OBJECTS{ rptEvtPeriod,rptEvtValue,rptEvtVldty,rptEvtDateTime,rptEvtObjType,rptEvtParaLen,rptEvtPara }
        STATUS current
        DESCRIPTION
            "Trap of Event:Laser bias Current Cur-Value"
        ::= { optixTrapsPER 209 }

    -- 1.3.6.1.4.1.2011.2.25.3.40.40.30.216
    pmPumptmpmax NOTIFICATION-TYPE
        OBJECTS{ rptEvtPeriod,rptEvtValue,rptEvtVldty,rptEvtDateTime,rptEvtObjType,rptEvtParaLen,rptEvtPara }
        STATUS current
        DESCRIPTION
            "Trap of Event:Pump Working Temperature Maximum"
        ::= { optixTrapsPER 216 }

    -- 1.3.6.1.4.1.2011.2.25.3.40.40.30.217
    pmPumptmpmin NOTIFICATION-TYPE
        OBJECTS{ rptEvtPeriod,rptEvtValue,rptEvtVldty,rptEvtDateTime,rptEvtObjType,rptEvtParaLen,rptEvtPara }
        STATUS current
        DESCRIPTION
            "Trap of Event:Pump Working Temperature Minimum"
        ::= { optixTrapsPER 217 }

    -- 1.3.6.1.4.1.2011.2.25.3.40.40.30.218
    pmPumptmpcur NOTIFICATION-TYPE
        OBJECTS{ rptEvtPeriod,rptEvtValue,rptEvtVldty,rptEvtDateTime,rptEvtObjType,rptEvtParaLen,rptEvtPara }
        STATUS current
        DESCRIPTION
            "Trap of Event:Pump Working Temperature Cur-Value"
        ::= { optixTrapsPER 218 }

    -- 1.3.6.1.4.1.2011.2.25.3.40.40.30.219
    pmPumpbisamax NOTIFICATION-TYPE
        OBJECTS{ rptEvtPeriod,rptEvtValue,rptEvtVldty,rptEvtDateTime,rptEvtObjType,rptEvtParaLen,rptEvtPara }
        STATUS current
        DESCRIPTION
            "Trap of Event:Pump Bias Current Maximum"
        ::= { optixTrapsPER 219 }

    -- 1.3.6.1.4.1.2011.2.25.3.40.40.30.220
    pmPumpbisamin NOTIFICATION-TYPE
        OBJECTS{ rptEvtPeriod,rptEvtValue,rptEvtVldty,rptEvtDateTime,rptEvtObjType,rptEvtParaLen,rptEvtPara }
        STATUS current
        DESCRIPTION
            "Trap of Event:Pump Bias Current Minimum"
        ::= { optixTrapsPER 220 }

    -- 1.3.6.1.4.1.2011.2.25.3.40.40.30.221
    pmPumpbisacur NOTIFICATION-TYPE
        OBJECTS{ rptEvtPeriod,rptEvtValue,rptEvtVldty,rptEvtDateTime,rptEvtObjType,rptEvtParaLen,rptEvtPara }
        STATUS current
        DESCRIPTION
            "Trap of Event:Pump Bias Current Cur-Value"
        ::= { optixTrapsPER 221 }

    -- 1.3.6.1.4.1.2011.2.25.3.40.40.30.4128
    pmLspOk NOTIFICATION-TYPE
        OBJECTS{ rptEvtPeriod,rptEvtValue,rptEvtVldty,rptEvtDateTime,rptEvtObjType,rptEvtParaLen,rptEvtPara }
        STATUS current
        DESCRIPTION
            "Trap of Event:Times of LSP connect successful"
        ::= { optixTrapsPER 4128 }

    -- 1.3.6.1.4.1.2011.2.25.3.40.40.30.4129
    pmLspFail NOTIFICATION-TYPE
        OBJECTS{ rptEvtPeriod,rptEvtValue,rptEvtVldty,rptEvtDateTime,rptEvtObjType,rptEvtParaLen,rptEvtPara }
        STATUS current
        DESCRIPTION
            "Trap of Event:Times of LSP connect failure"
        ::= { optixTrapsPER 4129 }

    -- 1.3.6.1.4.1.2011.2.25.3.40.40.30.4175
    pmPumpdrvcmax NOTIFICATION-TYPE
        OBJECTS{ rptEvtPeriod,rptEvtValue,rptEvtVldty,rptEvtDateTime,rptEvtObjType,rptEvtParaLen,rptEvtPara }
        STATUS current
        DESCRIPTION
            "Trap of Event:MAX Module Drive Current"
        ::= { optixTrapsPER 4175 }

    -- 1.3.6.1.4.1.2011.2.25.3.40.40.30.4176
    pmPumpdrvcmin NOTIFICATION-TYPE
        OBJECTS{ rptEvtPeriod,rptEvtValue,rptEvtVldty,rptEvtDateTime,rptEvtObjType,rptEvtParaLen,rptEvtPara }
        STATUS current
        DESCRIPTION
            "Trap of Event: MIN Module Drive Current"
        ::= { optixTrapsPER 4176 }

    -- 1.3.6.1.4.1.2011.2.25.3.40.40.30.4177
    pmPumpdrvccur NOTIFICATION-TYPE
        OBJECTS{ rptEvtPeriod,rptEvtValue,rptEvtVldty,rptEvtDateTime,rptEvtObjType,rptEvtParaLen,rptEvtPara }
        STATUS current
        DESCRIPTION
            "Trap of Event:Current Module Drive Current"
        ::= { optixTrapsPER 4177 }

    -- 1.3.6.1.4.1.2011.2.25.3.40.40.30.4178
    pmPumpdrvvgmax NOTIFICATION-TYPE
        OBJECTS{ rptEvtPeriod,rptEvtValue,rptEvtVldty,rptEvtDateTime,rptEvtObjType,rptEvtParaLen,rptEvtPara }
        STATUS current
        DESCRIPTION
            "Trap of Event:MAX Module Drive Voltage"
        ::= { optixTrapsPER 4178 }

    -- 1.3.6.1.4.1.2011.2.25.3.40.40.30.4179
    pmPumpdrvvgmin NOTIFICATION-TYPE
        OBJECTS{ rptEvtPeriod,rptEvtValue,rptEvtVldty,rptEvtDateTime,rptEvtObjType,rptEvtParaLen,rptEvtPara }
        STATUS current
        DESCRIPTION
            "Trap of Event:MIN Module Drive Voltage"
        ::= { optixTrapsPER 4179 }

    -- 1.3.6.1.4.1.2011.2.25.3.40.40.30.4180
    pmPumpdrvvgcur NOTIFICATION-TYPE
        OBJECTS{ rptEvtPeriod,rptEvtValue,rptEvtVldty,rptEvtDateTime,rptEvtObjType,rptEvtParaLen,rptEvtPara }
        STATUS current
        DESCRIPTION
            "Trap of Event:Current Module Drive Voltage"
        ::= { optixTrapsPER 4180 }

    -- 1.3.6.1.4.1.2011.2.25.3.40.40.30.15895
    pmTxBwutilExcs NOTIFICATION-TYPE
        OBJECTS{ rptEvtPeriod,rptEvtValue,rptEvtVldty,rptEvtDateTime,rptEvtObjType,rptEvtParaLen,rptEvtPara }
        STATUS current
        DESCRIPTION
            "Trap of Event:TX Bandwidth Utilization Threshold-Crossing Second"
        ::= { optixTrapsPER 15895 }

    -- 1.3.6.1.4.1.2011.2.25.3.40.40.30.15896
    pmRxBwutilExcs NOTIFICATION-TYPE
        OBJECTS{ rptEvtPeriod,rptEvtValue,rptEvtVldty,rptEvtDateTime,rptEvtObjType,rptEvtParaLen,rptEvtPara }
        STATUS current
        DESCRIPTION
            "Trap of Event:RX Bandwidth Utilization Threshold-Crossing Second"
        ::= { optixTrapsPER 15896 }

    -- 1.3.6.1.4.1.2011.2.25.3.40.40.30.15897
    pmBpskS62p5mWs NOTIFICATION-TYPE
        OBJECTS{ rptEvtPeriod,rptEvtValue,rptEvtVldty,rptEvtDateTime,rptEvtObjType,rptEvtParaLen,rptEvtPara }
        STATUS current
        DESCRIPTION
            "Trap of Event:BPSK Work Second in 62.5M Bandwidth"
        ::= { optixTrapsPER 15897 }

    -- 1.3.6.1.4.1.2011.2.25.3.40.40.30.15898
    pmBpskS125mWs NOTIFICATION-TYPE
        OBJECTS{ rptEvtPeriod,rptEvtValue,rptEvtVldty,rptEvtDateTime,rptEvtObjType,rptEvtParaLen,rptEvtPara }
        STATUS current
        DESCRIPTION
            "Trap of Event:BPSK Work Second in 125M Bandwidth"
        ::= { optixTrapsPER 15898 }	

    -- 1.3.6.1.4.1.2011.2.25.3.40.40.30.15899
    pmPskWs8 NOTIFICATION-TYPE
        OBJECTS{ rptEvtPeriod,rptEvtValue,rptEvtVldty,rptEvtDateTime,rptEvtObjType,rptEvtParaLen,rptEvtPara }
        STATUS current
        DESCRIPTION
            "Trap of Event:PSKWS8"
        ::= { optixTrapsPER 15899 }

    -- 1.3.6.1.4.1.2011.2.25.3.40.40.30.15903
    pmTolLdpwr NOTIFICATION-TYPE
        OBJECTS{ rptEvtPeriod,rptEvtValue,rptEvtVldty,rptEvtDateTime,rptEvtObjType,rptEvtParaLen,rptEvtPara }
        STATUS current
        DESCRIPTION
            "Trap of Event:TOL_LDPWR"
        ::= { optixTrapsPER 15903 }

    -- 1.3.6.1.4.1.2011.2.25.3.40.40.30.15904
    pmBatvoltcur NOTIFICATION-TYPE
        OBJECTS{ rptEvtPeriod,rptEvtValue,rptEvtVldty,rptEvtDateTime,rptEvtObjType,rptEvtParaLen,rptEvtPara }
        STATUS current
        DESCRIPTION
            "Trap of Event:BATVOLTCUR"
        ::= { optixTrapsPER 15904 }

    -- 1.3.6.1.4.1.2011.2.25.3.40.40.30.15905
    pmBatvoltmin NOTIFICATION-TYPE
        OBJECTS{ rptEvtPeriod,rptEvtValue,rptEvtVldty,rptEvtDateTime,rptEvtObjType,rptEvtParaLen,rptEvtPara }
        STATUS current
        DESCRIPTION
            "Trap of Event:BATVOLTMIN"
        ::= { optixTrapsPER 15905 }

    -- 1.3.6.1.4.1.2011.2.25.3.40.40.30.15906
    pmBatvoltmax NOTIFICATION-TYPE
        OBJECTS{ rptEvtPeriod,rptEvtValue,rptEvtVldty,rptEvtDateTime,rptEvtObjType,rptEvtParaLen,rptEvtPara }
        STATUS current
        DESCRIPTION
            "Trap of Event:BATVOLTMAX"
        ::= { optixTrapsPER 15906 }

    -- 1.3.6.1.4.1.2011.2.25.3.40.40.30.15907
    pmAcvoltcur NOTIFICATION-TYPE
        OBJECTS{ rptEvtPeriod,rptEvtValue,rptEvtVldty,rptEvtDateTime,rptEvtObjType,rptEvtParaLen,rptEvtPara }
        STATUS current
        DESCRIPTION
            "Trap of Event:ACVOLTCUR"
        ::= { optixTrapsPER 15907 }

    -- 1.3.6.1.4.1.2011.2.25.3.40.40.30.15908
    pmAcvoltmin NOTIFICATION-TYPE
        OBJECTS{ rptEvtPeriod,rptEvtValue,rptEvtVldty,rptEvtDateTime,rptEvtObjType,rptEvtParaLen,rptEvtPara }
        STATUS current
        DESCRIPTION
            "Trap of Event:ACVOLTMIN"
        ::= { optixTrapsPER 15908 }

    -- 1.3.6.1.4.1.2011.2.25.3.40.40.30.15909
    pmAcvlotmax NOTIFICATION-TYPE
        OBJECTS{ rptEvtPeriod,rptEvtValue,rptEvtVldty,rptEvtDateTime,rptEvtObjType,rptEvtParaLen,rptEvtPara }
        STATUS current
        DESCRIPTION
            "Trap of Event:ACVOLTMAX"
        ::= { optixTrapsPER 15909 }

    -- 1.3.6.1.4.1.2011.2.25.3.40.40.30.15910
    pmTolAcpwr NOTIFICATION-TYPE
        OBJECTS{ rptEvtPeriod,rptEvtValue,rptEvtVldty,rptEvtDateTime,rptEvtObjType,rptEvtParaLen,rptEvtPara }
        STATUS current
        DESCRIPTION
            "Trap of Event:TOL_ACPWR"
        ::= { optixTrapsPER 15910 }

    -- 1.3.6.1.4.1.2011.2.25.3.40.40.30.15911
    pmTolSolcurnt NOTIFICATION-TYPE
        OBJECTS{ rptEvtPeriod,rptEvtValue,rptEvtVldty,rptEvtDateTime,rptEvtObjType,rptEvtParaLen,rptEvtPara }
        STATUS current
        DESCRIPTION
            "Trap of Event:TOL_SOLCURNT"
        ::= { optixTrapsPER 15911 }

    -- 1.3.6.1.4.1.2011.2.25.3.40.40.30.15912
    pmTolSoloutpwr NOTIFICATION-TYPE
        OBJECTS{ rptEvtPeriod,rptEvtValue,rptEvtVldty,rptEvtDateTime,rptEvtObjType,rptEvtParaLen,rptEvtPara }
        STATUS current
        DESCRIPTION
            "Trap of Event:TOL_SOLOUTPWR"
        ::= { optixTrapsPER 15912 }

    -- 1.3.6.1.4.1.2011.2.25.3.40.40.30.16079
    pmQamws8192 NOTIFICATION-TYPE
        OBJECTS{ rptEvtPeriod,rptEvtValue,rptEvtVldty,rptEvtDateTime,rptEvtObjType,rptEvtParaLen,rptEvtPara }
        STATUS current
        DESCRIPTION
            "Trap of Event:8192QAM Working Second"
        ::= { optixTrapsPER 16079 }

    -- 1.3.6.1.4.1.2011.2.25.3.40.40.30.16080
    pmTxBwutilExcsMin NOTIFICATION-TYPE
        OBJECTS{ rptEvtPeriod,rptEvtValue,rptEvtVldty,rptEvtDateTime,rptEvtObjType,rptEvtParaLen,rptEvtPara }
        STATUS current
        DESCRIPTION
            "Trap of Event:TX Bandwidth Utilization Threshold-Crossing Second"
        ::= { optixTrapsPER 16080 }

    -- 1.3.6.1.4.1.2011.2.25.3.40.40.30.16081
    pmRxBwutilExcsMin NOTIFICATION-TYPE
        OBJECTS{ rptEvtPeriod,rptEvtValue,rptEvtVldty,rptEvtDateTime,rptEvtObjType,rptEvtParaLen,rptEvtPara }
        STATUS current
        DESCRIPTION
            "Trap of Event:RX Bandwidth Utilization Threshold-Crossing Second"
        ::= { optixTrapsPER 16081 }

    -- 1.3.6.1.4.1.2011.2.25.3.40.40.30.16082
    pmTxBwutilExcsMid NOTIFICATION-TYPE
        OBJECTS{ rptEvtPeriod,rptEvtValue,rptEvtVldty,rptEvtDateTime,rptEvtObjType,rptEvtParaLen,rptEvtPara }
        STATUS current
        DESCRIPTION
            "Trap of Event:TX Bandwidth Utilization Threshold-Crossing Second"
        ::= { optixTrapsPER 16082 }

    -- 1.3.6.1.4.1.2011.2.25.3.40.40.30.16083
    pmRxBwutilExcsMid NOTIFICATION-TYPE
        OBJECTS{ rptEvtPeriod,rptEvtValue,rptEvtVldty,rptEvtDateTime,rptEvtObjType,rptEvtParaLen,rptEvtPara }
        STATUS current
        DESCRIPTION
            "Trap of Event:TX Bandwidth Utilization Threshold-Crossing Second"
        ::= { optixTrapsPER 16083 }

    -- 1.3.6.1.4.1.2011.2.25.3.40.40.30.16084
    pmTxBwutilExcsMax NOTIFICATION-TYPE
        OBJECTS{ rptEvtPeriod,rptEvtValue,rptEvtVldty,rptEvtDateTime,rptEvtObjType,rptEvtParaLen,rptEvtPara }
        STATUS current
        DESCRIPTION
            "Trap of Event:TX Bandwidth Utilization Threshold-Crossing Second"
        ::= { optixTrapsPER 16084 }

    -- 1.3.6.1.4.1.2011.2.25.3.40.40.30.16085
    pmRxBwutilExcsMax NOTIFICATION-TYPE
        OBJECTS{ rptEvtPeriod,rptEvtValue,rptEvtVldty,rptEvtDateTime,rptEvtObjType,rptEvtParaLen,rptEvtPara }
        STATUS current
        DESCRIPTION
            "Trap of Event:RX Bandwidth Utilization Threshold-Crossing Second"
        ::= { optixTrapsPER 16085 }

    -- 1.3.6.1.4.1.2011.2.25.3.40.40.30.16108
    pmQAMWS16384 NOTIFICATION-TYPE
        OBJECTS{ rptEvtPeriod,rptEvtValue,rptEvtVldty,rptEvtDateTime,rptEvtObjType,rptEvtParaLen,rptEvtPara }
        STATUS current
        DESCRIPTION
            "Trap of Event:16384QAM Working Second"
        ::= { optixTrapsPER 16108 }

    -- 1.3.6.1.4.1.2011.2.25.3.40.40.30.8587
    pmCrc6Err NOTIFICATION-TYPE
        OBJECTS{ rptEvtPeriod,rptEvtValue,rptEvtVldty,rptEvtDateTime,rptEvtObjType,rptEvtParaLen,rptEvtPara }
        STATUS current
        DESCRIPTION
            "Trap of Event:errors of CRC6 check"
        ::= { optixTrapsPER 8587 }
		
    -- 1.3.6.1.4.1.2011.2.25.3.40.40.30.16086
    pmRealPowerMax NOTIFICATION-TYPE
        OBJECTS{ rptEvtPeriod,rptEvtValue,rptEvtVldty,rptEvtDateTime,rptEvtObjType,rptEvtParaLen,rptEvtPara }
        STATUS current
        DESCRIPTION
            "Trap of Event:Maximum value of real power during a period"
        ::= { optixTrapsPER 16086 }	
	-- 1.3.6.1.4.1.2011.2.25.3.40.40.30.16087
    pmRealPowerMin NOTIFICATION-TYPE
        OBJECTS{ rptEvtPeriod,rptEvtValue,rptEvtVldty,rptEvtDateTime,rptEvtObjType,rptEvtParaLen,rptEvtPara }
        STATUS current
        DESCRIPTION
            "Trap of Event:Minimum value of real power during a period"
        ::= { optixTrapsPER 16087 }	
	-- 1.3.6.1.4.1.2011.2.25.3.40.40.30.16088
    pmRealPowerCur NOTIFICATION-TYPE
        OBJECTS{ rptEvtPeriod,rptEvtValue,rptEvtVldty,rptEvtDateTime,rptEvtObjType,rptEvtParaLen,rptEvtPara }
        STATUS current
        DESCRIPTION
            "Trap of Event:Current value of real power"
        ::= { optixTrapsPER 16088 }	
	-- 1.3.6.1.4.1.2011.2.25.3.40.40.30.16089
    pmRealPowerAvg NOTIFICATION-TYPE
        OBJECTS{ rptEvtPeriod,rptEvtValue,rptEvtVldty,rptEvtDateTime,rptEvtObjType,rptEvtParaLen,rptEvtPara }
        STATUS current
        DESCRIPTION
            "Trap of Event:Average value of real power during a period"
        ::= { optixTrapsPER 16089 }	
	-- 1.3.6.1.4.1.2011.2.25.3.40.40.30.16090
    pmNomiPowerMax NOTIFICATION-TYPE
        OBJECTS{ rptEvtPeriod,rptEvtValue,rptEvtVldty,rptEvtDateTime,rptEvtObjType,rptEvtParaLen,rptEvtPara }
        STATUS current
        DESCRIPTION
            "Trap of Event:Maximum value of nominal power during a period"
        ::= { optixTrapsPER 16090 }	
	-- 1.3.6.1.4.1.2011.2.25.3.40.40.30.16091
    pmNomiPowerMin NOTIFICATION-TYPE
        OBJECTS{ rptEvtPeriod,rptEvtValue,rptEvtVldty,rptEvtDateTime,rptEvtObjType,rptEvtParaLen,rptEvtPara }
        STATUS current
        DESCRIPTION
            "Trap of Event:Minimum value of nominal power during a period"
        ::= { optixTrapsPER 16091 }	
	-- 1.3.6.1.4.1.2011.2.25.3.40.40.30.16092
    pmNomiPowerCur NOTIFICATION-TYPE
        OBJECTS{ rptEvtPeriod,rptEvtValue,rptEvtVldty,rptEvtDateTime,rptEvtObjType,rptEvtParaLen,rptEvtPara }
        STATUS current
        DESCRIPTION
            "Trap of Event:Current value of nominal power"
        ::= { optixTrapsPER 16092 }	
	-- 1.3.6.1.4.1.2011.2.25.3.40.40.30.16093
    pmNomiPowerAvg NOTIFICATION-TYPE
        OBJECTS{ rptEvtPeriod,rptEvtValue,rptEvtVldty,rptEvtDateTime,rptEvtObjType,rptEvtParaLen,rptEvtPara }
        STATUS current
        DESCRIPTION
            "Trap of Event:Average value of nominal power during a period"
        ::= { optixTrapsPER 16093 }
        -- 1.3.6.1.4.1.2011.2.25.3.40.40.30.16167
    pmMimoCapacityCur NOTIFICATION-TYPE
        OBJECTS{ rptEvtPeriod,rptEvtValue,rptEvtVldty,rptEvtDateTime,rptEvtObjType,rptEvtParaLen,rptEvtPara }
        STATUS current
        DESCRIPTION 
            "Trap of Event:Current value of mimo capacity"
        ::= { optixTrapsPER 16167 }	
	-- 1.3.6.1.4.1.2011.2.25.3.40.40.30.16168
    pmMimoCapacityMin NOTIFICATION-TYPE
        OBJECTS{ rptEvtPeriod,rptEvtValue,rptEvtVldty,rptEvtDateTime,rptEvtObjType,rptEvtParaLen,rptEvtPara }
        STATUS current
        DESCRIPTION
            "Trap of Event:Minimum value of mimo capacity during a period"
        ::= { optixTrapsPER 16168 }	
	-- 1.3.6.1.4.1.2011.2.25.3.40.40.30.16169
    pmMimoCapacityMax NOTIFICATION-TYPE
        OBJECTS{ rptEvtPeriod,rptEvtValue,rptEvtVldty,rptEvtDateTime,rptEvtObjType,rptEvtParaLen,rptEvtPara }
        STATUS current
        DESCRIPTION
            "Trap of Event:Maximum value of mimo capacity during a period"
        ::= { optixTrapsPER 16169 }	
	-- 1.3.6.1.4.1.2011.2.25.3.40.40.30.16170
    pmMimoCapacityAvg NOTIFICATION-TYPE
        OBJECTS{ rptEvtPeriod,rptEvtValue,rptEvtVldty,rptEvtDateTime,rptEvtObjType,rptEvtParaLen,rptEvtPara }
        STATUS current
        DESCRIPTION
            "Trap of Event:Average value of mimo capacity during a period"
        ::= { optixTrapsPER 16170 }
    -- 1.3.6.1.4.1.2011.2.25.3.40.40.30.16208
    pmVDeflectMax NOTIFICATION-TYPE
        OBJECTS{ rptEvtPeriod,rptEvtValue,rptEvtVldty,rptEvtDateTime,rptEvtObjType,rptEvtParaLen,rptEvtPara }
        STATUS current
        DESCRIPTION
            "Trap of Event:Maximum value of the antenna deflection degree in the vertical direction."
        ::= { optixTrapsPER 16208 }
    -- 1.3.6.1.4.1.2011.2.25.3.40.40.30.16209
    pmVDeflectMin NOTIFICATION-TYPE
        OBJECTS{ rptEvtPeriod,rptEvtValue,rptEvtVldty,rptEvtDateTime,rptEvtObjType,rptEvtParaLen,rptEvtPara }
        STATUS current
        DESCRIPTION
            "Trap of Event:Minimum value of the antenna deflection degree in the vertical direction."
        ::= { optixTrapsPER 16209 }
    -- 1.3.6.1.4.1.2011.2.25.3.40.40.30.16210
    pmVDeflectCur NOTIFICATION-TYPE
        OBJECTS{ rptEvtPeriod,rptEvtValue,rptEvtVldty,rptEvtDateTime,rptEvtObjType,rptEvtParaLen,rptEvtPara }
        STATUS current
        DESCRIPTION
            "Trap of Event:Current value of the antenna deflection degree in the vertical direction."
        ::= { optixTrapsPER 16210 }
    -- 1.3.6.1.4.1.2011.2.25.3.40.40.30.16211
    pmShakeCount NOTIFICATION-TYPE
        OBJECTS{ rptEvtPeriod,rptEvtValue,rptEvtVldty,rptEvtDateTime,rptEvtObjType,rptEvtParaLen,rptEvtPara }
        STATUS current
        DESCRIPTION
            "Trap of Event:Antenna shaking count."
        ::= { optixTrapsPER 16211 }
	-- 1.3.6.1.4.1.2011.2.25.3.40.40.30.16233
    pmHDeflectMax NOTIFICATION-TYPE
        OBJECTS{ rptEvtPeriod,rptEvtValue,rptEvtVldty,rptEvtDateTime,rptEvtObjType,rptEvtParaLen,rptEvtPara }
        STATUS current
        DESCRIPTION
            "Trap of Event:Maximum value of the antenna deflection degree in the horizontal  direction."
        ::= { optixTrapsPER 16233 }
    -- 1.3.6.1.4.1.2011.2.25.3.40.40.30.16234
    pmHDeflectMin NOTIFICATION-TYPE
        OBJECTS{ rptEvtPeriod,rptEvtValue,rptEvtVldty,rptEvtDateTime,rptEvtObjType,rptEvtParaLen,rptEvtPara }
        STATUS current
        DESCRIPTION
            "Trap of Event:Minimum value of the antenna deflection degree in the horizontal  direction."
        ::= { optixTrapsPER 16234 }
    -- 1.3.6.1.4.1.2011.2.25.3.40.40.30.16235
    pmHDeflectCur NOTIFICATION-TYPE
        OBJECTS{ rptEvtPeriod,rptEvtValue,rptEvtVldty,rptEvtDateTime,rptEvtObjType,rptEvtParaLen,rptEvtPara }
        STATUS current
        DESCRIPTION
            "Trap of Event:Current value of the antenna deflection degree in the horizontal  direction."
        ::= { optixTrapsPER 16235 }
	-- 1.3.6.1.4.1.2011.2.25.3.40.40.30.16241
    pmVDeflectTs NOTIFICATION-TYPE
        OBJECTS{ rptEvtPeriod,rptEvtValue,rptEvtVldty,rptEvtDateTime,rptEvtObjType,rptEvtParaLen,rptEvtPara }
        STATUS current
        DESCRIPTION
            "Trap of Event:Vertical deflection angle threshold second."
        ::= { optixTrapsPER 16241 }
	
	-- 1.3.6.1.4.1.2011.2.25.3.40.40.30.16449
    pmIntternalAngleMax NOTIFICATION-TYPE
        OBJECTS{ rptEvtPeriod,rptEvtValue,rptEvtVldty,rptEvtDateTime,rptEvtObjType,rptEvtParaLen,rptEvtPara }
        STATUS current
        DESCRIPTION
            "Trap of Event:Maximum value of actual motor angle."
        ::= { optixTrapsPER 16449 }
	-- 1.3.6.1.4.1.2011.2.25.3.40.40.30.16450
    pmIntternalAngleMin NOTIFICATION-TYPE
        OBJECTS{ rptEvtPeriod,rptEvtValue,rptEvtVldty,rptEvtDateTime,rptEvtObjType,rptEvtParaLen,rptEvtPara }
        STATUS current
        DESCRIPTION
            "Trap of Event:Minimum value of actual motor angle."
        ::= { optixTrapsPER 16450 }
	-- 1.3.6.1.4.1.2011.2.25.3.40.40.30.16451
    pmIntternalAngleCur NOTIFICATION-TYPE
        OBJECTS{ rptEvtPeriod,rptEvtValue,rptEvtVldty,rptEvtDateTime,rptEvtObjType,rptEvtParaLen,rptEvtPara }
        STATUS current
        DESCRIPTION
            "Trap of Event:Current value of actual motor angle."
        ::= { optixTrapsPER 16451 }
		
    -- 1.3.6.1.4.1.2011.2.25.3.40.40.100
    optixRtnPerTrapConformance OBJECT IDENTIFIER ::= { optixGlobalTrap 100 }

    -- 1.3.6.1.4.1.2011.2.25.3.40.40.100.1
    optixRtnPerTrapGroups OBJECT IDENTIFIER ::= { optixRtnPerTrapConformance 1 }

    -- 1.3.6.1.4.1.2011.2.25.3.40.40.100.1.1
    optixRtnPerTrapObjectGroup OBJECT-GROUP
        OBJECTS { pmRsBbe,pmRsEs,pmRsSes,pmRsOof,pmRsOfs,pmRsUas,pmRsCses,pmE1LcvSdh,pmE1LesSdh,pmE1LsesSdh,pmE1LLossSdh,pmMsBbe,pmMsEs,pmMsSes,pmMsFeBbe,pmMsFeEs,pmMsFeSes,pmMsUas,pmMsCses,pmMsFeCses,pmMsFeUas,pmAupjcHigh,pmAupjcLow,pmAupjcNew,pmHpBbe,pmHpEs,pmHpSes,pmHpFeBbe,pmHpFeEs,pmHpFeSes,pmHpUas,pmHpCses,pmHpFeCses,pmHpFeUas,pmTlbMax,pmTlbMin,pmTlbCur,pmTplMax,pmTplMin,pmTplCur,pmRplMax,pmRplMin,pmRplCur, pmOspiTmpMax,pmOspiTmpMin,pmOspiTmpCur,pmFecCorByteCnt,pmFecUncorBlockCnt,pmLpFeUas,pmLpBbe,pmLpEs,pmLpSes,pmLpFeBbe,pmLpFeEs,pmLpFeSes,pmLpUas,pmLpCses,pmLpFeCses,pmT1LcvSdh,pmT1LesSdh,pmT1LsesSdh,pmTupjcHigh,pmTupjcLow,pmTupjcNew,pmFecBefCorEr,pmAmDownCnt,pmAmUpCnt,pmRslMax,pmRslMin,pmRslCur,pmTslMax,pmTslMin,pmTslCur,pmCpuUsageMax,pmCpuUsageMin,pmCpuUsageCur,pmCpuUsageAvg,pmMemUsageCur,pmIfBbe,pmIfEs,pmIfSes,pmIfUas,pmIfCses,pmBdTempMax,pmBdTempMin,pmBdTempCur,pmQPSKWS,pmQAMWS16,pmQAMWS32,pmQAMWS64,pmQAMWS128,pmQAMWS256,pmQAMWS512,pmQAMWS1024,pmATPCPAdjust,pmATPCNAdjust,pmRslAvg,pmTslAvg,pmAMDownCnt,pmAMUpCnt,pmTLHTT,pmTLLTT,pmRLHTT,
pmRLLTT,pmOtu4Fesesr,pmXpicXpdValue,pmOduSsvTh,pmXpdMax,pmXpdMin,pmMplsPwLs,pmMplsPwSls,pmMplsPwCsls,pmMplsPwUas,pmE1Bbbe,pmE1Es,pmE1Ses,pmE1Cses,pmE1Uas,pmPgIfBbe,pmPgIfEs,pmPgIfSes,pmPgIfCses,pmPgIfUas,pmIfSnrMax,pmIfSnrMin,pmIfSnrAvg,pmMAXFREQDEV,pmMINFREQDEV,pmAVGFREQDEV,pmMAXPHASEOFFSET,pmMINPHASEOFFSET,pmAVGPHASEOFFSET,pmMAXMEANPATHDELAY,pmMINMEANPATHDELAY,pmAVGMEANPATHDELAY,pmMAXPOSITIVEDELAY,pmMINPOSITIVEDELAY,pmAVGPOSITIVEDELAY,pmCURPOSITIVEPDV,pmQpskSWS,pmQamSWS16,pmQamLWS512,pmQamLWs1024,pmIfBer,pmIfMseAvg,pmIfMseMax,pmIfMseMin,pmMplsTunnelLs,pmMplsTunnelSls,pmMplsTunnelCsls,pmMplsTunnelUas,pmEthCfmLs,pmEthCfmSls,pmEthCfmCsls,pmEthCfmUas,pmMplsPwLsN,pmMplsPwUasN,pmMplsPwCslsN,pmMplsPwSlsN,pmMplsTunnelSlsN,pmMplsTunnelLsN,pmMplsTunnelCslsN,pmMplsTunnelUasN,pmQAMWS2048,pmE3LcvSdh,pmE3LesSdh,pmE3LsesSdh,pmTcbbe,pmTcfebbe,pmTcobbe,pmEdfboxtmpmax,pmEdfboxtmpmin,pmEdfboxtmpcur,pmVc3bbe,pmVc3es,pmVc3ses,pmVc3febbe,pmVc3fees,pmVc3feses,pmVc3uas,pmVc3cses,pmVc3fecses,pmVc3feuas,pmOspiccvmax,pmOspiccvmin,
pmOspiccvcur,pmWcvmax,pmWcvmin,pmWcvcur,pmCcvmax,pmCcvmin,pmCcvcur,pmBcvmax,pmBcvmin,pmEdrplmax,pmEdrplmin,pmEdrplcur,pmEdwcsmax,pmEdwcsmin,pmEdwcscur,pmEdtmpmax,pmEdtmpmin,pmEdtmpcur,pmFecCor0bitCnt,pmFecCor1bitCnt,pmEmuvolmax,pmEmuvolmin,pmEmuvolcur,pmT3LcvSdh,pmT3LesSdh,pmT3LsesSdh,pmT1LlossSdh,pmCrc4Err,pmDdnCrc4Err,pmXcstmpmax,pmXcstmpmin,pmSumiopmax,pmSumiopmin,pmSumiopcur,pmSumoopmax,pmSumoopmin,pmSumoopcur,pmEnvtmpmax,pmEnvtmpmin,pmEnvtmpcur,pmLsclcmax,pmLsclcmin,pmLsclccur,pmPclswlmax,pmPclswlmin,pmPclswlcur,pmPclswlomax,pmPclswlomin,pmPclswlocur,pmPclsopmax,pmPclsopmin,pmPclsopcur,pmPclssnmax,pmPclssnmin,pmPclssncur,pmCrc4bbe,pmCrc4es,pmCrc4ses,pmCrc4febbe,pmCrc4fees,pmCrc4feses,pmCrc4uas,pmCrc4cses,pmCrc4fecses,pmIctmpmax,pmIctmpmin,pmIctmpcur,pmCrc4feuas,pmOtu2smbip8,pmOdu2pmbip8,pmIcclcmax,pmIcclcmin,pmIcclccur,pmCpTelDownCount,mCpTelDownTime,pmCpCcDownCount,pmCpCcDownTime,pmMemUsageMax,pmMemUsageMin,pmMemUsageAvg,pmQamws4096,pmQamLWs2048,pmE3LlossSdh,pmLineOutPowermax,pmLineOutPowermin,pmLineOutPowercur,
pmT3LlossSdh,pmLppsc,pmLppsd,pmDslCv,pmDslLosws,pmDslEs,pmDslSes,pmDslUas,pmDslLpa,pmDslSnr,pmPmutmpmax,pmPmutmpmin,pmPmutmpavg,pmPumptmpmax,pmPumptmpmin,pmPumptmpcur,pmPumpbisamax,pmPumpbisamin,pmPumpbisacur,pmLspOk,pmLspFail,pmPumpdrvcmax,pmPumpdrvcmin,pmPumpdrvccur,pmPumpdrvvgmax,pmPumpdrvvgmin,pmPumpdrvvgcur,pmCrc6Err,pmLsOopMax,pmLsOopMin,pmLsOopCur,pmLsIopMax,pmLsIopMin,pmLsIopCur,pmLsTmpMax,pmLsTmpMin,pmLsTmpCur,pmLsBiasMax,pmLsBiasMin,pmRxBwutilExcs,pmTxBwutilExcs,pmMAXNEGATIVEDELAY,pmMINNEGATIVEDELAY,pmAVGNEGATIVEDELAY,pmCURNEGATIVEPDV,pmQamws8192,pmTolLdpwr,pmBatvoltcur,pmBatvoltmin,pmBatvoltmax,pmAcvoltcur,pmAcvoltmin,pmAcvlotmax,pmTolAcpwr,pmTolSolcurnt,pmTolSoloutpwr,
pmLsBiasCur,pmTxBwutilExcsMin,pmRxBwutilExcsMin,pmTxBwutilExcsMid,pmRxBwutilExcsMid,pmTxBwutilExcsMax,pmRxBwutilExcsMax,pmMAXCLKDA,pmMINCLKDA,pmAVGCLKDA,pmRealPowerMax,pmRealPowerMin,pmRealPowerCur,pmRealPowerAvg,pmNomiPowerMax,pmNomiPowerMin,pmNomiPowerCur,pmNomiPowerAvg,pmQAMWS16384,pmQPSKS62P5MWS,pmQPSKS125MWS,pmQPSKS750MWS,pmPortBerCnt,pmQPSKS250MWS,pmQPSKS500MWS,pmBpsk250MWS,pmBpsk500MWS,pmBpsk750MWS,pmBpsk1000MWS,pmBpsk1500MWS,pmBpsk2000MWS,pmBpskS62p5mWs,pmBpskS125mWs,pmPskWs8,pmMimoCapacityCur,pmMimoCapacityMin,pmMimoCapacityMax,pmMimoCapacityAvg,pmVDeflectMax,pmVDeflectMin,pmVDeflectCur,pmShakeCount,pmHDeflectMax,pmHDeflectMin,pmHDeflectCur,pmVDeflectTs,pmIntternalAngleMax,pmIntternalAngleMin,pmIntternalAngleCur }
        STATUS current
        DESCRIPTION
            "Enter the description of the created OBJECT-GROUP."
        ::= { optixRtnPerTrapGroups 1 }

    -- 1.3.6.1.4.1.2011.2.25.3.40.40.100.2
    optixRtnPerTrapCompliances OBJECT IDENTIFIER ::= { optixRtnPerTrapConformance 2 }

    -- 1.3.6.1.4.1.2011.2.25.3.40.40.100.2.1
    optixRtnPerTrapbasicCompliance MODULE-COMPLIANCE
        STATUS current
        DESCRIPTION
            "Enter the description of the created MODULE-COMPLIANCE."
        MODULE -- this module
	    MANDATORY-GROUPS { optixRtnPerTrapObjectGroup }
        ::= { optixRtnPerTrapCompliances 1 }

END
