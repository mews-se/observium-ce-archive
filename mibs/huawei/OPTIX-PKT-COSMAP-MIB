-- OPTIX-PKT-COSMAP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-COSMAP-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        optixLogBoardId,optixLogSubCardId
            FROM OPTIX-BOARD-MANAGE-MIB
        ;

    optixPktCosMap MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the QoS service configuration information of a device."
        REVISION "201204200000Z"
        DESCRIPTION
            "The initial revision of this MIB module1."
        ::={ optixProvisionPtn 25 }

    -- 1.3.6.1.4.1.2011.2.25.4.50.25.1
    optixPktCosMapGroup OBJECT IDENTIFIER ::= { optixPktCosMap 1 }

    -- 1.3.6.1.4.1.2011.2.25.4.50.25.1.1
    optixDsMapNameTable OBJECT-TYPE
        SYNTAX SEQUENCE OF OptixDsMapNameEntry
        MAX-ACCESS not-accessible
        STATUS current
        DESCRIPTION
            "This table describes the basic COSMAP configurations."
        ::= { optixPktCosMapGroup 1 }

    -- 1.3.6.1.4.1.2011.2.25.4.50.25.1.1.1
    optixDsMapNameEntry OBJECT-TYPE
        SYNTAX OptixDsMapNameEntry
        MAX-ACCESS not-accessible
        STATUS current
        DESCRIPTION
            "This entry describes the basic COSMAP configurations."
        INDEX{ optixDsPriMapId }
        ::= { optixDsMapNameTable 1 }

    OptixDsMapNameEntry ::=
        SEQUENCE {
            optixDsPriMapId
                Unsigned32,
            optixDsPriMapName
                OCTET STRING,
            optixDsPriMapNameLen
                OCTET STRING,
            optixDsMapNameRowStatus
                RowStatus
        }

    -- 1.3.6.1.4.1.2011.2.25.4.50.25.1.1.1.1
    optixDsPriMapId OBJECT-TYPE
        SYNTAX Unsigned32
        MAX-ACCESS not-accessible
        STATUS current
        DESCRIPTION
            "This object indicates the DS packet priority mapping table ID of the QoS module. Value range: 1 to 8."
        ::= { optixDsMapNameEntry 1 }

    -- 1.3.6.1.4.1.2011.2.25.4.50.25.1.1.1.2
    optixDsPriMapName OBJECT-TYPE
        SYNTAX OCTET STRING (SIZE(0..32))
        MAX-ACCESS read-create
        STATUS current
        DESCRIPTION
            "This object indicates the DS packet priority mapping table name of the QoS module."
        ::= { optixDsMapNameEntry 2 }

    -- 1.3.6.1.4.1.2011.2.25.4.50.25.1.1.1.3
    optixDsPriMapNameLen OBJECT-TYPE
        SYNTAX OCTET STRING (SIZE(0..8))
        MAX-ACCESS read-only
        STATUS current
        DESCRIPTION
            "This object indicates the the length of DS packet priority mapping table name of the QoS module."
        ::= { optixDsMapNameEntry 3 }

    -- 1.3.6.1.4.1.2011.2.25.4.50.25.1.1.1.255
    optixDsMapNameRowStatus OBJECT-TYPE
        SYNTAX RowStatus
        MAX-ACCESS read-create
        STATUS current
        DESCRIPTION
            "This object indicates the DS row status of the QoS module."
        ::= { optixDsMapNameEntry 255 }

    -- 1.3.6.1.4.1.2011.2.25.4.50.25.1.2
    optixCosPriMapInTable OBJECT-TYPE
        SYNTAX SEQUENCE OF OptixCosPriMapInEntry
        MAX-ACCESS not-accessible
        STATUS current
        DESCRIPTION
            "This table describes the basic CoS MAP configurations in the input direction."
        ::= { optixPktCosMapGroup 2 }

    -- 1.3.6.1.4.1.2011.2.25.4.50.25.1.2.1
    optixCosPriMapInEntry OBJECT-TYPE
        SYNTAX OptixCosPriMapInEntry
        MAX-ACCESS not-accessible
        STATUS current
        DESCRIPTION
            "Thisentry describes the basic CoS MAP configurations in the input direction."
        INDEX{ optixDsPriMapId,optixCosPriMapInPackageType,optixCosPriMapInEncapsValue }
        ::= { optixCosPriMapInTable 1 }

    OptixCosPriMapInEntry ::=
        SEQUENCE {
            optixCosPriMapInPackageType
                INTEGER,
            optixCosPriMapInEncapsValue
                Unsigned32,
            optixCosPriMapInCos
                INTEGER,
            optixCosPriMapInRowStatus
                RowStatus
        }

    -- 1.3.6.1.4.1.2011.2.25.4.50.25.1.2.1.1
    optixCosPriMapInPackageType OBJECT-TYPE
        SYNTAX INTEGER
        {
            cvlan(1),
            svlan(2),
            deisvlan(3),
            ipDscp(4),
            mplsExp(5)
        }
        MAX-ACCESS not-accessible
        STATUS current
        DESCRIPTION
            "This object indiates the input DS packet type of the QoS module. 1: cvlan, 2: svlan, 3: deisvlan, 4: ipDscp, 5: mplsExp"
        ::= { optixCosPriMapInEntry 1 }

    -- 1.3.6.1.4.1.2011.2.25.4.50.25.1.2.1.2
    optixCosPriMapInEncapsValue OBJECT-TYPE
        SYNTAX Unsigned32
        MAX-ACCESS not-accessible
        STATUS current
        DESCRIPTION
            "This object indiates the input DS packet priority of the QoS module.The value ranges from 0 to 7 when the packet type is cvlan, svlan or mplsexp, ranges from 0 to 15 when the packet type is deisvlan,and ranges from 0 to 63 when the packet type is ipdscp."
        ::= { optixCosPriMapInEntry 2 }

    -- 1.3.6.1.4.1.2011.2.25.4.50.25.1.2.1.3
    optixCosPriMapInCos OBJECT-TYPE
        SYNTAX INTEGER
        {
            be(1),
            af11(2),
            af12(3),
            af13(4),
            af21(5),
            af22(6),
            af23(7),
            af31(8),
            af32(9),
            af33(10),
            af41(11),
            af42(12),
            af43(13),
            ef(14),
            cs6(15),
            cs7(16),
            all(255)
        }
        MAX-ACCESS read-create
        STATUS current
        DESCRIPTION
            "This object indiates the input DS packet CoS valueof the QoS module. 1: be, 2: af11, 3: af12, 4: af13, 5: af21, 6: af22, 7: af23, 8: af31, 9: af32, 10: af33, 11: af41, 12: af42, 13: af43, 14: ef, 15: cs6, 16: cs7, 255: all"
        ::= { optixCosPriMapInEntry 3 }

    -- 1.3.6.1.4.1.2011.2.25.4.50.25.1.2.1.255
    optixCosPriMapInRowStatus OBJECT-TYPE
        SYNTAX RowStatus
        MAX-ACCESS read-create
        STATUS current
        DESCRIPTION
            "This object indicates the DS row status of the QoS module."
        ::= { optixCosPriMapInEntry 255 }

    -- 1.3.6.1.4.1.2011.2.25.4.50.25.1.3
    optixCosPriMapOutTable OBJECT-TYPE
        SYNTAX SEQUENCE OF OptixCosPriMapOutEntry
        MAX-ACCESS not-accessible
        STATUS current
        DESCRIPTION
            "This table describes the basic CoS MAP configurations in the output direction."
        ::= { optixPktCosMapGroup 3 }

    -- 1.3.6.1.4.1.2011.2.25.4.50.25.1.3.1
    optixCosPriMapOutEntry OBJECT-TYPE
        SYNTAX OptixCosPriMapOutEntry
        MAX-ACCESS not-accessible
        STATUS current
        DESCRIPTION
            "This entry describes the basic CoS MAP configurations in the output direction."
        INDEX{ optixDsPriMapId,optixCosPriMapOutPackageType,optixCosPriMapOutCos }
        ::= { optixCosPriMapOutTable 1 }

    OptixCosPriMapOutEntry ::=
        SEQUENCE {
            optixCosPriMapOutPackageType
                INTEGER,
            optixCosPriMapOutCos
                INTEGER,
            optixCosPriMapOutPackagePri
                Unsigned32,
            optixCosPriMapOutRowStatus
                RowStatus
        }

    -- 1.3.6.1.4.1.2011.2.25.4.50.25.1.3.1.1
    optixCosPriMapOutPackageType OBJECT-TYPE
        SYNTAX INTEGER
        {
            cvlan(1),
            svlan(2),
            deisvlan(3),
            ipDscp(4),
            mplsExp(5)
        }
        MAX-ACCESS not-accessible
        STATUS current
        DESCRIPTION
            "This object indicates the output DS packet type of the QoS module. 1: cvlan, 2: svlan, 3: deisvlan, 4: ipDscp, 5: mplsExp"
        ::= { optixCosPriMapOutEntry 1 }

    -- 1.3.6.1.4.1.2011.2.25.4.50.25.1.3.1.2
    optixCosPriMapOutCos OBJECT-TYPE
        SYNTAX INTEGER
        {
            be(1),
            af11(2),
            af12(3),
            af13(4),
            af21(5),
            af22(6),
            af23(7),
            af31(8),
            af32(9),
            af33(10),
            af41(11),
            af42(12),
            af43(13),
            ef(14),
            cs6(15),
            cs7(16),
            all(255)
        }
        MAX-ACCESS not-accessible
        STATUS current
        DESCRIPTION
            "This object indicates the output DS packet CoS value of the QoS module. 1: be, 2: af11, 3: af12, 4: af13, 5: af21, 6: af22, 7: af23, 8: af31, 9: af32, 10: af33, 11: af41, 12: af42, 13: af43, 14: ef, 15: cs6, 16: cs7, 255: all"
        ::= { optixCosPriMapOutEntry 2 }

    -- 1.3.6.1.4.1.2011.2.25.4.50.25.1.3.1.3
    optixCosPriMapOutPackagePri OBJECT-TYPE
        SYNTAX Unsigned32
        MAX-ACCESS read-create
        STATUS current
        DESCRIPTION
            "This object indiates the output DS packet priority of the QoS module. If the packet type is cvlan, svlan, or mplsexp, the value ranges from 0 to 7. If the packet type is deisvlan, the value ranges from 0 to 7 and from 8 (0DE) to 15 (7DE). If the packet type is ipdscp, the value ranges from 0 to 63."
        ::= { optixCosPriMapOutEntry 3 }

    -- 1.3.6.1.4.1.2011.2.25.4.50.25.1.3.1.255
    optixCosPriMapOutRowStatus OBJECT-TYPE
        SYNTAX RowStatus
        MAX-ACCESS read-create
        STATUS current
        DESCRIPTION
            "This object indicates the DS row status of the QoS module."
        ::= { optixCosPriMapOutEntry 255 }

    -- 1.3.6.1.4.1.2011.2.25.4.50.25.1.4
    optixDsMapPortTable OBJECT-TYPE
        SYNTAX SEQUENCE OF OptixDsMapPortEntry
        MAX-ACCESS not-accessible
        STATUS current
        DESCRIPTION
            "This table describes the basic configurations of the QoS DS domain application relationship."
        ::= { optixPktCosMapGroup 4 }

    -- 1.3.6.1.4.1.2011.2.25.4.50.25.1.4.1
    optixDsMapPortEntry OBJECT-TYPE
        SYNTAX OptixDsMapPortEntry
        MAX-ACCESS not-accessible
        STATUS current
        DESCRIPTION
            "Thisentry describes the basic configurations of the QoS DS domain application relationship."
        INDEX{ optixLogBoardId,optixLogSubCardId,optixDSMapPortId }
        ::= { optixDsMapPortTable 1 }

    OptixDsMapPortEntry ::=
        SEQUENCE {
            optixDSMapPortId
                Unsigned32,
            optixDsMapSetId
                Unsigned32,
            optixCosMapPackageType
                INTEGER,
            optixDsMapPortRowStatus
                RowStatus
        }

    -- 1.3.6.1.4.1.2011.2.25.4.50.25.1.4.1.1
    optixDSMapPortId OBJECT-TYPE
        SYNTAX Unsigned32
        MAX-ACCESS not-accessible
        STATUS current
        DESCRIPTION
            "This object indicates the DS port number of the QoS module. Value range: 1 to 65535 (based on the number of ports supported by the board)."
        ::= { optixDsMapPortEntry 1 }

    -- 1.3.6.1.4.1.2011.2.25.4.50.25.1.4.1.2
    optixDsMapSetId OBJECT-TYPE
        SYNTAX Unsigned32
        MAX-ACCESS read-create
        STATUS current
        DESCRIPTION
            "This object indicates the DS mapping ID of the QoS module. Value range: 1 to 8."
        ::= { optixDsMapPortEntry 2 }

    -- 1.3.6.1.4.1.2011.2.25.4.50.25.1.4.1.3
    optixCosMapPackageType OBJECT-TYPE
        SYNTAX INTEGER
        {
            cvlan(1),
            svlan(2),
            deisvlan(3),
            ipDscp(4),
            mplsExp(5)
        }
        MAX-ACCESS read-create
        STATUS current
        DESCRIPTION
            "This object indicates the DS packet type of the QoS module. 1: cvlan, 2: svlan, 3: deisvlan, 4: ipDscp, 5: mplsExp"
        ::= { optixDsMapPortEntry 3 }

    -- 1.3.6.1.4.1.2011.2.25.4.50.25.1.4.1.255
    optixDsMapPortRowStatus OBJECT-TYPE
        SYNTAX RowStatus
        MAX-ACCESS read-create
        STATUS current
        DESCRIPTION
            "This object indicates the DS row status of the QoS module."
        ::= { optixDsMapPortEntry 255 }

    -- 1.3.6.1.4.1.2011.2.25.4.50.25.1.5
    optixAtmCosMapNameTable OBJECT-TYPE
        SYNTAX SEQUENCE OF OptixAtmCosMapNameEntry
        MAX-ACCESS not-accessible
        STATUS current
        DESCRIPTION
            "This table describes the ATM service configurations ."
        ::= { optixPktCosMapGroup 5 }

    -- 1.3.6.1.4.1.2011.2.25.4.50.25.1.5.1
    optixAtmCosMapNameEntry OBJECT-TYPE
        SYNTAX OptixAtmCosMapNameEntry
        MAX-ACCESS not-accessible
        STATUS current
        DESCRIPTION
            "Thisentry describes the ATM service configurations ."
        INDEX{ optixAtmCosMapId }
        ::= { optixAtmCosMapNameTable 1 }

    OptixAtmCosMapNameEntry ::=
        SEQUENCE {
            optixAtmCosMapId
                Unsigned32,
            optixAtmCosMapName
                OCTET STRING,
            optixAtmCosMapNameLen
                OCTET STRING,
            optixAtmCosMapNameRowStatus
                RowStatus
        }

    -- 1.3.6.1.4.1.2011.2.25.4.50.25.1.5.1.1
    optixAtmCosMapId OBJECT-TYPE
        SYNTAX Unsigned32
        MAX-ACCESS not-accessible
        STATUS current
        DESCRIPTION
            "This object indicates the CoS mapping ID. Value range: 1 to 8."
        ::= { optixAtmCosMapNameEntry 1 }

    -- 1.3.6.1.4.1.2011.2.25.4.50.25.1.5.1.2
    optixAtmCosMapName OBJECT-TYPE
        SYNTAX OCTET STRING (SIZE(0..32))
        MAX-ACCESS read-create
        STATUS current
        DESCRIPTION
            "This object indicates the CoS mapping name."
        ::= { optixAtmCosMapNameEntry 2 }

    -- 1.3.6.1.4.1.2011.2.25.4.50.25.1.5.1.3
    optixAtmCosMapNameLen OBJECT-TYPE
        SYNTAX OCTET STRING (SIZE(0..8))
        MAX-ACCESS read-only
        STATUS current
        DESCRIPTION
            "This object indicates the length of CoS mapping name."
        ::= { optixAtmCosMapNameEntry 3 }

    -- 1.3.6.1.4.1.2011.2.25.4.50.25.1.5.1.255
    optixAtmCosMapNameRowStatus OBJECT-TYPE
        SYNTAX RowStatus
        MAX-ACCESS read-create
        STATUS current
        DESCRIPTION
            "This object indicates the CoS row status of themapping name"
        ::= { optixAtmCosMapNameEntry 255 }

    -- 1.3.6.1.4.1.2011.2.25.4.50.25.1.6
    optixAtmCosMapTable OBJECT-TYPE
        SYNTAX SEQUENCE OF OptixAtmCosMapEntry
        MAX-ACCESS not-accessible
        STATUS current
        DESCRIPTION
            "This table describes the configurations of the priority mappingfor the ATM service."
        ::= { optixPktCosMapGroup 6 }

    -- 1.3.6.1.4.1.2011.2.25.4.50.25.1.6.1
    optixAtmCosMapEntry OBJECT-TYPE
        SYNTAX OptixAtmCosMapEntry
        MAX-ACCESS not-accessible
        STATUS current
        DESCRIPTION
            "Thisentry describes the configurations of the mapping from the ATM service to the priority."
        INDEX{ optixAtmCosMapId,optixAtmCosMapEncapsValue }
        ::= { optixAtmCosMapTable 1 }

    OptixAtmCosMapEntry ::=
        SEQUENCE {
            optixAtmCosMapEncapsValue
                INTEGER,
            optixAtmCosMapCos
                INTEGER,
            optixAtmCosMapCosHelp
                OCTET STRING,
            optixAtmCosMapRowStatus
                RowStatus
        }

    -- 1.3.6.1.4.1.2011.2.25.4.50.25.1.6.1.1
    optixAtmCosMapEncapsValue OBJECT-TYPE
        SYNTAX INTEGER
        {
            ubr(1),
            cbr(2),
            rtvbr(3),
            nrtvbr(4),
            ubrAdd(5),
            portTrans(6)
        }
        MAX-ACCESS not-accessible
        STATUS current
        DESCRIPTION
            "This object indicates the packet priority. 1: ubr, 2: cbr, 3: rtvbr, 4: nrtvbr, 5: ubrAdd, 6: portTrans"
        ::= { optixAtmCosMapEntry 1 }

    -- 1.3.6.1.4.1.2011.2.25.4.50.25.1.6.1.2
    optixAtmCosMapCos OBJECT-TYPE
        SYNTAX INTEGER
        {
            be(1),
            af11(2),
            af12(3),
            af13(4),
            af21(5),
            af22(6),
            af23(7),
            af31(8),
            af32(9),
            af33(10),
            af41(11),
            af42(12),
            af43(13),
            ef(14),
            cs6(15),
            cs7(16)
        }
        MAX-ACCESS read-create
        STATUS current
        DESCRIPTION
            "This object indicates the CoS. 1: be, 2: af11, 3: af12, 4: af13, 5: af21, 6: af22, 7: af23, 8: af31, 9: af32, 10: af33, 11: af41, 12: af42, 13: af43, 14: ef, 15: cs6, 16: cs7"
        ::= { optixAtmCosMapEntry 2 }

    -- 1.3.6.1.4.1.2011.2.25.4.50.25.1.6.1.3
    optixAtmCosMapCosHelp OBJECT-TYPE
        SYNTAX OCTET STRING (SIZE(0..32))
        MAX-ACCESS read-only
        STATUS current
        DESCRIPTION
            "This object indicates the help information ofthe CoS."
        ::= { optixAtmCosMapEntry 3 }

    -- 1.3.6.1.4.1.2011.2.25.4.50.25.1.6.1.255
    optixAtmCosMapRowStatus OBJECT-TYPE
        SYNTAX RowStatus
        MAX-ACCESS read-create
        STATUS current
        DESCRIPTION
            "This object indicates the CoS row status ."
        ::= { optixAtmCosMapEntry 255 }

    -- 1.3.6.1.4.1.2011.2.25.4.50.25.1.7
    optixAtmServCosMapTable OBJECT-TYPE
        SYNTAX SEQUENCE OF OptixAtmServCosMapEntry
        MAX-ACCESS not-accessible
        STATUS current
        DESCRIPTION
            "This table describes the  ATM service Cos mapping service ."
        ::= { optixPktCosMapGroup 7 }

    -- 1.3.6.1.4.1.2011.2.25.4.50.25.1.7.1
    optixAtmServCosMapEntry OBJECT-TYPE
        SYNTAX OptixAtmServCosMapEntry
        MAX-ACCESS not-accessible
        STATUS current
        DESCRIPTION
            "This entry describes the ATM service Cos mapping service ."
        INDEX{ optixAtmServId,optixVnniId }
        ::= { optixAtmServCosMapTable 1 }

    OptixAtmServCosMapEntry ::=
        SEQUENCE {
            optixAtmServId
                Unsigned32,
            optixVnniId
                Unsigned32,
            optixCosMapId
                Unsigned32,
            optixAtmServCosMapRowStatus
                RowStatus
        }

    -- 1.3.6.1.4.1.2011.2.25.4.50.25.1.7.1.1
    optixAtmServId OBJECT-TYPE
        SYNTAX Unsigned32
        MAX-ACCESS not-accessible
        STATUS current
        DESCRIPTION
            "This object describes the ATM service ID. Value range: 1 to 4294967295 (based on the number of ATM services supported by the equipment)."
        ::= { optixAtmServCosMapEntry 1 }

    -- 1.3.6.1.4.1.2011.2.25.4.50.25.1.7.1.2
    optixVnniId OBJECT-TYPE
        SYNTAX Unsigned32
        MAX-ACCESS not-accessible
        STATUS current
        DESCRIPTION
            "This object describes the vnni ID. Value range: 1 to 4294967295 (based on the number of V-UNIs supported by the equipment)."
        ::= { optixAtmServCosMapEntry 2 }

    -- 1.3.6.1.4.1.2011.2.25.4.50.25.1.7.1.3
    optixCosMapId OBJECT-TYPE
        SYNTAX Unsigned32
        MAX-ACCESS read-create
        STATUS current
        DESCRIPTION
            "This obiect describes the CoS mapping ID. Value range: 1 to 8."
        ::= { optixAtmServCosMapEntry 3 }

    -- 1.3.6.1.4.1.2011.2.25.4.50.25.1.7.1.255
    optixAtmServCosMapRowStatus OBJECT-TYPE
        SYNTAX RowStatus
        MAX-ACCESS read-create
        STATUS current
        DESCRIPTION
            "This object indicates the CoS row status ."
        ::= { optixAtmServCosMapEntry 255 }

    -- 1.3.6.1.4.1.2011.2.25.4.50.25.2
    optixPktQueueCosMapGroup OBJECT IDENTIFIER ::= { optixPktCosMap 2 }

    -- 1.3.6.1.4.1.2011.2.25.4.50.25.2.1
    optixPktQueueCosMapRestore OBJECT-TYPE
        SYNTAX INTEGER
        {
            invalid(255),
            restore(1)
        }
        MAX-ACCESS read-write
        STATUS current
        DESCRIPTION
            "This object indicates that the default mapping between the CoSs of queues 4 and 8 is to be restored."
        ::= { optixPktQueueCosMapGroup 1 }

    -- 1.3.6.1.4.1.2011.2.25.4.50.25.2.2
    optixPktQueueCosMapRelationTable OBJECT-TYPE
        SYNTAX SEQUENCE OF OptixPktQueueCosMapRelationEntry
        MAX-ACCESS not-accessible
        STATUS current
        DESCRIPTION
            "This table describes the mapping between CoSs of queues 4 and 8."
        ::= { optixPktQueueCosMapGroup 2 }

    -- 1.3.6.1.4.1.2011.2.25.4.50.25.2.2.1
    optixPktQueueCosMapRelationEntry OBJECT-TYPE
        SYNTAX OptixPktQueueCosMapRelationEntry
        MAX-ACCESS not-accessible
        STATUS current
        DESCRIPTION
            "This entry describes the mapping between CoSs of queues 4 and 8."
        INDEX{ optixPktQueue8CosMap }
        ::= { optixPktQueueCosMapRelationTable 1 }

    OptixPktQueueCosMapRelationEntry ::=
        SEQUENCE {
            optixPktQueue8CosMap
                INTEGER,
            optixPktQueue4CosMap
                INTEGER
        }

    -- 1.3.6.1.4.1.2011.2.25.4.50.25.2.2.1.1
    optixPktQueue8CosMap OBJECT-TYPE
        SYNTAX INTEGER
        {
            cs7(1),
            cs6(2),
            ef(3),
            af4(4),
            af3(5),
            af2(6),
            af1(7),
            be(8),
            all(0),
            none(255)
        }
        MAX-ACCESS not-accessible
        STATUS current
        DESCRIPTION
            "This object indicates the CoS of queue 8."
        ::= { optixPktQueueCosMapRelationEntry 1 }

    -- 1.3.6.1.4.1.2011.2.25.4.50.25.2.2.1.2
    optixPktQueue4CosMap OBJECT-TYPE
        SYNTAX INTEGER
        {
            cs7(1),
            cs6(2),
            ef(3),
            af4(4),
            af3(5),
            af2(6),
            af1(7),
            be(8),
            all(0),
            none(255)
        }
        MAX-ACCESS read-write
        STATUS current
        DESCRIPTION
            "This object indicates the CoS of queue 4."
        ::= { optixPktQueueCosMapRelationEntry 2 }

END
