-- OPTIX-RTN-CA-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-CA-MGR-MIB DEFINITIONS ::= BEGIN
    IMPORTS
        OBJECT-GROUP,MODULE-COMPLIANCE
            FROM SNMPv2-CONF
        Unsigned32,OBJECT-TYPE,MODULE-IDENTITY,Integer32
            FROM SNMPv2-SMI
        TEXTUAL-CONVENTION,RowStatus
            FROM SNMPv2-TC
        optixRtnOduIndex1,optixRtnOduIndex2
            FROM OPTIX-RTN-ODU-MGR-MIB
        optixProvisionRtn
            FROM OPTIX-OID-MIB
        OPTIXRtnEnableStateType,optixRtnIndex1,optixRtnIndex2,optixRtnIndex3,optixRtnIndex4
            FROM OPTIX-RTN-GENNERAL-MIB
        ;

    optixRtnCAParaMgr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query IF board related parameters required in radio link configuration and preventive maintenance, including the IF board modulation mode, bandwidth, AM management, and link identifier."
        REVISION "201204160935Z"
        DESCRIPTION
            "The initial revision of this MIB module1."
        ::={ optixProvisionRtn 10 }
    OPTIXRtnCaRoleType ::= TEXTUAL-CONVENTION
        STATUS current
        DESCRIPTION
            "Indicates the role of a ca protection group. Values: 0: slave 1: master -1:unknown"
        SYNTAX INTEGER
        {
            slave(0),
            master(1),
            unknown(-1)
        }
    OPTIXRtnCaPositionType ::= TEXTUAL-CONVENTION
        STATUS current
        DESCRIPTION
            "Indicates the position of a ca protection group. Values: 0: local 1: adjacency"
        SYNTAX Unsigned32
        {
            local(0),
            adjacency(1)
        }	
    OPTIXRtnCaGroupTypeStatus ::= TEXTUAL-CONVENTION
        STATUS current
        DESCRIPTION
            "Indicates the type of a ca protection group. Values: 1: non-cascade 2: cascade"
        SYNTAX Unsigned32
        {
            non-cascade(1),
            cascade(2)
        }
    -- 1.3.6.1.4.1.2011.2.25.4.40.10.9
    optixRtnCaAdjoin OBJECT IDENTIFIER ::= { optixRtnCAParaMgr 9 }
 
    -- 1.3.6.1.4.1.2011.2.25.4.40.10.9.1
    optixRtnCaAdjoinNeInfo OBJECT-TYPE
        SYNTAX OCTET STRING
        MAX-ACCESS read-only
        STATUS current
        DESCRIPTION
            "Indicates the ca group adjoin ne information."
        ::= { optixRtnCaAdjoin 1 }
        
    -- 1.3.6.1.4.1.2011.2.25.4.40.10.10
    optixRtnCAPara OBJECT IDENTIFIER ::= { optixRtnCAParaMgr 10 }

    -- 1.3.6.1.4.1.2011.2.25.4.40.10.10.220
    optixRtnCaGroupSyncCfgTable OBJECT-TYPE
        SYNTAX SEQUENCE OF OptixRtnCaGroupSyncCfgEntry
        MAX-ACCESS not-accessible
        STATUS current
        DESCRIPTION
            "Indicates the ca group information Table"
        ::= { optixRtnCAPara 220 }

    -- 1.3.6.1.4.1.2011.2.25.4.40.10.10.220.1
    optixRtnCaGroupSyncCfgEntry OBJECT-TYPE
        SYNTAX OptixRtnCaGroupSyncCfgEntry
        MAX-ACCESS not-accessible
        STATUS current
        DESCRIPTION
            "Indicates the ca group information Entry"
        INDEX{ optixRtnIndex1 }
        ::= { optixRtnCaGroupSyncCfgTable 1 }

    OptixRtnCaGroupSyncCfgEntry ::=
        SEQUENCE {
            optixRtnSyncRowStatus
                Unsigned32		
        }

    -- 1.3.6.1.4.1.2011.2.25.4.40.10.10.220.1.2
    optixRtnSyncRowStatus OBJECT-TYPE
        SYNTAX Unsigned32
        {
            null(1),
            sync(3)
        }
        MAX-ACCESS read-write
        STATUS current
        DESCRIPTION
            "Indicates the row status of the ca group."
        ::= { optixRtnCaGroupSyncCfgEntry 2 }
        
    -- 1.3.6.1.4.1.2011.2.25.4.40.10.10.230
    optixRtnCaGroupMemberTable OBJECT-TYPE
        SYNTAX SEQUENCE OF OptixRtnCaGroupMemberEntry
        MAX-ACCESS not-accessible
        STATUS current
        DESCRIPTION
            "Indicates the ca group information Table"
        ::= { optixRtnCAPara 230 }

    -- 1.3.6.1.4.1.2011.2.25.4.40.10.10.230.1
    optixRtnCaGroupMemberEntry OBJECT-TYPE
        SYNTAX OptixRtnCaGroupMemberEntry
        MAX-ACCESS not-accessible
        STATUS current
        DESCRIPTION
            "Indicates the ca group information Entry"
        INDEX{ optixRtnIndex1 }
        ::= { optixRtnCaGroupMemberTable 1 }

    OptixRtnCaGroupMemberEntry ::=
        SEQUENCE {
            optixRtnCaGroupMemberOduPowerInfo
                OCTET STRING,
            optixRtnCaGroupMemberAtPcautoenInfo
                OCTET STRING,
            optixRtnCaGroupMemberAtPcenInfo
                OCTET STRING,				
            optixRtnCaGroupMemberAcmParamInfo
                OCTET STRING,
            optixRtnCaGroupMemberAtpcthInfo
                OCTET STRING,
            optixRtnCaGroupMemberBandwidthInfo
                OCTET STRING,
            optixRtnCaGroupMemberOduMaxPowerInfo
                OCTET STRING,				
            optixRtnCaGroupMemberOduWorkInfo
                OCTET STRING,
            optixRtnCaGroupMemberOduTrspacingInfo
                OCTET STRING,
            optixRtnCaGroupMemberOduTxfreqInfo
                OCTET STRING		
        }

    -- 1.3.6.1.4.1.2011.2.25.4.40.10.10.230.1.2
    optixRtnCaGroupMemberOduPowerInfo OBJECT-TYPE
        SYNTAX OCTET STRING
        MAX-ACCESS read-write
        STATUS current
        DESCRIPTION
            "ca group mems information."
        ::= { optixRtnCaGroupMemberEntry 2 }

    -- 1.3.6.1.4.1.2011.2.25.4.40.10.10.230.1.3
    optixRtnCaGroupMemberAtPcautoenInfo OBJECT-TYPE
        SYNTAX OCTET STRING
        MAX-ACCESS read-write
        STATUS current
        DESCRIPTION
            "ca group mems information."
        ::= { optixRtnCaGroupMemberEntry 3 }

    -- 1.3.6.1.4.1.2011.2.25.4.40.10.10.230.1.4
    optixRtnCaGroupMemberAtPcenInfo OBJECT-TYPE
        SYNTAX OCTET STRING
        MAX-ACCESS read-write
        STATUS current
        DESCRIPTION
            "ca group mems information."
        ::= { optixRtnCaGroupMemberEntry 4 }
		
    -- 1.3.6.1.4.1.2011.2.25.4.40.10.10.230.1.5
    optixRtnCaGroupMemberAcmParamInfo OBJECT-TYPE
        SYNTAX OCTET STRING
        MAX-ACCESS read-write
        STATUS current
        DESCRIPTION
            "ca group mems information."
        ::= { optixRtnCaGroupMemberEntry 5 }
		
    -- 1.3.6.1.4.1.2011.2.25.4.40.10.10.230.1.6
    optixRtnCaGroupMemberAtpcthInfo OBJECT-TYPE
        SYNTAX OCTET STRING
        MAX-ACCESS read-write
        STATUS current
        DESCRIPTION
            "ca group mems information."
        ::= { optixRtnCaGroupMemberEntry 6 }

    -- 1.3.6.1.4.1.2011.2.25.4.40.10.10.230.1.7
    optixRtnCaGroupMemberBandwidthInfo OBJECT-TYPE
        SYNTAX OCTET STRING
        MAX-ACCESS read-write
        STATUS current
        DESCRIPTION
            "ca group mems information."
        ::= { optixRtnCaGroupMemberEntry 7 }
		
    -- 1.3.6.1.4.1.2011.2.25.4.40.10.10.230.1.8
    optixRtnCaGroupMemberOduMaxPowerInfo OBJECT-TYPE
        SYNTAX OCTET STRING
        MAX-ACCESS read-write
        STATUS current
        DESCRIPTION
            "ca group mems information."
        ::= { optixRtnCaGroupMemberEntry 8 }

    -- 1.3.6.1.4.1.2011.2.25.4.40.10.10.230.1.9
    optixRtnCaGroupMemberOduWorkInfo OBJECT-TYPE
        SYNTAX OCTET STRING
        MAX-ACCESS read-write
        STATUS current
        DESCRIPTION
            "ca group mems information."
        ::= { optixRtnCaGroupMemberEntry 9 }

    -- 1.3.6.1.4.1.2011.2.25.4.40.10.10.230.1.10
    optixRtnCaGroupMemberOduTrspacingInfo OBJECT-TYPE
        SYNTAX OCTET STRING
        MAX-ACCESS read-write
        STATUS current
        DESCRIPTION
            "ca group mems information."
        ::= { optixRtnCaGroupMemberEntry 10 }

    -- 1.3.6.1.4.1.2011.2.25.4.40.10.10.230.1.11
    optixRtnCaGroupMemberOduTxfreqInfo OBJECT-TYPE
        SYNTAX OCTET STRING
        MAX-ACCESS read-write
        STATUS current
        DESCRIPTION
            "ca group mems information."
        ::= { optixRtnCaGroupMemberEntry 11 }
		
    -- 1.3.6.1.4.1.2011.2.25.4.40.10.10.240
    optixRtnCaGroupTable OBJECT-TYPE
        SYNTAX SEQUENCE OF OptixRtnCaGroupEntry
        MAX-ACCESS not-accessible
        STATUS current
        DESCRIPTION
            "Indicates the CA work group"
        ::= { optixRtnCAPara 240 }

    -- 1.3.6.1.4.1.2011.2.25.4.40.10.10.240.1
    optixRtnCaGroupEntry OBJECT-TYPE
        SYNTAX OptixRtnCaGroupEntry
        MAX-ACCESS not-accessible
        STATUS current
        DESCRIPTION
            "Indicates the CA work group"
        INDEX{ optixRtnIndex1 }
        ::= { optixRtnCaGroupTable 1 }

    OptixRtnCaGroupEntry ::=
        SEQUENCE {
            optixRtnCaGroupType
               OPTIXRtnCaGroupTypeStatus,
            optixRtnCaGroupPosition
               OPTIXRtnCaPositionType,
            optixRtnCaBoardID
                Unsigned32,
            optixRtnCaSubCardID
                Unsigned32,
            optixRtnCaPortID
                Unsigned32,
            optixRtnCaRole
                OPTIXRtnCaRoleType,
            optixRtnOduBoardID
                Unsigned32,
            optixRtnOduPortID
                Unsigned32,				
            optixRtnOduChannel
                Unsigned32,				
            optixRtnSlaveMemsInfo
                OCTET STRING,
            optixRtnCfgRowStatus
                RowStatus
        }

    -- 1.3.6.1.4.1.2011.2.25.4.40.10.10.240.1.2
    optixRtnCaGroupType OBJECT-TYPE
        SYNTAX OPTIXRtnCaGroupTypeStatus
        MAX-ACCESS read-create
        STATUS current
        DESCRIPTION
            "Indicates the CA work group type"
        ::= { optixRtnCaGroupEntry 2 }

    -- 1.3.6.1.4.1.2011.2.25.4.40.10.10.240.1.3
    optixRtnCaGroupPosition OBJECT-TYPE
        SYNTAX OPTIXRtnCaPositionType
        MAX-ACCESS read-create
        STATUS current
        DESCRIPTION
            "Indicates the local or adjacency end.
	    0: local
	    1: adjacency"
        ::= { optixRtnCaGroupEntry 3 }

    -- 1.3.6.1.4.1.2011.2.25.4.40.10.10.240.1.4
    optixRtnCaBoardID OBJECT-TYPE
        SYNTAX Unsigned32
        MAX-ACCESS read-create
        STATUS current
        DESCRIPTION
            "Indicates the slot ID."
        ::= { optixRtnCaGroupEntry 4 }

    -- 1.3.6.1.4.1.2011.2.25.4.40.10.10.240.1.5
    optixRtnCaSubCardID OBJECT-TYPE
        SYNTAX Unsigned32
        MAX-ACCESS read-create
        STATUS current
        DESCRIPTION
            "Indicates the subboard ID."
        ::= { optixRtnCaGroupEntry 5 }

    -- 1.3.6.1.4.1.2011.2.25.4.40.10.10.240.1.6
    optixRtnCaPortID OBJECT-TYPE
        SYNTAX Unsigned32
        MAX-ACCESS read-create
        STATUS current
        DESCRIPTION
            "Indicates the port ID."
        ::= { optixRtnCaGroupEntry 6 }
    -- 1.3.6.1.4.1.2011.2.25.4.40.10.10.240.1.7
    optixRtnCaRole OBJECT-TYPE
        SYNTAX OPTIXRtnCaRoleType
        MAX-ACCESS read-only
        STATUS current
        DESCRIPTION
            "Indicates the role."
        ::= { optixRtnCaGroupEntry 7 }
    -- 1.3.6.1.4.1.2011.2.25.4.40.10.10.240.1.8
    optixRtnOduBoardID OBJECT-TYPE
        SYNTAX Unsigned32
        MAX-ACCESS read-only
        STATUS current
        DESCRIPTION
            "Indicates the odu board id."
        ::= { optixRtnCaGroupEntry 8 }		
    -- 1.3.6.1.4.1.2011.2.25.4.40.10.10.240.1.9
    optixRtnOduPortID OBJECT-TYPE
        SYNTAX Unsigned32
        MAX-ACCESS read-only
        STATUS current
        DESCRIPTION
            "Indicates the odu port id."
        ::= { optixRtnCaGroupEntry 9 }		
    -- 1.3.6.1.4.1.2011.2.25.4.40.10.10.240.1.10
    optixRtnOduChannel OBJECT-TYPE
        SYNTAX Unsigned32
        MAX-ACCESS read-only
        STATUS current
        DESCRIPTION
            "Indicates the odu port id."
        ::= { optixRtnCaGroupEntry 10 }			
    -- 1.3.6.1.4.1.2011.2.25.4.40.10.10.240.1.11
    optixRtnSlaveMemsInfo OBJECT-TYPE
        SYNTAX OCTET STRING
        MAX-ACCESS read-create
        STATUS current
        DESCRIPTION
            "Indicates the slave port information of the ca group."
        ::= { optixRtnCaGroupEntry 11 }

    -- 1.3.6.1.4.1.2011.2.25.4.40.10.10.240.1.50
    optixRtnCfgRowStatus OBJECT-TYPE
        SYNTAX RowStatus
        MAX-ACCESS read-create
        STATUS current
        DESCRIPTION
            "Indicates the row status of the ca group."
	DEFVAL{ active }
        ::= { optixRtnCaGroupEntry 50 }

    -- 1.3.6.1.4.1.2011.2.25.4.40.10.10.210
    optixRtnCascadeCaGroupTable OBJECT-TYPE
        SYNTAX SEQUENCE OF OptixRtnCascadeCaGroupEntry
        MAX-ACCESS not-accessible
        STATUS current
        DESCRIPTION
            "Indicates the CA work group"
        ::= { optixRtnCAPara 210 }

    -- 1.3.6.1.4.1.2011.2.25.4.40.10.10.210.1
    optixRtnCascadeCaGroupEntry OBJECT-TYPE
        SYNTAX OptixRtnCascadeCaGroupEntry
        MAX-ACCESS not-accessible
        STATUS current
        DESCRIPTION
            "Indicates the CA work group"
        INDEX{ optixRtnGroupID }
        ::= { optixRtnCascadeCaGroupTable 1 }

    OptixRtnCascadeCaGroupEntry ::=
        SEQUENCE {
            optixRtnCascadeCaGroupType
               OPTIXRtnCaGroupTypeStatus,
            optixRtnCascadeCaGroupPosition
               OPTIXRtnCaPositionType,
            optixRtnCascadeCaBoardID
                Unsigned32,
            optixRtnCascadeCaSubCardID
                Unsigned32,
            optixRtnCascadeCaPortID
                Unsigned32,
            optixRtnCascadeCaRole
                OPTIXRtnCaRoleType,
            optixRtnCascadeCaOduBoardID
                Unsigned32,
            optixRtnCascadeCaOduPortID
                Unsigned32,				
            optixRtnCascadeCaOduChannel
                Unsigned32,				
            optixRtnCascadeCaSlaveMemsInfo
                OCTET STRING,
            optixRtnCascadeCaGroupMemsOduMaxPowerInfo
                OCTET STRING,				
            optixRtnCascadeCaDelRowStatus
                RowStatus
        }

    -- 1.3.6.1.4.1.2011.2.25.4.40.10.10.210.1.2
    optixRtnCascadeCaGroupType OBJECT-TYPE
        SYNTAX OPTIXRtnCaGroupTypeStatus
        MAX-ACCESS read-create
        STATUS current
        DESCRIPTION
            "Indicates the CA work group type"
        ::= { optixRtnCascadeCaGroupEntry 2 }

    -- 1.3.6.1.4.1.2011.2.25.4.40.10.10.210.1.3
    optixRtnCascadeCaGroupPosition OBJECT-TYPE
        SYNTAX OPTIXRtnCaPositionType
        MAX-ACCESS read-create
        STATUS current
        DESCRIPTION
            "Indicates the local or adjacency end.
	    0: local
	    1: adjacency"
        ::= { optixRtnCascadeCaGroupEntry 3 }

    -- 1.3.6.1.4.1.2011.2.25.4.40.10.10.210.1.4
    optixRtnCascadeCaBoardID OBJECT-TYPE
        SYNTAX Unsigned32
        MAX-ACCESS read-create
        STATUS current
        DESCRIPTION
            "Indicates the slot ID."
        ::= { optixRtnCascadeCaGroupEntry 4 }

    -- 1.3.6.1.4.1.2011.2.25.4.40.10.10.210.1.5
    optixRtnCascadeCaSubCardID OBJECT-TYPE
        SYNTAX Unsigned32
        MAX-ACCESS read-create
        STATUS current
        DESCRIPTION
            "Indicates the subboard ID."
        ::= { optixRtnCascadeCaGroupEntry 5 }

    -- 1.3.6.1.4.1.2011.2.25.4.40.10.10.210.1.6
    optixRtnCascadeCaPortID OBJECT-TYPE
        SYNTAX Unsigned32
        MAX-ACCESS read-create
        STATUS current
        DESCRIPTION
            "Indicates the port ID."
        ::= { optixRtnCascadeCaGroupEntry 6 }
    -- 1.3.6.1.4.1.2011.2.25.4.40.10.10.210.1.7
    optixRtnCascadeCaRole OBJECT-TYPE
        SYNTAX OPTIXRtnCaRoleType
        MAX-ACCESS read-only
        STATUS current
        DESCRIPTION
            "Indicates the role."
        ::= { optixRtnCascadeCaGroupEntry 7 }
    -- 1.3.6.1.4.1.2011.2.25.4.40.10.10.210.1.8
    optixRtnCascadeCaOduBoardID OBJECT-TYPE
        SYNTAX Unsigned32
        MAX-ACCESS read-only
        STATUS current
        DESCRIPTION
            "Indicates the odu board id."
        ::= { optixRtnCascadeCaGroupEntry 8 }		
    -- 1.3.6.1.4.1.2011.2.25.4.40.10.10.210.1.9
    optixRtnCascadeCaOduPortID OBJECT-TYPE
        SYNTAX Unsigned32
        MAX-ACCESS read-only
        STATUS current
        DESCRIPTION
            "Indicates the odu port id."
        ::= { optixRtnCascadeCaGroupEntry 9 }		
    -- 1.3.6.1.4.1.2011.2.25.4.40.10.10.210.1.10
    optixRtnCascadeCaOduChannel OBJECT-TYPE
        SYNTAX Unsigned32
        MAX-ACCESS read-only
        STATUS current
        DESCRIPTION
            "Indicates the odu port id."
        ::= { optixRtnCascadeCaGroupEntry 10 }			
    -- 1.3.6.1.4.1.2011.2.25.4.40.10.10.210.1.11
    optixRtnCascadeCaSlaveMemsInfo OBJECT-TYPE
        SYNTAX OCTET STRING
        MAX-ACCESS read-create
        STATUS current
        DESCRIPTION
            "Indicates the slave port information of the ca group."
        ::= { optixRtnCascadeCaGroupEntry 11 }

    -- 1.3.6.1.4.1.2011.2.25.4.40.10.10.210.1.12
    optixRtnCascadeCaGroupMemsOduMaxPowerInfo OBJECT-TYPE
        SYNTAX OCTET STRING
        MAX-ACCESS read-write
        STATUS current
        DESCRIPTION
            "ca group mems information."
        ::= { optixRtnCascadeCaGroupEntry 12 }
		
    -- 1.3.6.1.4.1.2011.2.25.4.40.10.10.210.1.50
    optixRtnCascadeCaDelRowStatus OBJECT-TYPE
        SYNTAX RowStatus
        MAX-ACCESS read-create
        STATUS current
        DESCRIPTION
            "Indicates the row status delete of the ca group."
	DEFVAL{ active }
        ::= { optixRtnCascadeCaGroupEntry 50 }		
END
