--
-- HUAWEI-STORAGE-NAS-MIB.mib
-- MIB generated by MG-SOFT Visual MIB Builder Version 4.0 Build 347
-- Wednesday, July 15, 2015 at 17:31:06
--

--  HUAWEI-STORAGE-NAS-MIB.mib
-- MIB generated by MG-SOFT Visual MIB Builder Version 4.0 Build 347
-- Thursday, June 18, 2015 at 16:41:12
-- 

	HUAWEI-STORAGE-NAS-MIB DEFINITIONS ::= BEGIN
 
		IMPORTS
			OBJECT-GROUP, MODULE-COMPLIANCE			
				FROM SNMPv2-CONF			
			enterprises, Unsigned32, Counter32, Counter64, 
			OBJECT-TYPE, MODULE-IDENTITY			
				FROM SNMPv2-SMI			
			TEXTUAL-CONVENTION			
				FROM SNMPv2-TC;
	
	
		hwStorage MODULE-IDENTITY 
			LAST-UPDATED "201008111239Z"		-- August 11, 2010 at 12:39 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The HUAWEI-STORAGE-NAS-MIB contains objects to query the NAS information."
			REVISION "201411061532Z"		-- November 06, 2014 at 15:32 GMT
			DESCRIPTION 
				"   "
			::= { huaweistorage 4 }

		
	
--
-- Textual conventions
--
	
--  August 11, 2010 at 12:39 GMT
-- November 06, 2014 at 15:32 GMT
-- 
-- Textual conventions
-- 
--  August 11, 2010 at 12:39 GMT
-- April 06, 2013 at 13:54 GMT
-- 
-- Textual conventions
-- 
		NodeCodeString ::= TEXTUAL-CONVENTION
			DISPLAY-HINT 
				"255a"
			STATUS current
			DESCRIPTION 
				"characters in length."
			SYNTAX OCTET STRING (SIZE (15..17))

	
--
-- Node definitions
--
	
--  Node definitions
-- 
		huaweistorage OBJECT IDENTIFIER ::= { enterprises 34774 }

		
		hwISM OBJECT IDENTIFIER ::= { hwStorage 1 }

		
		hwStorageDevice OBJECT IDENTIFIER ::= { hwISM 23 }

		
		hwNasInfo OBJECT IDENTIFIER ::= { hwStorageDevice 7 }

		
--      
		-- 1.3.6.1.4.1.34774.4.1.23.7.1
		hwInfoShareNFSTable OBJECT-TYPE
			SYNTAX SEQUENCE OF HwInfoShareNFSEntry
			MAX-ACCESS not-accessible
			STATUS current
			DESCRIPTION
				"This table is used to check the NFS share information about a device."
			::= { hwNasInfo 1 }

		
		-- 1.3.6.1.4.1.34774.4.1.23.7.1.1
		hwInfoShareNFSEntry OBJECT-TYPE
			SYNTAX HwInfoShareNFSEntry
			MAX-ACCESS not-accessible
			STATUS current
			DESCRIPTION
				"A table containing the part component."
			INDEX { hwInfoShareNFSShareID }
			::= { hwInfoShareNFSTable 1 }

		
		HwInfoShareNFSEntry ::=
			SEQUENCE { 
				hwInfoShareNFSShareID
					OCTET STRING,
				hwInfoShareNFSFileSystemID
					OCTET STRING,
				hwInfoShareNFSDescription
					OCTET STRING,
				hwInfoShareNFSLocalPath
					OCTET STRING
			 }


		-- 1.3.6.1.4.1.34774.4.1.23.7.1.1.1
		hwInfoShareNFSShareID OBJECT-TYPE
			SYNTAX OCTET STRING
			MAX-ACCESS read-only
			STATUS current
			DESCRIPTION
				"Share ID, table index."
			::= { hwInfoShareNFSEntry 1 }

		
		-- 1.3.6.1.4.1.34774.4.1.23.7.1.1.2
		hwInfoShareNFSFileSystemID OBJECT-TYPE
			SYNTAX OCTET STRING
			MAX-ACCESS read-only
			STATUS current
			DESCRIPTION
				"File system ID."
			::= { hwInfoShareNFSEntry 2 }

		
		-- 1.3.6.1.4.1.34774.4.1.23.7.1.1.3
		hwInfoShareNFSDescription OBJECT-TYPE
			SYNTAX OCTET STRING
			MAX-ACCESS read-only
			STATUS current
			DESCRIPTION
				"Share NFS Description."
			::= { hwInfoShareNFSEntry 3 }

		
		-- 1.3.6.1.4.1.34774.4.1.23.7.1.1.4
		hwInfoShareNFSLocalPath OBJECT-TYPE
			SYNTAX OCTET STRING
			MAX-ACCESS read-only
			STATUS current
			DESCRIPTION
				"Share path."
			::= { hwInfoShareNFSEntry 4 }

		
		-- 1.3.6.1.4.1.34774.4.1.23.7.2
		hwInfoShareCIFSTable OBJECT-TYPE
			SYNTAX SEQUENCE OF HwInfoShareCIFSEntry
			MAX-ACCESS not-accessible
			STATUS current
			DESCRIPTION
				"This table is used to check the CIFS share information about a device."
			::= { hwNasInfo 2 }

		
--
		-- 1.3.6.1.4.1.34774.4.1.23.7.2.1
		hwInfoShareCIFSEntry OBJECT-TYPE
			SYNTAX HwInfoShareCIFSEntry
			MAX-ACCESS not-accessible
			STATUS current
			DESCRIPTION
				"A table containing the part component."
			INDEX { hwInfoShareCIFSID }
			::= { hwInfoShareCIFSTable 1 }

		
		HwInfoShareCIFSEntry ::=
			SEQUENCE { 
				hwInfoShareCIFSID
					OCTET STRING,
				hwInfoShareCIFSName
					OCTET STRING,
				hwInfoShareCIFSFileSystemID
					OCTET STRING,
				hwInfoShareCIFSDescription
					OCTET STRING,
				hwInfoShareCIFSLocalPath
					OCTET STRING,
				hwInfoShareCIFSOplockEnabled
					Unsigned32,
				hwInfoShareCIFSNotifyEnabled
					Unsigned32,
				hwInfoShareCIFSContAvailableEna
					Unsigned32
			 }

		-- 1.3.6.1.4.1.34774.4.1.23.7.2.1.1
		hwInfoShareCIFSID OBJECT-TYPE
			SYNTAX OCTET STRING
			MAX-ACCESS read-only
			STATUS current
			DESCRIPTION
				"Share ID, table index."
			::= { hwInfoShareCIFSEntry 1 }

		
		-- 1.3.6.1.4.1.34774.4.1.23.7.2.1.2
		hwInfoShareCIFSName OBJECT-TYPE
			SYNTAX OCTET STRING
			MAX-ACCESS read-only
			STATUS current
			DESCRIPTION
				"Object name."
			::= { hwInfoShareCIFSEntry 2 }

		
		-- 1.3.6.1.4.1.34774.4.1.23.7.2.1.3
		hwInfoShareCIFSFileSystemID OBJECT-TYPE
			SYNTAX OCTET STRING
			MAX-ACCESS read-only
			STATUS current
			DESCRIPTION
				"File system ID."
			::= { hwInfoShareCIFSEntry 3 }

		
		-- 1.3.6.1.4.1.34774.4.1.23.7.2.1.4
		hwInfoShareCIFSDescription OBJECT-TYPE
			SYNTAX OCTET STRING
			MAX-ACCESS read-only
			STATUS current
			DESCRIPTION
				"Share CIFS Description."
			::= { hwInfoShareCIFSEntry 4 }

		
		-- 1.3.6.1.4.1.34774.4.1.23.7.2.1.5
		hwInfoShareCIFSLocalPath OBJECT-TYPE
			SYNTAX OCTET STRING
			MAX-ACCESS read-only
			STATUS current
			DESCRIPTION
				"Share path."
			::= { hwInfoShareCIFSEntry 5 }

		
		-- 1.3.6.1.4.1.34774.4.1.23.7.2.1.6
		hwInfoShareCIFSOplockEnabled OBJECT-TYPE
			SYNTAX Unsigned32
			MAX-ACCESS read-only
			STATUS current
			DESCRIPTION
				"Optimization lock switch
				0: No
				1: Yes"
			::= { hwInfoShareCIFSEntry 6 }

		
		-- 1.3.6.1.4.1.34774.4.1.23.7.2.1.7
		hwInfoShareCIFSNotifyEnabled OBJECT-TYPE
			SYNTAX Unsigned32
			MAX-ACCESS read-only
			STATUS current
			DESCRIPTION
				"Notification switch
				0: No
				1: Yes"
			::= { hwInfoShareCIFSEntry 7 }

		
		-- 1.3.6.1.4.1.34774.4.1.23.7.2.1.8
		hwInfoShareCIFSContAvailableEna OBJECT-TYPE
			SYNTAX Unsigned32
			MAX-ACCESS read-only
			STATUS current
			DESCRIPTION
				"Whether failover is enabled
				0: No
				1: Yes"
			::= { hwInfoShareCIFSEntry 8 }

		
		-- 1.3.6.1.4.1.34774.4.1.23.7.3
		hwInfoSharePermsNFSTable OBJECT-TYPE
			SYNTAX SEQUENCE OF HwInfoSharePermsNFSEntry
			MAX-ACCESS not-accessible
			STATUS current
			DESCRIPTION
				"This table is used to check the NFS share permission of a device."
			::= { hwNasInfo 3 }

		
		-- 1.3.6.1.4.1.34774.4.1.23.7.3.1
		hwInfoSharePermsNFSEntry OBJECT-TYPE
			SYNTAX HwInfoSharePermsNFSEntry
			MAX-ACCESS not-accessible
			STATUS current
			DESCRIPTION
				"A table containing the part component."
			INDEX { hwInfoSharePermsNFSID }
			::= { hwInfoSharePermsNFSTable 1 }

		
		HwInfoSharePermsNFSEntry ::=
			SEQUENCE { 
				hwInfoSharePermsNFSID
					OCTET STRING,
				hwInfoSharePermsNFSAccessName
					OCTET STRING,
				hwInfoSharePermsNFSShareID
					OCTET STRING,
				hwInfoSharePermsNFSAccessType
					Unsigned32,
				hwInfoSharePermsNFSSyncEnabled
					Unsigned32,
				hwInfoSharePermsNFSAllSquashEna
					Unsigned32,
				hwInfoSharePermsNFSRootSquashEna
					Unsigned32
			 }

		-- 1.3.6.1.4.1.34774.4.1.23.7.3.1.1
		hwInfoSharePermsNFSID OBJECT-TYPE
			SYNTAX OCTET STRING
			MAX-ACCESS read-only
			STATUS current
			DESCRIPTION
				"Object ID, table index."
			::= { hwInfoSharePermsNFSEntry 1 }

		
		-- 1.3.6.1.4.1.34774.4.1.23.7.3.1.2
		hwInfoSharePermsNFSAccessName OBJECT-TYPE
			SYNTAX OCTET STRING
			MAX-ACCESS read-only
			STATUS current
			DESCRIPTION
				"Access name."
			::= { hwInfoSharePermsNFSEntry 2 }

		
		-- 1.3.6.1.4.1.34774.4.1.23.7.3.1.3
		hwInfoSharePermsNFSShareID OBJECT-TYPE
			SYNTAX OCTET STRING
			MAX-ACCESS read-only
			STATUS current
			DESCRIPTION
				"Share ID"
			::= { hwInfoSharePermsNFSEntry 3 }

		
		-- 1.3.6.1.4.1.34774.4.1.23.7.3.1.4
		hwInfoSharePermsNFSAccessType OBJECT-TYPE
			SYNTAX Unsigned32
			MAX-ACCESS read-only
			STATUS current
			DESCRIPTION
				"Access type
				0: read-only
				1: read and write
				4: read and write but cannot be deleted or renamed, supported by massive storage only)"
			::= { hwInfoSharePermsNFSEntry 4 }

		
		-- 1.3.6.1.4.1.34774.4.1.23.7.3.1.5
		hwInfoSharePermsNFSSyncEnabled OBJECT-TYPE
			SYNTAX Unsigned32
			MAX-ACCESS read-only
			STATUS current
			DESCRIPTION
				"Synchronization switch
				0: Data is synchronized
				1: Data is not synchronized"
			::= { hwInfoSharePermsNFSEntry 5 }

		
		-- 1.3.6.1.4.1.34774.4.1.23.7.3.1.6
		hwInfoSharePermsNFSAllSquashEna OBJECT-TYPE
			SYNTAX Unsigned32
			MAX-ACCESS read-only
			STATUS current
			DESCRIPTION
				"Whether the GID and UID of the shared directory are mapped as anonymous users
				0: yes
				1: no"
			::= { hwInfoSharePermsNFSEntry 6 }

		
		-- 1.3.6.1.4.1.34774.4.1.23.7.3.1.7
		hwInfoSharePermsNFSRootSquashEna OBJECT-TYPE
			SYNTAX Unsigned32
			MAX-ACCESS read-only
			STATUS current
			DESCRIPTION
				"Permission squash of user root
				0: rootSquash
				1: no rootSquash"
			::= { hwInfoSharePermsNFSEntry 7 }

		
		-- 1.3.6.1.4.1.34774.4.1.23.7.4
		hwInfoSharePermsCIFSTable OBJECT-TYPE
			SYNTAX SEQUENCE OF HwInfoSharePermsCIFSEntry
			MAX-ACCESS not-accessible
			STATUS current
			DESCRIPTION
				"This table is used to check the CIFS share permission of a device."
			::= { hwNasInfo 4 }

		
		-- 1.3.6.1.4.1.34774.4.1.23.7.4.1
		hwInfoSharePermsCIFSEntry OBJECT-TYPE
			SYNTAX HwInfoSharePermsCIFSEntry
			MAX-ACCESS not-accessible
			STATUS current
			DESCRIPTION
				"A table containing the part component."
			INDEX { hwInfoSharePermsCIFSID }
			::= { hwInfoSharePermsCIFSTable 1 }

		
		HwInfoSharePermsCIFSEntry ::=
			SEQUENCE { 
				hwInfoSharePermsCIFSID
					OCTET STRING,
				hwInfoSharePermsCIFSAccessName
					OCTET STRING,
				hwInfoSharePermsCIFSShareID
					OCTET STRING,
				hwInfoSharePermsCIFSDomainType
					Unsigned32,
				hwInfoSharePermsCIFSPermsType
					Unsigned32
			 }

		-- 1.3.6.1.4.1.34774.4.1.23.7.4.1.1
		hwInfoSharePermsCIFSID OBJECT-TYPE
			SYNTAX OCTET STRING
			MAX-ACCESS read-only
			STATUS current
			DESCRIPTION
				"Object ID, table index."
			::= { hwInfoSharePermsCIFSEntry 1 }

		
		-- 1.3.6.1.4.1.34774.4.1.23.7.4.1.2
		hwInfoSharePermsCIFSAccessName OBJECT-TYPE
			SYNTAX OCTET STRING
			MAX-ACCESS read-only
			STATUS current
			DESCRIPTION
				"Name of a user or user group."
			::= { hwInfoSharePermsCIFSEntry 2 }

		
		-- 1.3.6.1.4.1.34774.4.1.23.7.4.1.3
		hwInfoSharePermsCIFSShareID OBJECT-TYPE
			SYNTAX OCTET STRING
			MAX-ACCESS read-only
			STATUS current
			DESCRIPTION
				"Share ID"
			::= { hwInfoSharePermsCIFSEntry 3 }

		
		-- 1.3.6.1.4.1.34774.4.1.23.7.4.1.4
		hwInfoSharePermsCIFSDomainType OBJECT-TYPE
			SYNTAX Unsigned32
			MAX-ACCESS read-only
			STATUS current
			DESCRIPTION
				"Domain type
				0: AD
				1: LDAP
				2: local user"
			::= { hwInfoSharePermsCIFSEntry 4 }

		
		-- 1.3.6.1.4.1.34774.4.1.23.7.4.1.5
		hwInfoSharePermsCIFSPermsType OBJECT-TYPE
			SYNTAX Unsigned32
			MAX-ACCESS read-only
			STATUS current
			DESCRIPTION
				"Permission type
				0: read
				1: full control
				2: forbidden
				3: default
				4: read and write (cannot be deleted, renamed)
				5: read and write, being used in unified storage but not massive storage"
			::= { hwInfoSharePermsCIFSEntry 5 }

		
		-- 1.3.6.1.4.1.34774.4.1.23.7.5
		hwInfoLogicalPortTable OBJECT-TYPE
			SYNTAX SEQUENCE OF HwInfoLogicalPortEntry
			MAX-ACCESS not-accessible
			STATUS current
			DESCRIPTION
				"This table is used to check the logical port information about a device."
			::= { hwNasInfo 5 }

		
		-- 1.3.6.1.4.1.34774.4.1.23.7.5.1
		hwInfoLogicalPortEntry OBJECT-TYPE
			SYNTAX HwInfoLogicalPortEntry
			MAX-ACCESS not-accessible
			STATUS current
			DESCRIPTION
				"A table containing the part component."
			INDEX { hwInfoLogicalPortID }
			::= { hwInfoLogicalPortTable 1 }

		
		HwInfoLogicalPortEntry ::=
			SEQUENCE { 
				hwInfoLogicalPortID
					OCTET STRING,
				hwInfoLogicalPorttName
					OCTET STRING,
				hwInfoLogicalPortRunStatus
					Unsigned32,
				hwInfoLogicalPortIPv4Addr
					OCTET STRING,
				hwInfoLogicalPortIPv4Mask
					OCTET STRING,
				hwInfoLogicalPortIPv4Gateway
					OCTET STRING,
				hwInfoLogicalPortIPv6Addr
					OCTET STRING,
				hwInfoLogicalPortIPv6Mask
					OCTET STRING,
				hwInfoLogicalPortIPv6Gateway
					OCTET STRING,
				hwInfoLogicalPortRole
					Unsigned32,
				hwInfoLogicalPortSupportProt
					Unsigned32,
				hwInfoLogicalPortHomePortType
					Unsigned32,
				hwInfoLogicalPortHomePortID
					OCTET STRING,
				hwInfoLogicalPortOwnerCtrlID
					OCTET STRING,
				hwInfoLogicalPortCurrPortType
					Unsigned32,
				hwInfoLogicalPortCurrPortID
					OCTET STRING,
				hwInfoLogicalPortWorkCtrlID
					OCTET STRING,
				hwInfoLogicalPortActState
					Unsigned32,
				hwInfoLogicalPortAddrFamily
					Unsigned32,
				hwInfoLogicalPortIsPrivate
					Unsigned32,
				hwInfoLogicalPortFailOVGID
					OCTET STRING,
				hwInfoLogicalPortFailOVEnable
					Unsigned32,
				hwInfoLogicalPortFailBackMode
					Unsigned32,
				hwInfoLogicalPortFailOVGName
					OCTET STRING
			 }

		-- 1.3.6.1.4.1.34774.4.1.23.7.5.1.1
		hwInfoLogicalPortID OBJECT-TYPE
			SYNTAX OCTET STRING
			MAX-ACCESS read-only
			STATUS current
			DESCRIPTION
				"Object ID, table index."
			::= { hwInfoLogicalPortEntry 1 }

		
		-- 1.3.6.1.4.1.34774.4.1.23.7.5.1.2
		hwInfoLogicalPorttName OBJECT-TYPE
			SYNTAX OCTET STRING
			MAX-ACCESS read-only
			STATUS current
			DESCRIPTION
				"Object name"
			::= { hwInfoLogicalPortEntry 2 }

		
		-- 1.3.6.1.4.1.34774.4.1.23.7.5.1.3
		hwInfoLogicalPortRunStatus OBJECT-TYPE
			SYNTAX Unsigned32
			MAX-ACCESS read-only
			STATUS current
			DESCRIPTION
				"Operating status for details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoLogicalPortEntry 3 }

		
		-- 1.3.6.1.4.1.34774.4.1.23.7.5.1.4
		hwInfoLogicalPortIPv4Addr OBJECT-TYPE
			SYNTAX OCTET STRING
			MAX-ACCESS read-only
			STATUS current
			DESCRIPTION
				"IPv4 address"
			::= { hwInfoLogicalPortEntry 4 }

		
		-- 1.3.6.1.4.1.34774.4.1.23.7.5.1.5
		hwInfoLogicalPortIPv4Mask OBJECT-TYPE
			SYNTAX OCTET STRING
			MAX-ACCESS read-only
			STATUS current
			DESCRIPTION
				"IPv4 mask"
			::= { hwInfoLogicalPortEntry 5 }

		
		-- 1.3.6.1.4.1.34774.4.1.23.7.5.1.6
		hwInfoLogicalPortIPv4Gateway OBJECT-TYPE
			SYNTAX OCTET STRING
			MAX-ACCESS read-only
			STATUS current
			DESCRIPTION
				"IPv4 gateway"
			::= { hwInfoLogicalPortEntry 6 }

		
		-- 1.3.6.1.4.1.34774.4.1.23.7.5.1.7
		hwInfoLogicalPortIPv6Addr OBJECT-TYPE
			SYNTAX OCTET STRING
			MAX-ACCESS read-only
			STATUS current
			DESCRIPTION
				"IPv6 address"
			::= { hwInfoLogicalPortEntry 7 }

		
		-- 1.3.6.1.4.1.34774.4.1.23.7.5.1.8
		hwInfoLogicalPortIPv6Mask OBJECT-TYPE
			SYNTAX OCTET STRING
			MAX-ACCESS read-only
			STATUS current
			DESCRIPTION
				"IPv6 mask"
			::= { hwInfoLogicalPortEntry 8 }

		
		-- 1.3.6.1.4.1.34774.4.1.23.7.5.1.9
		hwInfoLogicalPortIPv6Gateway OBJECT-TYPE
			SYNTAX OCTET STRING
			MAX-ACCESS read-only
			STATUS current
			DESCRIPTION
				"IPv6 gateway"
			::= { hwInfoLogicalPortEntry 9 }

		
		-- 1.3.6.1.4.1.34774.4.1.23.7.5.1.10
		hwInfoLogicalPortRole OBJECT-TYPE
			SYNTAX Unsigned32
			MAX-ACCESS read-only
			STATUS current
			DESCRIPTION
				"Role of the logical port
				0: unknown
				1: management
				2: service
				3: all"
			::= { hwInfoLogicalPortEntry 10 }

		
		-- 1.3.6.1.4.1.34774.4.1.23.7.5.1.11
		hwInfoLogicalPortSupportProt OBJECT-TYPE
			SYNTAX Unsigned32
			MAX-ACCESS read-only
			STATUS current
			DESCRIPTION
				"Protocol:
				0: none
				1: NFS
				2: CIFS
				3: NFS + CIFS
				4: iSCSI
				8: FC/FCoE
				16: HTTPS
				32: NDMP
				35: NFS+CIFS+NDMP
				51: HTTPS+NFS+CIFS+NDMP"
			::= { hwInfoLogicalPortEntry 11 }

		
		-- 1.3.6.1.4.1.34774.4.1.23.7.5.1.12
		hwInfoLogicalPortHomePortType OBJECT-TYPE
			SYNTAX Unsigned32
			MAX-ACCESS read-only
			STATUS current
			DESCRIPTION
				"Type of the parent port:
				1: ETH
				2: FC
				3: FCoE
				4: SAS
				5: PCIe
				6: IB
				7: bond
				8: VLAN
				9: LIF"
			::= { hwInfoLogicalPortEntry 12 }

		
		-- 1.3.6.1.4.1.34774.4.1.23.7.5.1.13
		hwInfoLogicalPortHomePortID OBJECT-TYPE
			SYNTAX OCTET STRING
			MAX-ACCESS read-only
			STATUS current
			DESCRIPTION
				"ID of the parent port."
			::= { hwInfoLogicalPortEntry 13 }

		
		-- 1.3.6.1.4.1.34774.4.1.23.7.5.1.14
		hwInfoLogicalPortOwnerCtrlID OBJECT-TYPE
			SYNTAX OCTET STRING
			MAX-ACCESS read-only
			STATUS current
			DESCRIPTION
				"ID of the parent node."
			::= { hwInfoLogicalPortEntry 14 }

		
		-- 1.3.6.1.4.1.34774.4.1.23.7.5.1.15
		hwInfoLogicalPortCurrPortType OBJECT-TYPE
			SYNTAX Unsigned32
			MAX-ACCESS read-only
			STATUS current
			DESCRIPTION
				"Port type
				1: ETH
				2: FC
				3: FCoE
				4: SAS
				5: PCIe
				6: IB
				7: bond
				8: VLAN
				9: LIF"
			::= { hwInfoLogicalPortEntry 15 }

		
		-- 1.3.6.1.4.1.34774.4.1.23.7.5.1.16
		hwInfoLogicalPortCurrPortID OBJECT-TYPE
			SYNTAX OCTET STRING
			MAX-ACCESS read-only
			STATUS current
			DESCRIPTION
				"Port ID"
			::= { hwInfoLogicalPortEntry 16 }

		
		-- 1.3.6.1.4.1.34774.4.1.23.7.5.1.17
		hwInfoLogicalPortWorkCtrlID OBJECT-TYPE
			SYNTAX OCTET STRING
			MAX-ACCESS read-only
			STATUS current
			DESCRIPTION
				"Node ID"
			::= { hwInfoLogicalPortEntry 17 }

		
		-- 1.3.6.1.4.1.34774.4.1.23.7.5.1.18
		hwInfoLogicalPortActState OBJECT-TYPE
			SYNTAX Unsigned32
			MAX-ACCESS read-only
			STATUS current
			DESCRIPTION
				"Active or not
				0: No
				1: Yes"
			::= { hwInfoLogicalPortEntry 18 }

		
		-- 1.3.6.1.4.1.34774.4.1.23.7.5.1.19
		hwInfoLogicalPortAddrFamily OBJECT-TYPE
			SYNTAX Unsigned32
			MAX-ACCESS read-only
			STATUS current
			DESCRIPTION
				"Address type
				0: IPv4
				1: IPv6"
			::= { hwInfoLogicalPortEntry 19 }

		
		-- 1.3.6.1.4.1.34774.4.1.23.7.5.1.20
		hwInfoLogicalPortIsPrivate OBJECT-TYPE
			SYNTAX Unsigned32
			MAX-ACCESS read-only
			STATUS current
			DESCRIPTION
				"Configurable or not
				0: No
				1: Yes"
			::= { hwInfoLogicalPortEntry 20 }

		
		-- 1.3.6.1.4.1.34774.4.1.23.7.5.1.21
		hwInfoLogicalPortFailOVGID OBJECT-TYPE
			SYNTAX OCTET STRING
			MAX-ACCESS read-only
			STATUS current
			DESCRIPTION
				"ID of the owning failover group."
			::= { hwInfoLogicalPortEntry 21 }

		
		-- 1.3.6.1.4.1.34774.4.1.23.7.5.1.22
		hwInfoLogicalPortFailOVEnable OBJECT-TYPE
			SYNTAX Unsigned32
			MAX-ACCESS read-only
			STATUS current
			DESCRIPTION
				"Whether failover is enabled
				0: No
				1: Yes"
			::= { hwInfoLogicalPortEntry 22 }

		
		-- 1.3.6.1.4.1.34774.4.1.23.7.5.1.23
		hwInfoLogicalPortFailBackMode OBJECT-TYPE
			SYNTAX Unsigned32
			MAX-ACCESS read-only
			STATUS current
			DESCRIPTION
				"Failover mode:
				1: manual
				2: automatic"
			::= { hwInfoLogicalPortEntry 23 }

		
		-- 1.3.6.1.4.1.34774.4.1.23.7.5.1.24
		hwInfoLogicalPortFailOVGName OBJECT-TYPE
			SYNTAX OCTET STRING
			MAX-ACCESS read-only
			STATUS current
			DESCRIPTION
				"Name of the owning failover group."
			::= { hwInfoLogicalPortEntry 24 }

		
		-- 1.3.6.1.4.1.34774.4.1.23.7.6
		hwInfoFileSysTable OBJECT-TYPE
			SYNTAX SEQUENCE OF HwInfoFileSysEntry
			MAX-ACCESS not-accessible
			STATUS current
			DESCRIPTION
				"This table is used to check the file system information about a device."
			::= { hwNasInfo 6 }

		
		-- 1.3.6.1.4.1.34774.4.1.23.7.6.1
		hwInfoFileSysEntry OBJECT-TYPE
			SYNTAX HwInfoFileSysEntry
			MAX-ACCESS not-accessible
			STATUS current
			DESCRIPTION
				"A table containing the part component."
			INDEX { hwInfoFileSysID }
			::= { hwInfoFileSysTable 1 }

		
		HwInfoFileSysEntry ::=
			SEQUENCE { 
				hwInfoFileSysID
					OCTET STRING,
				hwInfoFileSysName
					OCTET STRING,
				hwInfoFileSysHeathStatus
					Unsigned32,
				hwInfoFileSysRunningStatus
					Unsigned32,
				hwInfoFileSysDescription
					OCTET STRING,
				hwInfoFileSysSubType
					Unsigned32,
				hwInfoFileSysAllocType
					Unsigned32,
				hwInfoFileSysCapacity
					Counter64,
				hwInfoFileSysSnapshotReservePer
					Unsigned32,
				hwInfoFileSysSnapshotUseCapacity
					Counter64,
				hwInfoFileSysSectorSize
					Unsigned32,
				hwInfoFileSysOwningContrller
					OCTET STRING,
				hwInfoFileSysWorkingController
					OCTET STRING,
				hwInfoFileSysIOPriotiry
					Unsigned32,
				hwInfoFileSysEnableCompression
					Unsigned32,
				hwInfoFileSysCompression
					Unsigned32,
				hwInfoFileSysIsShowSnapDir
					Unsigned32,
				hwInfoFileSysAvailableCapacity
					Counter64,
				hwInfoFileSysAvAndAllcCapRatio
					Unsigned32,
				hwInfoFileSysSCCachedSize
					Counter64,
				hwInfoFileSysSCHitRage
					Unsigned32,
				hwInfoFileSysCompressSavedRatio
					Unsigned32
			 }

		-- 1.3.6.1.4.1.34774.4.1.23.7.6.1.1
		hwInfoFileSysID OBJECT-TYPE
			SYNTAX OCTET STRING
			MAX-ACCESS read-only
			STATUS current
			DESCRIPTION
				"Object ID, table index."
			::= { hwInfoFileSysEntry 1 }

		
		-- 1.3.6.1.4.1.34774.4.1.23.7.6.1.2
		hwInfoFileSysName OBJECT-TYPE
			SYNTAX OCTET STRING
			MAX-ACCESS read-only
			STATUS current
			DESCRIPTION
				"File system name."
			::= { hwInfoFileSysEntry 2 }

		
		-- 1.3.6.1.4.1.34774.4.1.23.7.6.1.3
		hwInfoFileSysHeathStatus OBJECT-TYPE
			SYNTAX Unsigned32
			MAX-ACCESS read-only
			STATUS current
			DESCRIPTION
				"Health status, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoFileSysEntry 3 }

		
		-- 1.3.6.1.4.1.34774.4.1.23.7.6.1.4
		hwInfoFileSysRunningStatus OBJECT-TYPE
			SYNTAX Unsigned32
			MAX-ACCESS read-only
			STATUS current
			DESCRIPTION
				"Operating status, for details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoFileSysEntry 4 }

		
		-- 1.3.6.1.4.1.34774.4.1.23.7.6.1.5
		hwInfoFileSysDescription OBJECT-TYPE
			SYNTAX OCTET STRING
			MAX-ACCESS read-only
			STATUS current
			DESCRIPTION
				"File system Description."
			::= { hwInfoFileSysEntry 5 }

		
		-- 1.3.6.1.4.1.34774.4.1.23.7.6.1.6
		hwInfoFileSysSubType OBJECT-TYPE
			SYNTAX Unsigned32
			MAX-ACCESS read-only
			STATUS current
			DESCRIPTION
				"Subtype:
				0: Normal
				1: WORM"
			::= { hwInfoFileSysEntry 6 }

		
		-- 1.3.6.1.4.1.34774.4.1.23.7.6.1.7
		hwInfoFileSysAllocType OBJECT-TYPE
			SYNTAX Unsigned32
			MAX-ACCESS read-only
			STATUS current
			DESCRIPTION
				"Space allocation type:
				0: thick
				1: thin"
			::= { hwInfoFileSysEntry 7 }

		
		-- 1.3.6.1.4.1.34774.4.1.23.7.6.1.8
		hwInfoFileSysCapacity OBJECT-TYPE
			SYNTAX Counter64
			MAX-ACCESS read-only
			STATUS current
			DESCRIPTION
				"Configured capacity (unit: MB)."
			::= { hwInfoFileSysEntry 8 }

		
		-- 1.3.6.1.4.1.34774.4.1.23.7.6.1.9
		hwInfoFileSysSnapshotReservePer OBJECT-TYPE
			SYNTAX Unsigned32
			MAX-ACCESS read-only
			STATUS current
			DESCRIPTION
				"Space reserved for snapshot (unit: %)."
			::= { hwInfoFileSysEntry 9 }

		
		-- 1.3.6.1.4.1.34774.4.1.23.7.6.1.10
		hwInfoFileSysSnapshotUseCapacity OBJECT-TYPE
			SYNTAX Counter64
			MAX-ACCESS read-only
			STATUS current
			DESCRIPTION
				"Capacity used by snapshots (unit: MB)."
			::= { hwInfoFileSysEntry 10 }

		
		-- 1.3.6.1.4.1.34774.4.1.23.7.6.1.11
		hwInfoFileSysSectorSize OBJECT-TYPE
			SYNTAX Unsigned32
			MAX-ACCESS read-only
			STATUS current
			DESCRIPTION
				"Block size (unit: byte)."
			::= { hwInfoFileSysEntry 11 }

		
		-- 1.3.6.1.4.1.34774.4.1.23.7.6.1.12
		hwInfoFileSysOwningContrller OBJECT-TYPE
			SYNTAX OCTET STRING
			MAX-ACCESS read-only
			STATUS current
			DESCRIPTION
				"Owning controller"
			::= { hwInfoFileSysEntry 12 }

		
		-- 1.3.6.1.4.1.34774.4.1.23.7.6.1.13
		hwInfoFileSysWorkingController OBJECT-TYPE
			SYNTAX OCTET STRING
			MAX-ACCESS read-only
			STATUS current
			DESCRIPTION
				"Working controller"
			::= { hwInfoFileSysEntry 13 }

		
		-- 1.3.6.1.4.1.34774.4.1.23.7.6.1.14
		hwInfoFileSysIOPriotiry OBJECT-TYPE
			SYNTAX Unsigned32
			MAX-ACCESS read-only
			STATUS current
			DESCRIPTION
				"File system I/O priority:
				1: low
				2: medium
				3: high"
			::= { hwInfoFileSysEntry 14 }

		
		-- 1.3.6.1.4.1.34774.4.1.23.7.6.1.15
		hwInfoFileSysEnableCompression OBJECT-TYPE
			SYNTAX Unsigned32
			MAX-ACCESS read-only
			STATUS current
			DESCRIPTION
				"Whether compression is enabled
				0: No
				1: Yes"
			::= { hwInfoFileSysEntry 15 }

		
		-- 1.3.6.1.4.1.34774.4.1.23.7.6.1.16
		hwInfoFileSysCompression OBJECT-TYPE
			SYNTAX Unsigned32
			MAX-ACCESS read-only
			STATUS current
			DESCRIPTION
				"Compression algorithm:
				0: fast
				1: slow"
			::= { hwInfoFileSysEntry 16 }

		
		-- 1.3.6.1.4.1.34774.4.1.23.7.6.1.17
		hwInfoFileSysIsShowSnapDir OBJECT-TYPE
			SYNTAX Unsigned32
			MAX-ACCESS read-only
			STATUS current
			DESCRIPTION
				"Snapshot directory visible or not
				0: No
				1: Yes"
			::= { hwInfoFileSysEntry 17 }

		
		-- 1.3.6.1.4.1.34774.4.1.23.7.6.1.18
		hwInfoFileSysAvailableCapacity OBJECT-TYPE
			SYNTAX Counter64
			MAX-ACCESS read-only
			STATUS current
			DESCRIPTION
				"Available file system capacity (unit: MB)."
			::= { hwInfoFileSysEntry 18 }

		
		-- 1.3.6.1.4.1.34774.4.1.23.7.6.1.19
		hwInfoFileSysAvAndAllcCapRatio OBJECT-TYPE
			SYNTAX Unsigned32
			MAX-ACCESS read-only
			STATUS current
			DESCRIPTION
				"Percentage of available file system used capacity to initial capacity."
			::= { hwInfoFileSysEntry 19 }

		
		-- 1.3.6.1.4.1.34774.4.1.23.7.6.1.20
		hwInfoFileSysSCCachedSize OBJECT-TYPE
			SYNTAX Counter64
			MAX-ACCESS read-only
			STATUS current
			DESCRIPTION
				"SmartCache size (unit: KB)."
			::= { hwInfoFileSysEntry 20 }

		
		-- 1.3.6.1.4.1.34774.4.1.23.7.6.1.21
		hwInfoFileSysSCHitRage OBJECT-TYPE
			SYNTAX Unsigned32
			MAX-ACCESS read-only
			STATUS current
			DESCRIPTION
				"SmartCache hit ratio (unit: %)."
			::= { hwInfoFileSysEntry 21 }

		
		-- 1.3.6.1.4.1.34774.4.1.23.7.6.1.22
		hwInfoFileSysCompressSavedRatio OBJECT-TYPE
			SYNTAX Unsigned32
			MAX-ACCESS read-only
			STATUS current
			DESCRIPTION
				"Compression ratio (unit: %)."
			::= { hwInfoFileSysEntry 22 }

		
--   1.6
-- 1.6
		isoConformance OBJECT IDENTIFIER ::= { iso 6 }

		
--   1.6.1
-- 1.6.1
		isoGroups OBJECT IDENTIFIER ::= { isoConformance 1 }

		
--   1.6.1.1
-- 1.6.1.1
		currentObjectGroup OBJECT-GROUP
			OBJECTS { hwInfoShareCIFSContAvailableEna, hwInfoSharePermsNFSID, hwInfoSharePermsNFSAccessName, hwInfoSharePermsNFSShareID, hwInfoSharePermsNFSAccessType, 
				hwInfoSharePermsNFSSyncEnabled, hwInfoSharePermsNFSAllSquashEna, hwInfoSharePermsNFSRootSquashEna, hwInfoSharePermsCIFSID, hwInfoSharePermsCIFSAccessName, 
				hwInfoSharePermsCIFSShareID, hwInfoSharePermsCIFSDomainType, hwInfoSharePermsCIFSPermsType, hwInfoLogicalPortSupportProt, hwInfoLogicalPortHomePortType, 
				hwInfoLogicalPortFailBackMode, hwInfoFileSysID, hwInfoFileSysName, hwInfoFileSysHeathStatus, hwInfoFileSysRunningStatus, 
				hwInfoFileSysDescription, hwInfoFileSysSubType, hwInfoFileSysAllocType, hwInfoFileSysCapacity, hwInfoFileSysSnapshotReservePer, 
				hwInfoFileSysSnapshotUseCapacity, hwInfoFileSysSectorSize, hwInfoFileSysOwningContrller, hwInfoFileSysWorkingController, hwInfoFileSysIOPriotiry, 
				hwInfoFileSysEnableCompression, hwInfoFileSysCompression, hwInfoFileSysIsShowSnapDir, hwInfoFileSysAvailableCapacity, hwInfoFileSysAvAndAllcCapRatio, 
				hwInfoFileSysSCCachedSize, hwInfoFileSysSCHitRage, hwInfoFileSysCompressSavedRatio, hwInfoShareNFSShareID, hwInfoShareNFSFileSystemID, 
				hwInfoShareNFSDescription, hwInfoShareCIFSID, hwInfoShareCIFSFileSystemID, hwInfoShareCIFSDescription, hwInfoLogicalPortID, 
				hwInfoShareNFSLocalPath, hwInfoShareCIFSName, hwInfoShareCIFSLocalPath, hwInfoShareCIFSOplockEnabled, hwInfoShareCIFSNotifyEnabled, 
				hwInfoLogicalPorttName, hwInfoLogicalPortRunStatus, hwInfoLogicalPortIPv4Addr, hwInfoLogicalPortIPv4Mask, hwInfoLogicalPortIPv4Gateway, 
				hwInfoLogicalPortIPv6Addr, hwInfoLogicalPortIPv6Mask, hwInfoLogicalPortIPv6Gateway, hwInfoLogicalPortRole, hwInfoLogicalPortHomePortID, 
				hwInfoLogicalPortOwnerCtrlID, hwInfoLogicalPortCurrPortType, hwInfoLogicalPortCurrPortID, hwInfoLogicalPortWorkCtrlID, hwInfoLogicalPortActState, 
				hwInfoLogicalPortAddrFamily, hwInfoLogicalPortIsPrivate, hwInfoLogicalPortFailOVGID, hwInfoLogicalPortFailOVEnable, hwInfoLogicalPortFailOVGName
				 }
			STATUS current
			DESCRIPTION 
				"Enter the description of the created OBJECT-GROUP."
			::= { isoGroups 1 }

		
--   1.6.2
-- 1.6.2
		isoCompliances OBJECT IDENTIFIER ::= { isoConformance 2 }

		
--    this module
-- 1.6.2.1
-- this module
-- 1.6.2.1
-- this module
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- HUAWEI-STORAGE-NAS-MIB.mib
--
