-- OPTIX-RTN-DEVICE-MNG-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-DEVICE-MNG-MIB DEFINITIONS ::= BEGIN
    IMPORTS
        optixRtnBoardID,optixRtnSubCardID,optixRtnPortID
            FROM OPTIX-RTN-IFBOARD-ATTRIB-MIB
        optixProvisionRtn
            FROM OPTIX-OID-MIB
        MacAddress,RowStatus,TEXTUAL-CONVENTION
            FROM SNMPv2-TC
        OBJECT-GROUP,MODULE-COMPLIANCE
            FROM SNMPv2-CONF
        Unsigned32,OBJECT-TYPE,MODULE-IDENTITY,NOTIFICATION-TYPE
            FROM SNMPv2-SMI
        optixRtnIndex1,optixRtnIndex2,optixRtnIndex3,optixRtnIndex4,optixRtnIFPortlist
            FROM OPTIX-RTN-GENNERAL-MIB
        ;

    optixRtnDeviceMng MODULE-IDENTITY
        LAST-UPDATED "201404211418Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to manage device"
        REVISION "201404211418Z"
        DESCRIPTION
            "NA"
        ::={ optixProvisionRtn 7 }

    -- 1.3.6.1.4.1.2011.2.25.4.40.7.1
    optixRtnDbRestoreMgr OBJECT IDENTIFIER ::= { optixRtnDeviceMng 1 }

    -- 1.3.6.1.4.1.2011.2.25.4.40.7.1.1
    optixRtnNeDbRestoreBoardId OBJECT-TYPE
        SYNTAX Unsigned32
        MAX-ACCESS read-write
        STATUS current
        DESCRIPTION
            "Board ID"
        DEFVAL{ 0 }
        ::= { optixRtnDbRestoreMgr 1 }

    -- 1.3.6.1.4.1.2011.2.25.4.40.7.1.2
    optixRtnNeDbRestoreSubId OBJECT-TYPE
        SYNTAX Unsigned32
        MAX-ACCESS read-write
        STATUS current
        DESCRIPTION
            "Subboard ID"
        ::= { optixRtnDbRestoreMgr 2 }

    -- 1.3.6.1.4.1.2011.2.25.4.40.7.1.3
    optixRtnNeDbRestorePortId OBJECT-TYPE
        SYNTAX Unsigned32
        MAX-ACCESS read-write
        STATUS current
        DESCRIPTION
            "Port ID"
        ::= { optixRtnDbRestoreMgr 3 }

    -- 1.3.6.1.4.1.2011.2.25.4.40.7.2
    optixRtnNeRecoverMgr OBJECT IDENTIFIER ::= { optixRtnDeviceMng 2 }

    -- 1.3.6.1.4.1.2011.2.25.4.40.7.2.1
    optixRtnNeRecoverEnableStatus OBJECT-TYPE
        SYNTAX INTEGER
        {
            disable(0),
            enable(1)
        }
        MAX-ACCESS read-write
        STATUS current
        DESCRIPTION
            "NE recovery enable status"
        DEFVAL{ 0 }
        ::= { optixRtnNeRecoverMgr 1 }

    -- 1.3.6.1.4.1.2011.2.25.4.40.7.2.2
    optixRtnNeRecoverPeriod OBJECT-TYPE
        SYNTAX INTEGER
        {
            min30(30),
            min60(60),
            min90(90),
            min120(120)
        }
        MAX-ACCESS read-write
        STATUS current
        DESCRIPTION
            "NE recovery period"
        DEFVAL{ 30 }
        ::= { optixRtnNeRecoverMgr 2 }

    -- 1.3.6.1.4.1.2011.2.25.4.40.7.3
    optixDbRestoreTrapCommon OBJECT IDENTIFIER ::= { optixRtnDeviceMng 3 }

    -- 1.3.6.1.4.1.2011.2.25.4.40.7.3.1
    optixRptRtnDbRestoreExtEventOld OBJECT IDENTIFIER ::= { optixDbRestoreTrapCommon 1 }

    -- 1.3.6.1.4.1.2011.2.25.4.40.7.3.1.1
    optixRtnDbRestoreExtBidOld OBJECT-TYPE
        SYNTAX Unsigned32 (1..255)
        MAX-ACCESS accessible-for-notify
        STATUS deprecated
        DESCRIPTION
            "Board ID"
        ::= { optixRptRtnDbRestoreExtEventOld 1 }

    -- 1.3.6.1.4.1.2011.2.25.4.40.7.3.1.2
    optixRtnDbRestoreExtSubIdOld OBJECT-TYPE
        SYNTAX Unsigned32 (1..255)
        MAX-ACCESS accessible-for-notify
        STATUS deprecated
        DESCRIPTION
            "Subboard ID"
        ::= { optixRptRtnDbRestoreExtEventOld 2 }

    -- 1.3.6.1.4.1.2011.2.25.4.40.7.3.1.3
    optixRtnDbRestoreExtPidOld OBJECT-TYPE
        SYNTAX Unsigned32
        MAX-ACCESS accessible-for-notify
        STATUS deprecated
        DESCRIPTION
            "Port ID"
        ::= { optixRptRtnDbRestoreExtEventOld 3 }

    -- 1.3.6.1.4.1.2011.2.25.4.40.7.3.1.4
    optixRtnSysParamRestoreExtResultOld OBJECT-TYPE
        SYNTAX INTEGER
        {
            success(0),
            failure(1)
        }
        MAX-ACCESS accessible-for-notify
        STATUS deprecated
        DESCRIPTION
            "System parameter restoration result"
        ::= { optixRptRtnDbRestoreExtEventOld 4 }

    -- 1.3.6.1.4.1.2011.2.25.4.40.7.3.1.5
    optixRtnLicenseExtResultOld OBJECT-TYPE
        SYNTAX INTEGER
        {
            success(0),
            failure(1)
        }
        MAX-ACCESS accessible-for-notify
        STATUS deprecated
        DESCRIPTION
            "License restoration result"
        ::= { optixRptRtnDbRestoreExtEventOld 5 }
		
    -- 1.3.6.1.4.1.2011.2.25.4.40.7.3.1.6
    optixRtnDbRestoreExtResultOld OBJECT-TYPE
        SYNTAX INTEGER
        {
            success(0),
            failure(1)
        }
        MAX-ACCESS accessible-for-notify
        STATUS deprecated
        DESCRIPTION
            "Database restoration result"
        ::= { optixRptRtnDbRestoreExtEventOld 6 }

-- 1.3.6.1.4.1.2011.2.25.4.40.7.3.2
    optixRptRtnDbRestoreExtEvent OBJECT IDENTIFIER ::= { optixDbRestoreTrapCommon 2 }

    -- 1.3.6.1.4.1.2011.2.25.4.40.7.3.2.1
    optixRtnDbRestoreExtBid OBJECT-TYPE
        SYNTAX Unsigned32 (1..255)
        MAX-ACCESS accessible-for-notify
        STATUS current
        DESCRIPTION
            "Board ID"
        ::= { optixRptRtnDbRestoreExtEvent 1 }

    -- 1.3.6.1.4.1.2011.2.25.4.40.7.3.2.2
    optixRtnDbRestoreExtSubId OBJECT-TYPE
        SYNTAX Unsigned32 (1..255)
        MAX-ACCESS accessible-for-notify
        STATUS current
        DESCRIPTION
            "Subboard ID"
        ::= { optixRptRtnDbRestoreExtEvent 2 }

    -- 1.3.6.1.4.1.2011.2.25.4.40.7.3.2.3
    optixRtnDbRestoreExtPid OBJECT-TYPE
        SYNTAX Unsigned32
        MAX-ACCESS accessible-for-notify
        STATUS current
        DESCRIPTION
            "Port ID"
        ::= { optixRptRtnDbRestoreExtEvent 3 }

    -- 1.3.6.1.4.1.2011.2.25.4.40.7.3.2.4
    optixRtnSysParamRestoreExtResult OBJECT-TYPE
        SYNTAX INTEGER
        {
            success(0),
            failure(1)
        }
        MAX-ACCESS accessible-for-notify
        STATUS current
        DESCRIPTION
            "System parameter restoration result"
        ::= { optixRptRtnDbRestoreExtEvent 4 }

    -- 1.3.6.1.4.1.2011.2.25.4.40.7.3.2.5
    optixRtnLicenseExtResult OBJECT-TYPE
        SYNTAX INTEGER
        {
            success(0),
            failure(1)
        }
        MAX-ACCESS accessible-for-notify
        STATUS current
        DESCRIPTION
            "License restoration result"
        ::= { optixRptRtnDbRestoreExtEvent 5 }
		
    -- 1.3.6.1.4.1.2011.2.25.4.40.7.3.2.6
    optixRtnDbRestoreExtResult OBJECT-TYPE
        SYNTAX INTEGER
        {
            success(0),
            failure(1)
        }
        MAX-ACCESS accessible-for-notify
        STATUS current
        DESCRIPTION
            "Database restoration result"
        ::= { optixRptRtnDbRestoreExtEvent 6 }

    -- 1.3.6.1.4.1.2011.2.25.4.40.7.4
    optixRtnClkMgr OBJECT IDENTIFIER ::= { optixRtnDeviceMng 4 }

    -- 1.3.6.1.4.1.2011.2.25.4.40.7.4.1
    optixRtnClksyn OBJECT IDENTIFIER ::= { optixRtnClkMgr 1 }
    
    -- 1.3.6.1.4.1.2011.2.25.4.40.7.4.1.1
    optixRtnSynCtrlmode OBJECT-TYPE
	SYNTAX INTEGER
	{
		centralized(1),
		standalone(0)
	}
	MAX-ACCESS read-write
	STATUS current
	DESCRIPTION
		"SynCtrlmode"
	::= { optixRtnClksyn 1 }

    -- 1.3.6.1.4.1.2011.2.25.4.40.7.4.2
    optixRtnClkfiber  OBJECT IDENTIFIER ::= { optixRtnClkMgr 2 }
    
    -- 1.3.6.1.4.1.2011.2.25.4.40.7.4.2.1
    optixRtnFiberLength  OBJECT-TYPE
		SYNTAX Unsigned32
		MAX-ACCESS read-write
		STATUS current
		DESCRIPTION
			"FiberLength"
		::= { optixRtnClkfiber  1 }

    -- 1.3.6.1.4.1.2011.2.25.4.40.7.5
    optixRtnCCDPParaMgr OBJECT IDENTIFIER ::= { optixRtnDeviceMng 5 }

    -- 1.3.6.1.4.1.2011.2.25.4.40.7.5.1
    optixRtnCCDPTable OBJECT-TYPE
        SYNTAX SEQUENCE OF OptixRtnCCDPEntry
        MAX-ACCESS not-accessible
        STATUS current
        DESCRIPTION
            "Indicates the CCDP cascading port number table."
        ::= { optixRtnCCDPParaMgr 1 }

    -- 1.3.6.1.4.1.2011.2.25.4.40.7.5.1.1
    optixRtnCCDPEntry OBJECT-TYPE
        SYNTAX OptixRtnCCDPEntry
        MAX-ACCESS not-accessible
        STATUS current
        DESCRIPTION
            "CCDP ENTRY"
        INDEX{ optixRtnBoardID,optixRtnSubCardID,optixRtnPortID }
        ::= { optixRtnCCDPTable 1 }

    OptixRtnCCDPEntry ::=
        SEQUENCE {
            optixRtnCascadingPortId
                Unsigned32
        }

    -- 1.3.6.1.4.1.2011.2.25.4.40.7.5.1.1.2
    optixRtnCascadingPortId OBJECT-TYPE
        SYNTAX Unsigned32
        MAX-ACCESS read-write
        STATUS current
        DESCRIPTION
            "CCDP cascading port number"
        ::= { optixRtnCCDPEntry 2 }

    -- 1.3.6.1.4.1.2011.2.25.4.40.7.10
    optixRtnECC OBJECT IDENTIFIER ::= { optixRtnDeviceMng 10 }

    -- 1.3.6.1.4.1.2011.2.25.4.40.7.10.2
    optixRtnECCProtoIDTable OBJECT-TYPE
        SYNTAX SEQUENCE OF OptixRtnECCProtoIDEntry
        MAX-ACCESS not-accessible
        STATUS current
        DESCRIPTION
            "ProtoID Table"
        ::= { optixRtnECC 2 }

    -- 1.3.6.1.4.1.2011.2.25.4.40.7.10.2.1
    optixRtnECCProtoIDEntry OBJECT-TYPE
        SYNTAX OptixRtnECCProtoIDEntry
        MAX-ACCESS not-accessible
        STATUS current
        DESCRIPTION
            "ProtoID Entry"
        INDEX{ optixRtnECCBoardID,optixRtnECCPortID,optixRtnECCChanType }
        ::= { optixRtnECCProtoIDTable 1 }

    OptixRtnECCProtoIDEntry ::=
        SEQUENCE {
            optixRtnECCProtoIDChanType
                INTEGER,
            optixRtnECCProtoIDProtoID
                INTEGER,
            optixRtnECCProtoIDRowStatus
                RowStatus
        }

    -- 1.3.6.1.4.1.2011.2.25.4.40.7.10.2.1.1
    optixRtnECCProtoIDChanType OBJECT-TYPE
        SYNTAX INTEGER
        {
            d1d3(1),
            d4d12(2),
            d1d12(3),
            d1d1(7)
        }
        MAX-ACCESS read-create
        STATUS current
        DESCRIPTION
            "Chan Type"
        DEFVAL{ 1 }
        ::= { optixRtnECCProtoIDEntry 1 }

    -- 1.3.6.1.4.1.2011.2.25.4.40.7.10.2.1.2
    optixRtnECCProtoIDProtoID OBJECT-TYPE
        SYNTAX INTEGER
        {
            ip(1),
            hwecc(3),
            auto(7),
            l2dcn(8)
        }
        MAX-ACCESS read-create
        STATUS current
        DESCRIPTION
            "ProtoID"
        DEFVAL{ 1 }
        ::= { optixRtnECCProtoIDEntry 2 }

    -- 1.3.6.1.4.1.2011.2.25.4.40.7.10.2.1.255
    optixRtnECCProtoIDRowStatus OBJECT-TYPE
        SYNTAX RowStatus
        MAX-ACCESS read-create
        STATUS current
        DESCRIPTION
            "RowStatus"
        DEFVAL{ 255 }
        ::= { optixRtnECCProtoIDEntry 255 }

    -- 1.3.6.1.4.1.2011.2.25.4.40.7.10.4
    optixRtnECCPortStateTable OBJECT-TYPE
        SYNTAX SEQUENCE OF OptixRtnECCPortStateEntry
        MAX-ACCESS not-accessible
        STATUS current
        DESCRIPTION
            "PortState Table"
        ::= { optixRtnECC 4 }

    -- 1.3.6.1.4.1.2011.2.25.4.40.7.10.4.1
    optixRtnECCPortStateEntry OBJECT-TYPE
        SYNTAX OptixRtnECCPortStateEntry
        MAX-ACCESS not-accessible
        STATUS current
        DESCRIPTION
            "PortState  entry"
        INDEX{ optixRtnECCBoardID,optixRtnECCSubCard,optixRtnECCPortID,optixRtnECCChanType }
        ::= { optixRtnECCPortStateTable 1 }

    OptixRtnECCPortStateEntry ::=
        SEQUENCE {
            optixRtnECCOSPFPortSwitchState
                INTEGER,
            optixRtnECCOPQLSASwitchState
                INTEGER
        }

    -- 1.3.6.1.4.1.2011.2.25.4.40.7.10.4.1.1
    optixRtnECCOSPFPortSwitchState OBJECT-TYPE
        SYNTAX INTEGER
        {
            portenable(0),
            portdisable(1)
        }
        MAX-ACCESS read-write
        STATUS current
        DESCRIPTION
            "Port switch state"
        DEFVAL{ 0 }
        ::= { optixRtnECCPortStateEntry 1 }

    -- 1.3.6.1.4.1.2011.2.25.4.40.7.10.4.1.2
    optixRtnECCOPQLSASwitchState OBJECT-TYPE
        SYNTAX INTEGER
        {
            portenable(0),
            portdisable(1)
        }
        MAX-ACCESS read-write
        STATUS current
        DESCRIPTION
            "OPQL switch state"
        DEFVAL{ 0 }
        ::= { optixRtnECCPortStateEntry 2 }

    -- 1.3.6.1.4.1.2011.2.25.4.40.7.10.5
    optixRtnECCDCCPHYTable OBJECT-TYPE
        SYNTAX SEQUENCE OF OptixRtnECCDCCPHYEntry
        MAX-ACCESS not-accessible
        STATUS current
        DESCRIPTION
            "DCC PHY Table"
        ::= { optixRtnECC 5 }

    -- 1.3.6.1.4.1.2011.2.25.4.40.7.10.5.1
    optixRtnECCDCCPHYEntry OBJECT-TYPE
        SYNTAX OptixRtnECCDCCPHYEntry
        MAX-ACCESS not-accessible
        STATUS current
        DESCRIPTION
            "DCC PHY Entry"
        INDEX{ optixRtnECCBoardID,optixRtnECCPortID,optixRtnECCOHPType }
        ::= { optixRtnECCDCCPHYTable 1 }

    OptixRtnECCDCCPHYEntry ::=
        SEQUENCE {
            optixRtnECCDCCPHYBoardidDst
                Unsigned32,
            optixRtnECCDCCPHYPortidDst
                Unsigned32,
            optixRtnECCDCCPHYOHPTypeDst
                INTEGER,
            optixRtnECCDCCPHYRowStatus
                RowStatus
        }

    -- 1.3.6.1.4.1.2011.2.25.4.40.7.10.5.1.4
    optixRtnECCDCCPHYBoardidDst OBJECT-TYPE
        SYNTAX Unsigned32 (1..255)
        MAX-ACCESS read-create
        STATUS current
        DESCRIPTION
            "Board ID"
        DEFVAL{ 1 }
        ::= { optixRtnECCDCCPHYEntry 4 }

    -- 1.3.6.1.4.1.2011.2.25.4.40.7.10.5.1.5
    optixRtnECCDCCPHYPortidDst OBJECT-TYPE
        SYNTAX Unsigned32 (1..255)
        MAX-ACCESS read-create
        STATUS current
        DESCRIPTION
            "Port ID"
        DEFVAL{ 255 }
        ::= { optixRtnECCDCCPHYEntry 5 }

    -- 1.3.6.1.4.1.2011.2.25.4.40.7.10.5.1.6
    optixRtnECCDCCPHYOHPTypeDst OBJECT-TYPE
        SYNTAX INTEGER
        {
            d1(2),
            d2(3),
            d3(4),
            d4(9),
            d5(11),
            d6(12),
            d7(13),
            d8(14),
            d9(15),
            d10(16),
            d11(17),
            d12(18),
            k1(7),
            k2(8),
            k3(22),
            e1(0),
            e2(20),
            f1(1),
            f3(21),
            x1(5),
            x2(6),
            x3(19),
            x4(10)
        }
        MAX-ACCESS read-create
        STATUS current
        DESCRIPTION
            "OHP Type"
        DEFVAL{ 2 }
        ::= { optixRtnECCDCCPHYEntry 6 }

    -- 1.3.6.1.4.1.2011.2.25.4.40.7.10.5.1.255
    optixRtnECCDCCPHYRowStatus OBJECT-TYPE
        SYNTAX RowStatus
        MAX-ACCESS read-create
        STATUS current
        DESCRIPTION
            "row status."
        DEFVAL{ 255 }
        ::= { optixRtnECCDCCPHYEntry 255 }

    -- 1.3.6.1.4.1.2011.2.25.4.40.7.10.10
    optixRtnECCIndexTable OBJECT-TYPE
        SYNTAX SEQUENCE OF OptixRtnECCIndexEntry
        MAX-ACCESS not-accessible
        STATUS current
        DESCRIPTION
            "ECC index"
        ::= { optixRtnECC 10 }

    -- 1.3.6.1.4.1.2011.2.25.4.40.7.10.10.1
    optixRtnECCIndexEntry OBJECT-TYPE
        SYNTAX OptixRtnECCIndexEntry
        MAX-ACCESS not-accessible
        STATUS current
        DESCRIPTION
            "ECC index entry"
        INDEX{ optixRtnECCBoardID,optixRtnECCSubCard,optixRtnECCPortID,optixRtnECCChanType }
        ::= { optixRtnECCIndexTable 1 }

    OptixRtnECCIndexEntry ::=
        SEQUENCE {
            optixRtnECCBoardID
                Unsigned32,
            optixRtnECCSubCard
                Unsigned32,
            optixRtnECCPortID
                Unsigned32,
            optixRtnECCChanType
                INTEGER,
            optixRtnECCOHPType
                INTEGER
        }

    -- 1.3.6.1.4.1.2011.2.25.4.40.7.10.10.1.1
    optixRtnECCBoardID OBJECT-TYPE
        SYNTAX Unsigned32 (1..255)
        MAX-ACCESS not-accessible
        STATUS current
        DESCRIPTION
            "Board ID"
        DEFVAL{ 1 }
        ::= { optixRtnECCIndexEntry 1 }

    -- 1.3.6.1.4.1.2011.2.25.4.40.7.10.10.1.2
    optixRtnECCSubCard OBJECT-TYPE
        SYNTAX Unsigned32 (1..255)
        MAX-ACCESS not-accessible
        STATUS current
        DESCRIPTION
            "Sub Card"
        DEFVAL{ 255 }
        ::= { optixRtnECCIndexEntry 2 }

    -- 1.3.6.1.4.1.2011.2.25.4.40.7.10.10.1.3
    optixRtnECCPortID OBJECT-TYPE
        SYNTAX Unsigned32 (1..255)
        MAX-ACCESS not-accessible
        STATUS current
        DESCRIPTION
            "Port ID"
        DEFVAL{ 1 }
        ::= { optixRtnECCIndexEntry 3 }

    -- 1.3.6.1.4.1.2011.2.25.4.40.7.10.10.1.4
    optixRtnECCChanType OBJECT-TYPE
        SYNTAX INTEGER
        {
            d1d3(1),
            d4d12(2),
            d1d12(3),
            d1d1(7)
        }
        MAX-ACCESS not-accessible
        STATUS current
        DESCRIPTION
            "Chan Type"
        DEFVAL{ 1 }
        ::= { optixRtnECCIndexEntry 4 }

    -- 1.3.6.1.4.1.2011.2.25.4.40.7.10.10.1.5
    optixRtnECCOHPType OBJECT-TYPE
        SYNTAX INTEGER
        {
            ok(0),
            connecting(1),
            closing(2),
            closed(3),
            deleting(4),
            connecterr(5),
            cloceerr(6),
            deldeteerr(7)
        }
        MAX-ACCESS not-accessible
        STATUS current
        DESCRIPTION
            "OHP Type"
        DEFVAL{ 0 }
        ::= { optixRtnECCIndexEntry 5 }

    -- 1.3.6.1.4.1.2011.2.25.4.40.7.10.30
    optixRtnECCFiberPortTable OBJECT-TYPE
        SYNTAX SEQUENCE OF OptixRtnECCFiberPortEntry
        MAX-ACCESS not-accessible
        STATUS current
        DESCRIPTION
            "FiberPortTable"
        ::= { optixRtnECC 30 }

    -- 1.3.6.1.4.1.2011.2.25.4.40.7.10.30.1
    optixRtnECCFiberPortEntry OBJECT-TYPE
        SYNTAX OptixRtnECCFiberPortEntry
        MAX-ACCESS not-accessible
        STATUS current
        DESCRIPTION
            "FiberPortTable"
        INDEX{ optixRtnECCBoardID,optixRtnECCSubCard,optixRtnECCPortID }
        ::= { optixRtnECCFiberPortTable 1 }

    OptixRtnECCFiberPortEntry ::=
        SEQUENCE {
            optixRtnECCFiberPortPortState
                INTEGER,
            optixRtnECCFiberPortDccRate
                INTEGER
        }

    -- 1.3.6.1.4.1.2011.2.25.4.40.7.10.30.1.1
    optixRtnECCFiberPortPortState OBJECT-TYPE
        SYNTAX INTEGER
        {
            portenable(1),
            portdisable(2)
        }
        MAX-ACCESS read-write
        STATUS current
        DESCRIPTION
            "FiberPort state"
        DEFVAL{ 1 }
        ::= { optixRtnECCFiberPortEntry 1 }

    -- 1.3.6.1.4.1.2011.2.25.4.40.7.10.30.1.2
    optixRtnECCFiberPortDccRate OBJECT-TYPE
        SYNTAX INTEGER
        {
            d1d3(1),
            d4d12(2),
            d1d12(3),
            d1d1(7)
        }
        MAX-ACCESS read-write
        STATUS current
        DESCRIPTION
            "DCC Rate"
        DEFVAL{ 1 }
        ::= { optixRtnECCFiberPortEntry 2 }

    -- 1.3.6.1.4.1.2011.2.25.4.40.7.20
    optixRtnDeviceComAttr OBJECT IDENTIFIER ::= { optixRtnDeviceMng 20 }

    -- 1.3.6.1.4.1.2011.2.25.4.40.7.20.1
    optixRtnDevPowerMode OBJECT-TYPE
        SYNTAX INTEGER
        {
            dc(1),
            poe(2)
        }
        MAX-ACCESS read-only
        STATUS current
        DESCRIPTION
            "Query the power mode of ne."
        ::= { optixRtnDeviceComAttr 1 }

    -- 1.3.6.1.4.1.2011.2.25.4.40.7.30
    optixRtnECCGetInfo OBJECT IDENTIFIER ::= { optixRtnDeviceMng 30 }

    -- 1.3.6.1.4.1.2011.2.25.4.40.7.30.1
    optixRtnECCGetInfoTable OBJECT-TYPE
        SYNTAX SEQUENCE OF OptixRtnECCGetInfoEntry
        MAX-ACCESS not-accessible
        STATUS current
        DESCRIPTION
            "ECCGetInfoTable"
        ::= { optixRtnECCGetInfo 1 }

    -- 1.3.6.1.4.1.2011.2.25.4.40.7.30.1.1
    optixRtnECCGetInfoEntry OBJECT-TYPE
        SYNTAX OptixRtnECCGetInfoEntry
        MAX-ACCESS not-accessible
        STATUS current
        DESCRIPTION
            "ECCGetInfoEntry"
		INDEX{ optixRtnECCBoardID,optixRtnECCSubCard,optixRtnECCPortID }	
        ::= { optixRtnECCGetInfoTable 1 }

    OptixRtnECCGetInfoEntry ::=
        SEQUENCE {
            optixRtnECCGetFiberPortInfoPortState
                INTEGER,
            optixRtnECCGetFiberPortInfoPortRate
                INTEGER,
            optixRtnECCGetFiberPortInfoLinkChan
                Unsigned32,
            optixRtnECCGetFiberPortInfoLogicChanState
                INTEGER
        }

    -- 1.3.6.1.4.1.2011.2.25.4.40.7.30.1.1.4
    optixRtnECCGetFiberPortInfoPortState OBJECT-TYPE
        SYNTAX INTEGER
        {
            portenable(1),
            portdisable(2)
        }
        MAX-ACCESS read-only
        STATUS current
        DESCRIPTION
            "Port State"
        DEFVAL{ 1 }
        ::= { optixRtnECCGetInfoEntry 4 }

    -- 1.3.6.1.4.1.2011.2.25.4.40.7.30.1.1.5
    optixRtnECCGetFiberPortInfoPortRate OBJECT-TYPE
        SYNTAX INTEGER
        {
            d1d3(1),
            d4d12(2),
            d1d12(3),
            d1d1(7)
        }
        MAX-ACCESS read-only
        STATUS current
        DESCRIPTION
            "Port Rate"
        DEFVAL{ 1 }
        ::= { optixRtnECCGetInfoEntry 5 }

    -- 1.3.6.1.4.1.2011.2.25.4.40.7.30.1.1.6
    optixRtnECCGetFiberPortInfoLinkChan OBJECT-TYPE
        SYNTAX Unsigned32 (1..65535)
        MAX-ACCESS read-only
        STATUS current
        DESCRIPTION
            "Link Chan"
        ::= { optixRtnECCGetInfoEntry 6 }

    -- 1.3.6.1.4.1.2011.2.25.4.40.7.30.1.1.7
    optixRtnECCGetFiberPortInfoLogicChanState OBJECT-TYPE
        SYNTAX INTEGER
        {
            ok(0),
            rxf(2),
            txf(4),
            rxfandtxf(6)
        }
        MAX-ACCESS read-only
        STATUS current
        DESCRIPTION
            "Logic Chan State"
        DEFVAL{ 0 }
        ::= { optixRtnECCGetInfoEntry 7 }

    -- 1.3.6.1.4.1.2011.2.25.4.40.7.40
    optixRtnWifiMgr OBJECT IDENTIFIER ::= { optixRtnDeviceMng 40 }

    -- 1.3.6.1.4.1.2011.2.25.4.40.7.40.1
    optixRTNWifiSSIDName OBJECT-TYPE
        SYNTAX OCTET STRING (SIZE(1..32))
        MAX-ACCESS read-write
        STATUS current
        DESCRIPTION
            "SSID Name"
        ::= { optixRtnWifiMgr 1 }

    -- 1.3.6.1.4.1.2011.2.25.4.40.7.40.2
    optixRTNWifiWorkMode OBJECT-TYPE
        SYNTAX INTEGER
        {
            close(0),
            open(1),
            auto(2)
        }
        MAX-ACCESS read-write
        STATUS current
        DESCRIPTION
            "Work Mode"
        DEFVAL{ 1 }
        ::= { optixRtnWifiMgr 2 }

    -- 1.3.6.1.4.1.2011.2.25.4.40.7.40.3
    optixRTNWifiCurPassword OBJECT-TYPE
        SYNTAX OCTET STRING (SIZE(1..16))
        MAX-ACCESS read-write
        STATUS current
        DESCRIPTION
            "Indicates the current password of the Wi-Fi."
        ::= { optixRtnWifiMgr 3 }

    -- 1.3.6.1.4.1.2011.2.25.4.40.7.40.4
    optixRTNWifiNewPassword OBJECT-TYPE
        SYNTAX OCTET STRING (SIZE(1..16))
        MAX-ACCESS read-write
        STATUS current
        DESCRIPTION
            "Indicates the new password of the Wi-Fi."
        ::= { optixRtnWifiMgr 4 }

    -- 1.3.6.1.4.1.2011.2.25.4.40.7.40.5
    optixRTNWifiOnlineStatus OBJECT-TYPE
        SYNTAX INTEGER
        {
            offline(0),
            online(1)
        }
        MAX-ACCESS read-only
        STATUS current
        DESCRIPTION
            "Online Status"
        ::= { optixRtnWifiMgr 5 }

    -- 1.3.6.1.4.1.2011.2.25.4.40.7.40.6
    optixRTNWifiPowerStatus OBJECT-TYPE
        SYNTAX INTEGER
        {
            poweroff(0),
            poweron(1)
        }
        MAX-ACCESS read-only
        STATUS current
        DESCRIPTION
            "Power Status.(The node has only 300 device support)"
        ::= { optixRtnWifiMgr 6 }

    -- 1.3.6.1.4.1.2011.2.25.4.40.7.40.7
    optixRTNWifiAutoModeTime OBJECT-TYPE
        SYNTAX Unsigned32
        MAX-ACCESS read-write
        STATUS current
        DESCRIPTION
            "Auto mode time.(The node has only 300 device support)"
        DEFVAL{ 15 }
        ::= { optixRtnWifiMgr 7 }

    -- 1.3.6.1.4.1.2011.2.25.4.40.7.40.8
    optixRTNWifiHideSSID OBJECT-TYPE
        SYNTAX INTEGER
        {
            close(0),
            open(1)
        }
        MAX-ACCESS read-write
        STATUS current
        DESCRIPTION
            "Whether to hide SSID"
        DEFVAL{ 0 }
        ::= { optixRtnWifiMgr 8 }

    -- 1.3.6.1.4.1.2011.2.25.4.40.7.40.9
    optixRTNWifiRealWorkMode OBJECT-TYPE
        SYNTAX INTEGER
        {
            close(0),
            open(1),
            auto(2),
            offline(3)
        }
        MAX-ACCESS read-only
        STATUS current
        DESCRIPTION
            "Actual working mode.(The node has only 300 device support)"
        DEFVAL{ 1 }
        ::= { optixRtnWifiMgr 9 }

    -- 1.3.6.1.4.1.2011.2.25.4.40.7.40.10
    optixRTNWifiMainTainTimeDate OBJECT-TYPE
        SYNTAX OCTET STRING
        MAX-ACCESS read-write
        STATUS current
        DESCRIPTION
            "Maintenance window (date).(The node has only 300 device support)"
        DEFVAL{ "1990-00-00" }
        ::= { optixRtnWifiMgr 10 }

    -- 1.3.6.1.4.1.2011.2.25.4.40.7.40.11
    optixRTNWifiIMainTainTimeHour OBJECT-TYPE
        SYNTAX Unsigned32
        MAX-ACCESS read-write
        STATUS current
        DESCRIPTION
            "Maintenance window (hour).(The node has only 300 device support)"
        DEFVAL{ 0 }
        ::= { optixRtnWifiMgr 11 }

    -- 1.3.6.1.4.1.2011.2.25.4.40.7.40.12
    optixRTNWifiIMainTainTimeLen OBJECT-TYPE
        SYNTAX Unsigned32
        MAX-ACCESS read-write
        STATUS current
        DESCRIPTION
            "Maintenance window (duration).(The node has only 300 device support)"
        DEFVAL{ 0 }
        ::= { optixRtnWifiMgr 12 }

    -- 1.3.6.1.4.1.2011.2.25.4.40.7.40.13
    optixRTNWifiChannelSelectMode OBJECT-TYPE
        SYNTAX INTEGER
        {
            auto(0),
            manual(1)
        }
        MAX-ACCESS read-write
        STATUS current
        DESCRIPTION
            "Wi-Fi channel selection mode.(The node has only 300 device support)"
        DEFVAL{ 0 }
        ::= { optixRtnWifiMgr 13 }

    -- 1.3.6.1.4.1.2011.2.25.4.40.7.40.14
    optixRTNWifiMunualChannel OBJECT-TYPE
        SYNTAX Unsigned32 (1..11)
        MAX-ACCESS read-write
        STATUS current
        DESCRIPTION
            "Configure the Wi-Fi channel that is manually specified.(The node has only 300 device support)"
        DEFVAL{ 6 }
        ::= { optixRtnWifiMgr 14 }

    -- 1.3.6.1.4.1.2011.2.25.4.40.7.40.15
    optixRTNWifiWorkChannel OBJECT-TYPE
        SYNTAX Unsigned32
        MAX-ACCESS read-only
        STATUS current
        DESCRIPTION
            "Query the actual working Wi-Fi channel.(The node has only 300 device support)"
        ::= { optixRtnWifiMgr 15 }

    -- 1.3.6.1.4.1.2011.2.25.4.40.7.40.16
    optixWifiMacFilter OBJECT-TYPE
	SYNTAX INTEGER
	{
	disable(0),
	enable(1)
	}
	MAX-ACCESS read-write
	STATUS current
	DESCRIPTION
	"the status of the mac list filter.(The node has only 300 device support)"
	::= { optixRtnWifiMgr 16 }

    -- 1.3.6.1.4.1.2011.2.25.4.40.7.40.17
    optixWifiAddMac OBJECT-TYPE
	SYNTAX OCTET STRING(SIZE(0..64))
	MAX-ACCESS read-create
	STATUS current
	DESCRIPTION
	"the MAC address to be added.(The node has only 300 device support)"
	::= { optixRtnWifiMgr 17 }

    -- 1.3.6.1.4.1.2011.2.25.4.40.7.40.18
    optixWifiDelMac OBJECT-TYPE
	SYNTAX OCTET STRING(SIZE(0..64))
	MAX-ACCESS read-create
	STATUS current
	DESCRIPTION
	"the MAC address to be deleted.(The node has only 300 device support)"
	DEFVAL{ "" }
	::= { optixRtnWifiMgr 18 }	

    -- 1.3.6.1.4.1.2011.2.25.4.40.7.43
    optixRtnWifiMacListTable OBJECT-TYPE
        SYNTAX SEQUENCE OF OptixRtnWifiMacListEntry
        MAX-ACCESS not-accessible
        STATUS current
        DESCRIPTION
            "Describes AM parameters of an IF board, including the AM status."
        ::= { optixRtnDeviceMng 43 }

    -- 1.3.6.1.4.1.2011.2.25.4.40.7.43.1
    optixRtnWifiMacListEntry OBJECT-TYPE
        SYNTAX OptixRtnWifiMacListEntry
        MAX-ACCESS not-accessible
        STATUS current
        DESCRIPTION
            "Indicates the management entry for the AM parameters of an IF port."
        INDEX{ optixRtnWifiMacListListIndex }
        ::= { optixRtnWifiMacListTable 1 }

    OptixRtnWifiMacListEntry ::=
        SEQUENCE {
            optixRtnWifiMacListListIndex
                INTEGER,
            optixRtnWifiMacListListMac
                OCTET STRING
        }

    -- 1.3.6.1.4.1.2011.2.25.4.40.7.43.1.1
    optixRtnWifiMacListListIndex OBJECT-TYPE
        SYNTAX INTEGER
        MAX-ACCESS not-accessible
        STATUS current
        DESCRIPTION
            "Wifi Index"
        ::= { optixRtnWifiMacListEntry 1 }

    -- 1.3.6.1.4.1.2011.2.25.4.40.7.43.1.2
    optixRtnWifiMacListListMac OBJECT-TYPE
        SYNTAX OCTET STRING
        MAX-ACCESS read-only
        STATUS current
        DESCRIPTION
            "Wifi MAC"
        ::= { optixRtnWifiMacListEntry 2 }

    -- 1.3.6.1.4.1.2011.2.25.4.40.7.50
    optixRtnUSBMgr OBJECT IDENTIFIER ::= { optixRtnDeviceMng 50 }

    -- 1.3.6.1.4.1.2011.2.25.4.40.7.50.1
    optixRTNUSBCompat OBJECT-TYPE
        SYNTAX INTEGER
        {
            disable(0),
            enable(1)
        }
        MAX-ACCESS read-write
        STATUS current
        DESCRIPTION
            "Compatibility Status.(The node 320/380H/3202F device does not support)"
        DEFVAL{ 1 }
        ::= { optixRtnUSBMgr 1 }

    -- 1.3.6.1.4.1.2011.2.25.4.40.7.60
    optixRtnLongHaulMgr OBJECT IDENTIFIER ::= { optixRtnDeviceMng 60 }

    -- 1.3.6.1.4.1.2011.2.25.4.40.7.60.1
    optixRtnLongHaulType OBJECT-TYPE
        SYNTAX INTEGER
        {
            outdoor(0),
            indoor(1)
        }
        MAX-ACCESS read-write
        STATUS current
        DESCRIPTION
            "LongHaul Shelf Type.(The node 300 device does not support)"
	DEFVAL{ 0 }
        ::= { optixRtnLongHaulMgr 1 }

    -- 1.3.6.1.4.1.2011.2.25.4.40.7.70
    optixRtnDeviceTrapCommon OBJECT IDENTIFIER ::= { optixRtnDeviceMng 70 }

    -- 1.3.6.1.4.1.2011.2.25.4.40.7.70.1
    optixRptRtnPowerOnEvent OBJECT IDENTIFIER ::= { optixRtnDeviceTrapCommon 1 }

    -- 1.3.6.1.4.1.2011.2.25.4.40.7.70.1.1
    optixRptRtnPowerOnNeId OBJECT-TYPE
        SYNTAX Unsigned32
        MAX-ACCESS accessible-for-notify
        STATUS current
        DESCRIPTION
            "Indicates the NEID."
        ::= { optixRptRtnPowerOnEvent 1 }

    -- 1.3.6.1.4.1.2011.2.25.4.40.7.70.1.2
    optixRptRtnPowerOnTime OBJECT-TYPE
        SYNTAX OCTET STRING
        MAX-ACCESS accessible-for-notify
        STATUS current
        DESCRIPTION
            "Indicates the Power On Time."
        ::= { optixRptRtnPowerOnEvent 2 }

    -- 1.3.6.1.4.1.2011.2.25.4.40.7.70.2
    optixRptRtnWifiConnectEvent OBJECT IDENTIFIER ::= { optixRtnDeviceTrapCommon 2 }

    -- 1.3.6.1.4.1.2011.2.25.4.40.7.70.2.1
    optixRptRtnWifiConnectMac OBJECT-TYPE
        SYNTAX Unsigned32
        MAX-ACCESS accessible-for-notify
        STATUS current
        DESCRIPTION
            "Indicates the WifiConnect Mac."
        ::= { optixRptRtnWifiConnectEvent 1 }

    -- 1.3.6.1.4.1.2011.2.25.4.40.7.70.2.2
    optixRptRtnWifiConnectTime OBJECT-TYPE
        SYNTAX Unsigned32
        MAX-ACCESS accessible-for-notify
        STATUS current
        DESCRIPTION
            "Indicates the WifiConnect Time."
        ::= { optixRptRtnWifiConnectEvent 2 }

    -- 1.3.6.1.4.1.2011.2.25.4.40.7.80
    optixRtnDeviceTrap OBJECT IDENTIFIER ::= { optixRtnDeviceMng 80 }

    -- 1.3.6.1.4.1.2011.2.25.4.40.7.80.10
    optixRtnPowerOnTrap NOTIFICATION-TYPE
        OBJECTS{ optixRptRtnPowerOnNeId,optixRptRtnPowerOnTime }
        STATUS current
        DESCRIPTION
            "Indicates an Power On event."
        ::= { optixRtnDeviceTrap 10 }
		
    -- 1.3.6.1.4.1.2011.2.25.4.40.7.80.20
    optixRtnWifiConnectTrap NOTIFICATION-TYPE
        OBJECTS{ optixRptRtnWifiConnectMac,optixRptRtnWifiConnectTime }
        STATUS current
        DESCRIPTION
            "Indicates an Wifi Connect event."
        ::= { optixRtnDeviceTrap 20 }

    -- 1.3.6.1.4.1.2011.2.25.4.40.7.80.40
    optixRtnDbRestoreExtTrap NOTIFICATION-TYPE
        OBJECTS{ optixRtnDbRestoreExtBid,optixRtnDbRestoreExtSubId,optixRtnDbRestoreExtPid,optixRtnSysParamRestoreExtResult,optixRtnLicenseExtResult,optixRtnDbRestoreExtResult }
        STATUS current
        DESCRIPTION
            "Indicates an DbRestore event."
        ::= { optixRtnDeviceTrap 40 }

    -- 1.3.6.1.4.1.2011.2.25.4.40.7.90
    optixRtnRemoteBackupMgr OBJECT IDENTIFIER ::= { optixRtnDeviceMng 90 }

    -- 1.3.6.1.4.1.2011.2.25.4.40.7.90.1
    optixRtnRemoteBackupPkinfo OBJECT-TYPE
        SYNTAX OCTET STRING (SIZE(8..32))
        MAX-ACCESS read-write
        STATUS current
        DESCRIPTION
            "Restored security key configuration in the remote configurations"
        ::= { optixRtnRemoteBackupMgr 1 }

    -- 1.3.6.1.4.1.2011.2.25.4.40.7.90.2
    optixRtnRemoteBackupEnable OBJECT-TYPE
        SYNTAX INTEGER
        {
            disable(0),
            enable(1)
        }
        MAX-ACCESS read-write
        STATUS current
        DESCRIPTION
            "Indicates whether the remote backup function is enabled."
        ::= { optixRtnRemoteBackupMgr 2 }

    -- 1.3.6.1.4.1.2011.2.25.4.40.7.100
    optixRtnTeleComLoopTable OBJECT-TYPE
	SYNTAX SEQUENCE OF OptixRtnTeleComLoopEntry
	MAX-ACCESS not-accessible
	STATUS current
	DESCRIPTION
	"mode.(The node 300 device does not support)"
	::= { optixRtnDeviceMng 100 }
	
    -- 1.3.6.1.4.1.2011.2.25.4.40.7.100.1
    optixRtnTeleComLoopEntry OBJECT-TYPE
	SYNTAX OptixRtnTeleComLoopEntry
	MAX-ACCESS not-accessible
	STATUS current
	DESCRIPTION
	"mode.(The node 300 device does not support)"
	INDEX{ optixRtnBoardID,optixRtnSubCardID,optixRtnPortID,optixRtnIVC4ID }
	::= { optixRtnTeleComLoopTable 1 }

    OptixRtnTeleComLoopEntry ::=
        SEQUENCE {
            optixRtnIVC4ID
                Unsigned32,
	    optixRtnTeleComLoopMode
	        INTEGER				
        }

    -- 1.3.6.1.4.1.2011.2.25.4.40.7.100.1.4
    optixRtnIVC4ID OBJECT-TYPE
        SYNTAX Unsigned32
        MAX-ACCESS not-accessible
        STATUS current
        DESCRIPTION
            "Indicates the IVC4 ID.(The node 300 device does not support)"
        ::= { optixRtnTeleComLoopEntry 4 }		

    -- 1.3.6.1.4.1.2011.2.25.4.40.7.100.1.5
    optixRtnTeleComLoopMode OBJECT-TYPE
	SYNTAX INTEGER
	{
	      noloop(0),
	  outloop(2)
	}
	MAX-ACCESS read-write
	STATUS current
	DESCRIPTION
		"Indicates IF telecom mode.(The node 300 device does not support)"
	::= { optixRtnTeleComLoopEntry 5 }

    -- 1.3.6.1.4.1.2011.2.25.4.40.7.110
    optixRtnIfPdTable OBJECT-TYPE
	SYNTAX SEQUENCE OF OptixRtnIfPdEntry
	MAX-ACCESS not-accessible
	STATUS current
	DESCRIPTION
	"mode"
	::= { optixRtnDeviceMng 110 }
	
    -- 1.3.6.1.4.1.2011.2.25.4.40.7.110.1
    optixRtnIfPdEntry OBJECT-TYPE
	SYNTAX OptixRtnIfPdEntry
	MAX-ACCESS not-accessible
	STATUS current
	DESCRIPTION
	"mode"
	INDEX{ optixRtnBoardID,optixRtnSubCardID,optixRtnPortID }
	::= { optixRtnIfPdTable 1 }

    OptixRtnIfPdEntry ::=
        SEQUENCE {
	    optixRtnIfPdMode
	    	Unsigned32				
        }
			
    -- 1.3.6.1.4.1.2011.2.25.4.40.7.110.1.4
    optixRtnIfPdMode OBJECT-TYPE
	SYNTAX Unsigned32
	{
		disable(0),
            	enable(1)
	}
	MAX-ACCESS read-write
	STATUS current
	DESCRIPTION
		"mode"
	::= { optixRtnIfPdEntry 4 }		
	
    -- 1.3.6.1.4.1.2011.2.25.4.40.7.120
    optixRtnCfgBackupInfoMgrTable OBJECT-TYPE
        SYNTAX SEQUENCE OF OptixRtnCfgBackupInfoMgrEntry
        MAX-ACCESS not-accessible
        STATUS current
        DESCRIPTION
            "Indicates the status and time of the terminal or remote backup."
        ::= { optixRtnDeviceMng 120 }

    -- 1.3.6.1.4.1.2011.2.25.4.40.7.120.1
    optixRtnCfgBackupInfoMgrEntry OBJECT-TYPE
        SYNTAX OptixRtnCfgBackupInfoMgrEntry
        MAX-ACCESS not-accessible
        STATUS current
        DESCRIPTION
            "Indicates the management entry for the AM parameters of an IF port."
        INDEX{ optixRtnIndex1,optixRtnIndex2 }
        ::= { optixRtnCfgBackupInfoMgrTable 1 }

    OptixRtnCfgBackupInfoMgrEntry ::=
        SEQUENCE {
            optixRtnCfgBackupNeId  
            	Unsigned32,
            optixRtnCfgBackupStatus
            	Unsigned32,
            optixRtnCfgBackupTime
                OCTET STRING        
        }
  
    -- 1.3.6.1.4.1.2011.2.25.4.40.7.120.1.1
    optixRtnCfgBackupNeId OBJECT-TYPE
        SYNTAX   Unsigned32        
        MAX-ACCESS read-only
        STATUS current
        DESCRIPTION
            "backup NeId"
        ::= { optixRtnCfgBackupInfoMgrEntry 1 }   
        
    -- 1.3.6.1.4.1.2011.2.25.4.40.7.120.1.2
    optixRtnCfgBackupStatus OBJECT-TYPE
        SYNTAX   Unsigned32  
	{
            yes(1),
            no(0)
        }		
        MAX-ACCESS read-only
        STATUS current
        DESCRIPTION
            "backup status."
        ::= { optixRtnCfgBackupInfoMgrEntry 2 }


    -- 1.3.6.1.4.1.2011.2.25.4.40.7.120.1.3
    optixRtnCfgBackupTime OBJECT-TYPE
        SYNTAX  OCTET STRING       
        MAX-ACCESS read-only
        STATUS current
        DESCRIPTION
            "backup time."
        ::= { optixRtnCfgBackupInfoMgrEntry 3 }

    -- 1.3.6.1.4.1.2011.2.25.4.40.7.136
    optixRtnCfgPerthIndexTable OBJECT-TYPE
        SYNTAX SEQUENCE OF OptixRtnCfgPerthIndexEntry
        MAX-ACCESS not-accessible
        STATUS current
        DESCRIPTION
            ""
        ::= { optixRtnDeviceMng 136 }

    -- 1.3.6.1.4.1.2011.2.25.4.40.7.136.1
    optixRtnCfgPerthIndexEntry OBJECT-TYPE
        SYNTAX OptixRtnCfgPerthIndexEntry
        MAX-ACCESS not-accessible
        STATUS current
        DESCRIPTION
            ""
        INDEX{ optixRtnIFPortPerID,optixRtnIFPerObjType,optixRtnIFPerObjLen,optixRtnIFPerObjPara }
        ::= { optixRtnCfgPerthIndexTable 1 }

    OptixRtnCfgPerthIndexEntry ::=
        SEQUENCE {
            optixRtnIFPortPerID 
            	Unsigned32,
            optixRtnIFPerObjType 
            	Unsigned32,
            optixRtnIFPerObjLen 
            	Unsigned32,
            optixRtnIFPerObjPara 
            	Unsigned32      
        }

    -- 1.3.6.1.4.1.2011.2.25.4.40.7.136.1.1
    optixRtnIFPortPerID OBJECT-TYPE
        SYNTAX   Unsigned32        
        MAX-ACCESS not-accessible
        STATUS current
        DESCRIPTION
            "perth eid"
        ::= { optixRtnCfgPerthIndexEntry 1 }
		
    -- 1.3.6.1.4.1.2011.2.25.4.40.7.136.1.2
    optixRtnIFPerObjType OBJECT-TYPE
        SYNTAX   Unsigned32        
        MAX-ACCESS not-accessible
        STATUS current
        DESCRIPTION
            "perth eid objtype"
        ::= { optixRtnCfgPerthIndexEntry 2 }
		
    -- 1.3.6.1.4.1.2011.2.25.4.40.7.136.1.3
    optixRtnIFPerObjLen OBJECT-TYPE
        SYNTAX   Unsigned32        
        MAX-ACCESS not-accessible
        STATUS current
        DESCRIPTION
            "perth eid objlen"
        ::= { optixRtnCfgPerthIndexEntry 3 }
		
    -- 1.3.6.1.4.1.2011.2.25.4.40.7.136.1.4
    optixRtnIFPerObjPara OBJECT-TYPE
        SYNTAX   Unsigned32        
        MAX-ACCESS not-accessible
        STATUS current
        DESCRIPTION
            "perth eid objpara"
        ::= { optixRtnCfgPerthIndexEntry 4 }

    -- 1.3.6.1.4.1.2011.2.25.4.40.7.137 
    optixRtnCfgPerthTable OBJECT-TYPE
        SYNTAX SEQUENCE OF OptixRtnCfgPerthEntry
        MAX-ACCESS not-accessible
        STATUS current
        DESCRIPTION
            ""
        ::= { optixRtnDeviceMng 137 }

    -- 1.3.6.1.4.1.2011.2.25.4.40.7.137.1
    optixRtnCfgPerthEntry OBJECT-TYPE
        SYNTAX OptixRtnCfgPerthEntry
        MAX-ACCESS not-accessible
        STATUS current
        DESCRIPTION
            ""
        INDEX{ optixRtnIFPortPerID,optixRtnIFPerObjType,optixRtnIFPerObjLen,optixRtnIFPerObjPara }
        ::= { optixRtnCfgPerthTable 1 }

    OptixRtnCfgPerthEntry ::=
        SEQUENCE {
            optixRtnCfgPerthThreshold 
            	Unsigned32       
        }

    -- 1.3.6.1.4.1.2011.2.25.4.40.7.137.1.5
    optixRtnCfgPerthThreshold OBJECT-TYPE
        SYNTAX   Unsigned32        
        MAX-ACCESS read-write
        STATUS current
        DESCRIPTION
            "perth threshold"
        ::= { optixRtnCfgPerthEntry 5 }

    -- 1.3.6.1.4.1.2011.2.25.4.40.7.138
    optixRtnCfgNePerthTable OBJECT-TYPE
        SYNTAX SEQUENCE OF OptixRtnCfgNePerthEntry
        MAX-ACCESS not-accessible
        STATUS current
        DESCRIPTION
            "Indicates the ne perth threshold."
        ::= { optixRtnDeviceMng 138 }

    -- 1.3.6.1.4.1.2011.2.25.4.40.7.138.1
    optixRtnCfgNePerthEntry OBJECT-TYPE
        SYNTAX OptixRtnCfgNePerthEntry
        MAX-ACCESS not-accessible
        STATUS current
        DESCRIPTION
            "Indicates the ne perth entry."
        INDEX{ optixRtnIFPortPerID }
        ::= { optixRtnCfgNePerthTable 1 }

    OptixRtnCfgNePerthEntry ::=
        SEQUENCE {
            optixRtnCfgNePerthEnbleStatus
            	Unsigned32,
            optixRtnCfgNePerthThreshold 
            	Unsigned32       
        }

    -- 1.3.6.1.4.1.2011.2.25.4.40.7.138.1.2
    optixRtnCfgNePerthEnbleStatus OBJECT-TYPE
        SYNTAX Unsigned32
        {
             disable(0),
             enable(1)
        }
        MAX-ACCESS read-write
        STATUS current
        DESCRIPTION
            "The Ne Perth Status"
        ::= { optixRtnCfgNePerthEntry 2 }

    -- 1.3.6.1.4.1.2011.2.25.4.40.7.138.1.3
    optixRtnCfgNePerthThreshold OBJECT-TYPE
        SYNTAX   Unsigned32        
        MAX-ACCESS read-write
        STATUS current
        DESCRIPTION
            "The ne nerth threshold"
        ::= { optixRtnCfgNePerthEntry 3 }

    -- 1.3.6.1.4.1.2011.2.25.4.40.7.145 
    optixRtnCfgPfperInfoTable OBJECT-TYPE
        SYNTAX SEQUENCE OF OptixRtnCfgPfperInfoEntry
        MAX-ACCESS not-accessible
        STATUS current
        DESCRIPTION
            ""
        ::= { optixRtnDeviceMng 145 }

    -- 1.3.6.1.4.1.2011.2.25.4.40.7.145.1
    optixRtnCfgPfperInfoEntry OBJECT-TYPE
        SYNTAX OptixRtnCfgPfperInfoEntry
        MAX-ACCESS not-accessible
        STATUS current
        DESCRIPTION
            ""
        INDEX{ optixRtnBoardID,optixRtnSubCardID,optixRtnPortID,optixRtnIFPortlist }
        ::= { optixRtnCfgPfperInfoTable 1 }

    OptixRtnCfgPfperInfoEntry ::=
        SEQUENCE {
            optixRtnCfgPfperInfoStartTime 
            	OCTET STRING,
            optixRtnCfgPfperInfoEndTime 
            	OCTET STRING,
            optixRtnCfgPfperInfoAT 
            	Unsigned32,
            optixRtnCfgPfperInfoUT 
            	Unsigned32,
            optixRtnCfgPfperInfoPFT 
            	Unsigned32				
        }

    -- 1.3.6.1.4.1.2011.2.25.4.40.7.145.1.1
    optixRtnCfgPfperInfoStartTime OBJECT-TYPE
        SYNTAX  OCTET STRING        
        MAX-ACCESS read-only
        STATUS current
        DESCRIPTION
            "perth threshold"
        ::= { optixRtnCfgPfperInfoEntry 1 }	

    -- 1.3.6.1.4.1.2011.2.25.4.40.7.145.1.2
    optixRtnCfgPfperInfoEndTime OBJECT-TYPE
        SYNTAX  OCTET STRING        
        MAX-ACCESS read-only
        STATUS current
        DESCRIPTION
            "perth threshold"
        ::= { optixRtnCfgPfperInfoEntry 2 }

    -- 1.3.6.1.4.1.2011.2.25.4.40.7.145.1.3
    optixRtnCfgPfperInfoAT OBJECT-TYPE
        SYNTAX   Unsigned32        
        MAX-ACCESS read-only
        STATUS current
        DESCRIPTION
            "perth threshold"
        ::= { optixRtnCfgPfperInfoEntry 3 }

    -- 1.3.6.1.4.1.2011.2.25.4.40.7.145.1.4
    optixRtnCfgPfperInfoUT OBJECT-TYPE
        SYNTAX   Unsigned32        
        MAX-ACCESS read-only
        STATUS current
        DESCRIPTION
            "perth threshold"
        ::= { optixRtnCfgPfperInfoEntry 4 }

    -- 1.3.6.1.4.1.2011.2.25.4.40.7.145.1.5
    optixRtnCfgPfperInfoPFT OBJECT-TYPE
        SYNTAX   Unsigned32        
        MAX-ACCESS read-only
        STATUS current
        DESCRIPTION
            "perth threshold"
        ::= { optixRtnCfgPfperInfoEntry 5 }

    -- 1.3.6.1.4.1.2011.2.25.4.40.7.146 
    optixRtnResetInfoTable OBJECT-TYPE
        SYNTAX SEQUENCE OF OptixRtnResetInfoEntry
        MAX-ACCESS not-accessible
        STATUS current
        DESCRIPTION
            ""
        ::= { optixRtnDeviceMng 146 }

    -- 1.3.6.1.4.1.2011.2.25.4.40.7.146.1
    optixRtnResetInfoEntry OBJECT-TYPE
        SYNTAX OptixRtnResetInfoEntry
        MAX-ACCESS not-accessible
        STATUS current
        DESCRIPTION
            ""
        INDEX{ optixRtnIFPortlist }
        ::= { optixRtnResetInfoTable 1 }

    OptixRtnResetInfoEntry ::=
        SEQUENCE {
            optixRtnResetTime 
            	OCTET STRING,
            optixRtnWorkTime 
            	OCTET STRING,
            optixRtnResetType 
            	Unsigned32
        }

    -- 1.3.6.1.4.1.2011.2.25.4.40.7.146.1.1
    optixRtnResetTime OBJECT-TYPE
        SYNTAX  OCTET STRING        
        MAX-ACCESS read-only
        STATUS current
        DESCRIPTION
            "Reset Time"
        ::= { optixRtnResetInfoEntry 1 }	

    -- 1.3.6.1.4.1.2011.2.25.4.40.7.146.1.2
    optixRtnWorkTime OBJECT-TYPE
        SYNTAX  OCTET STRING        
        MAX-ACCESS read-only
        STATUS current
        DESCRIPTION
            "Work Time"
        ::= { optixRtnResetInfoEntry 2 }

    -- 1.3.6.1.4.1.2011.2.25.4.40.7.146.1.3
    optixRtnResetType OBJECT-TYPE
        SYNTAX  Unsigned32        
        MAX-ACCESS read-only
        STATUS current
        DESCRIPTION
            "Reset Type"
        ::= { optixRtnResetInfoEntry 3 }

    -- 1.3.6.1.4.1.2011.2.25.4.40.7.150 
    optixRtnIbtaWorkModeTable OBJECT-TYPE
        SYNTAX SEQUENCE OF OptixRtnIbtaWorkModeEntry
        MAX-ACCESS not-accessible
        STATUS current
        DESCRIPTION
            "Querying and Setting the IBTA Working Mode."
        ::= { optixRtnDeviceMng 150 }

    -- 1.3.6.1.4.1.2011.2.25.4.40.7.150.1
    optixRtnIbtaWorkModeEntry OBJECT-TYPE
        SYNTAX OptixRtnIbtaWorkModeEntry
        MAX-ACCESS not-accessible
        STATUS current
        DESCRIPTION
            "Querying and Setting the IBTA Working Mode."
        INDEX{ optixRtnBoardID,optixRtnSubCardID }
        ::= { optixRtnIbtaWorkModeTable 1 }

    OptixRtnIbtaWorkModeEntry ::=
        SEQUENCE {
            optixRtnIbtaWorkMode
            	INTEGER
        }

    -- 1.3.6.1.4.1.2011.2.25.4.40.7.150.1.1
    optixRtnIbtaWorkMode OBJECT-TYPE
        SYNTAX INTEGER
        {
             disable(0),
             normal(1)
        }      
        MAX-ACCESS read-write
        STATUS current
        DESCRIPTION
            "Working Mode."
        ::= { optixRtnIbtaWorkModeEntry 1 }

    -- 1.3.6.1.4.1.2011.2.25.4.40.7.151
    optixRtnIbtaMSModeTable OBJECT-TYPE
        SYNTAX SEQUENCE OF OptixRtnIbtaMSModeEntry
        MAX-ACCESS not-accessible
        STATUS current
        DESCRIPTION
            "Querying and Setting the IBTA master slave Mode."
        ::= { optixRtnDeviceMng 151 }
	
	-- 1.3.6.1.4.1.2011.2.25.4.40.7.151.1
    optixRtnIbtaMSModeEntry OBJECT-TYPE
        SYNTAX OptixRtnIbtaMSModeEntry
        MAX-ACCESS not-accessible
        STATUS current
        DESCRIPTION
            "Querying and Setting the IBTA master slave Mode."
        INDEX{ optixRtnBoardID,optixRtnSubCardID }
        ::= { optixRtnIbtaMSModeTable 1 }

    OptixRtnIbtaMSModeEntry ::=
        SEQUENCE {
            optixRtnIbtaMSMode
            	INTEGER
        }
	
	-- 1.3.6.1.4.1.2011.2.25.4.40.7.151.1.1
    optixRtnIbtaMSMode OBJECT-TYPE
        SYNTAX INTEGER
        {
             disable(0),
             enable(1)
        }      
        MAX-ACCESS read-write
        STATUS current
        DESCRIPTION
            "Master slave Mode."
        ::= { optixRtnIbtaMSModeEntry 1 }

    -- 1.3.6.1.4.1.2011.2.25.4.40.7.152 
    optixRtnIbtaRealWorkModeTable OBJECT-TYPE
        SYNTAX SEQUENCE OF OptixRtnIbtaRealWorkModeEntry
        MAX-ACCESS not-accessible
        STATUS current
        DESCRIPTION
            "Querying the IBTA Real Working Mode."
        ::= { optixRtnDeviceMng 152 }

    -- 1.3.6.1.4.1.2011.2.25.4.40.7.152.1
    optixRtnIbtaRealWorkModeEntry OBJECT-TYPE
        SYNTAX OptixRtnIbtaRealWorkModeEntry
        MAX-ACCESS not-accessible
        STATUS current
        DESCRIPTION
            "Querying the IBTA Working Mode."
        INDEX{ optixRtnBoardID,optixRtnSubCardID }
        ::= { optixRtnIbtaRealWorkModeTable 1 }

    OptixRtnIbtaRealWorkModeEntry ::=
        SEQUENCE {
            optixRtnIbtaRealWorkMode
            	INTEGER
        }

    -- 1.3.6.1.4.1.2011.2.25.4.40.7.152.1.1
    optixRtnIbtaRealWorkMode OBJECT-TYPE
        SYNTAX INTEGER
        {
             disable(0),
             normal(1)
        }      
        MAX-ACCESS read-only
        STATUS current
        DESCRIPTION
            "Real Working Mode."
        ::= { optixRtnIbtaRealWorkModeEntry 1 }
		
	-- 1.3.6.1.4.1.2011.2.25.4.40.7.153 
    optixRtnIbtaAngleTable OBJECT-TYPE
        SYNTAX SEQUENCE OF OptixRtnIbtaAngleEntry
        MAX-ACCESS not-accessible
        STATUS current
        DESCRIPTION
            "Querying the IBTA Angle Mode."
        ::= { optixRtnDeviceMng 153 }

    -- 1.3.6.1.4.1.2011.2.25.4.40.7.153.1
    optixRtnIbtaAngleEntry OBJECT-TYPE
        SYNTAX OptixRtnIbtaAngleEntry
        MAX-ACCESS not-accessible
        STATUS current
        DESCRIPTION
            "Querying the IBTA Angle Mode."
        INDEX{ optixRtnBoardID,optixRtnSubCardID }
        ::= { optixRtnIbtaAngleTable 1 }

    OptixRtnIbtaAngleEntry ::=
        SEQUENCE {
            optixRtnIbtaWorkAngle
            	Unsigned32,
			optixRtnIbtaCurrentAngle
            	Unsigned32
        }

    -- 1.3.6.1.4.1.2011.2.25.4.40.7.153.1.1
    optixRtnIbtaWorkAngle OBJECT-TYPE
        SYNTAX Unsigned32
        MAX-ACCESS read-only
        STATUS current
        DESCRIPTION
            "Working Angle."
        ::= { optixRtnIbtaAngleEntry 1 }
	
	-- 1.3.6.1.4.1.2011.2.25.4.40.7.153.1.2
    optixRtnIbtaCurrentAngle OBJECT-TYPE
        SYNTAX Unsigned32
        MAX-ACCESS read-only
        STATUS current
        DESCRIPTION
            "Current Angle."
        ::= { optixRtnIbtaAngleEntry 2 }
		
END
