-- OPTIX-CFMOAM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-CFMOAM-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,IpAddress,NOTIFICATION-TYPE
            FROM SNMPv2-SMI
        RowStatus,MacAddress
            FROM SNMPv2-TC
        optixLogBoardId,optixLogSubCardId
            FROM OPTIX-BOARD-MANAGE-MIB
        optixPortId
            FROM OPTIX-PORT-MANAGE-MIB
        ;

    optixCfmoam MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the 802.1ag configuration information of device"
        REVISION "201204200000Z"
        DESCRIPTION
            "The initial revision of this MIB module1."
        ::={ optixProvisionPtn 15 }

    -- 1.3.6.1.4.1.2011.2.25.4.50.15.1
    optixCfmoamGroup OBJECT IDENTIFIER ::= { optixCfmoam 1 }

    -- 1.3.6.1.4.1.2011.2.25.4.50.15.1.1
    optixCfmoamMdTable OBJECT-TYPE
        SYNTAX SEQUENCE OF OptixCfmoamMdEntry
        MAX-ACCESS not-accessible
        STATUS current
        DESCRIPTION
            "This table describes the basic MD configuration information of the Layer 2 802.1ag protocol."
        ::= { optixCfmoamGroup 1 }

    -- 1.3.6.1.4.1.2011.2.25.4.50.15.1.1.1
    optixCfmoamMdEntry OBJECT-TYPE
        SYNTAX OptixCfmoamMdEntry
        MAX-ACCESS not-accessible
        STATUS current
        DESCRIPTION
            "This entry describes the basic MD configuration information of the Layer 2 802.1ag protocol."
        INDEX{ optixCfmoamMdId }
        ::= { optixCfmoamMdTable 1 }

    OptixCfmoamMdEntry ::=
        SEQUENCE {
            optixCfmoamMdId
                Unsigned32,
            optixCfmoamMdName
                OCTET STRING,
            optixCfmoamMdLevel
                Unsigned32,
            optixCfmoamRowStatus
                RowStatus
        }

    -- 1.3.6.1.4.1.2011.2.25.4.50.15.1.1.1.1
    optixCfmoamMdId OBJECT-TYPE
        SYNTAX Unsigned32
        MAX-ACCESS not-accessible
        STATUS current
        DESCRIPTION
            "This object indicates the MD index of the 802.1ag protocol. The index is numbered globally on an NE. Value range: 1 to 4294967040."
        ::= { optixCfmoamMdEntry 1 }

    -- 1.3.6.1.4.1.2011.2.25.4.50.15.1.1.1.2
    optixCfmoamMdName OBJECT-TYPE
        SYNTAX OCTET STRING(SIZE(0..22))
        MAX-ACCESS read-create
        STATUS current
        DESCRIPTION
            "This object indicates the MD name of the 802.1ag protocol."
        ::= { optixCfmoamMdEntry 2 }

    -- 1.3.6.1.4.1.2011.2.25.4.50.15.1.1.1.3
    optixCfmoamMdLevel OBJECT-TYPE
        SYNTAX Unsigned32
        MAX-ACCESS read-create
        STATUS current
        DESCRIPTION
            "This object indicates the MD level of the 802.1ag protocol. Value range: 0 to 7. A larger value indicates a higher level."
        ::= { optixCfmoamMdEntry 3 }

    -- 1.3.6.1.4.1.2011.2.25.4.50.15.1.1.1.255
    optixCfmoamRowStatus OBJECT-TYPE
        SYNTAX RowStatus
        MAX-ACCESS read-create
        STATUS current
        DESCRIPTION
            "This object indicates the row status of the 802.1ag protocol."
        ::= { optixCfmoamMdEntry 255 }

    -- 1.3.6.1.4.1.2011.2.25.4.50.15.1.2
    optixCfmoamMaTable OBJECT-TYPE
        SYNTAX SEQUENCE OF OptixCfmoamMaEntry
        MAX-ACCESS not-accessible
        STATUS current
        DESCRIPTION
            "This table describes the basic MA configuration information of the Layer 2 802.1ag protocol."
        ::= { optixCfmoamGroup 2 }

    -- 1.3.6.1.4.1.2011.2.25.4.50.15.1.2.1
    optixCfmoamMaEntry OBJECT-TYPE
        SYNTAX OptixCfmoamMaEntry
        MAX-ACCESS not-accessible
        STATUS current
        DESCRIPTION
            "This entry describes the basic MA configuration information of the Layer 2 802.1ag protocol."
        INDEX{ optixCfmoamMdId,optixCfmoamMaId }
        ::= { optixCfmoamMaTable 1 }

    OptixCfmoamMaEntry ::=
        SEQUENCE {
            optixCfmoamMaId
                Unsigned32,
            optixCfmoamMaName
                OCTET STRING,
            optixCfmoamMaServeId
                Unsigned32,
            optixCfmoamMaCcperiod
                Unsigned32,
            optixCfmoamMaRmepList
                OCTET STRING,
            optixCfmoamMaStandard
                INTEGER,
            optixCfmoamMaIDFormat
                INTEGER,
            optixCfmoamMaIDVlaue
                OCTET STRING,
            optixCfmoamMaRowStatus
                RowStatus
        }

    -- 1.3.6.1.4.1.2011.2.25.4.50.15.1.2.1.1
    optixCfmoamMaId OBJECT-TYPE
        SYNTAX Unsigned32
        MAX-ACCESS not-accessible
        STATUS current
        DESCRIPTION
            "This object indicates the MA index of the 802.1ag protocol. The index is numbered globally on an NE. Value range: 1 to 4294967040."
        ::= { optixCfmoamMaEntry 1 }

    -- 1.3.6.1.4.1.2011.2.25.4.50.15.1.2.1.2
    optixCfmoamMaName OBJECT-TYPE
        SYNTAX OCTET STRING(SIZE(0..22))
        MAX-ACCESS read-create
        STATUS current
        DESCRIPTION
            "This object indicates the MA name of the 802.1ag protocol."
        ::= { optixCfmoamMaEntry 2 }

    -- 1.3.6.1.4.1.2011.2.25.4.50.15.1.2.1.3
    optixCfmoamMaServeId OBJECT-TYPE
        SYNTAX Unsigned32
        MAX-ACCESS read-create
        STATUS current
        DESCRIPTION
            "This object indicates the service index of the 802.1ag protocol. The index is numbered globally on an NE. Value range: 1 to 4294967294."
        ::= { optixCfmoamMaEntry 3 }

    -- 1.3.6.1.4.1.2011.2.25.4.50.15.1.2.1.4
    optixCfmoamMaCcperiod OBJECT-TYPE
        SYNTAX Unsigned32
        MAX-ACCESS read-create
        STATUS current
        DESCRIPTION
            "This object indicates the CC period of the 802.1ag protocol. 1: 3.33 ms, 2: 10 ms, 3: 100 ms, 4: 1s (default), 5: 10s, 6: 1 minute, 7: 10 minutes"
        ::= { optixCfmoamMaEntry 4 }

    -- 1.3.6.1.4.1.2011.2.25.4.50.15.1.2.1.5
    optixCfmoamMaRmepList OBJECT-TYPE
        SYNTAX OCTET STRING
        MAX-ACCESS read-only
        STATUS current
        DESCRIPTION
            "This object indicates the MEP list of the 802.1ag protocol."
        ::= { optixCfmoamMaEntry 5 }

    -- 1.3.6.1.4.1.2011.2.25.4.50.15.1.2.1.6
    optixCfmoamMaStandard OBJECT-TYPE
        SYNTAX INTEGER
        {
            snmp8021Ag(1),
            snmpY1731(2)
        }
        MAX-ACCESS read-create
        STATUS current
        DESCRIPTION
            "This object indicates the standand of the 802.1ag protocol. 1: 802.1ag, 2: Y.1731"
        ::= { optixCfmoamMaEntry 6 }

    -- 1.3.6.1.4.1.2011.2.25.4.50.15.1.2.1.7
    optixCfmoamMaIDFormat OBJECT-TYPE
        SYNTAX INTEGER
        {
            icc(32)
        }
        MAX-ACCESS read-create
        STATUS current
        DESCRIPTION
            "This object indicates the ID format of the 802.1ag protocol. 32: icc"
        ::= { optixCfmoamMaEntry 7 }

    -- 1.3.6.1.4.1.2011.2.25.4.50.15.1.2.1.8
    optixCfmoamMaIDVlaue OBJECT-TYPE
        SYNTAX OCTET STRING (SIZE(0..45))
        MAX-ACCESS read-create
        STATUS current
        DESCRIPTION
            "This object indicates the ID vlaue of the 802.1ag protocol. The maximum value is 45 bytes."
        ::= { optixCfmoamMaEntry 8 }

    -- 1.3.6.1.4.1.2011.2.25.4.50.15.1.2.1.255
    optixCfmoamMaRowStatus OBJECT-TYPE
        SYNTAX RowStatus
        MAX-ACCESS read-create
        STATUS current
        DESCRIPTION
            "This object indicates the MA row status of the 802.1ag protocol."
        ::= { optixCfmoamMaEntry 255 }

    -- 1.3.6.1.4.1.2011.2.25.4.50.15.1.3
    optixCfmoamMepTable OBJECT-TYPE
        SYNTAX SEQUENCE OF OptixCfmoamMepEntry
        MAX-ACCESS not-accessible
        STATUS current
        DESCRIPTION
            "This table describes the basic MEP configuration information of the Layer 2 802.1ag protocol."
        ::= { optixCfmoamGroup 3 }

    -- 1.3.6.1.4.1.2011.2.25.4.50.15.1.3.1
    optixCfmoamMepEntry OBJECT-TYPE
        SYNTAX OptixCfmoamMepEntry
        MAX-ACCESS not-accessible
        STATUS current
        DESCRIPTION
            "This entry describes the basic MEP configuration information of the Layer 2 802.1ag protocol."
        INDEX{ optixCfmoamMdId,optixCfmoamMaId,optixCfmoamMepId }
        ::= { optixCfmoamMepTable 1 }

    OptixCfmoamMepEntry ::=
        SEQUENCE {
            optixCfmoamMepId
                Unsigned32,
            optixCfmoamMepDirect
                INTEGER,
            optixCfmoamMepLogicPortType
                INTEGER,
            optixCfmoamMepLogicPortid
                Unsigned32,
            optixCfmoamMepVlan
                Unsigned32,
            optixCfmoamMepCcStatus
                INTEGER,
            optixCfmoamMepAisStatus
                INTEGER,
            optixCfmoamMepClientLevel
                Unsigned32,
            optixCfmoamMepAisPrd
                INTEGER,
            optixCfmoamMepLmRmepId
                Unsigned32,
            optixCfmoamMepLmRule
                OCTET STRING,
            optixCfmoamMepServeId
                Unsigned32,
            optixCfmoamMepEthbnStatus
                INTEGER,
            optixCfmoamMepEthbnLevel
                Unsigned32,
            optixCfmoamMepPeriodType
                INTEGER,
            optixCfmoamMepPeriod
                Unsigned32,
            optixCfmoamMepHoldTime
                Unsigned32,
            optixCfmoamMepPaketLen
                Unsigned32,
            optixCfmoamMepRowStatus
                RowStatus
        }

    -- 1.3.6.1.4.1.2011.2.25.4.50.15.1.3.1.1
    optixCfmoamMepId OBJECT-TYPE
        SYNTAX Unsigned32
        MAX-ACCESS not-accessible
        STATUS current
        DESCRIPTION
            "This object indicates the MEP ID of the 802.1ag protocol. Value range: 1 to 8191."
        ::= { optixCfmoamMepEntry 1 }

    -- 1.3.6.1.4.1.2011.2.25.4.50.15.1.3.1.2
    optixCfmoamMepDirect OBJECT-TYPE
        SYNTAX INTEGER
        {
            ingress(1),
            egress(2)
        }
        MAX-ACCESS read-create
        STATUS current
        DESCRIPTION
            "This object indicates the MEP direction of the 802.1ag protocol. 1: ingress, 2: egress"
        ::= { optixCfmoamMepEntry 2 }

    -- 1.3.6.1.4.1.2011.2.25.4.50.15.1.3.1.3
    optixCfmoamMepLogicPortType OBJECT-TYPE
        SYNTAX INTEGER
        {
            vuni(1),
            vnni(2)
        }
        MAX-ACCESS read-create
        STATUS current
        DESCRIPTION
            "This object indicates the logical port type of the 802.1ag protocol. 1: V-UNI, 2: V-NNI"
        ::= { optixCfmoamMepEntry 3 }

    -- 1.3.6.1.4.1.2011.2.25.4.50.15.1.3.1.4
    optixCfmoamMepLogicPortid OBJECT-TYPE
        SYNTAX Unsigned32
        MAX-ACCESS read-create
        STATUS current
        DESCRIPTION
            "This object indicates the logical port number of the 802.1ag protocol. If the logical port type is V-NNI, the bearer type must be PHY port or QinQ link."
        ::= { optixCfmoamMepEntry 4 }

    -- 1.3.6.1.4.1.2011.2.25.4.50.15.1.3.1.5
    optixCfmoamMepVlan OBJECT-TYPE
        SYNTAX Unsigned32
        MAX-ACCESS read-create
        STATUS current
        DESCRIPTION
            "This object indicates the VLAN of the 802.1ag protocol. Value range: 1 to 4094. If services are carried by ports, this parameter must be set to 0xffff."
        ::= { optixCfmoamMepEntry 5 }

    -- 1.3.6.1.4.1.2011.2.25.4.50.15.1.3.1.6
    optixCfmoamMepCcStatus OBJECT-TYPE
        SYNTAX INTEGER
        {
            enable(1),
            disable(0)
        }
        MAX-ACCESS read-create
        STATUS current
        DESCRIPTION
            "This object indicates the CC status of the 802.1ag protocol. 1: enable, 0: disable"
        ::= { optixCfmoamMepEntry 6 }

    -- 1.3.6.1.4.1.2011.2.25.4.50.15.1.3.1.7
    optixCfmoamMepAisStatus OBJECT-TYPE
        SYNTAX INTEGER
        {
            enable(1),
            disable(0)
        }
        MAX-ACCESS read-create
        STATUS current
        DESCRIPTION
            "This object indicates the enable status of inserting ETH AIS for the 802.1ag protocol. 1: enable, 0: disable"
        ::= { optixCfmoamMepEntry 7 }

    -- 1.3.6.1.4.1.2011.2.25.4.50.15.1.3.1.8
    optixCfmoamMepClientLevel OBJECT-TYPE
        SYNTAX Unsigned32
        MAX-ACCESS read-create
        STATUS current
        DESCRIPTION
            "This object indicates the MD level of the AIS insertion object for the 802.1ag protocol. Value range: 0 to 7."
        ::= { optixCfmoamMepEntry 8 }

    -- 1.3.6.1.4.1.2011.2.25.4.50.15.1.3.1.9
    optixCfmoamMepAisPrd OBJECT-TYPE
        SYNTAX INTEGER
        {
            second(1),
            minute(2)
        }
        MAX-ACCESS read-create
        STATUS current
        DESCRIPTION
            "This object indicates the retransmission period of the ETH AIS packets forthe802.1ag protocol.1:second,2:minute"
        ::= { optixCfmoamMepEntry 9 }

    -- 1.3.6.1.4.1.2011.2.25.4.50.15.1.3.1.10
    optixCfmoamMepLmRmepId OBJECT-TYPE
        SYNTAX Unsigned32
        MAX-ACCESS read-create
        STATUS current
        DESCRIPTION
            "Eline matching remote maintenance point. Value range: 1 to 8191."
        ::= { optixCfmoamMepEntry 10 }

    -- 1.3.6.1.4.1.2011.2.25.4.50.15.1.3.1.11
    optixCfmoamMepLmRule OBJECT-TYPE
        SYNTAX OCTET STRING
        MAX-ACCESS read-create
        STATUS current
        DESCRIPTION
            "Eline LM matching rule"
        ::= { optixCfmoamMepEntry 11 }

    -- 1.3.6.1.4.1.2011.2.25.4.50.15.1.3.1.12
    optixCfmoamMepServeId OBJECT-TYPE
        SYNTAX Unsigned32
        MAX-ACCESS read-create
        STATUS current
        DESCRIPTION
            "This object indicates the service index of the 802.1ag protocol. The index is numbered globally on an NE. Value range: 1 to 4294967294."
        ::= { optixCfmoamMepEntry 12 }

    -- 1.3.6.1.4.1.2011.2.25.4.50.15.1.3.1.13
    optixCfmoamMepEthbnStatus OBJECT-TYPE
        SYNTAX INTEGER
        {
            disable(0),
            enable(1)
        }
        MAX-ACCESS read-create
        STATUS current
        DESCRIPTION
            "This parameter indicates whether IEEE 802.1ag-compliant MEP bandwidth notification is enabled. Its value is disable (0, default) or enable(1)."
        ::= { optixCfmoamMepEntry 13 }

    -- 1.3.6.1.4.1.2011.2.25.4.50.15.1.3.1.14
    optixCfmoamMepEthbnLevel OBJECT-TYPE
        SYNTAX Unsigned32
        MAX-ACCESS read-create
        STATUS current
        DESCRIPTION
            "This parameter indicates the MD level of an IEEE 802.1ag-compliant bandwidth notification object. Its value range is 0-7."
        ::= { optixCfmoamMepEntry 14 }

    -- 1.3.6.1.4.1.2011.2.25.4.50.15.1.3.1.15
    optixCfmoamMepPeriodType OBJECT-TYPE
        SYNTAX INTEGER
        {
            period(1),
            nonperiod(2)
        }
        MAX-ACCESS read-create
        STATUS current
        DESCRIPTION
            "This parameter indicates the period type for IEEE 802.1ag-compliant MEP bandwidth notification. Its value is period(1) or nonperiod(2)."
        ::= { optixCfmoamMepEntry 15 }

    -- 1.3.6.1.4.1.2011.2.25.4.50.15.1.3.1.16
    optixCfmoamMepPeriod OBJECT-TYPE
        SYNTAX Unsigned32
        MAX-ACCESS read-create
        STATUS current
        DESCRIPTION
            "This parameter indicates the period for IEEE 802.1ag-compliant MEP bandwidth notification. Its value is 1s (default value), 10s, or 60s."
        ::= { optixCfmoamMepEntry 16 }

    -- 1.3.6.1.4.1.2011.2.25.4.50.15.1.3.1.17
    optixCfmoamMepHoldTime OBJECT-TYPE
        SYNTAX Unsigned32
        MAX-ACCESS read-create
        STATUS current
        DESCRIPTION
            "This parameter indicates the IEEE 802.1ag-compliant MEP bandwidth hold time. Its value range is 0-10s. Its default value is 0s."
        ::= { optixCfmoamMepEntry 17 }

    -- 1.3.6.1.4.1.2011.2.25.4.50.15.1.3.1.18
    optixCfmoamMepPaketLen OBJECT-TYPE
        SYNTAX Unsigned32
        MAX-ACCESS read-create
        STATUS current
        DESCRIPTION
            "This parameter indicates the IEEE 802.1ag-compliant MEP bandwidth notification packet length. Its value range is 64-9600. Its default value is 64."
        ::= { optixCfmoamMepEntry 18 }

    -- 1.3.6.1.4.1.2011.2.25.4.50.15.1.3.1.255
    optixCfmoamMepRowStatus OBJECT-TYPE
        SYNTAX RowStatus
        MAX-ACCESS read-create
        STATUS current
        DESCRIPTION
            "This object indicates the MEP row status of the 802.1ag protocol."
        ::= { optixCfmoamMepEntry 255 }

    -- 1.3.6.1.4.1.2011.2.25.4.50.15.1.4
    optixCfmoamMipTable OBJECT-TYPE
        SYNTAX SEQUENCE OF OptixCfmoamMipEntry
        MAX-ACCESS not-accessible
        STATUS current
        DESCRIPTION
            "This table describes the basic MIP configuration information of the Layer 2 802.1ag protocol."
        ::= { optixCfmoamGroup 4 }

    -- 1.3.6.1.4.1.2011.2.25.4.50.15.1.4.1
    optixCfmoamMipEntry OBJECT-TYPE
        SYNTAX OptixCfmoamMipEntry
        MAX-ACCESS not-accessible
        STATUS current
        DESCRIPTION
            "This entry describes the basic MIP configuration information of the Layer 2 802.1ag protocol."
        INDEX{ optixCfmoamMdId,optixCfmoamMipId }
        ::= { optixCfmoamMipTable 1 }

    OptixCfmoamMipEntry ::=
        SEQUENCE {
            optixCfmoamMipId
                Unsigned32,
            optixCfmoamMipBoardId
                Unsigned32,
            optixCfmoamMipSubboardId
                Unsigned32,
            optixCfmoamMipPortId
                Unsigned32,
            optixCfmoamMipRowStatus
                RowStatus
        }

    -- 1.3.6.1.4.1.2011.2.25.4.50.15.1.4.1.1
    optixCfmoamMipId OBJECT-TYPE
        SYNTAX Unsigned32
        MAX-ACCESS not-accessible
        STATUS current
        DESCRIPTION
            "This object indicates the MIP ID of the 802.1ag protocol. Value range: 1 to 8191."
        ::= { optixCfmoamMipEntry 1 }

    -- 1.3.6.1.4.1.2011.2.25.4.50.15.1.4.1.2
    optixCfmoamMipBoardId OBJECT-TYPE
        SYNTAX Unsigned32
        MAX-ACCESS read-create
        STATUS current
        DESCRIPTION
            "This object indicates the slot ID of the 802.1ag protocol."
        ::= { optixCfmoamMipEntry 2 }

    -- 1.3.6.1.4.1.2011.2.25.4.50.15.1.4.1.3
    optixCfmoamMipSubboardId OBJECT-TYPE
        SYNTAX Unsigned32
        MAX-ACCESS read-create
        STATUS current
        DESCRIPTION
            "This object indicates the subboard ID of the 802.1ag protocol."
        ::= { optixCfmoamMipEntry 3 }

    -- 1.3.6.1.4.1.2011.2.25.4.50.15.1.4.1.4
    optixCfmoamMipPortId OBJECT-TYPE
        SYNTAX Unsigned32
        MAX-ACCESS read-create
        STATUS current
        DESCRIPTION
            "This object indicates the port numberof the 802.1ag protocol."
        ::= { optixCfmoamMipEntry 4 }

    -- 1.3.6.1.4.1.2011.2.25.4.50.15.1.4.1.255
    optixCfmoamMipRowStatus OBJECT-TYPE
        SYNTAX RowStatus
        MAX-ACCESS read-create
        STATUS current
        DESCRIPTION
            "This object indicates the MIP row status of the 802.1ag protocol."
        ::= { optixCfmoamMipEntry 255 }

    -- 1.3.6.1.4.1.2011.2.25.4.50.15.1.5
    optixCfmoamTestIDTable OBJECT-TYPE
        SYNTAX SEQUENCE OF OptixCfmoamTestIDEntry
        MAX-ACCESS not-accessible
        STATUS current
        DESCRIPTION
            "This table describes the basic TESTID configuration information of the Layer 2 Y.1731 protocol."
        ::= { optixCfmoamGroup 5 }

    -- 1.3.6.1.4.1.2011.2.25.4.50.15.1.5.1
    optixCfmoamTestIDEntry OBJECT-TYPE
        SYNTAX OptixCfmoamTestIDEntry
        MAX-ACCESS not-accessible
        STATUS current
        DESCRIPTION
            "This entry describes the basic TESTID configuration information of the Layer 2 Y.1731 protocol."
        INDEX{ optixCfmoamMdId,optixCfmoamMaId,optixCfmoamMepId,optixCfmoamTestId }
        ::= { optixCfmoamTestIDTable 1 }

    OptixCfmoamTestIDEntry ::=
        SEQUENCE {
            optixCfmoamTestId
                Unsigned32,
            optixCfmoamTestIDRmepId
                Unsigned32,
            optixCfmoamTestIDInPri
                Unsigned32,
            optixCfmoamTestIDOutPri
                Unsigned32,
            optixCfmoamTestIDForwardMACLrn
                INTEGER,
            optixCfmoamTestIDCfgForwardMAC
                OCTET STRING,
            optixCfmoamTestIDBackwardMACLrn
                INTEGER,
            optixCfmoamTestIDCfgBackwardMAC
                OCTET STRING,
            optixCfmoamTestIDForwardMAC
                OCTET STRING,
            optixCfmoamTestIDBackwardMAC
                OCTET STRING,
            optixCfmoamTestIDMode
                INTEGER,
            optixCfmoamTestIDRowStatus
                RowStatus
        }

    -- 1.3.6.1.4.1.2011.2.25.4.50.15.1.5.1.1
    optixCfmoamTestId OBJECT-TYPE
        SYNTAX Unsigned32
        MAX-ACCESS not-accessible
        STATUS current
        DESCRIPTION
            "This object indicates the TEST index of the Y.1731 protocol."
        ::= { optixCfmoamTestIDEntry 1 }

    -- 1.3.6.1.4.1.2011.2.25.4.50.15.1.5.1.2
    optixCfmoamTestIDRmepId OBJECT-TYPE
        SYNTAX Unsigned32
        MAX-ACCESS read-create
        STATUS current
        DESCRIPTION
            "This object indicates the remote MEP ID of the Y.1731 protocol. Value range: 1 to 8191."
        ::= { optixCfmoamTestIDEntry 2 }

    -- 1.3.6.1.4.1.2011.2.25.4.50.15.1.5.1.3
    optixCfmoamTestIDInPri OBJECT-TYPE
        SYNTAX Unsigned32
        MAX-ACCESS read-create
        STATUS current
        DESCRIPTION
            "This object indicates the ingress direction pri of the Y.1731 protocol. Value range: 0 to 7."
        ::= { optixCfmoamTestIDEntry 3 }

    -- 1.3.6.1.4.1.2011.2.25.4.50.15.1.5.1.4
    optixCfmoamTestIDOutPri OBJECT-TYPE
        SYNTAX Unsigned32
        MAX-ACCESS read-create
        STATUS current
        DESCRIPTION
            "This object indicates the engress direction pri of the Y.1731 protocol. Value range: 0 to 7."
        ::= { optixCfmoamTestIDEntry 4 }

    -- 1.3.6.1.4.1.2011.2.25.4.50.15.1.5.1.5
    optixCfmoamTestIDForwardMACLrn OBJECT-TYPE
        SYNTAX INTEGER
        {
            disable(0),
            enable(1)
        }
        MAX-ACCESS read-create
        STATUS current
        DESCRIPTION
            "This object indicates the ForwardMAC learn of the Y.1731 protocol. 1: enable, 0: disable"
        ::= { optixCfmoamTestIDEntry 5 }

    -- 1.3.6.1.4.1.2011.2.25.4.50.15.1.5.1.6
    optixCfmoamTestIDCfgForwardMAC OBJECT-TYPE
        SYNTAX OCTET STRING (SIZE(0..24))
        MAX-ACCESS read-create
        STATUS current
        DESCRIPTION
            "This object indicates the User configure ForwardMAC of the Y.1731 protocol."
        ::= { optixCfmoamTestIDEntry 6 }

    -- 1.3.6.1.4.1.2011.2.25.4.50.15.1.5.1.7
    optixCfmoamTestIDBackwardMACLrn OBJECT-TYPE
        SYNTAX INTEGER
        {
            disable(0),
            enable(1)
        }
        MAX-ACCESS read-create
        STATUS current
        DESCRIPTION
            "This object indicates the BackwardMAC learn of the Y.1731 protocol. 1: enable, 0: disable"
        ::= { optixCfmoamTestIDEntry 7 }

    -- 1.3.6.1.4.1.2011.2.25.4.50.15.1.5.1.8
    optixCfmoamTestIDCfgBackwardMAC OBJECT-TYPE
        SYNTAX OCTET STRING (SIZE(0..24))
        MAX-ACCESS read-create
        STATUS current
        DESCRIPTION
            "This object indicates the User configure BackwardMAC of the Y.1731 protocol."
        ::= { optixCfmoamTestIDEntry 8 }

    -- 1.3.6.1.4.1.2011.2.25.4.50.15.1.5.1.9
    optixCfmoamTestIDForwardMAC OBJECT-TYPE
        SYNTAX OCTET STRING (SIZE(0..24))
        MAX-ACCESS read-only
        STATUS current
        DESCRIPTION
            "This object indicates the ForwardMAC of the Y.1731 protocol(if learn mode,it's learned ForwardMAC,else it's User configure ForwardMAC)."
        ::= { optixCfmoamTestIDEntry 9 }

    -- 1.3.6.1.4.1.2011.2.25.4.50.15.1.5.1.10
    optixCfmoamTestIDBackwardMAC OBJECT-TYPE
        SYNTAX OCTET STRING (SIZE(0..24))
        MAX-ACCESS read-only
        STATUS current
        DESCRIPTION
            "This object indicates the BackwardMAC of the Y.1731 protocol(if learn mode,it's learned BackwardMAC,else it's User configure BackwardMAC)."
        ::= { optixCfmoamTestIDEntry 10 }

    -- 1.3.6.1.4.1.2011.2.25.4.50.15.1.5.1.11
    optixCfmoamTestIDMode OBJECT-TYPE
        SYNTAX INTEGER
        {
            active(0),
            passive(1),
            invalid(255)
        }
        MAX-ACCESS read-create
        STATUS current
        DESCRIPTION
            "This object indicates the work mode of the Y.1731 protocol. 255: invalid, 0: active, 1: passive"
        ::= { optixCfmoamTestIDEntry 11 }

    -- 1.3.6.1.4.1.2011.2.25.4.50.15.1.5.1.255
    optixCfmoamTestIDRowStatus OBJECT-TYPE
        SYNTAX RowStatus
        MAX-ACCESS read-create
        STATUS current
        DESCRIPTION
            "This object indicates the row status of the Y.1731 protocol."
        ::= { optixCfmoamTestIDEntry 255 }

    -- 1.3.6.1.4.1.2011.2.25.4.50.15.1.6
    optixCfmoamRmepTable OBJECT-TYPE
        SYNTAX SEQUENCE OF OptixCfmoamRmepEntry
        MAX-ACCESS not-accessible
        STATUS current
        DESCRIPTION
            "This table describes the basic RMEP configuration information of the Layer 2 802.1ag protocol."
        ::= { optixCfmoamGroup 6 }

    -- 1.3.6.1.4.1.2011.2.25.4.50.15.1.6.1
    optixCfmoamRmepEntry OBJECT-TYPE
        SYNTAX OptixCfmoamRmepEntry
        MAX-ACCESS not-accessible
        STATUS current
        DESCRIPTION
            "This entry describes the basic RMEP configuration information of the Layer 2 802.1ag protocol."
        INDEX{ optixCfmoamMdId,optixCfmoamMaId }
        ::= { optixCfmoamRmepTable 1 }

    OptixCfmoamRmepEntry ::=
        SEQUENCE {
            optixCfmoamRmepNum
                Unsigned32,
            optixCfmoamRmepList
                OCTET STRING,
            optixCfmoamRmepRowStatus
                RowStatus
        }

    -- 1.3.6.1.4.1.2011.2.25.4.50.15.1.6.1.1
    optixCfmoamRmepNum OBJECT-TYPE
        SYNTAX Unsigned32
        MAX-ACCESS read-create
        STATUS current
        DESCRIPTION
            "This object indicates the RMEP number of the 802.1ag protocol. Value range: 0 to 2048."
        ::= { optixCfmoamRmepEntry 1 }

    -- 1.3.6.1.4.1.2011.2.25.4.50.15.1.6.1.2
    optixCfmoamRmepList OBJECT-TYPE
        SYNTAX OCTET STRING (SIZE(0..1024))
        MAX-ACCESS read-create
        STATUS current
        DESCRIPTION
            "This object indicates the RMEP list of the 802.1ag protocol. Value range: 1 to 8191. Use &amp;amp; to connect multiple values. For example, 1&amp;amp;2&amp;amp;3"
        ::= { optixCfmoamRmepEntry 2 }

    -- 1.3.6.1.4.1.2011.2.25.4.50.15.1.6.1.255
    optixCfmoamRmepRowStatus OBJECT-TYPE
        SYNTAX RowStatus
        MAX-ACCESS read-create
        STATUS current
        DESCRIPTION
            "This object indicates the RMEP row status of the 802.1ag protocol."
        ::= { optixCfmoamRmepEntry 255 }

    -- 1.3.6.1.4.1.2011.2.25.4.50.15.1.7
    optixCfmoamLbTestTable OBJECT-TYPE
        SYNTAX SEQUENCE OF OptixCfmoamLbTestEntry
        MAX-ACCESS not-accessible
        STATUS current
        DESCRIPTION
            "This table describes Start LB test of the Layer 2 802.1ag protocol."
        ::= { optixCfmoamGroup 7 }

    -- 1.3.6.1.4.1.2011.2.25.4.50.15.1.7.1
    optixCfmoamLbTestEntry OBJECT-TYPE
        SYNTAX OptixCfmoamLbTestEntry
        MAX-ACCESS not-accessible
        STATUS current
        DESCRIPTION
            "This entry describes Start LB test of the Layer 2 802.1ag protocol."
        INDEX{ optixCfmoamMdId,optixCfmoamMaId,optixCfmoamMepId }
        ::= { optixCfmoamLbTestTable 1 }

    OptixCfmoamLbTestEntry ::=
        SEQUENCE {
            optixCfmoamLbTestDmepType
                INTEGER,
            optixCfmoamLbTestMAC
                OCTET STRING,
            optixCfmoamLbTestPackNum
                Unsigned32,
            optixCfmoamLbTestLength
                Unsigned32,
            optixCfmoamLbTestPriority
                Unsigned32,
            optixCfmoamLbTestStop
                INTEGER
        }

    -- 1.3.6.1.4.1.2011.2.25.4.50.15.1.7.1.1
    optixCfmoamLbTestDmepType OBJECT-TYPE
        SYNTAX INTEGER
        {
            mepid(1),
            mac(2)
        }
        MAX-ACCESS read-write
        STATUS current
        DESCRIPTION
            "Query invalid,Dest mark type of Start LB test. 1: MEP ID, 2: MAC"
        ::= { optixCfmoamLbTestEntry 1 }

    -- 1.3.6.1.4.1.2011.2.25.4.50.15.1.7.1.2
    optixCfmoamLbTestMAC OBJECT-TYPE
        SYNTAX OCTET STRING
        MAX-ACCESS read-write
        STATUS current
        DESCRIPTION
            "Query invalid,MEPID or MAC of Start LB test"
        ::= { optixCfmoamLbTestEntry 2 }

    -- 1.3.6.1.4.1.2011.2.25.4.50.15.1.7.1.3
    optixCfmoamLbTestPackNum OBJECT-TYPE
        SYNTAX Unsigned32
        MAX-ACCESS read-write
        STATUS current
        DESCRIPTION
            "Query invalid,packet number of Start LB test ,bound(1~65535),default:3"
        ::= { optixCfmoamLbTestEntry 3 }

    -- 1.3.6.1.4.1.2011.2.25.4.50.15.1.7.1.4
    optixCfmoamLbTestLength OBJECT-TYPE
        SYNTAX Unsigned32
        MAX-ACCESS read-write
        STATUS current
        DESCRIPTION
            "Query invalid,packet length of Start LB test ,bound(64~0xffff),default:64"
        ::= { optixCfmoamLbTestEntry 4 }

    -- 1.3.6.1.4.1.2011.2.25.4.50.15.1.7.1.5
    optixCfmoamLbTestPriority OBJECT-TYPE
        SYNTAX Unsigned32
        MAX-ACCESS read-write
        STATUS current
        DESCRIPTION
            "Query invalid,packet priority of Start LB test ,bound(0~7),default:7"
        ::= { optixCfmoamLbTestEntry 5 }

    -- 1.3.6.1.4.1.2011.2.25.4.50.15.1.7.1.6
    optixCfmoamLbTestStop OBJECT-TYPE
        SYNTAX INTEGER
        {
            stop(0),
            invalid(255)
        }
        MAX-ACCESS read-write
        STATUS current
        DESCRIPTION
            "Query invalid,be uset to stop LB test"
        ::= { optixCfmoamLbTestEntry 6 }

    -- 1.3.6.1.4.1.2011.2.25.4.50.15.1.8
    optixCfmoamLtTestTable OBJECT-TYPE
        SYNTAX SEQUENCE OF OptixCfmoamLtTestEntry
        MAX-ACCESS not-accessible
        STATUS current
        DESCRIPTION
            "This table describes Start LT test of the Layer 2 802.1ag protocol."
        ::= { optixCfmoamGroup 8 }

    -- 1.3.6.1.4.1.2011.2.25.4.50.15.1.8.1
    optixCfmoamLtTestEntry OBJECT-TYPE
        SYNTAX OptixCfmoamLtTestEntry
        MAX-ACCESS not-accessible
        STATUS current
        DESCRIPTION
            "This entry describes Start LT test of the Layer 2 802.1ag protocol."
        INDEX{ optixCfmoamMdId,optixCfmoamMaId,optixCfmoamMepId,optixCfmoamLtTestDestMpType,optixCfmoamLtTestMAC }
        ::= { optixCfmoamLtTestTable 1 }

    OptixCfmoamLtTestEntry ::=
        SEQUENCE {
            optixCfmoamLtTestDestMpType
                INTEGER,
            optixCfmoamLtTestMAC
                MacAddress,
            optixCfmoamLtTestLSRIP
                IpAddress,
            optixCfmoamLtTestMEPMAC
                OCTET STRING,
            optixCfmoamLtTestBoardID
                Unsigned32,
            optixCfmoamLtTestSubBoardID
                Unsigned32,
            optixCfmoamLtTestPortID
                Unsigned32,
            optixCfmoamLtTestHop
                Unsigned32,
            optixCfmoamLtTestResult
                INTEGER
        }

    -- 1.3.6.1.4.1.2011.2.25.4.50.15.1.8.1.1
    optixCfmoamLtTestDestMpType OBJECT-TYPE
        SYNTAX INTEGER
        {
            mepid(1),
            mac(2)
        }
        MAX-ACCESS not-accessible
        STATUS current
        DESCRIPTION
            "Dest mark type of Start LT test. 1: MEP ID, 2: MAC"
        ::= { optixCfmoamLtTestEntry 1 }

    -- 1.3.6.1.4.1.2011.2.25.4.50.15.1.8.1.2
    optixCfmoamLtTestMAC OBJECT-TYPE
        SYNTAX MacAddress
        MAX-ACCESS not-accessible
        STATUS current
        DESCRIPTION
            "MEPID or MAC of Start LT test. The sink MEP ID ranges from 1 to 8191. The MAC address of the sink MEP must not be a multicast MAC address."
        ::= { optixCfmoamLtTestEntry 2 }

    -- 1.3.6.1.4.1.2011.2.25.4.50.15.1.8.1.3
    optixCfmoamLtTestLSRIP OBJECT-TYPE
        SYNTAX IpAddress
        MAX-ACCESS read-only
        STATUS current
        DESCRIPTION
            "device IP address of LT test"
        ::= { optixCfmoamLtTestEntry 3 }

    -- 1.3.6.1.4.1.2011.2.25.4.50.15.1.8.1.4
    optixCfmoamLtTestMEPMAC OBJECT-TYPE
        SYNTAX OCTET STRING
        MAX-ACCESS read-only
        STATUS current
        DESCRIPTION
            "mep mac address of LT test"
        ::= { optixCfmoamLtTestEntry 4 }

    -- 1.3.6.1.4.1.2011.2.25.4.50.15.1.8.1.5
    optixCfmoamLtTestBoardID OBJECT-TYPE
        SYNTAX Unsigned32
        MAX-ACCESS read-only
        STATUS current
        DESCRIPTION
            "boardid of LT test"
        ::= { optixCfmoamLtTestEntry 5 }

    -- 1.3.6.1.4.1.2011.2.25.4.50.15.1.8.1.6
    optixCfmoamLtTestSubBoardID OBJECT-TYPE
        SYNTAX Unsigned32
        MAX-ACCESS read-only
        STATUS current
        DESCRIPTION
            "subboardid of LT test"
        ::= { optixCfmoamLtTestEntry 6 }

    -- 1.3.6.1.4.1.2011.2.25.4.50.15.1.8.1.7
    optixCfmoamLtTestPortID OBJECT-TYPE
        SYNTAX Unsigned32
        MAX-ACCESS read-only
        STATUS current
        DESCRIPTION
            "portid of LT test"
        ::= { optixCfmoamLtTestEntry 7 }

    -- 1.3.6.1.4.1.2011.2.25.4.50.15.1.8.1.8
    optixCfmoamLtTestHop OBJECT-TYPE
        SYNTAX Unsigned32
        MAX-ACCESS read-only
        STATUS current
        DESCRIPTION
            "the top of source mep to dest mep of LT test"
        ::= { optixCfmoamLtTestEntry 8 }

    -- 1.3.6.1.4.1.2011.2.25.4.50.15.1.8.1.9
    optixCfmoamLtTestResult OBJECT-TYPE
        SYNTAX INTEGER
        {
            success(0),
            fail(1)
        }
        MAX-ACCESS read-only
        STATUS current
        DESCRIPTION
            "result of LT test(0:success 1:failure)."
        ::= { optixCfmoamLtTestEntry 9 }

    -- 1.3.6.1.4.1.2011.2.25.4.50.15.1.9
    optixCfmoamTrapMember OBJECT IDENTIFIER ::= { optixCfmoamGroup 9 }

    -- 1.3.6.1.4.1.2011.2.25.4.50.15.1.9.1
    optixCfmoamTrapMdID OBJECT-TYPE
        SYNTAX Unsigned32
        MAX-ACCESS accessible-for-notify
        STATUS current
        DESCRIPTION
            "Trap MD Index. The index is numbered globally on an NE. Value range: 1 to 4294967040."
        ::= { optixCfmoamTrapMember 1 }

    -- 1.3.6.1.4.1.2011.2.25.4.50.15.1.9.2
    optixCfmoamTrapMaID OBJECT-TYPE
        SYNTAX Unsigned32
        MAX-ACCESS accessible-for-notify
        STATUS current
        DESCRIPTION
            "Trap Ma Index. The index is numbered globally on an NE. Value range: 1 to 4294967040."
        ::= { optixCfmoamTrapMember 2 }

    -- 1.3.6.1.4.1.2011.2.25.4.50.15.1.9.3
    optixCfmoamTrapSrcMepID OBJECT-TYPE
        SYNTAX Unsigned32
        MAX-ACCESS accessible-for-notify
        STATUS current
        DESCRIPTION
            "Trap source MEP Index.Value range: 1 to 8191."
        ::= { optixCfmoamTrapMember 3 }

    -- 1.3.6.1.4.1.2011.2.25.4.50.15.1.9.4
    optixCfmoamTrapDestMpType OBJECT-TYPE
        SYNTAX INTEGER
        {
            mepid(1),
            mac(2)
        }
        MAX-ACCESS accessible-for-notify
        STATUS current
        DESCRIPTION
            "Trap dest MP type.1:mepid,2:mac"
        ::= { optixCfmoamTrapMember 4 }

    -- 1.3.6.1.4.1.2011.2.25.4.50.15.1.9.5
    optixCfmoamTrapDestMp OBJECT-TYPE
        SYNTAX OCTET STRING
        MAX-ACCESS accessible-for-notify
        STATUS current
        DESCRIPTION
            "Trap dest MPID or MAC. For dest maintenance point ID range:1 to 8191"
        ::= { optixCfmoamTrapMember 5 }

    -- 1.3.6.1.4.1.2011.2.25.4.50.15.1.9.6
    optixCfmoamTrapDelay OBJECT-TYPE
        SYNTAX Unsigned32
        MAX-ACCESS accessible-for-notify
        STATUS current
        DESCRIPTION
            "Trap delay(unit:ms)."
        ::= { optixCfmoamTrapMember 6 }

    -- 1.3.6.1.4.1.2011.2.25.4.50.15.1.9.7
    optixCfmoamTrapTestState OBJECT-TYPE
        SYNTAX INTEGER
        {
            success(0),
            failure(1)
        }
        MAX-ACCESS accessible-for-notify
        STATUS current
        DESCRIPTION
            "Trap test state(0:success 1:failure)."
        ::= { optixCfmoamTrapMember 7 }

    -- 1.3.6.1.4.1.2011.2.25.4.50.15.1.9.8
    optixCfmoamTrapSendPackNum OBJECT-TYPE
        SYNTAX Unsigned32
        MAX-ACCESS accessible-for-notify
        STATUS current
        DESCRIPTION
            "Trap send packet number. Value range: 1 to 65535."
        ::= { optixCfmoamTrapMember 8 }

    -- 1.3.6.1.4.1.2011.2.25.4.50.15.1.9.9
    optixCfmoamTrapReceivePackNum OBJECT-TYPE
        SYNTAX Unsigned32
        MAX-ACCESS accessible-for-notify
        STATUS current
        DESCRIPTION
            "Trap receive packet number. Value range: 1 to 65535."
        ::= { optixCfmoamTrapMember 9 }

    -- 1.3.6.1.4.1.2011.2.25.4.50.15.1.9.10
    optixCfmoamTrapDropRate OBJECT-TYPE
        SYNTAX Unsigned32
        MAX-ACCESS accessible-for-notify
        STATUS current
        DESCRIPTION
            "Trap drop packet rate. Value range: 1 to 100."
        ::= { optixCfmoamTrapMember 10 }

    -- 1.3.6.1.4.1.2011.2.25.4.50.15.1.9.11
    optixCfmoamTrapMaxDelay OBJECT-TYPE
        SYNTAX Unsigned32
        MAX-ACCESS accessible-for-notify
        STATUS current
        DESCRIPTION
            "Trap max delay (unit:ms). Value range: 1 to 65535."
        ::= { optixCfmoamTrapMember 11 }

    -- 1.3.6.1.4.1.2011.2.25.4.50.15.1.9.12
    optixCfmoamTrapMinDelay OBJECT-TYPE
        SYNTAX Unsigned32
        MAX-ACCESS accessible-for-notify
        STATUS current
        DESCRIPTION
            "Trap min delay (unit:ms). Value range: 1 to 65535."
        ::= { optixCfmoamTrapMember 12 }

    -- 1.3.6.1.4.1.2011.2.25.4.50.15.1.9.13
    optixCfmoamTrapAverageDelay OBJECT-TYPE
        SYNTAX Unsigned32
        MAX-ACCESS accessible-for-notify
        STATUS current
        DESCRIPTION
            "Trap Average delay (unit:ms). Value range: 1 to 65535."
        ::= { optixCfmoamTrapMember 13 }

    -- 1.3.6.1.4.1.2011.2.25.4.50.15.1.9.14
    optixCfmoamTrapRspLSRIP OBJECT-TYPE
        SYNTAX OCTET STRING
        MAX-ACCESS accessible-for-notify
        STATUS current
        DESCRIPTION
            "Trap response device IP address"
        ::= { optixCfmoamTrapMember 14 }

    -- 1.3.6.1.4.1.2011.2.25.4.50.15.1.9.15
    optixCfmoamTrapRspMEPMAC OBJECT-TYPE
        SYNTAX OCTET STRING
        MAX-ACCESS accessible-for-notify
        STATUS current
        DESCRIPTION
            "Trap response mep mac address"
        ::= { optixCfmoamTrapMember 15 }

    -- 1.3.6.1.4.1.2011.2.25.4.50.15.1.9.16
    optixCfmoamTrapRspBoardID OBJECT-TYPE
        SYNTAX Unsigned32
        MAX-ACCESS accessible-for-notify
        STATUS current
        DESCRIPTION
            "Trap boardid"
        ::= { optixCfmoamTrapMember 16 }

    -- 1.3.6.1.4.1.2011.2.25.4.50.15.1.9.17
    optixCfmoamTrapRspSubBoardID OBJECT-TYPE
        SYNTAX Unsigned32
        MAX-ACCESS accessible-for-notify
        STATUS current
        DESCRIPTION
            "Trap subboardid"
        ::= { optixCfmoamTrapMember 17 }

    -- 1.3.6.1.4.1.2011.2.25.4.50.15.1.9.18
    optixCfmoamTrapRspPortID OBJECT-TYPE
        SYNTAX Unsigned32
        MAX-ACCESS accessible-for-notify
        STATUS current
        DESCRIPTION
            "Trap portid"
        ::= { optixCfmoamTrapMember 18 }

    -- 1.3.6.1.4.1.2011.2.25.4.50.15.1.9.19
    optixCfmoamTrapHop OBJECT-TYPE
        SYNTAX Unsigned32
        MAX-ACCESS accessible-for-notify
        STATUS current
        DESCRIPTION
            "Trap response the top of source MEP to dest MEP. Value range: 1 to 255."
        ::= { optixCfmoamTrapMember 19 }

    -- 1.3.6.1.4.1.2011.2.25.4.50.15.1.9.20
    optixCfmoamTrapSaltusNum OBJECT-TYPE
        SYNTAX Unsigned32
        MAX-ACCESS accessible-for-notify
        STATUS current
        DESCRIPTION
            "Number of changes reported in the event"
        ::= { optixCfmoamTrapMember 20 }

    -- 1.3.6.1.4.1.2011.2.25.4.50.15.1.9.21
    optixCfmoamTrapSaltusBit OBJECT-TYPE
        SYNTAX Unsigned32
        MAX-ACCESS accessible-for-notify
        STATUS current
        DESCRIPTION
            "First change bit reported in the event"
        ::= { optixCfmoamTrapMember 21 }

    -- 1.3.6.1.4.1.2011.2.25.4.50.15.1.10
    optixCfmoamTrapEvent OBJECT IDENTIFIER ::= { optixCfmoamGroup 10 }

    -- 1.3.6.1.4.1.2011.2.25.4.50.15.1.10.1
    optixCfmoamTrapLbRsp NOTIFICATION-TYPE
        STATUS current
        DESCRIPTION
            "LB rsp trap."
        ::= { optixCfmoamTrapEvent 1 }

    -- 1.3.6.1.4.1.2011.2.25.4.50.15.1.10.2
    optixCfmoamTrapLbStatistic NOTIFICATION-TYPE
        STATUS current
        DESCRIPTION
            "LB statistic trap."
        ::= { optixCfmoamTrapEvent 2 }

    -- 1.3.6.1.4.1.2011.2.25.4.50.15.1.10.3
    optixCfmoamTrapLbRspOverTime NOTIFICATION-TYPE
        STATUS current
        DESCRIPTION
            "LB rsp overtime trap."
        ::= { optixCfmoamTrapEvent 3 }

    -- 1.3.6.1.4.1.2011.2.25.4.50.15.1.10.4
    optixCfmoamExtTrapLbRsp NOTIFICATION-TYPE
        STATUS current
        DESCRIPTION
            "Extension LB response event"
        ::= { optixCfmoamTrapEvent 4 }

    -- 1.3.6.1.4.1.2011.2.25.4.50.15.1.11
    optixCfmoamGetMepOnPortTable OBJECT-TYPE
        SYNTAX SEQUENCE OF OptixCfmoamGetMepOnPortEntry
        MAX-ACCESS not-accessible
        STATUS current
        DESCRIPTION
            "This table describes the basic MEP configuration information of the Layer 2 802.1ag protocol."
        ::= { optixCfmoamGroup 11 }

    -- 1.3.6.1.4.1.2011.2.25.4.50.15.1.11.1
    optixCfmoamGetMepOnPortEntry OBJECT-TYPE
        SYNTAX OptixCfmoamGetMepOnPortEntry
        MAX-ACCESS not-accessible
        STATUS current
        DESCRIPTION
            "This entry describes the basic MEP configuration information of the Layer 2 802.1ag protocol."
        INDEX{ optixLogBoardId,optixLogSubCardId,optixPortId }
        ::= { optixCfmoamGetMepOnPortTable 1 }

    OptixCfmoamGetMepOnPortEntry ::=
        SEQUENCE {
            optixCfmoamOnPortMdId
                Unsigned32,
            optixCfmoamOnPortMdName
                OCTET STRING,
            optixCfmoamOnPortMaId
                Unsigned32,
            optixCfmoamOnPortMaName
                OCTET STRING,
            optixCfmoamOnPortMepId
                Unsigned32,
            optixCfmoamOnPortMepDirect
                INTEGER
        }

    -- 1.3.6.1.4.1.2011.2.25.4.50.15.1.11.1.1
    optixCfmoamOnPortMdId OBJECT-TYPE
        SYNTAX Unsigned32
        MAX-ACCESS read-only
        STATUS current
        DESCRIPTION
            "This object indicates the MD index of the 802.1ag protocol. The index is numbered globally on an NE. Value range: 1 to 4294967040."
        ::= { optixCfmoamGetMepOnPortEntry 1 }

    -- 1.3.6.1.4.1.2011.2.25.4.50.15.1.11.1.2
    optixCfmoamOnPortMdName OBJECT-TYPE
        SYNTAX OCTET STRING
        MAX-ACCESS read-only
        STATUS current
        DESCRIPTION
            "This object indicates the MD name of the 802.1ag protocol."
        ::= { optixCfmoamGetMepOnPortEntry 2 }

    -- 1.3.6.1.4.1.2011.2.25.4.50.15.1.11.1.3
    optixCfmoamOnPortMaId OBJECT-TYPE
        SYNTAX Unsigned32
        MAX-ACCESS read-only
        STATUS current
        DESCRIPTION
            "This object indicates the MA index of the 802.1ag protocol. The index is numbered globally on an NE. Value range: 1 to 4294967040."
        ::= { optixCfmoamGetMepOnPortEntry 3 }

    -- 1.3.6.1.4.1.2011.2.25.4.50.15.1.11.1.4
    optixCfmoamOnPortMaName OBJECT-TYPE
        SYNTAX OCTET STRING
        MAX-ACCESS read-only
        STATUS current
        DESCRIPTION
            "This object indicates the MA name of the 802.1ag protocol."
        ::= { optixCfmoamGetMepOnPortEntry 4 }

    -- 1.3.6.1.4.1.2011.2.25.4.50.15.1.11.1.5
    optixCfmoamOnPortMepId OBJECT-TYPE
        SYNTAX Unsigned32
        MAX-ACCESS read-only
        STATUS current
        DESCRIPTION
            "This object indicates the MEP ID of the 802.1ag protocol. Value range: 1 to 8191."
        ::= { optixCfmoamGetMepOnPortEntry 5 }

    -- 1.3.6.1.4.1.2011.2.25.4.50.15.1.11.1.6
    optixCfmoamOnPortMepDirect OBJECT-TYPE
        SYNTAX INTEGER
        {
            ingress(1),
            egress(2)
        }
        MAX-ACCESS read-only
        STATUS current
        DESCRIPTION
            "This object indicates the MEP direction of the 802.1ag protocol. 1: ingress, 2: egress"
        ::= { optixCfmoamGetMepOnPortEntry 6 }

    -- 1.3.6.1.4.1.2011.2.25.4.50.15.1.12
    optixCfmoamExtLbTestTable OBJECT-TYPE
        SYNTAX SEQUENCE OF OptixCfmoamExtLbTestEntry
        MAX-ACCESS not-accessible
        STATUS current
        DESCRIPTION
            "This table describes Start LB test of the Layer 2 802.1ag protocol."
        ::= { optixCfmoamGroup 12 }

    -- 1.3.6.1.4.1.2011.2.25.4.50.15.1.12.1
    optixCfmoamExtLbTestEntry OBJECT-TYPE
        SYNTAX OptixCfmoamExtLbTestEntry
        MAX-ACCESS not-accessible
        STATUS current
        DESCRIPTION
            "This entry describes Start LB test of the Layer 2 802.1ag protocol."
        INDEX{ optixCfmoamMdId,optixCfmoamMaId,optixCfmoamMepId }
        ::= { optixCfmoamExtLbTestTable 1 }

    OptixCfmoamExtLbTestEntry ::=
        SEQUENCE {
            optixCfmoamExtLbTestDmepType
                INTEGER,
            optixCfmoamExtLbTestMAC
                OCTET STRING,
            optixCfmoamExtLbTestPackNum
                Unsigned32,
            optixCfmoamExtLbTestLength
                Unsigned32,
            optixCfmoamExtLbTestPriority
                Unsigned32,
            optixCfmoamExtLbTestVlan
                Unsigned32,
            optixCfmoamExtLbTestMode
                Unsigned32
        }

    -- 1.3.6.1.4.1.2011.2.25.4.50.15.1.12.1.1
    optixCfmoamExtLbTestDmepType OBJECT-TYPE
        SYNTAX INTEGER
        {
            mepid(1),
            mac(2)
        }
        MAX-ACCESS read-write
        STATUS current
        DESCRIPTION
            "Invalid query. Identifier type of the sink-end MEP that initiates the MEP LB test. 1: MEP ID; 2: MAC address"
        ::= { optixCfmoamExtLbTestEntry 1 }

    -- 1.3.6.1.4.1.2011.2.25.4.50.15.1.12.1.2
    optixCfmoamExtLbTestMAC OBJECT-TYPE
        SYNTAX OCTET STRING
        MAX-ACCESS read-write
        STATUS current
        DESCRIPTION
            "Invalid query. ID or MAC address of the MEP that initiates the MEP LB test."
        ::= { optixCfmoamExtLbTestEntry 2 }

    -- 1.3.6.1.4.1.2011.2.25.4.50.15.1.12.1.3
    optixCfmoamExtLbTestPackNum OBJECT-TYPE
        SYNTAX Unsigned32
        MAX-ACCESS read-write
        STATUS current
        DESCRIPTION
            "Invalid query. Number of transmitted packets for initiating the MEP LB test. (Value range: 1-65535; Default value: 3)"
        ::= { optixCfmoamExtLbTestEntry 3 }

    -- 1.3.6.1.4.1.2011.2.25.4.50.15.1.12.1.4
    optixCfmoamExtLbTestLength OBJECT-TYPE
        SYNTAX Unsigned32
        MAX-ACCESS read-write
        STATUS current
        DESCRIPTION
            "Invalid query. Number of transmitted packets for initiating the MEP LB test. (Value range: 1-65535; Default value: 3)"
        ::= { optixCfmoamExtLbTestEntry 4 }

    -- 1.3.6.1.4.1.2011.2.25.4.50.15.1.12.1.5
    optixCfmoamExtLbTestPriority OBJECT-TYPE
        SYNTAX Unsigned32
        MAX-ACCESS read-write
        STATUS current
        DESCRIPTION
            "Invalid query. Length of transmitted packets for initiating the MEP LB test. (Value range: 64-0xffff; Default value: 64)"
        ::= { optixCfmoamExtLbTestEntry 5 }

    -- 1.3.6.1.4.1.2011.2.25.4.50.15.1.12.1.6
    optixCfmoamExtLbTestVlan OBJECT-TYPE
        SYNTAX Unsigned32
        MAX-ACCESS read-write
        STATUS current
        DESCRIPTION
            "Invalid query. VLAN ID of transmitted packets for initiating the MEP LB test. (Value range: 0-0xffe; Default value: 0)"
        ::= { optixCfmoamExtLbTestEntry 6 }

    -- 1.3.6.1.4.1.2011.2.25.4.50.15.1.12.1.7
    optixCfmoamExtLbTestMode OBJECT-TYPE
        SYNTAX Unsigned32
        MAX-ACCESS read-write
        STATUS current
        DESCRIPTION
            "Invalid query. Packet payload mode for initiating the MEP LB test. (Value range: 0-2; Default value: 0)"
        ::= { optixCfmoamExtLbTestEntry 7 }

END
