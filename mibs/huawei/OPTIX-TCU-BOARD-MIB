-- OPTIX-TCU-BOARD-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-TCU-BOARD-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        ;

    optixTCUBoard MODULE-IDENTITY
        LAST-UPDATED "201301221007Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes the TCU boardconfigurations."
        REVISION "201301221007Z"
        DESCRIPTION
            "The initial revision of this MIB module."
        ::={ optixProvisionEqpt 2 }

    -- 1.3.6.1.4.1.2011.2.25.4.30.2.1
    optixTCU OBJECT IDENTIFIER ::= { optixTCUBoard 1 }

    -- 1.3.6.1.4.1.2011.2.25.4.30.2.1.1
    optixTCUTable OBJECT-TYPE
        SYNTAX SEQUENCE OF OptixTCUEntry
        MAX-ACCESS not-accessible
        STATUS current
        DESCRIPTION
            "This table contains basic configuration information of TCU"
        ::= { optixTCU 1 }

    -- 1.3.6.1.4.1.2011.2.25.4.30.2.1.1.1
    optixTCUEntry OBJECT-TYPE
        SYNTAX OptixTCUEntry
        MAX-ACCESS not-accessible
        STATUS current
        DESCRIPTION
            "Entry containins basic information of TCU"
        INDEX{ optixLogBoardId,optixLogSubCardId }
        ::= { optixTCUTable 1 }

    OptixTCUEntry ::=
        SEQUENCE {
            optixTCUSpeedMode
                INTEGER,
            optixTCUHighTh
                OCTET STRING,
            optixTCULowTh
                OCTET STRING,
            optixTCUInFanSpeed
                Unsigned32,
            optixTCUOutFanSpeed
                Unsigned32,
            optixTCUBoardTemp
                OCTET STRING,
            optixTCUOutTakeTemp
                OCTET STRING,
            optixTCUInTakeTemp
                OCTET STRING,
            optixTCUInnerFanpara
                Unsigned32,
            optixTCUOuterfanpara
                Unsigned32,
            optixTCUDiscretePara
                INTEGER
        }

    -- 1.3.6.1.4.1.2011.2.25.4.30.2.1.1.1.1
    optixTCUSpeedMode OBJECT-TYPE
        SYNTAX INTEGER
        {
            tempCtrl(0),
            neDiscretectrl(1),
            neDutyratioctrl(2)
        }
        MAX-ACCESS read-write
        STATUS current
        DESCRIPTION
            "This parameter specifies the speed and adjust mode of bid and subbid. 0: tempCtrl, 1: neDiscretectrl, 2: neDutyratioctrl"
        ::= { optixTCUEntry 1 }

    -- 1.3.6.1.4.1.2011.2.25.4.30.2.1.1.1.2
    optixTCUHighTh OBJECT-TYPE
        SYNTAX OCTET STRING
        MAX-ACCESS read-write
        STATUS current
        DESCRIPTION
            "This parameter specifies the high tempth of bid sbid."
        ::= { optixTCUEntry 2 }

    -- 1.3.6.1.4.1.2011.2.25.4.30.2.1.1.1.3
    optixTCULowTh OBJECT-TYPE
        SYNTAX OCTET STRING
        MAX-ACCESS read-write
        STATUS current
        DESCRIPTION
            "This parameter specifies the low tempth of bid sbid."
        ::= { optixTCUEntry 3 }

    -- 1.3.6.1.4.1.2011.2.25.4.30.2.1.1.1.4
    optixTCUInFanSpeed OBJECT-TYPE
        SYNTAX Unsigned32
        MAX-ACCESS read-only
        STATUS current
        DESCRIPTION
            "This parameter specifies the fan speed of inside. Value range: 0 to 65535."
        ::= { optixTCUEntry 4 }

    -- 1.3.6.1.4.1.2011.2.25.4.30.2.1.1.1.5
    optixTCUOutFanSpeed OBJECT-TYPE
        SYNTAX Unsigned32
        MAX-ACCESS read-only
        STATUS current
        DESCRIPTION
            "This parameter specifies the fan speed of outside. Value range: 0 to 65535."
        ::= { optixTCUEntry 5 }

    -- 1.3.6.1.4.1.2011.2.25.4.30.2.1.1.1.6
    optixTCUBoardTemp OBJECT-TYPE
        SYNTAX OCTET STRING
        MAX-ACCESS read-only
        STATUS current
        DESCRIPTION
            "This parameter specifies the value of temp control unit."
        ::= { optixTCUEntry 6 }

    -- 1.3.6.1.4.1.2011.2.25.4.30.2.1.1.1.7
    optixTCUOutTakeTemp OBJECT-TYPE
        SYNTAX OCTET STRING
        MAX-ACCESS read-only
        STATUS current
        DESCRIPTION
            "This parameter specifies the temp value of NE out wind tunnnel."
        ::= { optixTCUEntry 7 }

    -- 1.3.6.1.4.1.2011.2.25.4.30.2.1.1.1.8
    optixTCUInTakeTemp OBJECT-TYPE
        SYNTAX OCTET STRING
        MAX-ACCESS read-only
        STATUS current
        DESCRIPTION
            "This parameter specifies the temp value of NE in wind tunnnel."
        ::= { optixTCUEntry 8 }

    -- 1.3.6.1.4.1.2011.2.25.4.30.2.1.1.1.9
    optixTCUInnerFanpara OBJECT-TYPE
        SYNTAX Unsigned32
        MAX-ACCESS read-write
        STATUS current
        DESCRIPTION
            "This object indicates the para of inside fan speed. Value range: 20 to 100 and 0."
        ::= { optixTCUEntry 9 }

    -- 1.3.6.1.4.1.2011.2.25.4.30.2.1.1.1.10
    optixTCUOuterfanpara OBJECT-TYPE
        SYNTAX Unsigned32
        MAX-ACCESS read-write
        STATUS current
        DESCRIPTION
            "This object indicates the para of outside fan speed. Value range: 20 to 100 and 0."
        ::= { optixTCUEntry 10 }

    -- 1.3.6.1.4.1.2011.2.25.4.30.2.1.1.1.11
    optixTCUDiscretePara OBJECT-TYPE
        SYNTAX INTEGER
        {
            highspeed(0),
            lowspeed(1)
        }
        MAX-ACCESS read-write
        STATUS current
        DESCRIPTION
            "This object indicates the para of TCU discrete speed."
        DEFVAL{ 0 }
        ::= { optixTCUEntry 11 }

    -- 1.3.6.1.4.1.2011.2.25.4.30.2.1.2
    optixTCUIoalmvalTable OBJECT-TYPE
        SYNTAX SEQUENCE OF OptixTCUIoalmvalEntry
        MAX-ACCESS not-accessible
        STATUS current
        DESCRIPTION
            "This table contains basic configuration information of TCU"
        ::= { optixTCU 2 }

    -- 1.3.6.1.4.1.2011.2.25.4.30.2.1.2.1
    optixTCUIoalmvalEntry OBJECT-TYPE
        SYNTAX OptixTCUIoalmvalEntry
        MAX-ACCESS not-accessible
        STATUS current
        DESCRIPTION
            "Entry containins basic information of TCU"
        INDEX{ optixLogBoardId,optixLogSubCardId,optixTCUAlmId }
        ::= { optixTCUIoalmvalTable 1 }

    OptixTCUIoalmvalEntry ::=
        SEQUENCE {
            optixTCUAlmId
                Unsigned32,
            optixTCUAlmIoval
                INTEGER
        }

    -- 1.3.6.1.4.1.2011.2.25.4.30.2.1.2.1.1
    optixTCUAlmId OBJECT-TYPE
        SYNTAX Unsigned32
        MAX-ACCESS not-accessible
        STATUS current
        DESCRIPTION
            "This parameter specifies the TCU index. 0: odcSmokeOver, 1: odcWaterAlm, 2: odcDoorOpen, 3: odcSurgeProtectionFail"
        ::= { optixTCUIoalmvalEntry 1 }

    -- 1.3.6.1.4.1.2011.2.25.4.30.2.1.2.1.2
    optixTCUAlmIoval OBJECT-TYPE
        SYNTAX INTEGER
        {
            high(0),
            low(1)
        }
        MAX-ACCESS read-write
        STATUS current
        DESCRIPTION
            "This parameter specifies the temperature value of NE in wind tunnnel. 0: high, 1: low"
        ::= { optixTCUIoalmvalEntry 2 }

    -- 1.3.6.1.4.1.2011.2.25.4.30.2.1.3
    optixTCUFuncTable OBJECT-TYPE
        SYNTAX SEQUENCE OF OptixTCUFuncEntry
        MAX-ACCESS not-accessible
        STATUS current
        DESCRIPTION
            "This table contains the information of TCU functional item configurations."
        ::= { optixTCU 3 }

    -- 1.3.6.1.4.1.2011.2.25.4.30.2.1.3.1
    optixTCUFuncEntry OBJECT-TYPE
        SYNTAX OptixTCUFuncEntry
        MAX-ACCESS not-accessible
        STATUS current
        DESCRIPTION
            "This entry contains the information of TCU functional items."
        INDEX{ optixLogBoardId,optixTCUFuncTtem }
        ::= { optixTCUFuncTable 1 }

    OptixTCUFuncEntry ::=
        SEQUENCE {
            optixTCUFuncTtem
                INTEGER,
            optixTCUFuncItemEnable
                INTEGER
        }

    -- 1.3.6.1.4.1.2011.2.25.4.30.2.1.3.1.1
    optixTCUFuncTtem OBJECT-TYPE
        SYNTAX INTEGER
        {
            odcSurgeProtectionFail(1),
            odcSmokeOver(4),
            odcWaterAlm(5),
            odcDoorOpen(6)
        }
        MAX-ACCESS not-accessible
        STATUS current
        DESCRIPTION
            "This parameter specifies the functional item of TCU. 1: odcSurgeProtectionFail, 4: odcSmokeOver, 5: odcWaterAlm, 6: odcDoorOpen"
        ::= { optixTCUFuncEntry 1 }

    -- 1.3.6.1.4.1.2011.2.25.4.30.2.1.3.1.2
    optixTCUFuncItemEnable OBJECT-TYPE
        SYNTAX INTEGER
        {
            enable(1),
            disable(0)
        }
        MAX-ACCESS read-write
        STATUS current
        DESCRIPTION
            "This parameter specifies the enable state of TCU functional items. 0: disable, 1: enable"
        ::= { optixTCUFuncEntry 2 }

END
