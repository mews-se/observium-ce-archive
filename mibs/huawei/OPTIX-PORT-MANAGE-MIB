-- OPTIX-PORT-MANAGE-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PORT-MANAGE-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY,NOTIFICATION-TYPE
            FROM SNMPv2-SMI
        RowStatus
            FROM SNMPv2-TC
        optixLogBoardId,optixLogSubCardId
            FROM OPTIX-BOARD-MANAGE-MIB
        optixOamPortType
            FROM OPTIX-MISC-MIB
        ;

    optixPortMng MODULE-IDENTITY
        LAST-UPDATED "201204270000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes the general port configurations."
        REVISION "201204270000Z"
        DESCRIPTION
            "The initial revision of this MIB module."
        REVISION "201204270000Z"
        DESCRIPTION
            "The initial revision of this MIB module."
        ::={ optixProvisionEqpt 36 }

    -- 1.3.6.1.4.1.2011.2.25.4.30.36.1
    optixPortMngGroup OBJECT IDENTIFIER ::= { optixPortMng 1 }

    -- 1.3.6.1.4.1.2011.2.25.4.30.36.1.1
    optixPortMngTable OBJECT-TYPE
        SYNTAX SEQUENCE OF OptixPortMngEntry
        MAX-ACCESS not-accessible
        STATUS current
        DESCRIPTION
            "This table describes the general logical configurations of boards."
        ::= { optixPortMngGroup 1 }

    -- 1.3.6.1.4.1.2011.2.25.4.30.36.1.1.1
    optixPortMngEntry OBJECT-TYPE
        SYNTAX OptixPortMngEntry
        MAX-ACCESS not-accessible
        STATUS current
        DESCRIPTION
            "This entry describes the general logical configurations of boards."
        INDEX{ optixLogBoardId,optixLogSubCardId,optixPortId }
        ::= { optixPortMngTable 1 }

    OptixPortMngEntry ::=
        SEQUENCE {
            optixPortId
                Unsigned32,
            optixPortname
                OCTET STRING,
            optixPortType
                INTEGER,
            optixPortLevel
                INTEGER,
            optixPhyPortType
                INTEGER,
            optixPhyPortLevel
                INTEGER,
            optixLogPortStatus
                RowStatus
        }

    -- 1.3.6.1.4.1.2011.2.25.4.30.36.1.1.1.1
    optixPortId OBJECT-TYPE
        SYNTAX Unsigned32
        MAX-ACCESS not-accessible
        STATUS current
        DESCRIPTION
            "This object indicates the port number."
        ::= { optixPortMngEntry 1 }

    -- 1.3.6.1.4.1.2011.2.25.4.30.36.1.1.1.2
    optixPortname OBJECT-TYPE
        SYNTAX OCTET STRING (SIZE(0..64))
        MAX-ACCESS read-create
        STATUS current
        DESCRIPTION
            "This object indicates the port name."
        ::= { optixPortMngEntry 2 }

    -- 1.3.6.1.4.1.2011.2.25.4.30.36.1.1.1.3
    optixPortType OBJECT-TYPE
        SYNTAX INTEGER
        {
            unknown(254),
            null(255),
            sdhOpport(1),
            sdhEport(2),
            macOpport(5),
            macEport(6),
            cpriPort(30),
            lineport(8),
            obsaiport(31),
            atomgpsport(32),
            xpiccasport(33),
            mimocasport(34),
            cacasport(35),
            seplacasport(36)
        }
        MAX-ACCESS read-create
        STATUS current
        DESCRIPTION
            "This object indicates the port type. 1: sdhOpport, 5: macOpport, 6: macEport, 254: unknown, 2: sdhEport, 30: cpriPort, 8: lineport, 31: obsaiport, 32: atomgpsport, 33: xpiccasport, 34: mimocasport, 35: cacasport, 36: seplacasport, 255: null"
        ::= { optixPortMngEntry 3 }

    -- 1.3.6.1.4.1.2011.2.25.4.30.36.1.1.1.4
    optixPortLevel OBJECT-TYPE
        SYNTAX INTEGER
        {
            stm1(1),
            stm4(2),
            stm16(3),
            stm64(4),
            stm256(5),
            ptnGe(6),
            ptnFe(7),
            ptn10ge(8),
            ptn2p5ge(10),
            fe(80),
            ge(81),
            cpri1p25(128),
            cpri2p5(129),
            cpri1p25transparent(130),
            cpri1p25compress(131),
            cpri2p5transparent(132),
            cpri2p5compress(133),
            cpri3gtransparent(134),
            cpri3gcompress(135),
            cpri5gtransparent(136),
            cpri5gcompress(137),
            cpri6gtransparent(138),
            cpri6gcompress(139),
            cpri10gtransparent(140),
            cpri10gcompress(141),
            unknown(254),
            null(255),
            obsai1p5(142),
            obsai3g(143)
        }
        MAX-ACCESS read-create
        STATUS current
        DESCRIPTION
            "This object indicates the port rate. 1: STM-1, 2: STM-4, 3: STM-16, 4: STM-64, 5: STM-256, 6: PTN GE, 7: PTN FE, 8: PTN 10GE, 10: PTN 2.5GE, 80: FE, 81: GE, 128: cpri-1p25, 129: cpri-2p5, 130: cpri-1p25transparent, 131: cpri-1p25compress, 132: cpri-2p5transparent, 133: cpri-2p5compress, 134: cpri-3gtransparent, 135: cpri-3gcompress, 136: cpri-5gtransparent, 137: cpri-5gcompress, 138: cpri-6gtransparent, 139: cpri-6gcompress, 140: cpri-10gtransparent, 141: cpri-10gcompress, 254: unknown, 255: null,142:obsai1p5,143:obsai3g"
        ::= { optixPortMngEntry 4 }

    -- 1.3.6.1.4.1.2011.2.25.4.30.36.1.1.1.5
    optixPhyPortType OBJECT-TYPE
        SYNTAX INTEGER
        {
            lineport(8),
            unknown(254),
            null(255),
            sdhOpport(1),
            sdhEport(2),
            macOpport(5),
            macEport(6),
            cpriPort(30)
        }
        MAX-ACCESS read-only
        STATUS current
        DESCRIPTION
            "This object indicates the physical port type. 1: sdhOpport, 5: macOpport, 6: macEport, 254: unknown, 2: sdhEport, 30: cpriPort, 8: lineport"
        ::= { optixPortMngEntry 5 }

    -- 1.3.6.1.4.1.2011.2.25.4.30.36.1.1.1.6
    optixPhyPortLevel OBJECT-TYPE
        SYNTAX INTEGER
        {
            stm1(1),
            stm4(2),
            stm16(3),
            stm64(4),
            stm256(5),
            ptnGe(6),
            ptnFe(7),
            fe(80),
            ge(81),
            unknown(254),
            null(255),
            ptn2p5ge(10),
            ptn10Ge(8),
            cpri1p25(128),
            cpri2p5(129),
            cpri1p25trans(130),
            cpri1p25comp(131),
            cpri2p5trans(132),
            cpri2p5comp(133),
            cpri3gtrans(134),
            cpri3gcomp(135),
            cpri5gtrans(136),
            cpri5gcomp(137),
            cpri6gtrans(138),
            cpri6gcomp(139),
            cpri10gtrans(140),
            cpri9p8comp(141),
            obsai1p5(142),
            obsai3g(143)
        }
        MAX-ACCESS read-only
        STATUS current
        DESCRIPTION
            "This object indicates the physical port rate. stm1(1),stm4(2),stm16(3),stm64(4),stm256(5),ptnGe(6),ptnFe(7),fe(80),ge(81),unknown(254),null(255),ptn2p5ge(10),ptn10Ge(8),cpri1p25(128),cpri2p5(129),cpri1p25trans(130),cpri1p25comp(131),cpri2p5trans(132),cpri2p5comp(133),cpri3gtrans(134),cpri3gcomp(135),cpri5gtrans(136),cpri5gcomp(137),cpri6gtrans(138),cpri6gcomp(139),cpri10gtrans(140),cpri9p8comp(141),obsai1p5(142),obsai3g(143)"
        ::= { optixPortMngEntry 6 }

    -- 1.3.6.1.4.1.2011.2.25.4.30.36.1.1.1.7
    optixLogPortStatus OBJECT-TYPE
        SYNTAX RowStatus
        MAX-ACCESS read-create
        STATUS current
        DESCRIPTION
            "This object indicates the row status."
        DEFVAL{ active }
        ::= { optixPortMngEntry 7 }

    -- 1.3.6.1.4.1.2011.2.25.4.30.36.1.2
    optixPortOnlineTrapMember OBJECT IDENTIFIER ::= { optixPortMngGroup 2 }

    -- 1.3.6.1.4.1.2011.2.25.4.30.36.1.2.1
    optixPortOnlineBdId OBJECT-TYPE
        SYNTAX Unsigned32
        MAX-ACCESS accessible-for-notify
        STATUS current
        DESCRIPTION
            "the Board ID of Port Online Event"
        ::= { optixPortOnlineTrapMember 1 }

    -- 1.3.6.1.4.1.2011.2.25.4.30.36.1.2.2
    optixPortOnlineSubBdId OBJECT-TYPE
        SYNTAX Unsigned32
        MAX-ACCESS accessible-for-notify
        STATUS current
        DESCRIPTION
            "the SubBoard ID of Port Online Event"
        ::= { optixPortOnlineTrapMember 2 }

    -- 1.3.6.1.4.1.2011.2.25.4.30.36.1.2.3
    optixPortOnlinePortId OBJECT-TYPE
        SYNTAX Unsigned32
        MAX-ACCESS accessible-for-notify
        STATUS current
        DESCRIPTION
            "the Port ID of Port Online Event"
        ::= { optixPortOnlineTrapMember 3 }

    -- 1.3.6.1.4.1.2011.2.25.4.30.36.1.2.4
    optixPortOnlinePortType OBJECT-TYPE
        SYNTAX INTEGER
        {
            lineport(8),
            unknown(254),
            sdhOpport(1),
            sdhEport(2),
            macOpport(5),
            macEport(6),
            cpriPort(30),
            null(255)
        }
        MAX-ACCESS accessible-for-notify
        STATUS current
        DESCRIPTION
            "This object indicates the rate of an online port."
        ::= { optixPortOnlineTrapMember 4 }

    -- 1.3.6.1.4.1.2011.2.25.4.30.36.1.2.5
    optixPortOnlinePortLevel OBJECT-TYPE
        SYNTAX INTEGER
        {
            stm1(1),
            stm4(2),
            stm16(3),
            stm64(4),
            stm256(5),
            fe(80),
            ge(81),
            unknown(254),
            ptnGe(6),
            ptnFe(7),
            snmpnull(255)
        }
        MAX-ACCESS accessible-for-notify
        STATUS current
        DESCRIPTION
            "the Port Level of Port Online Event"
        ::= { optixPortOnlineTrapMember 5 }

    -- 1.3.6.1.4.1.2011.2.25.4.30.36.1.3
    optixPortOnlineTrapReport OBJECT IDENTIFIER ::= { optixPortMngGroup 3 }

    -- 1.3.6.1.4.1.2011.2.25.4.30.36.1.3.1
    optixPortOnlineTrap NOTIFICATION-TYPE
        OBJECTS{ optixPortOnlinePortLevel,optixPortOnlinePortType,optixPortOnlinePortId,optixPortOnlineSubBdId,optixPortOnlineBdId }
        STATUS current
        DESCRIPTION
            "the Event of Port Online"
        ::= { optixPortOnlineTrapReport 1 }

    -- 1.3.6.1.4.1.2011.2.25.4.30.36.1.4
    optixMaxPortNumTable OBJECT-TYPE
        SYNTAX SEQUENCE OF OptixMaxPortNumEntry
        MAX-ACCESS not-accessible
        STATUS current
        DESCRIPTION
            "This table describes the max port number"
        ::= { optixPortMngGroup 4 }

    -- 1.3.6.1.4.1.2011.2.25.4.30.36.1.4.1
    optixMaxPortNumEntry OBJECT-TYPE
        SYNTAX OptixMaxPortNumEntry
        MAX-ACCESS not-accessible
        STATUS current
        DESCRIPTION
            "This entry describes the max port number"
        INDEX{ optixLogBoardId,optixLogSubCardId }
        ::= { optixMaxPortNumTable 1 }

    OptixMaxPortNumEntry ::=
        SEQUENCE {
            optixNeMaxPortNum
                Unsigned32,
            optixNeValidportNum
                Unsigned32,
            optixNeValidportList
                OCTET STRING
        }

    -- 1.3.6.1.4.1.2011.2.25.4.30.36.1.4.1.1
    optixNeMaxPortNum OBJECT-TYPE
        SYNTAX Unsigned32
        MAX-ACCESS read-only
        STATUS current
        DESCRIPTION
            "This object describes the max port number"
        ::= { optixMaxPortNumEntry 1 }

    -- 1.3.6.1.4.1.2011.2.25.4.30.36.1.4.1.2
    optixNeValidportNum OBJECT-TYPE
        SYNTAX Unsigned32
        MAX-ACCESS read-only
        STATUS current
        DESCRIPTION
            "This object describes number of valid ports."
        ::= { optixMaxPortNumEntry 2 }

    -- 1.3.6.1.4.1.2011.2.25.4.30.36.1.4.1.3
    optixNeValidportList OBJECT-TYPE
        SYNTAX OCTET STRING
        MAX-ACCESS read-only
        STATUS current
        DESCRIPTION
            "This object describes number of valid ports."
        ::= { optixMaxPortNumEntry 3 }

    -- 1.3.6.1.4.1.2011.2.25.4.30.36.1.5
    optixReplacePortTable OBJECT-TYPE
        SYNTAX SEQUENCE OF OptixReplacePortEntry
        MAX-ACCESS not-accessible
        STATUS current
        DESCRIPTION
            "This table describes the configuration of replace port"
        ::= { optixPortMngGroup 5 }

    -- 1.3.6.1.4.1.2011.2.25.4.30.36.1.5.1
    optixReplacePortEntry OBJECT-TYPE
        SYNTAX OptixReplacePortEntry
        MAX-ACCESS not-accessible
        STATUS current
        DESCRIPTION
            "This entry describes the configuration of replace port"
        INDEX{ optixLogBoardId,optixLogSubCardId,optixPortId }
        ::= { optixReplacePortTable 1 }

    OptixReplacePortEntry ::=
        SEQUENCE {
            optixReplaceList
                OCTET STRING
        }

    -- 1.3.6.1.4.1.2011.2.25.4.30.36.1.5.1.1
    optixReplaceList OBJECT-TYPE
        SYNTAX OCTET STRING (SIZE(0..128))
        MAX-ACCESS read-only
        STATUS current
        DESCRIPTION
            "This object indicates replace port list"
        ::= { optixReplacePortEntry 1 }

    -- 1.3.6.1.4.1.2011.2.25.4.30.36.1.6
    optixPortModeTable OBJECT-TYPE
        SYNTAX SEQUENCE OF OptixPortModeEntry
        MAX-ACCESS not-accessible
        STATUS current
        DESCRIPTION
            "This table describes the configuration of port multimode"
        ::= { optixPortMngGroup 6 }

    -- 1.3.6.1.4.1.2011.2.25.4.30.36.1.6.1
    optixPortModeEntry OBJECT-TYPE
        SYNTAX OptixPortModeEntry
        MAX-ACCESS not-accessible
        STATUS current
        DESCRIPTION
            "This entry describes the configuration of port multimode"
        INDEX{ optixLogBoardId,optixLogSubCardId,optixPortId }
        ::= { optixPortModeTable 1 }

    OptixPortModeEntry ::=
        SEQUENCE {
            optixMultiPortMode
                INTEGER
        }

    -- 1.3.6.1.4.1.2011.2.25.4.30.36.1.6.1.1
    optixMultiPortMode OBJECT-TYPE
        SYNTAX INTEGER
        {
            fstclk(0),
            scnclk(1),
            fsttime(2),
            scntime(3),
            mon(4),
            eow(5),
            s1f1(6),
            debugcom(7),
            clkMon(8),
            extS1(9),
            mon2(10),
            snmp16the1(11)
        }
        MAX-ACCESS read-write
        STATUS current
        DESCRIPTION
            "This object indicates port multiportmode"
        ::= { optixPortModeEntry 1 }

    -- 1.3.6.1.4.1.2011.2.25.4.30.36.1.7
    optixOamPortTable OBJECT-TYPE
        SYNTAX SEQUENCE OF OptixOamPortEntry
        MAX-ACCESS not-accessible
        STATUS current
        DESCRIPTION
            "NMS/EXT port status table"
        ::= { optixPortMngGroup 7 }

    -- 1.3.6.1.4.1.2011.2.25.4.30.36.1.7.1
    optixOamPortEntry OBJECT-TYPE
        SYNTAX OptixOamPortEntry
        MAX-ACCESS not-accessible
        STATUS current
        DESCRIPTION
            "Entry for querying the NMS/EXT port status"
        INDEX{ optixOamPortBoardID,optixNmsExtPortType }
        ::= { optixOamPortTable 1 }

    OptixOamPortEntry ::=
        SEQUENCE {
            optixOamPortBoardID
                Unsigned32,
            optixNmsExtPortType
                INTEGER,
            optixNmsExtPortState
                Unsigned32
        }

    -- 1.3.6.1.4.1.2011.2.25.4.30.36.1.7.1.1
    optixOamPortBoardID OBJECT-TYPE
        SYNTAX Unsigned32
        MAX-ACCESS not-accessible
        STATUS current
        DESCRIPTION
            "Slot number corresponding to a specific NMS/EXT port status"
        ::= { optixOamPortEntry 1 }

    -- 1.3.6.1.4.1.2011.2.25.4.30.36.1.7.1.2
    optixNmsExtPortType OBJECT-TYPE
        SYNTAX INTEGER
        {
            com(1),
            eth(2),
            oam(3),
            ext(5)
        }
        MAX-ACCESS not-accessible
        STATUS current
        DESCRIPTION
            "Port type corresponding to a specific NMS/EXT port status"
        ::= { optixOamPortEntry 2 }

    -- 1.3.6.1.4.1.2011.2.25.4.30.36.1.7.1.3
    optixNmsExtPortState OBJECT-TYPE
        SYNTAX Unsigned32
        MAX-ACCESS read-only
        STATUS current
        DESCRIPTION
            "NMS/EXT port status information"
        ::= { optixOamPortEntry 3 }

END
