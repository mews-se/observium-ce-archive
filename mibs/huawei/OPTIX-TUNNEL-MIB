-- OPTIX-TUNNEL-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-TUNNEL-MIB DEFINITIONS ::= BEGIN
    IMPORTS
        OBJECT-GROUP,MODULE-COMPLIANCE
            FROM SNMPv2-CONF
        MODULE-IDENTITY,OBJECT-TYPE,Unsigned32,Integer32,IpAddress,NOTIFICATION-TYPE
            FROM SNMPv2-SMI
        RowStatus
            FROM SNMPv2-TC
        optixProvisionPtn
            FROM OPTIX-OID-MIB
        ;

    optixTunnelMod MODULE-IDENTITY
        LAST-UPDATED "201204090000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage MPLS tunnels. The MPLS tunnel is defined in the MPLS protocol, which just provides a channel from the local end to the remote end and has no requirements on the type of encapsulated services carried through the PW.In other words, the data packets are encapsulated to the PW and tagged with MPLS labels for transmission in the MPLS tunnel. The data packets are de-encapsulated at the sink end. The input and output nodes of the MPLS tunnelare called ingress and egressnodes respectively and the intermediate nodesare called transit nodes.As the carrier of the PWs on the network, the MPLS tunnel transparently transmits data packets through the service channel. Multiple types of services can be carried through the MPLS tunnel, such as CES, ATM/IMA, ETH services, and protocol packets. This module describes the configurations of the MPLS tunnel, query of cross-connections, and status reporting."
        REVISION "201204090000Z"
        DESCRIPTION
            "Initial version of this MIB module"
        ::={ optixProvisionPtn 9 }

    -- 1.3.6.1.4.1.2011.2.25.4.50.9.1
    optixTunnelObject OBJECT IDENTIFIER ::= { optixTunnelMod 1 }

    -- 1.3.6.1.4.1.2011.2.25.4.50.9.1.1
    optixStartLabel OBJECT-TYPE
        SYNTAX Unsigned32
        MAX-ACCESS read-write
        STATUS current
        DESCRIPTION
            "This object indicates the initial value of the space for MPLS global labels on the device."
        DEFVAL{ 0 }
        ::= { optixTunnelObject 1 }

    -- 1.3.6.1.4.1.2011.2.25.4.50.9.1.2
    optixLabelSize OBJECT-TYPE
        SYNTAX Unsigned32
        MAX-ACCESS read-write
        STATUS current
        DESCRIPTION
            "This object indicates the size of the space for MPLS global labels on the device."
        DEFVAL{ 32768 }
        ::= { optixTunnelObject 2 }

    -- 1.3.6.1.4.1.2011.2.25.4.50.9.1.3
    optixMultiStartLabel OBJECT-TYPE
        SYNTAX Unsigned32
        MAX-ACCESS read-write
        STATUS current
        DESCRIPTION
            "This object indicates the initial value of the space for MPLS multicast labels on the device."
        DEFVAL{ 28672 }
        ::= { optixTunnelObject 3 }

    -- 1.3.6.1.4.1.2011.2.25.4.50.9.1.4
    optixMultiLabelSize OBJECT-TYPE
        SYNTAX Unsigned32
        MAX-ACCESS read-write
        STATUS current
        DESCRIPTION
            "This object indicates the size of the space for MPLS global labels on the device."
        DEFVAL{ 4096 }
        ::= { optixTunnelObject 4 }

    -- 1.3.6.1.4.1.2011.2.25.4.50.9.1.5
    optixAvailLabelNum OBJECT-TYPE
        SYNTAX Unsigned32(128)
        MAX-ACCESS read-only
        STATUS current
        DESCRIPTION
            "This object indicates the number of available MPLS labels on the deivce that is queried at one time. The value is always 128."
        ::= { optixTunnelObject 5 }

    -- 1.3.6.1.4.1.2011.2.25.4.50.9.1.6
    optixAvailLabelList OBJECT-TYPE
        SYNTAX OCTET STRING(SIZE(0..512))
        MAX-ACCESS read-only
        STATUS current
        DESCRIPTION
            "This object indicates thelist of available MPLS labels on the deivce that is queried at one time. Each label occupies 4 bytes."
        ::= { optixTunnelObject 6 }

    -- 1.3.6.1.4.1.2011.2.25.4.50.9.1.7
    optixStaticUcTunnelTable OBJECT-TYPE
        SYNTAX SEQUENCE OF OptixStaticUcTunnelEntry
        MAX-ACCESS not-accessible
        STATUS current
        DESCRIPTION
            "This table is used to configure and manage the static unicast MPLS tunnels. The tunnel must be configured on each node along the tunnel."
        ::= { optixTunnelObject 7 }

    -- 1.3.6.1.4.1.2011.2.25.4.50.9.1.7.1
    optixStaticUcTunnelEntry OBJECT-TYPE
        SYNTAX OptixStaticUcTunnelEntry
        MAX-ACCESS not-accessible
        STATUS current
        DESCRIPTION
            "This entry indicates the parameter table for static unicast tunnels."
        INDEX{ optixStcUcTnlIndex }
        ::= { optixStaticUcTunnelTable 1 }

    OptixStaticUcTunnelEntry ::=
        SEQUENCE {
            optixStcUcTnlIndex
                Unsigned32,
            optixStcUcTnlPosition
                INTEGER,
            optixStcUcTnldirection
                INTEGER,
            optixStcUcTnlIngressId
                IpAddress,
            optixStcUcTnlEgressId
                IpAddress,
            optixStcUcTnlTunnelId
                Unsigned32,
            optixStcUcTnlInBid
                Unsigned32,
            optixStcUcTnlInSubBid
                Unsigned32,
            optixStcUcTnlInPortId
                Unsigned32,
            optixStcUcTnlInLabel
                Unsigned32,
            optixStcUcTnlOutBid
                Unsigned32,
            optixStcUcTnlOutSubBid
                Unsigned32,
            optixStcUcTnlOutPortId
                Unsigned32,
            optixStcUcTnlOutLabel
                Unsigned32,
            optixStcUcTnlNextHop
                IpAddress,
            optixStcUcTnlRsvInLabel
                Unsigned32,
            optixStcUcTnlRsvOutLabel
                Unsigned32,
            optixStcUcTnlRsvNextHop
                IpAddress,
            optixStcUcTnlName
                OCTET STRING,
            optixStcUcTnlBandwidthCIR
                Unsigned32,
            optixStcUcTnlBandwidthCBS
                Unsigned32,
            optixStcUcTnlBandwidthPIR
                Unsigned32,
            optixStcUcTnlBandwidthPBS
                Unsigned32,
            optixStcUcTnlDsType
                INTEGER,
            optixStcUcTnlDsCos
                INTEGER,
            optixStcUcTnlExp
                Unsigned32,
            optixStcUcTnlLspMode
                INTEGER,
            optixStcUcTnlEnable
                INTEGER,
            optixStcUcTnlVlanId
                Unsigned32,
            optixStcUcTnlVlanpri
                Unsigned32,
            optixStcUcTnlState
                INTEGER,
            optixStcUcTnlBwLimit
                INTEGER,
            optixStcUcTnlCheckRet
                INTEGER,
            optixStcUcTnlCT
                Unsigned32,
            optixStcUcTnlSetupPri
                Unsigned32,
            optixStcUcTnlHoldPri
                Unsigned32,
            optixStcUcTnlRowStatus
                RowStatus
        }

    -- 1.3.6.1.4.1.2011.2.25.4.50.9.1.7.1.1
    optixStcUcTnlIndex OBJECT-TYPE
        SYNTAX Unsigned32(1..16777215)
        MAX-ACCESS not-accessible
        STATUS current
        DESCRIPTION
            "This object indicates the tunnel index, ranging from 1 to 0x00ffffff,0 means auto."
        ::= { optixStaticUcTunnelEntry 1 }

    -- 1.3.6.1.4.1.2011.2.25.4.50.9.1.7.1.2
    optixStcUcTnlPosition OBJECT-TYPE
        SYNTAX INTEGER
        {
            ingress(1),
            transit(2),
            egress(3)
        }
        MAX-ACCESS read-create
        STATUS current
        DESCRIPTION
            "This object indicates the tunnel node location. 1: ingress 2: transit 3: egress"
        ::= { optixStaticUcTunnelEntry 2 }

    -- 1.3.6.1.4.1.2011.2.25.4.50.9.1.7.1.3
    optixStcUcTnldirection OBJECT-TYPE
        SYNTAX INTEGER
        {
            uni(0),
            bi(1)
        }
        MAX-ACCESS read-create
        STATUS current
        DESCRIPTION
            "This object indicates the tunnel direction. 0: uni 1: bi"
        ::= { optixStaticUcTunnelEntry 3 }

    -- 1.3.6.1.4.1.2011.2.25.4.50.9.1.7.1.4
    optixStcUcTnlIngressId OBJECT-TYPE
        SYNTAX IpAddress
        MAX-ACCESS read-create
        STATUS current
        DESCRIPTION
            "This object indicates the source node ID, which is an unicast address but not a multicast/broadcast/network address/ NE address/loopback address/reserved address. If the values of them are all 0, this node ID is the node ID of the local device."
        ::= { optixStaticUcTunnelEntry 4 }

    -- 1.3.6.1.4.1.2011.2.25.4.50.9.1.7.1.5
    optixStcUcTnlEgressId OBJECT-TYPE
        SYNTAX IpAddress
        MAX-ACCESS read-create
        STATUS current
        DESCRIPTION
            "This object indicates the sink node ID, which is an unicast address but not a multicast/broadcast/network address/ NE address/loopback address/reserved address. If the values of them are all 0, this node ID is the node ID of the local device."
        ::= { optixStaticUcTunnelEntry 5 }

    -- 1.3.6.1.4.1.2011.2.25.4.50.9.1.7.1.6
    optixStcUcTnlTunnelId OBJECT-TYPE
        SYNTAX Unsigned32(1..65535)
        MAX-ACCESS read-create
        STATUS current
        DESCRIPTION
            "This object indicates the tunnel ID, ranging from 1 to 0xffff."
        ::= { optixStaticUcTunnelEntry 6 }

    -- 1.3.6.1.4.1.2011.2.25.4.50.9.1.7.1.7
    optixStcUcTnlInBid OBJECT-TYPE
        SYNTAX Unsigned32(1..65535)
        MAX-ACCESS read-create
        STATUS current
        DESCRIPTION
            "This object indicates the input slot ID."
        ::= { optixStaticUcTunnelEntry 7 }

    -- 1.3.6.1.4.1.2011.2.25.4.50.9.1.7.1.8
    optixStcUcTnlInSubBid OBJECT-TYPE
        SYNTAX Unsigned32(1..255)
        MAX-ACCESS read-create
        STATUS current
        DESCRIPTION
            "This object indicates the input subboard ID. If no subboard is available, the value is 255."
        ::= { optixStaticUcTunnelEntry 8 }

    -- 1.3.6.1.4.1.2011.2.25.4.50.9.1.7.1.9
    optixStcUcTnlInPortId OBJECT-TYPE
        SYNTAX Unsigned32(1..65535)
        MAX-ACCESS read-create
        STATUS current
        DESCRIPTION
            "This object indicates the input port number."
        ::= { optixStaticUcTunnelEntry 9 }

    -- 1.3.6.1.4.1.2011.2.25.4.50.9.1.7.1.10
    optixStcUcTnlInLabel OBJECT-TYPE
        SYNTAX Unsigned32
        MAX-ACCESS read-create
        STATUS current
        DESCRIPTION
            "This object indicates the forward ingress label. The corresponding spacecannot exceed that of the unicast label."
        ::= { optixStaticUcTunnelEntry 10 }

    -- 1.3.6.1.4.1.2011.2.25.4.50.9.1.7.1.11
    optixStcUcTnlOutBid OBJECT-TYPE
        SYNTAX Unsigned32(1..65535)
        MAX-ACCESS read-create
        STATUS current
        DESCRIPTION
            "This object indicates the output slot ID."
        ::= { optixStaticUcTunnelEntry 11 }

    -- 1.3.6.1.4.1.2011.2.25.4.50.9.1.7.1.12
    optixStcUcTnlOutSubBid OBJECT-TYPE
        SYNTAX Unsigned32(1..255)
        MAX-ACCESS read-create
        STATUS current
        DESCRIPTION
            "This object indicates the output subboard ID. If no subboard is available, the value is 255."
        ::= { optixStaticUcTunnelEntry 12 }

    -- 1.3.6.1.4.1.2011.2.25.4.50.9.1.7.1.13
    optixStcUcTnlOutPortId OBJECT-TYPE
        SYNTAX Unsigned32(1..65535)
        MAX-ACCESS read-create
        STATUS current
        DESCRIPTION
            "This object indicates the output port number."
        ::= { optixStaticUcTunnelEntry 13 }

    -- 1.3.6.1.4.1.2011.2.25.4.50.9.1.7.1.14
    optixStcUcTnlOutLabel OBJECT-TYPE
        SYNTAX Unsigned32
        MAX-ACCESS read-create
        STATUS current
        DESCRIPTION
            "This object indicates the forward egress label."
        ::= { optixStaticUcTunnelEntry 14 }

    -- 1.3.6.1.4.1.2011.2.25.4.50.9.1.7.1.15
    optixStcUcTnlNextHop OBJECT-TYPE
        SYNTAX IpAddress
        MAX-ACCESS read-create
        STATUS current
        DESCRIPTION
            "This object indicates the forward next hop address, which is an unicast address, but not a multicast/broadcast/0.0.0.0 address/loopback address/reserved address."
        ::= { optixStaticUcTunnelEntry 15 }

    -- 1.3.6.1.4.1.2011.2.25.4.50.9.1.7.1.16
    optixStcUcTnlRsvInLabel OBJECT-TYPE
        SYNTAX Unsigned32
        MAX-ACCESS read-create
        STATUS current
        DESCRIPTION
            "This object indicates the backward ingress label. The corresponding space cannot exceed that of the unicast label."
        ::= { optixStaticUcTunnelEntry 16 }

    -- 1.3.6.1.4.1.2011.2.25.4.50.9.1.7.1.17
    optixStcUcTnlRsvOutLabel OBJECT-TYPE
        SYNTAX Unsigned32
        MAX-ACCESS read-create
        STATUS current
        DESCRIPTION
            "This object indicates the backward egress label."
        ::= { optixStaticUcTunnelEntry 17 }

    -- 1.3.6.1.4.1.2011.2.25.4.50.9.1.7.1.18
    optixStcUcTnlRsvNextHop OBJECT-TYPE
        SYNTAX IpAddress
        MAX-ACCESS read-create
        STATUS current
        DESCRIPTION
            "This object indicates the backward next hop address, which is an unicast address, but not a multicast/broadcast/0.0.0.0 address/loopback address/reserved address."
        ::= { optixStaticUcTunnelEntry 18 }

    -- 1.3.6.1.4.1.2011.2.25.4.50.9.1.7.1.19
    optixStcUcTnlName OBJECT-TYPE
        SYNTAX OCTET STRING(SIZE(0..64))
        MAX-ACCESS read-create
        STATUS current
        DESCRIPTION
            "This object indicates the tunnel name. The tunnel name can be null, space, or chinese characters of a maximum of 64 bytes."
        DEFVAL{ "" }
        ::= { optixStaticUcTunnelEntry 19 }

    -- 1.3.6.1.4.1.2011.2.25.4.50.9.1.7.1.20
    optixStcUcTnlBandwidthCIR OBJECT-TYPE
        SYNTAX Unsigned32
        MAX-ACCESS read-create
        STATUS current
        DESCRIPTION
            "Indicates the CIR. 0: The bandwidth is not restricted."
        DEFVAL{ 0 }
        ::= { optixStaticUcTunnelEntry 20 }

    -- 1.3.6.1.4.1.2011.2.25.4.50.9.1.7.1.21
    optixStcUcTnlBandwidthCBS OBJECT-TYPE
        SYNTAX Unsigned32
        MAX-ACCESS read-create
        STATUS current
        DESCRIPTION
            "Indicates the CBS. 0: The bandwidth is not restricted."
        DEFVAL{ 0 }
        ::= { optixStaticUcTunnelEntry 21 }

    -- 1.3.6.1.4.1.2011.2.25.4.50.9.1.7.1.22
    optixStcUcTnlBandwidthPIR OBJECT-TYPE
        SYNTAX Unsigned32
        MAX-ACCESS read-create
        STATUS current
        DESCRIPTION
            "Indicates the PIR. 0: The bandwidth is not restricted."
        DEFVAL{ 0 }
        ::= { optixStaticUcTunnelEntry 22 }

    -- 1.3.6.1.4.1.2011.2.25.4.50.9.1.7.1.23
    optixStcUcTnlBandwidthPBS OBJECT-TYPE
        SYNTAX Unsigned32
        MAX-ACCESS read-create
        STATUS current
        DESCRIPTION
            "Indicates the PBS. 0: The bandwidth is not restricted."
        DEFVAL{ 0 }
        ::= { optixStaticUcTunnelEntry 23 }

    -- 1.3.6.1.4.1.2011.2.25.4.50.9.1.7.1.24
    optixStcUcTnlDsType OBJECT-TYPE
        SYNTAX INTEGER
        {
            elsp(0),
            llsp(1)
        }
        MAX-ACCESS read-create
        STATUS current
        DESCRIPTION
            "This object indicates the tunnel schedualing type."
        DEFVAL{ 0 }
        ::= { optixStaticUcTunnelEntry 24 }

    -- 1.3.6.1.4.1.2011.2.25.4.50.9.1.7.1.25
    optixStcUcTnlDsCos OBJECT-TYPE
        SYNTAX INTEGER
        {
            be(1),
            af1(2),
            af2(3),
            af3(4),
            af4(5),
            ef(6),
            cs6(7),
            cs7(8),
            null(255)
        }
        MAX-ACCESS read-create
        STATUS current
        DESCRIPTION
            "This object indicates the tunnel COS value:1:be 2:af1 3:af2 4:af3 5:af4 6:ef 7:cs6 8:cs7 255:null"
        DEFVAL{ 255 }
        ::= { optixStaticUcTunnelEntry 25 }

    -- 1.3.6.1.4.1.2011.2.25.4.50.9.1.7.1.26
    optixStcUcTnlExp OBJECT-TYPE
        SYNTAX Unsigned32(0..7|255)
        MAX-ACCESS read-create
        STATUS current
        DESCRIPTION
            "This object indicates the tunnel EXP value."
        DEFVAL{ 255 }
        ::= { optixStaticUcTunnelEntry 26 }

    -- 1.3.6.1.4.1.2011.2.25.4.50.9.1.7.1.27
    optixStcUcTnlLspMode OBJECT-TYPE
        SYNTAX INTEGER
        {
            uniform(1),
            pipe(2)
        }
        MAX-ACCESS read-create
        STATUS current
        DESCRIPTION
            "This object indicates the LSP mode. 1: uniform 2: pipe"
        DEFVAL{ 1 }
        ::= { optixStaticUcTunnelEntry 27 }

    -- 1.3.6.1.4.1.2011.2.25.4.50.9.1.7.1.28
    optixStcUcTnlEnable OBJECT-TYPE
        SYNTAX INTEGER
        {
            disable(0),
            enable(1)
        }
        MAX-ACCESS read-create
        STATUS current
        DESCRIPTION
            "Indicates whether an LSP is enabled. 1: enable 0: disable"
        DEFVAL{ 1 }
        ::= { optixStaticUcTunnelEntry 28 }

    -- 1.3.6.1.4.1.2011.2.25.4.50.9.1.7.1.29
    optixStcUcTnlVlanId OBJECT-TYPE
        SYNTAX Unsigned32(1..4094|65535)
        MAX-ACCESS read-create
        STATUS current
        DESCRIPTION
            "This object indicates the VLAN ID. Valid values: 1-4094, 0xffff."
        DEFVAL{ 65535 }
        ::= { optixStaticUcTunnelEntry 29 }

    -- 1.3.6.1.4.1.2011.2.25.4.50.9.1.7.1.30
    optixStcUcTnlVlanpri OBJECT-TYPE
        SYNTAX Unsigned32(255)
        MAX-ACCESS read-create
        STATUS current
        DESCRIPTION
            "This object indicates the VLAN priority. Valid values: 0xff"
        DEFVAL{ 255 }
        ::= { optixStaticUcTunnelEntry 30 }

    -- 1.3.6.1.4.1.2011.2.25.4.50.9.1.7.1.31
    optixStcUcTnlState OBJECT-TYPE
        SYNTAX INTEGER
        {
            up(0),
            down(1),
            fail(2)
        }
        MAX-ACCESS read-only
        STATUS current
        DESCRIPTION
            "This object indicates the tunnel status. 0: up 1: down 2: fail (The tunnel cannot be created.)"
        ::= { optixStaticUcTunnelEntry 31 }

    -- 1.3.6.1.4.1.2011.2.25.4.50.9.1.7.1.32
    optixStcUcTnlBwLimit OBJECT-TYPE
        SYNTAX INTEGER
        {
            disable(0),
            enable(1)
        }
        MAX-ACCESS read-create
        STATUS current
        DESCRIPTION
            "This object indicates the tunnel bandwidth limit state. 0:disabel 1:enable"
        ::= { optixStaticUcTunnelEntry 32 }

    -- 1.3.6.1.4.1.2011.2.25.4.50.9.1.7.1.33
    optixStcUcTnlCheckRet OBJECT-TYPE
        SYNTAX INTEGER
        {
            normal(0),
            abnormal(1)
        }
        MAX-ACCESS read-only
        STATUS current
        DESCRIPTION
            "This object indicates the check result of tunnels."
        ::= { optixStaticUcTunnelEntry 33 }

    -- 1.3.6.1.4.1.2011.2.25.4.50.9.1.7.1.34
    optixStcUcTnlCT OBJECT-TYPE
        SYNTAX Unsigned32
        MAX-ACCESS read-only
        STATUS current
        DESCRIPTION
            "This object indicates the CT of tunnels."
        ::= { optixStaticUcTunnelEntry 34 }

    -- 1.3.6.1.4.1.2011.2.25.4.50.9.1.7.1.35
    optixStcUcTnlSetupPri OBJECT-TYPE
        SYNTAX Unsigned32
        MAX-ACCESS read-only
        STATUS current
        DESCRIPTION
            "This object indicates the setup priority of tunnels."
        ::= { optixStaticUcTunnelEntry 35 }

    -- 1.3.6.1.4.1.2011.2.25.4.50.9.1.7.1.36
    optixStcUcTnlHoldPri OBJECT-TYPE
        SYNTAX Unsigned32
        MAX-ACCESS read-only
        STATUS current
        DESCRIPTION
            "This object indicates the hold priority of tunnels."
        ::= { optixStaticUcTunnelEntry 36 }

    -- 1.3.6.1.4.1.2011.2.25.4.50.9.1.7.1.255
    optixStcUcTnlRowStatus OBJECT-TYPE
        SYNTAX RowStatus
        MAX-ACCESS read-create
        STATUS current
        DESCRIPTION
            "This object indicates the row status. 1: active 4: createAndGo 6: destroy"
        ::= { optixStaticUcTunnelEntry 255 }

    -- 1.3.6.1.4.1.2011.2.25.4.50.9.1.8
    optixTunnelCrossTable OBJECT-TYPE
        SYNTAX SEQUENCE OF OptixTunnelCrossEntry
        MAX-ACCESS not-accessible
        STATUS current
        DESCRIPTION
            "This table is used to query the actual tunnel forwarding and cross-connect paths. For bidirectional tunnels, there are forward and backward cross-connections. For unidirectional tunnels, thereare only forward cross-connections."
        ::= { optixTunnelObject 8 }

    -- 1.3.6.1.4.1.2011.2.25.4.50.9.1.8.1
    optixTunnelCrossEntry OBJECT-TYPE
        SYNTAX OptixTunnelCrossEntry
        MAX-ACCESS not-accessible
        STATUS current
        DESCRIPTION
            "This entry is used to query the parameter table for actualtunnel cross-connections."
        INDEX{ optixTunnelIndex,optixTunneldirection }
        ::= { optixTunnelCrossTable 1 }

    OptixTunnelCrossEntry ::=
        SEQUENCE {
            optixTunnelIndex
                Unsigned32,
            optixTunneldirection
                INTEGER,
            optixTnlInBid
                Unsigned32,
            optixTnlInSubBid
                Unsigned32,
            optixTnlInPortId
                Unsigned32,
            optixTnlInLabel
                Unsigned32,
            optixTnlOutBid
                Unsigned32,
            optixTnlOutSubBid
                Unsigned32,
            optixTnlOutPortId
                Unsigned32,
            optixTnlOutLabel
                Unsigned32,
            optixTnlNextHop
                IpAddress,
            optixTnlIngressId
                IpAddress,
            optixTnlEgressId
                IpAddress,
            optixTnlTunnelId
                Unsigned32,
            optixTnlInstance
                Unsigned32
        }

    -- 1.3.6.1.4.1.2011.2.25.4.50.9.1.8.1.1
    optixTunnelIndex OBJECT-TYPE
        SYNTAX Unsigned32(1..16777215)
        MAX-ACCESS not-accessible
        STATUS current
        DESCRIPTION
            "This object indicates the tunnel index, ranging from 1 to 0x00ffffff."
        ::= { optixTunnelCrossEntry 1 }

    -- 1.3.6.1.4.1.2011.2.25.4.50.9.1.8.1.2
    optixTunneldirection OBJECT-TYPE
        SYNTAX INTEGER
        {
            posit(1),
            minus(2)
        }
        MAX-ACCESS not-accessible
        STATUS current
        DESCRIPTION
            "This object indicates the cross-connect direction. 1: forward 2: backward"
        ::= { optixTunnelCrossEntry 2 }

    -- 1.3.6.1.4.1.2011.2.25.4.50.9.1.8.1.3
    optixTnlInBid OBJECT-TYPE
        SYNTAX Unsigned32(1..65535)
        MAX-ACCESS read-only
        STATUS current
        DESCRIPTION
            "This object indicates the input slot ID."
        ::= { optixTunnelCrossEntry 3 }

    -- 1.3.6.1.4.1.2011.2.25.4.50.9.1.8.1.4
    optixTnlInSubBid OBJECT-TYPE
        SYNTAX Unsigned32(1..255)
        MAX-ACCESS read-only
        STATUS current
        DESCRIPTION
            "This object indicates the input subboard ID. If no subboard is available, the value is 255."
        ::= { optixTunnelCrossEntry 4 }

    -- 1.3.6.1.4.1.2011.2.25.4.50.9.1.8.1.5
    optixTnlInPortId OBJECT-TYPE
        SYNTAX Unsigned32(1..65535)
        MAX-ACCESS read-only
        STATUS current
        DESCRIPTION
            "This object indicates the input port number."
        ::= { optixTunnelCrossEntry 5 }

    -- 1.3.6.1.4.1.2011.2.25.4.50.9.1.8.1.6
    optixTnlInLabel OBJECT-TYPE
        SYNTAX Unsigned32
        MAX-ACCESS read-only
        STATUS current
        DESCRIPTION
            "This object indicates the forward ingress label. The corresponding space cannot exceed that of the unicast label."
        ::= { optixTunnelCrossEntry 6 }

    -- 1.3.6.1.4.1.2011.2.25.4.50.9.1.8.1.7
    optixTnlOutBid OBJECT-TYPE
        SYNTAX Unsigned32(1..65535)
        MAX-ACCESS read-only
        STATUS current
        DESCRIPTION
            "This object indicates the output slot ID."
        ::= { optixTunnelCrossEntry 7 }

    -- 1.3.6.1.4.1.2011.2.25.4.50.9.1.8.1.8
    optixTnlOutSubBid OBJECT-TYPE
        SYNTAX Unsigned32(1..255)
        MAX-ACCESS read-only
        STATUS current
        DESCRIPTION
            "This object indicates the output subboard ID. If no subboard is available, the value is 255."
        ::= { optixTunnelCrossEntry 8 }

    -- 1.3.6.1.4.1.2011.2.25.4.50.9.1.8.1.9
    optixTnlOutPortId OBJECT-TYPE
        SYNTAX Unsigned32(1..65535)
        MAX-ACCESS read-only
        STATUS current
        DESCRIPTION
            "This object indicates the output port number."
        ::= { optixTunnelCrossEntry 9 }

    -- 1.3.6.1.4.1.2011.2.25.4.50.9.1.8.1.10
    optixTnlOutLabel OBJECT-TYPE
        SYNTAX Unsigned32
        MAX-ACCESS read-only
        STATUS current
        DESCRIPTION
            "This object indicates the forward egress label."
        ::= { optixTunnelCrossEntry 10 }

    -- 1.3.6.1.4.1.2011.2.25.4.50.9.1.8.1.11
    optixTnlNextHop OBJECT-TYPE
        SYNTAX IpAddress
        MAX-ACCESS read-only
        STATUS current
        DESCRIPTION
            "This object indicates the forward next hop address, which is an unicast address, but not a multicast/broadcast/0.0.0.0 address/loopback address/reserved address."
        ::= { optixTunnelCrossEntry 11 }

    -- 1.3.6.1.4.1.2011.2.25.4.50.9.1.8.1.12
    optixTnlIngressId OBJECT-TYPE
        SYNTAX IpAddress
        MAX-ACCESS read-only
        STATUS current
        DESCRIPTION
            "This object indicates the source node ID, which is an unicast address, but not a multicast/broadcast/network address/ NE address/loopback address/reserved address. If the values of them are all 0, this node ID is the node ID of the local device."
        ::= { optixTunnelCrossEntry 12 }

    -- 1.3.6.1.4.1.2011.2.25.4.50.9.1.8.1.13
    optixTnlEgressId OBJECT-TYPE
        SYNTAX IpAddress
        MAX-ACCESS read-only
        STATUS current
        DESCRIPTION
            "This object indicates the sink node ID, which is an unicast address, but not a multicast/broadcast/network address/ NE address/loopback address/reserved address. If the values of them are all 0, this node ID is the node ID of the local device."
        ::= { optixTunnelCrossEntry 13 }

    -- 1.3.6.1.4.1.2011.2.25.4.50.9.1.8.1.14
    optixTnlTunnelId OBJECT-TYPE
        SYNTAX Unsigned32(1..65535)
        MAX-ACCESS read-only
        STATUS current
        DESCRIPTION
            "This object indicates the tunnel ID, ranging from 1 to 0xffff."
        ::= { optixTunnelCrossEntry 14 }

    -- 1.3.6.1.4.1.2011.2.25.4.50.9.1.8.1.15
    optixTnlInstance OBJECT-TYPE
        SYNTAX Unsigned32(1..65535)
        MAX-ACCESS read-only
        STATUS current
        DESCRIPTION
            "This object indicates the tunnel channel instance."
        ::= { optixTunnelCrossEntry 15 }

    -- 1.3.6.1.4.1.2011.2.25.4.50.9.1.9
    optixTunnelCarryCESNumberTable OBJECT-TYPE
        SYNTAX SEQUENCE OF OptixTunnelCarryCESNumberEntry
        MAX-ACCESS not-accessible
        STATUS current
        DESCRIPTION
            "This table is used to query the number of CES services that can be configured on the free bandwidth."
        ::= { optixTunnelObject 9 }

    -- 1.3.6.1.4.1.2011.2.25.4.50.9.1.9.1
    optixTunnelCarryCESNumberEntry OBJECT-TYPE
        SYNTAX OptixTunnelCarryCESNumberEntry
        MAX-ACCESS not-accessible
        STATUS current
        DESCRIPTION
            "This entry is used to query theinformation table for PWs carried on the tunnel."
        INDEX{ optixCarryCESTunnelIndex,optixCarryCESType,optixCarryCESLevel,optixCarryCESPathNumber,optixCarryCESRTPEnable,optixCarryCESLoadtime,optixCarryCESIsmspw,optixCarryCESSohThorough,optixCarryCESLoadbytes }
        ::= { optixTunnelCarryCESNumberTable 1 }

    OptixTunnelCarryCESNumberEntry ::=
        SEQUENCE {
            optixCarryCESTunnelIndex
                Unsigned32,
            optixCarryCESType
                INTEGER,
            optixCarryCESLevel
                INTEGER,
            optixCarryCESPathNumber
                Unsigned32,
            optixCarryCESRTPEnable
                INTEGER,
            optixCarryCESLoadtime
                Unsigned32,
            optixCarryCESIsmspw
                INTEGER,
            optixCarryCESSohThorough
                INTEGER,
            optixCarryCESLoadbytes
                Unsigned32,
            optixCarryCESNumber
                Unsigned32
        }

    -- 1.3.6.1.4.1.2011.2.25.4.50.9.1.9.1.1
    optixCarryCESTunnelIndex OBJECT-TYPE
        SYNTAX Unsigned32(1..16777215)
        MAX-ACCESS not-accessible
        STATUS current
        DESCRIPTION
            "This object indicates the tunnel index, ranging from 1 to 0x00ffffff."
        ::= { optixTunnelCarryCESNumberEntry 1 }

    -- 1.3.6.1.4.1.2011.2.25.4.50.9.1.9.1.2
    optixCarryCESType OBJECT-TYPE
        SYNTAX INTEGER
        {
            cep(16),
            satope1(17),
            cesopsnbas(21)
        }
        MAX-ACCESS not-accessible
        STATUS current
        DESCRIPTION
            "This object indcates the PW type. 0x0010: SONET/SDH Circuit Emulation over Packet 0x0011: Structure-agnostic E1 over Packet 0x0015: CESoPSN basic mode"
        ::= { optixTunnelCarryCESNumberEntry 2 }

    -- 1.3.6.1.4.1.2011.2.25.4.50.9.1.9.1.3
    optixCarryCESLevel OBJECT-TYPE
        SYNTAX INTEGER
        {
            vc12(1),
            vc3(2),
            vc11(3),
            vc4(4),
            triplicatevc3(5)
        }
        MAX-ACCESS not-accessible
        STATUS current
        DESCRIPTION
            "This object indicates the service emulation level. 1: VC12 2: VC3 3: VC11 4: VC4 5: VC4 (3 x VC3)"
        ::= { optixTunnelCarryCESNumberEntry 3 }

    -- 1.3.6.1.4.1.2011.2.25.4.50.9.1.9.1.4
    optixCarryCESPathNumber OBJECT-TYPE
        SYNTAX Unsigned32
        MAX-ACCESS not-accessible
        STATUS current
        DESCRIPTION
            "This object indicates the number of timeslots/channels."
        ::= { optixTunnelCarryCESNumberEntry 4 }

    -- 1.3.6.1.4.1.2011.2.25.4.50.9.1.9.1.5
    optixCarryCESRTPEnable OBJECT-TYPE
        SYNTAX INTEGER
        {
            disable(0),
            enablehuawei(1),
            enablestandard(2)
        }
        MAX-ACCESS not-accessible
        STATUS current
        DESCRIPTION
            "This object indicates the enable status of the RTP header encapsulation. 0: disable 1: enablehwrtp 2: enablestdrtp"
        ::= { optixTunnelCarryCESNumberEntry 5 }

    -- 1.3.6.1.4.1.2011.2.25.4.50.9.1.9.1.6
    optixCarryCESLoadtime OBJECT-TYPE
        SYNTAX Unsigned32
        MAX-ACCESS not-accessible
        STATUS current
        DESCRIPTION
            "This object indicates the packet loading time. Valid values: 125-5000 us; step: 125.For VC4/VC4 (3VC3) CES packets, the loading time is not supported. The value is 0xffff."
        ::= { optixTunnelCarryCESNumberEntry 6 }

    -- 1.3.6.1.4.1.2011.2.25.4.50.9.1.9.1.7
    optixCarryCESIsmspw OBJECT-TYPE
        SYNTAX INTEGER
        {
            no(0),
            yes(1)
        }
        MAX-ACCESS not-accessible
        STATUS current
        DESCRIPTION
            "This object is used to check whether the PW is an MS-PW. 0: no 1: yes"
        ::= { optixTunnelCarryCESNumberEntry 7 }

    -- 1.3.6.1.4.1.2011.2.25.4.50.9.1.9.1.8
    optixCarryCESSohThorough OBJECT-TYPE
        SYNTAX INTEGER
        {
            disable(0),
            enable(1)
        }
        MAX-ACCESS not-accessible
        STATUS current
        DESCRIPTION
            "This object indicates the enabled status of the transmission of section overheads. 0: disable 1: enable (Only for VC4 CES services)"
        ::= { optixTunnelCarryCESNumberEntry 8 }

    -- 1.3.6.1.4.1.2011.2.25.4.50.9.1.9.1.9
    optixCarryCESLoadbytes OBJECT-TYPE
        SYNTAX Unsigned32(65535)
        MAX-ACCESS not-accessible
        STATUS current
        DESCRIPTION
            "This object indicates the number of load bytes. For VC4/VC4 (3 x VC3) CES packets, the loading time is not supported. The value is 0xffff."
        ::= { optixTunnelCarryCESNumberEntry 9 }

    -- 1.3.6.1.4.1.2011.2.25.4.50.9.1.9.1.10
    optixCarryCESNumber OBJECT-TYPE
        SYNTAX Unsigned32
        MAX-ACCESS read-only
        STATUS current
        DESCRIPTION
            "This object indicates the number of CES services that can be configured on the free bandwidth of the tunnel/port."
        ::= { optixTunnelCarryCESNumberEntry 10 }

    -- 1.3.6.1.4.1.2011.2.25.4.50.9.2
    optixTunnelTrap OBJECT IDENTIFIER ::= { optixTunnelMod 2 }

    -- 1.3.6.1.4.1.2011.2.25.4.50.9.2.1
    optixTunnelTrapMember OBJECT IDENTIFIER ::= { optixTunnelTrap 1 }

    -- 1.3.6.1.4.1.2011.2.25.4.50.9.2.1.1
    optixStaticUcTunnelStatus OBJECT-TYPE
        SYNTAX INTEGER
        {
            up(0),
            down(1)
        }
        MAX-ACCESS accessible-for-notify
        STATUS current
        DESCRIPTION
            "This object indicates the changed status of the static tunnel. 0: up, 1: down"
        ::= { optixTunnelTrapMember 1 }

    -- 1.3.6.1.4.1.2011.2.25.4.50.9.2.1.2
    optixStaticUcTunnelStatusNumber OBJECT-TYPE
        SYNTAX Unsigned32(1..200)
        MAX-ACCESS accessible-for-notify
        STATUS current
        DESCRIPTION
            "This object indicates the number of tunnels that change their states. Value range: 1 to 200."
        ::= { optixTunnelTrapMember 2 }

    -- 1.3.6.1.4.1.2011.2.25.4.50.9.2.1.3
    optixStaticUcTunnelStatusList OBJECT-TYPE
        SYNTAX OCTET STRING(SIZE(1..800))
        MAX-ACCESS accessible-for-notify
        STATUS current
        DESCRIPTION
            "This object indicates the indexlist of static tunnels that change their states. Each tunnel index occupies four bytes."
        ::= { optixTunnelTrapMember 3 }

    -- 1.3.6.1.4.1.2011.2.25.4.50.9.2.2
    optixTunnelTrapReport OBJECT IDENTIFIER ::= { optixTunnelTrap 2 }

    -- 1.3.6.1.4.1.2011.2.25.4.50.9.2.2.1
    optixTunnelStatusTrap NOTIFICATION-TYPE
        OBJECTS{ optixStaticUcTunnelStatus,optixStaticUcTunnelStatusNumber,optixStaticUcTunnelStatusList }
        STATUS current
        DESCRIPTION
            "This object is used to report the status change events of the static tunnels. When the tunnelsare up/down, the status change events are reported, indicating which tunnel changes its status."
        ::= { optixTunnelTrapReport 1 }

    -- 1.3.6.1.4.1.2011.2.25.4.50.9.3
    optixTunnelGroup OBJECT IDENTIFIER ::= { optixTunnelMod 3 }

    -- 1.3.6.1.4.1.2011.2.25.4.50.9.3.1
    optixTunnelTotalNum OBJECT-TYPE
        SYNTAX Unsigned32
        MAX-ACCESS read-only
        STATUS current
        DESCRIPTION
            "This object indicates the total number of tunnels. One bidirectional tunnel is considered as two tunnels."
        ::= { optixTunnelGroup 1 }

    -- 1.3.6.1.4.1.2011.2.25.4.50.9.3.2
    optixTunnelInRsvTunl OBJECT-TYPE
        SYNTAX Unsigned32
        MAX-ACCESS read-only
        STATUS current
        DESCRIPTION
            "This object indicates the number of ingress RSVP tunnels."
        ::= { optixTunnelGroup 2 }

    -- 1.3.6.1.4.1.2011.2.25.4.50.9.3.3
    optixTunnelTrstRsvTunl OBJECT-TYPE
        SYNTAX Unsigned32
        MAX-ACCESS read-only
        STATUS current
        DESCRIPTION
            "This object indicates the number of transit RSVP tunnels."
        ::= { optixTunnelGroup 3 }

    -- 1.3.6.1.4.1.2011.2.25.4.50.9.3.4
    optixTunnelEgRsvTunl OBJECT-TYPE
        SYNTAX Unsigned32
        MAX-ACCESS read-only
        STATUS current
        DESCRIPTION
            "This object indicates the number of egress RSVP tunnels."
        ::= { optixTunnelGroup 4 }

    -- 1.3.6.1.4.1.2011.2.25.4.50.9.3.5
    optixTunnelUniInStcTunl OBJECT-TYPE
        SYNTAX Unsigned32
        MAX-ACCESS read-only
        STATUS current
        DESCRIPTION
            "This object indicates the number of unidirectional ingress static tunnels."
        ::= { optixTunnelGroup 5 }

    -- 1.3.6.1.4.1.2011.2.25.4.50.9.3.6
    optixTunnelUniTrstStcTunl OBJECT-TYPE
        SYNTAX Unsigned32
        MAX-ACCESS read-only
        STATUS current
        DESCRIPTION
            "This object indicates the number of unidirectional transit static tunnels."
        ::= { optixTunnelGroup 6 }

    -- 1.3.6.1.4.1.2011.2.25.4.50.9.3.7
    optixTunnelUniEgStcTunl OBJECT-TYPE
        SYNTAX Unsigned32
        MAX-ACCESS read-only
        STATUS current
        DESCRIPTION
            "This object indicates the number of unidirectional egress static tunnels."
        ::= { optixTunnelGroup 7 }

    -- 1.3.6.1.4.1.2011.2.25.4.50.9.3.8
    optixTunnelBiInStcTunl OBJECT-TYPE
        SYNTAX Unsigned32
        MAX-ACCESS read-only
        STATUS current
        DESCRIPTION
            "This object indicates the number of bidirectional ingress static tunnels."
        ::= { optixTunnelGroup 8 }

    -- 1.3.6.1.4.1.2011.2.25.4.50.9.3.9
    optixTunnelBiTrstTunl OBJECT-TYPE
        SYNTAX Unsigned32
        MAX-ACCESS read-only
        STATUS current
        DESCRIPTION
            "This object indicates the number of bidirectional transit static tunnels."
        ::= { optixTunnelGroup 9 }

    -- 1.3.6.1.4.1.2011.2.25.4.50.9.3.10
    optixTunnelBiEgStcTunl OBJECT-TYPE
        SYNTAX Unsigned32
        MAX-ACCESS read-only
        STATUS current
        DESCRIPTION
            "This object indicates the number of bidirectional egress static tunnels."
        ::= { optixTunnelGroup 10 }

END
