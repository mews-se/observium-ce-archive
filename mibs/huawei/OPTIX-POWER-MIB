-- OPTIX-POWER-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-POWER-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        optixLogBoardId
            FROM OPTIX-BOARD-MANAGE-MIB
        ;

    optixPowerMng MODULE-IDENTITY
        LAST-UPDATED "201205030000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes NE consumption."
        REVISION "201205030000Z"
        DESCRIPTION
            "The initial revision of this MIB module."
        REVISION "201205030000Z"
        DESCRIPTION
            "The initial revision of this MIB module."
        ::={ optixProvisionEqpt 37 }

    -- 1.3.6.1.4.1.2011.2.25.4.30.37.1
    optixPowerMngGroup OBJECT IDENTIFIER ::= { optixPowerMng 1 }

    -- 1.3.6.1.4.1.2011.2.25.4.30.37.1.1
    optixLogPower OBJECT-TYPE
        SYNTAX Unsigned32
        MAX-ACCESS read-only
        STATUS current
        DESCRIPTION
            "This object indicates the logical NE consumption."
        ::= { optixPowerMngGroup 1 }

    -- 1.3.6.1.4.1.2011.2.25.4.30.37.1.2
    optixPhyPower OBJECT-TYPE
        SYNTAX Unsigned32
        MAX-ACCESS read-only
        STATUS current
        DESCRIPTION
            "This object indicates the physical NE consumption."
        ::= { optixPowerMngGroup 2 }

    -- 1.3.6.1.4.1.2011.2.25.4.30.37.1.3
    optixMarkPower OBJECT-TYPE
        SYNTAX OCTET STRING
        MAX-ACCESS read-only
        STATUS current
        DESCRIPTION
            "This object indicates thenominal NE consumption."
        ::= { optixPowerMngGroup 3 }

    -- 1.3.6.1.4.1.2011.2.25.4.30.37.1.4
    optixRealPower OBJECT-TYPE
        SYNTAX OCTET STRING
        MAX-ACCESS read-only
        STATUS current
        DESCRIPTION
            "This object indicates thecurrent NE consumption."
        ::= { optixPowerMngGroup 4 }

    -- 1.3.6.1.4.1.2011.2.25.4.30.37.1.5
    optixSavePower OBJECT-TYPE
        SYNTAX OCTET STRING
        MAX-ACCESS read-only
        STATUS current
        DESCRIPTION
            "This object indicates theaverage NE consumption."
        ::= { optixPowerMngGroup 5 }

    -- 1.3.6.1.4.1.2011.2.25.4.30.37.1.6
    optixBoardPowerTable OBJECT-TYPE
        SYNTAX SEQUENCE OF OptixBoardPowerEntry
        MAX-ACCESS not-accessible
        STATUS current
        DESCRIPTION
            "This table describes the board consumption."
        ::= { optixPowerMngGroup 6 }

    -- 1.3.6.1.4.1.2011.2.25.4.30.37.1.6.1
    optixBoardPowerEntry OBJECT-TYPE
        SYNTAX OptixBoardPowerEntry
        MAX-ACCESS not-accessible
        STATUS current
        DESCRIPTION
            "Thisentry describes the board consumption."
        INDEX{ optixLogBoardId }
        ::= { optixBoardPowerTable 1 }

    OptixBoardPowerEntry ::=
        SEQUENCE {
            optixBoardLogPower
                OCTET STRING,
            optixBoardPhyPower
                Unsigned32,
            optixBoardCurLogPower
                OCTET STRING
        }

    -- 1.3.6.1.4.1.2011.2.25.4.30.37.1.6.1.1
    optixBoardLogPower OBJECT-TYPE
        SYNTAX OCTET STRING
        MAX-ACCESS read-only
        STATUS current
        DESCRIPTION
            "This object indicates the logicalboard consumption."
        ::= { optixBoardPowerEntry 1 }

    -- 1.3.6.1.4.1.2011.2.25.4.30.37.1.6.1.2
    optixBoardPhyPower OBJECT-TYPE
        SYNTAX Unsigned32
        MAX-ACCESS read-only
        STATUS current
        DESCRIPTION
            "This object indicates the physical board consumption."
        ::= { optixBoardPowerEntry 2 }

    -- 1.3.6.1.4.1.2011.2.25.4.30.37.1.6.1.3
    optixBoardCurLogPower OBJECT-TYPE
        SYNTAX OCTET STRING
        MAX-ACCESS read-only
        STATUS current
        DESCRIPTION
            "This object indicates thecurrent board consumption."
        ::= { optixBoardPowerEntry 3 }

    -- 1.3.6.1.4.1.2011.2.25.4.30.37.2
    optixPowerMngNEGroup OBJECT IDENTIFIER ::= { optixPowerMng 2 }

    -- 1.3.6.1.4.1.2011.2.25.4.30.37.2.1
    optixNePowerTh OBJECT-TYPE
        SYNTAX Unsigned32
        MAX-ACCESS read-write
        STATUS current
        DESCRIPTION
            "This object indicates the threshold of the NE consumption. Value range: 0x0000 to 0xffff."
        ::= { optixPowerMngNEGroup 1 }

    -- 1.3.6.1.4.1.2011.2.25.4.30.37.2.2
    optixNeSavePowerMode OBJECT-TYPE
        SYNTAX INTEGER
        {
            standardMode(1),
            basicMode(2),
            deepMode(3),
            customMode(4)
        }
        MAX-ACCESS read-write
        STATUS current
        DESCRIPTION
            "This object indicates the mode of the NE slave power.1: standardMode, 2: basicMode, 3: deepMode, 4: customMode"
        ::= { optixPowerMngNEGroup 2 }

END
