-- OPTIX-PKT-PPP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-PPP-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        ;

    optixPktPpp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of ppp protocol"
        REVISION "201204200000Z"
        DESCRIPTION
            "The initial revision of this MIB module1."
        ::={ optixProvisionPtn 29 }

    -- 1.3.6.1.4.1.2011.2.25.4.50.29.1
    optixPktPppGroup OBJECT IDENTIFIER ::= { optixPktPpp 1 }

    -- 1.3.6.1.4.1.2011.2.25.4.50.29.1.1
    optixPPPTable OBJECT-TYPE
        SYNTAX SEQUENCE OF OptixPPPEntry
        MAX-ACCESS not-accessible
        STATUS current
        DESCRIPTION
            "This table describes the basic PPP configurations."
        ::= { optixPktPppGroup 1 }

    -- 1.3.6.1.4.1.2011.2.25.4.50.29.1.1.1
    optixPPPEntry OBJECT-TYPE
        SYNTAX OptixPPPEntry
        MAX-ACCESS not-accessible
        STATUS current
        DESCRIPTION
            "This entry describes the basic PPP configurations."
        INDEX{ optixLogBoardId,optixLogSubCardId,optixSPId }
        ::= { optixPPPTable 1 }

    OptixPPPEntry ::=
        SEQUENCE {
            optixSPId
                Unsigned32,
            optixSPPPPDelayState
                INTEGER,
            optixSPPPPState
                INTEGER,
            optixSPPPPNegotIp
                OCTET STRING,
            optixSPPPPNegotMask
                OCTET STRING,
            optixSPPPPNegotMRU
                Unsigned32,
            optixSPPPPLCPState
                INTEGER,
            optixSPPPPNCPState
                INTEGER,
            optixSPPPPShutDown
                INTEGER,
            optixSPPPPStateReset
                INTEGER
        }

    -- 1.3.6.1.4.1.2011.2.25.4.50.29.1.1.1.1
    optixSPId OBJECT-TYPE
        SYNTAX Unsigned32
        MAX-ACCESS not-accessible
        STATUS current
        DESCRIPTION
            "This object indicates the port number of the PPP links. E1: fractional E1 port number, POS: STM-1/STM-4 POS port number, SP: serial port number"
        ::= { optixPPPEntry 1 }

    -- 1.3.6.1.4.1.2011.2.25.4.50.29.1.1.1.2
    optixSPPPPDelayState OBJECT-TYPE
        SYNTAX INTEGER
        {
            unknown(0),
            valid(1),
            invalid(2),
            snmp0xff(255)
        }
        MAX-ACCESS read-only
        STATUS current
        DESCRIPTION
            "This object indicates the delay status of the PPP links. 0: unknown, 1: valid, 2: invalid, 255: snmp0xff"
        ::= { optixPPPEntry 2 }

    -- 1.3.6.1.4.1.2011.2.25.4.50.29.1.1.1.3
    optixSPPPPState OBJECT-TYPE
        SYNTAX INTEGER
        {
            up(1),
            down(2)
        }
        MAX-ACCESS read-only
        STATUS current
        DESCRIPTION
            "This object indicates the PPP link status. 1: up, 2: down"
        ::= { optixPPPEntry 3 }

    -- 1.3.6.1.4.1.2011.2.25.4.50.29.1.1.1.4
    optixSPPPPNegotIp OBJECT-TYPE
        SYNTAX OCTET STRING (SIZE(0..32))
        MAX-ACCESS read-only
        STATUS current
        DESCRIPTION
            "This object indicates the IP negotiation result of the PPP."
        ::= { optixPPPEntry 4 }

    -- 1.3.6.1.4.1.2011.2.25.4.50.29.1.1.1.5
    optixSPPPPNegotMask OBJECT-TYPE
        SYNTAX OCTET STRING (SIZE(0..32))
        MAX-ACCESS read-only
        STATUS current
        DESCRIPTION
            "This object indicates the mask negotiation result of the PPP."
        ::= { optixPPPEntry 5 }

    -- 1.3.6.1.4.1.2011.2.25.4.50.29.1.1.1.6
    optixSPPPPNegotMRU OBJECT-TYPE
        SYNTAX Unsigned32
        MAX-ACCESS read-only
        STATUS current
        DESCRIPTION
            "This object indicates the negotiation result of the PPP MRU."
        ::= { optixPPPEntry 6 }

    -- 1.3.6.1.4.1.2011.2.25.4.50.29.1.1.1.7
    optixSPPPPLCPState OBJECT-TYPE
        SYNTAX INTEGER
        {
            up(1),
            down(2)
        }
        MAX-ACCESS read-only
        STATUS current
        DESCRIPTION
            "This object indicates the LCP status of the PPP. 1: up, 2: down"
        ::= { optixPPPEntry 7 }

    -- 1.3.6.1.4.1.2011.2.25.4.50.29.1.1.1.8
    optixSPPPPNCPState OBJECT-TYPE
        SYNTAX INTEGER
        {
            up(1),
            down(2)
        }
        MAX-ACCESS read-only
        STATUS current
        DESCRIPTION
            "This object indicates the NCP status of the PPP. 1: up, 2: down"
        ::= { optixPPPEntry 8 }

    -- 1.3.6.1.4.1.2011.2.25.4.50.29.1.1.1.9
    optixSPPPPShutDown OBJECT-TYPE
        SYNTAX INTEGER
        {
            unshutdown(0),
            shutdown(1)
        }
        MAX-ACCESS read-only
        STATUS current
        DESCRIPTION
            "This object indicates the start/stop status of the PPP channel. 0: unshutdown, 1: shutdown"
        ::= { optixPPPEntry 9 }

    -- 1.3.6.1.4.1.2011.2.25.4.50.29.1.1.1.10
    optixSPPPPStateReset OBJECT-TYPE
        SYNTAX INTEGER
        {
            reset(1)
        }
        MAX-ACCESS read-write
        STATUS current
        DESCRIPTION
            "This parameter indicates that the MLPPP links need to be reset."
        ::= { optixPPPEntry 10 }

END
