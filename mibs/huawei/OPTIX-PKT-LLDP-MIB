-- OPTIX-PKT-LLDP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-LLDP-MIB DEFINITIONS ::= BEGIN
    IMPORTS
        optixProvisionPtn
            FROM OPTIX-OID-MIB
        OBJECT-GROUP,MODULE-COMPLIANCE
            FROM SNMPv2-CONF
        optixLogBoardId,optixLogSubCardId
            FROM OPTIX-BOARD-MANAGE-MIB
        Unsigned32,OBJECT-TYPE,MODULE-IDENTITY,NOTIFICATION-TYPE,IpAddress
            FROM SNMPv2-SMI
        MacAddress,RowStatus
            FROM SNMPv2-TC
        ;

    optixPktLLDP MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of device"
        REVISION "201204200000Z"
        DESCRIPTION
            "The initial revision of this MIB module1."
        ::={ optixProvisionPtn 27 }

    -- 1.3.6.1.4.1.2011.2.25.4.50.27.1
    optixPktLLDPGroup OBJECT IDENTIFIER ::= { optixPktLLDP 1 }

    -- 1.3.6.1.4.1.2011.2.25.4.50.27.1.1
    optixLldpSendInterval OBJECT-TYPE
        SYNTAX Unsigned32
        MAX-ACCESS read-write
        STATUS current
        DESCRIPTION
            "This object indicates the transmit interval of the LLDP port. Value range: 1 to 3600. The default value is 30."
        ::= { optixPktLLDPGroup 1 }

    -- 1.3.6.1.4.1.2011.2.25.4.50.27.1.2
    optixLldpResetDelay OBJECT-TYPE
        SYNTAX Unsigned32
        MAX-ACCESS read-write
        STATUS current
        DESCRIPTION
            "This object indicates the retransmission delay time of the LLDP port. Value range: 1 to 10. The default value is 2."
        ::= { optixPktLLDPGroup 2 }

    -- 1.3.6.1.4.1.2011.2.25.4.50.27.1.3
    optixLldpTTLMilt OBJECT-TYPE
        SYNTAX Unsigned32
        MAX-ACCESS read-write
        STATUS current
        DESCRIPTION
            "This object indicates the TTL multiplier of the LLDP port. Value range: 1 to 100. The default value is 4."
        ::= { optixPktLLDPGroup 3 }

    -- 1.3.6.1.4.1.2011.2.25.4.50.27.1.4
    optixLldpFastPduNum OBJECT-TYPE
        SYNTAX Unsigned32
        MAX-ACCESS read-write
        STATUS current
        DESCRIPTION
            "This object indicates the number of packets transmitted in the fast mode at the LLDP port. Value range: 1 to 8. The default value is 4."
        ::= { optixPktLLDPGroup 4 }

    -- 1.3.6.1.4.1.2011.2.25.4.50.27.1.5
    optixPKTLLDPTable OBJECT-TYPE
        SYNTAX SEQUENCE OF OptixPKTLLDPEntry
        MAX-ACCESS not-accessible
        STATUS current
        DESCRIPTION
            "This table describes the basicLLDP portconfigurations."
        ::= { optixPktLLDPGroup 5 }

    -- 1.3.6.1.4.1.2011.2.25.4.50.27.1.5.1
    optixPKTLLDPEntry OBJECT-TYPE
        SYNTAX OptixPKTLLDPEntry
        MAX-ACCESS not-accessible
        STATUS current
        DESCRIPTION
            "This entry describes the basic LLDP port configurations."
        INDEX{ optixLldpBoardId,optixLldpSubCardId,optixLldpPortId }
        ::= { optixPKTLLDPTable 1 }

    OptixPKTLLDPEntry ::=
        SEQUENCE {
            optixLldpBoardId
                Unsigned32,
            optixLldpSubCardId
                Unsigned32,
            optixLldpPortId
                Unsigned32,
            optixLldpWorkModle
                INTEGER,
            optixLldpVlanId
                Unsigned32,
            optixLldpVlanPri
                Unsigned32,
            optixLldpGroupType
                INTEGER,
            optixLldpPerReceiveMsg
                Unsigned32,
            optixLldpSendMsg
                Unsigned32,
            optixLldpLostMsg
                Unsigned32,
            optixLldpErrMsg
                Unsigned32,
            optixLldpAgeNeighbor
                Unsigned32,
            optixLldpLostTlv
                Unsigned32,
            optixLldpUnknowTlv
                Unsigned32,
            optixLldpClrstatistic
                INTEGER
        }

    -- 1.3.6.1.4.1.2011.2.25.4.50.27.1.5.1.1
    optixLldpBoardId OBJECT-TYPE
        SYNTAX Unsigned32
        MAX-ACCESS not-accessible
        STATUS current
        DESCRIPTION
            "This object indicates the slot ID of the LLDP port."
        ::= { optixPKTLLDPEntry 1 }

    -- 1.3.6.1.4.1.2011.2.25.4.50.27.1.5.1.2
    optixLldpSubCardId OBJECT-TYPE
        SYNTAX Unsigned32
        MAX-ACCESS not-accessible
        STATUS current
        DESCRIPTION
            "This object indicates the sbuboard ID of the LLDP port."
        ::= { optixPKTLLDPEntry 2 }

    -- 1.3.6.1.4.1.2011.2.25.4.50.27.1.5.1.3
    optixLldpPortId OBJECT-TYPE
        SYNTAX Unsigned32
        MAX-ACCESS not-accessible
        STATUS current
        DESCRIPTION
            "This object indicates the port number of the LLDP port."
        ::= { optixPKTLLDPEntry 3 }

    -- 1.3.6.1.4.1.2011.2.25.4.50.27.1.5.1.4
    optixLldpWorkModle OBJECT-TYPE
        SYNTAX INTEGER
        {
            disable(0),
            tx(1),
            rx(2),
            txrx(3)
        }
        MAX-ACCESS read-write
        STATUS current
        DESCRIPTION
            "This object indicates the working mode of the LLDP port. 0: disable, 1: tx, 2: rx, 3: txrx"
        ::= { optixPKTLLDPEntry 4 }

    -- 1.3.6.1.4.1.2011.2.25.4.50.27.1.5.1.5
    optixLldpVlanId OBJECT-TYPE
        SYNTAX Unsigned32
        MAX-ACCESS read-write
        STATUS current
        DESCRIPTION
            "This object indicates the VLAN ID of the LLDP port. 0: disable, 1: tx, 2: rx, 3: txrx"
        ::= { optixPKTLLDPEntry 5 }

    -- 1.3.6.1.4.1.2011.2.25.4.50.27.1.5.1.6
    optixLldpVlanPri OBJECT-TYPE
        SYNTAX Unsigned32
        MAX-ACCESS read-write
        STATUS current
        DESCRIPTION
            "This object indicates the VLANpriority of the LLDP port. Value range: 0 to 7."
        ::= { optixPKTLLDPEntry 6 }

    -- 1.3.6.1.4.1.2011.2.25.4.50.27.1.5.1.7
    optixLldpGroupType OBJECT-TYPE
        SYNTAX INTEGER
        {
            nb(1),
            nntb(2),
            ncb(3)
        }
        MAX-ACCESS read-write
        STATUS current
        DESCRIPTION
            "This object indicates themulticast mode of the LLDP port. 1: nb, 2: nntb, 3: ncb"
        ::= { optixPKTLLDPEntry 7 }

    -- 1.3.6.1.4.1.2011.2.25.4.50.27.1.5.1.9
    optixLldpPerReceiveMsg OBJECT-TYPE
        SYNTAX Unsigned32
        MAX-ACCESS read-only
        STATUS current
        DESCRIPTION
            "This object indicates receive LLDP Message Num of the LLDP. Value range: 0 to 0xffffffff."
        ::= { optixPKTLLDPEntry 9 }

    -- 1.3.6.1.4.1.2011.2.25.4.50.27.1.5.1.10
    optixLldpSendMsg OBJECT-TYPE
        SYNTAX Unsigned32
        MAX-ACCESS read-only
        STATUS current
        DESCRIPTION
            "This object indicates Send LLDP Message Num of the LLDP. Value range: 0 to 0xffffffff."
        ::= { optixPKTLLDPEntry 10 }

    -- 1.3.6.1.4.1.2011.2.25.4.50.27.1.5.1.11
    optixLldpLostMsg OBJECT-TYPE
        SYNTAX Unsigned32
        MAX-ACCESS read-only
        STATUS current
        DESCRIPTION
            "This object indicates Lost LLDP Message Num of the LLDP. Value range: 0 to 0xffffffff."
        ::= { optixPKTLLDPEntry 11 }

    -- 1.3.6.1.4.1.2011.2.25.4.50.27.1.5.1.12
    optixLldpErrMsg OBJECT-TYPE
        SYNTAX Unsigned32
        MAX-ACCESS read-only
        STATUS current
        DESCRIPTION
            "This object indicates Error LLDP Message Num of the LLDP. Value range: 0 to 0xffffffff."
        ::= { optixPKTLLDPEntry 12 }

    -- 1.3.6.1.4.1.2011.2.25.4.50.27.1.5.1.13
    optixLldpAgeNeighbor OBJECT-TYPE
        SYNTAX Unsigned32
        MAX-ACCESS read-only
        STATUS current
        DESCRIPTION
            "This object indicates Age Neighbor Num of the LLDP. Value range: 0 to 0xffffffff."
        ::= { optixPKTLLDPEntry 13 }

    -- 1.3.6.1.4.1.2011.2.25.4.50.27.1.5.1.14
    optixLldpLostTlv OBJECT-TYPE
        SYNTAX Unsigned32
        MAX-ACCESS read-only
        STATUS current
        DESCRIPTION
            "This object indicates the Lost LLDP TLV Num of the LLDP. Value range: 0 to 0xffffffff."
        ::= { optixPKTLLDPEntry 14 }

    -- 1.3.6.1.4.1.2011.2.25.4.50.27.1.5.1.15
    optixLldpUnknowTlv OBJECT-TYPE
        SYNTAX Unsigned32
        MAX-ACCESS read-only
        STATUS current
        DESCRIPTION
            "This object indicates the Unknow LLDP TLV Num of the LLDP. Value range: 0 to 0xffffffff."
        ::= { optixPKTLLDPEntry 15 }

    -- 1.3.6.1.4.1.2011.2.25.4.50.27.1.5.1.16
    optixLldpClrstatistic OBJECT-TYPE
        SYNTAX INTEGER
        {
            clear(1),
            invalid(255)
        }
        MAX-ACCESS read-write
        STATUS current
        DESCRIPTION
            "This object query invalid,be used to clear LLDP statistic.Value range: 0 to 0xffffffff."
        ::= { optixPKTLLDPEntry 16 }

    -- 1.3.6.1.4.1.2011.2.25.4.50.27.1.6
    optixPKTLldpNeigheorInfoEvent OBJECT IDENTIFIER ::= { optixPktLLDPGroup 6 }

    -- 1.3.6.1.4.1.2011.2.25.4.50.27.1.6.1
    optixPKTLldpNeigheorInfo NOTIFICATION-TYPE
        OBJECTS{ optixLldpNeigheorInfoBoardId,optixLldpNeigheorInfoSubCardId,optixLldpNeigheorInfoPortId,optixLldpNeigheorInfoType,optixLldpNeigheorInfoNum }
        STATUS current
        DESCRIPTION
            "This object is used to reportthe neighbour information of the LLDP port."
        ::= { optixPKTLldpNeigheorInfoEvent 1 }

    -- 1.3.6.1.4.1.2011.2.25.4.50.27.1.7
    optixPKTLldpNeigheorInfoTrapMember OBJECT IDENTIFIER ::= { optixPktLLDPGroup 7 }

    -- 1.3.6.1.4.1.2011.2.25.4.50.27.1.7.1
    optixLldpNeigheorInfoBoardId OBJECT-TYPE
        SYNTAX Unsigned32
        MAX-ACCESS accessible-for-notify
        STATUS current
        DESCRIPTION
            "This object indicates the slot ID of the LLDP port."
        ::= { optixPKTLldpNeigheorInfoTrapMember 1 }

    -- 1.3.6.1.4.1.2011.2.25.4.50.27.1.7.2
    optixLldpNeigheorInfoSubCardId OBJECT-TYPE
        SYNTAX Unsigned32
        MAX-ACCESS accessible-for-notify
        STATUS current
        DESCRIPTION
            "This object indicates the sbuboard ID of the LLDP port."
        ::= { optixPKTLldpNeigheorInfoTrapMember 2 }

    -- 1.3.6.1.4.1.2011.2.25.4.50.27.1.7.3
    optixLldpNeigheorInfoPortId OBJECT-TYPE
        SYNTAX Unsigned32
        MAX-ACCESS accessible-for-notify
        STATUS current
        DESCRIPTION
            "This object indicates the port number of the LLDP port."
        ::= { optixPKTLldpNeigheorInfoTrapMember 3 }

    -- 1.3.6.1.4.1.2011.2.25.4.50.27.1.7.4
    optixLldpNeigheorInfoType OBJECT-TYPE
        SYNTAX INTEGER
        {
            insert(1),
            update(2),
            delete(3),
            drop(4),
            ageout(5)
        }
        MAX-ACCESS accessible-for-notify
        STATUS current
        DESCRIPTION
            "This object is used to report the neighbour information Typt of the LLDP port. 1: insert, 2: update, 3: delete, 4: drop, 5: ageout"
        ::= { optixPKTLldpNeigheorInfoTrapMember 4 }

    -- 1.3.6.1.4.1.2011.2.25.4.50.27.1.7.5
    optixLldpNeigheorInfoNum OBJECT-TYPE
        SYNTAX Unsigned32
        MAX-ACCESS accessible-for-notify
        STATUS current
        DESCRIPTION
            "This object is used to report the neighbour information Number of the LLDP port. Value range: 0 to 0xffffffff."
        ::= { optixPKTLldpNeigheorInfoTrapMember 5 }

    -- 1.3.6.1.4.1.2011.2.25.4.50.27.1.8
    optixPKTLLDPNeigheorInfoTable OBJECT-TYPE
        SYNTAX SEQUENCE OF OptixPKTLLDPNeigheorInfoEntry
        MAX-ACCESS not-accessible
        STATUS current
        DESCRIPTION
            "This table describes the basicLLDP port neighbour information configurations."
        ::= { optixPktLLDPGroup 8 }

    -- 1.3.6.1.4.1.2011.2.25.4.50.27.1.8.1
    optixPKTLLDPNeigheorInfoEntry OBJECT-TYPE
        SYNTAX OptixPKTLLDPNeigheorInfoEntry
        MAX-ACCESS not-accessible
        STATUS current
        DESCRIPTION
            "This entry describes the basicLLDP port neighbour information configurations."
        INDEX{ optixLldpBoardId,optixLldpSubCardId,optixLldpPortId,optixPKTLLDPNeigheorInfoIndex }
        ::= { optixPKTLLDPNeigheorInfoTable 1 }

    OptixPKTLLDPNeigheorInfoEntry ::=
        SEQUENCE {
            optixPKTLLDPNeigheorInfoIndex
                Unsigned32,
            optixPKTLLDPLastTime
                Unsigned32,
            optixPKTLLDPRemainTime
                Unsigned32,
            optixPKTLLDPDestAddrIndex
                OCTET STRING,
            optixPKTLLDPChassisID
                OCTET STRING,
            optixPKTLLDPPortID
                OCTET STRING,
            optixPKTLLDPPortDescription
                OCTET STRING,
            optixPKTLLDPSystemName
                OCTET STRING,
            optixPKTLLDPSystemDescription
                OCTET STRING,
            optixPKTLLDPSystemCapabilities
                OCTET STRING,
            optixPKTLLDPManagementAddress
                OCTET STRING,
            optixPKTLLDPPortVLANID
                OCTET STRING,
            optixPKTLLDPPortAndProtocolVLANID
                OCTET STRING,
            optixPKTLLDPManagementVID
                OCTET STRING,
            optixPKTLLDPLinkAggregation
                OCTET STRING,
            optixPKTLLDPMACPHYConfigurationStatus
                OCTET STRING,
            optixPKTLLDPMaximumFrameSize
                OCTET STRING
        }

    -- 1.3.6.1.4.1.2011.2.25.4.50.27.1.8.1.1
    optixPKTLLDPNeigheorInfoIndex OBJECT-TYPE
        SYNTAX Unsigned32
        MAX-ACCESS not-accessible
        STATUS current
        DESCRIPTION
            "This object is used to report the neighbour information Index of the LLDP port. Value range: 0 to 0xffffffff."
        ::= { optixPKTLLDPNeigheorInfoEntry 1 }

    -- 1.3.6.1.4.1.2011.2.25.4.50.27.1.8.1.2
    optixPKTLLDPLastTime OBJECT-TYPE
        SYNTAX Unsigned32
        MAX-ACCESS read-only
        STATUS current
        DESCRIPTION
            "This object is used to report the neighbour information Last Time of the LLDP port. Value range: 0 to 0xffffffff."
        ::= { optixPKTLLDPNeigheorInfoEntry 2 }

    -- 1.3.6.1.4.1.2011.2.25.4.50.27.1.8.1.3
    optixPKTLLDPRemainTime OBJECT-TYPE
        SYNTAX Unsigned32
        MAX-ACCESS read-only
        STATUS current
        DESCRIPTION
            "This object is used to report the neighbour information Remain Time of the LLDP port. Value range: 0 to 0xffffffff."
        ::= { optixPKTLLDPNeigheorInfoEntry 3 }

    -- 1.3.6.1.4.1.2011.2.25.4.50.27.1.8.1.4
    optixPKTLLDPDestAddrIndex OBJECT-TYPE
        SYNTAX OCTET STRING
        MAX-ACCESS read-only
        STATUS current
        DESCRIPTION
            "This object is used to report the neighbour information Address Index of the LLDP port. Value range: 1 to 3. 1: nearest bridge (01-80-C2-00-00-0E), 2: nearest non-TPMR bridge (01-80-C2-00-00-03), 3: nearest customer bridge (01-80-C2-00-00-00)"
        ::= { optixPKTLLDPNeigheorInfoEntry 4 }

    -- 1.3.6.1.4.1.2011.2.25.4.50.27.1.8.1.5
    optixPKTLLDPChassisID OBJECT-TYPE
        SYNTAX OCTET STRING
        MAX-ACCESS read-only
        STATUS current
        DESCRIPTION
            "This object is used to report the neighbour information Chassis ID of the LLDP port."
        ::= { optixPKTLLDPNeigheorInfoEntry 5 }

    -- 1.3.6.1.4.1.2011.2.25.4.50.27.1.8.1.6
    optixPKTLLDPPortID OBJECT-TYPE
        SYNTAX OCTET STRING
        MAX-ACCESS read-only
        STATUS current
        DESCRIPTION
            "This object is used to report the neighbour information PortID String of the LLDP port."
        ::= { optixPKTLLDPNeigheorInfoEntry 6 }

    -- 1.3.6.1.4.1.2011.2.25.4.50.27.1.8.1.7
    optixPKTLLDPPortDescription OBJECT-TYPE
        SYNTAX OCTET STRING
        MAX-ACCESS read-only
        STATUS current
        DESCRIPTION
            "This object is used to report the neighbour information Port Description of the LLDP port."
        ::= { optixPKTLLDPNeigheorInfoEntry 7 }

    -- 1.3.6.1.4.1.2011.2.25.4.50.27.1.8.1.8
    optixPKTLLDPSystemName OBJECT-TYPE
        SYNTAX OCTET STRING
        MAX-ACCESS read-only
        STATUS current
        DESCRIPTION
            "This object is used to report the neighbour information System Name of the LLDP port."
        ::= { optixPKTLLDPNeigheorInfoEntry 8 }

    -- 1.3.6.1.4.1.2011.2.25.4.50.27.1.8.1.9
    optixPKTLLDPSystemDescription OBJECT-TYPE
        SYNTAX OCTET STRING
        MAX-ACCESS read-only
        STATUS current
        DESCRIPTION
            "This object is used to report the neighbour information System Description of the LLDP port."
        ::= { optixPKTLLDPNeigheorInfoEntry 9 }

    -- 1.3.6.1.4.1.2011.2.25.4.50.27.1.8.1.10
    optixPKTLLDPSystemCapabilities OBJECT-TYPE
        SYNTAX OCTET STRING
        MAX-ACCESS read-only
        STATUS current
        DESCRIPTION
            "This object is used to report the neighbour information System Capabilities of the LLDP port."
        ::= { optixPKTLLDPNeigheorInfoEntry 10 }

    -- 1.3.6.1.4.1.2011.2.25.4.50.27.1.8.1.11
    optixPKTLLDPManagementAddress OBJECT-TYPE
        SYNTAX OCTET STRING
        MAX-ACCESS read-only
        STATUS current
        DESCRIPTION
            "This object is used to report the neighbour information Management Address of the LLDP port."
        ::= { optixPKTLLDPNeigheorInfoEntry 11 }

    -- 1.3.6.1.4.1.2011.2.25.4.50.27.1.8.1.12
    optixPKTLLDPPortVLANID OBJECT-TYPE
        SYNTAX OCTET STRING
        MAX-ACCESS read-only
        STATUS current
        DESCRIPTION
            "This object is used to report the neighbour information Port VLANID of the LLDP port."
        ::= { optixPKTLLDPNeigheorInfoEntry 12 }

    -- 1.3.6.1.4.1.2011.2.25.4.50.27.1.8.1.13
    optixPKTLLDPPortAndProtocolVLANID OBJECT-TYPE
        SYNTAX OCTET STRING
        MAX-ACCESS read-only
        STATUS current
        DESCRIPTION
            "This object is used to report the neighbour information Port And Protocol VLANID of the LLDP port."
        ::= { optixPKTLLDPNeigheorInfoEntry 13 }

    -- 1.3.6.1.4.1.2011.2.25.4.50.27.1.8.1.14
    optixPKTLLDPManagementVID OBJECT-TYPE
        SYNTAX OCTET STRING
        MAX-ACCESS read-only
        STATUS current
        DESCRIPTION
            "This object is used to report the neighbour information Management VLANID of the LLDP port."
        ::= { optixPKTLLDPNeigheorInfoEntry 14 }

    -- 1.3.6.1.4.1.2011.2.25.4.50.27.1.8.1.15
    optixPKTLLDPLinkAggregation OBJECT-TYPE
        SYNTAX OCTET STRING
        MAX-ACCESS read-only
        STATUS current
        DESCRIPTION
            "This object is used to report the neighbour information Link Aggregation of the LLDP port."
        ::= { optixPKTLLDPNeigheorInfoEntry 15 }

    -- 1.3.6.1.4.1.2011.2.25.4.50.27.1.8.1.16
    optixPKTLLDPMACPHYConfigurationStatus OBJECT-TYPE
        SYNTAX OCTET STRING
        MAX-ACCESS read-only
        STATUS current
        DESCRIPTION
            "This object is used to report the neighbour information MAC/PHYConfiguration/Status of the LLDP port."
        ::= { optixPKTLLDPNeigheorInfoEntry 16 }

    -- 1.3.6.1.4.1.2011.2.25.4.50.27.1.8.1.17
    optixPKTLLDPMaximumFrameSize OBJECT-TYPE
        SYNTAX OCTET STRING
        MAX-ACCESS read-only
        STATUS current
        DESCRIPTION
            "This object is used to report the neighbour information Max FrameSize of the LLDP port."
        ::= { optixPKTLLDPNeigheorInfoEntry 17 }

    -- 1.3.6.1.4.1.2011.2.25.4.50.27.1.9
    optixPKTLLDPBaseStationInfoTable OBJECT-TYPE
        SYNTAX SEQUENCE OF OptixPKTLLDPBaseStationInfoEntry
        MAX-ACCESS not-accessible
        STATUS current
        DESCRIPTION
            "This table describes the Base Station information configurations based on LLDP."
        ::= { optixPktLLDPGroup 9 }

    -- 1.3.6.1.4.1.2011.2.25.4.50.27.1.9.1
    optixPKTLLDPBaseStationInfoEntry OBJECT-TYPE
        SYNTAX OptixPKTLLDPBaseStationInfoEntry
        MAX-ACCESS not-accessible
        STATUS current
        DESCRIPTION
            "This entry describes the Base Station information configurations based on LLDP."
        INDEX{ optixLldpBoardId,optixLldpSubCardId,optixLldpPortId,optixPKTLLDPOMMAC }
        ::= { optixPKTLLDPBaseStationInfoTable 1 }

    OptixPKTLLDPBaseStationInfoEntry ::=
        SEQUENCE {
            optixPKTLLDPOMIP
                IpAddress,
            optixPKTLLDPSysName
                OCTET STRING,
            optixPKTLLDPOMMAC
                OCTET STRING,
            optixPKTLLDPMTU
                Unsigned32,
            optixPKTLLDPOperMau
                OCTET STRING,
            optixPKTLLDPVlanID
                OCTET STRING,
            optixPKTLLDPOmchState
                INTEGER,
            optixPKTLLDPOmControlPlaneState
                Unsigned32,	
        }

    -- 1.3.6.1.4.1.2011.2.25.4.50.27.1.9.1.1
    optixPKTLLDPOMIP OBJECT-TYPE
        SYNTAX IpAddress
        MAX-ACCESS read-only
        STATUS current
        DESCRIPTION
            "This object describes the IP address of the Base Station based on LLDP."
        ::= { optixPKTLLDPBaseStationInfoEntry 1 }

    -- 1.3.6.1.4.1.2011.2.25.4.50.27.1.9.1.2
    optixPKTLLDPSysName OBJECT-TYPE
        SYNTAX OCTET STRING
        MAX-ACCESS read-only
        STATUS current
        DESCRIPTION
            "This object describes the system name of the Base Station based on LLDP."
        ::= { optixPKTLLDPBaseStationInfoEntry 2 }

    -- 1.3.6.1.4.1.2011.2.25.4.50.27.1.9.1.3
    optixPKTLLDPOMMAC OBJECT-TYPE
        SYNTAX OCTET STRING
        MAX-ACCESS not-accessible
        STATUS current
        DESCRIPTION
            "This object describes the MAC address of the Base Station based on LLDP."
        ::= { optixPKTLLDPBaseStationInfoEntry 3 }

    -- 1.3.6.1.4.1.2011.2.25.4.50.27.1.9.1.4
    optixPKTLLDPMTU OBJECT-TYPE
        SYNTAX Unsigned32
        MAX-ACCESS read-only
        STATUS current
        DESCRIPTION
            "This object describes the max length of package of port at Base Station based on LLDP."
        ::= { optixPKTLLDPBaseStationInfoEntry 4 }

    -- 1.3.6.1.4.1.2011.2.25.4.50.27.1.9.1.5
    optixPKTLLDPOperMau OBJECT-TYPE
        SYNTAX OCTET STRING
        MAX-ACCESS read-only
        STATUS current
        DESCRIPTION
            "This object describes the working mode of port of the Base Station based on LLDP."
        ::= { optixPKTLLDPBaseStationInfoEntry 5 }

    -- 1.3.6.1.4.1.2011.2.25.4.50.27.1.9.1.6
    optixPKTLLDPVlanID OBJECT-TYPE
        SYNTAX OCTET STRING
        MAX-ACCESS read-only
        STATUS current
        DESCRIPTION
            "This object describes information list of VLANID of Base Station based on LLDP."
        ::= { optixPKTLLDPBaseStationInfoEntry 6 }

    -- 1.3.6.1.4.1.2011.2.25.4.50.27.1.9.1.7
    optixPKTLLDPOmchState OBJECT-TYPE
        SYNTAX INTEGER {normal(0),abnormal(1),invalid(255)}
        MAX-ACCESS read-only
        STATUS current
        DESCRIPTION
            "This object describes the om state of the Base Station based on LLDP."
        ::= { optixPKTLLDPBaseStationInfoEntry 7 }

    -- 1.3.6.1.4.1.2011.2.25.4.50.27.1.9.1.8
    optixPKTLLDPOmControlPlaneState OBJECT-TYPE
        SYNTAX Unsigned32 (0..65535)
        MAX-ACCESS read-only
        STATUS current
        DESCRIPTION
            "This object describes the Om Service State of the Base Station based on LLDP."
        ::= { optixPKTLLDPBaseStationInfoEntry 8 }

    -- 1.3.6.1.4.1.2011.2.25.4.50.27.2
    optixPktLLDPNEGroup OBJECT IDENTIFIER ::= { optixPktLLDP 2 }

    -- 1.3.6.1.4.1.2011.2.25.4.50.27.2.1
    optixPKTLLDPSysMacAddr OBJECT-TYPE
        SYNTAX OCTET STRING
        MAX-ACCESS read-only
        STATUS current
        DESCRIPTION
            "This object indicates the mac address of the LLDP port."
        ::= { optixPktLLDPNEGroup 1 }

    -- 1.3.6.1.4.1.2011.2.25.4.50.27.2.2
    optixPKTLLDPGlobalEnable OBJECT-TYPE
        SYNTAX INTEGER
        {
            disable(0),
            enable(1)
        }
        MAX-ACCESS read-write
        STATUS current
        DESCRIPTION
            "This object indicates the global enable status of the LLDP."
        ::= { optixPktLLDPNEGroup 2 }

END
