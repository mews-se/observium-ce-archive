-- OPTIX-SDH-SYS-SYN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-SYS-SYN-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY,NOTIFICATION-TYPE
            FROM SNMPv2-SMI
        optixLogBoardId
            FROM OPTIX-BOARD-MANAGE-MIB
        ;

    optixSdhSysSyn MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations ofsystem clock source management."
        REVISION "201204200000Z"
        DESCRIPTION
            "The initial revision of this MIB module1."
        ::={ optixProvisionSdh 48 }

    -- 1.3.6.1.4.1.2011.2.25.4.10.48.1
    optixSdhSysSynGroup OBJECT IDENTIFIER ::= { optixSdhSysSyn 1 }

    -- 1.3.6.1.4.1.2011.2.25.4.10.48.1.1
    optixSdhSysSynTable OBJECT-TYPE
        SYNTAX SEQUENCE OF OptixSdhSysSynEntry
        MAX-ACCESS not-accessible
        STATUS current
        DESCRIPTION
            "This table describes the configurations of SDH system synchronization source"
        ::= { optixSdhSysSynGroup 1 }

    -- 1.3.6.1.4.1.2011.2.25.4.10.48.1.1.1
    optixSdhSysSynEntry OBJECT-TYPE
        SYNTAX OptixSdhSysSynEntry
        MAX-ACCESS not-accessible
        STATUS current
        DESCRIPTION
            "This entry describes the configurations of SDH system synchronization source"
        INDEX{ optixLogBoardId }
        ::= { optixSdhSysSynTable 1 }

    OptixSdhSysSynEntry ::=
        SEQUENCE {
            optixSdhSysSynSwState
                INTEGER,
            optixSdhSysSynCurrentSyn
                Unsigned32,
            optixSdhSysSynQualityLevel1
                INTEGER,
            optixSdhSysSynQualityLevel2
                INTEGER,
            optixSdhSysSynCurSyn
                Unsigned32,
            optixSdhSysSynWorkMode
                INTEGER,
            optixSdhSysSyn24HourKeepMode
                Unsigned32,
            optixSdhSynProtectSynRvtMode
                INTEGER,
            optixSdhSynProtectSynWtrTime
                Unsigned32,
            optixSysSynPriTableCLkNumber
                Unsigned32,
            optixSysSynPriTableCLkList
                OCTET STRING,
            optixSdhSysSynCurSynS1Value
                INTEGER,
            optixSynbaddetectObjFlag
                INTEGER
        }

    -- 1.3.6.1.4.1.2011.2.25.4.10.48.1.1.1.1
    optixSdhSysSynSwState OBJECT-TYPE
        SYNTAX INTEGER
        {
            synAuto(0),
            synMan(1),
            synForce(2)
        }
        MAX-ACCESS read-write
        STATUS current
        DESCRIPTION
            "This parameter specifies switch state. 0: synAuto, 1: synMan, 2: synForce"
        ::= { optixSdhSysSynEntry 1 }

    -- 1.3.6.1.4.1.2011.2.25.4.10.48.1.1.1.2
    optixSdhSysSynCurrentSyn OBJECT-TYPE
        SYNTAX Unsigned32
        MAX-ACCESS read-write
        STATUS current
        DESCRIPTION
            "This parameter specifies current synchronize. Value range: 0x01ff0001 to 0x06ff0006 with 0x00f00001, 0x00f00002, and 0x00f10001."
        ::= { optixSdhSysSynEntry 2 }

    -- 1.3.6.1.4.1.2011.2.25.4.10.48.1.1.1.3
    optixSdhSysSynQualityLevel1 OBJECT-TYPE
        SYNTAX INTEGER
        {
            qlUnknown(0),
            qlPrc(2),
            qlSsua(4),
            qlSsub(8),
            qlSec(11),
            qlDnu(15)
        }
        MAX-ACCESS read-write
        STATUS current
        DESCRIPTION
            "This parameter specifies quality level 1. 0: qlUnknown, 2: qlPrc, 4: qlSsua, 8: qlSsub, 11: qlSec, 15: qlDnu"
        ::= { optixSdhSysSynEntry 3 }

    -- 1.3.6.1.4.1.2011.2.25.4.10.48.1.1.1.4
    optixSdhSysSynQualityLevel2 OBJECT-TYPE
        SYNTAX INTEGER
        {
            qlUnknown(0),
            qlPrc(2),
            qlSsua(4),
            qlSsub(8),
            qlSec(11),
            qlDnu(15)
        }
        MAX-ACCESS read-write
        STATUS current
        DESCRIPTION
            "This parameter specifies quality level 2. 0: qlUnknown, 2: qlPrc, 4: qlSsua, 8: qlSsub, 11: qlSec, 15: qlDnu"
        ::= { optixSdhSysSynEntry 4 }

    -- 1.3.6.1.4.1.2011.2.25.4.10.48.1.1.1.5
    optixSdhSysSynCurSyn OBJECT-TYPE
        SYNTAX Unsigned32
        MAX-ACCESS read-only
        STATUS current
        DESCRIPTION
            "This parameter specifies cur synchronize. Value range: 0x01ff0001 to 0x06ff0006 with 0x00f00001, 0x00f00002, and 0x00f10001."
        ::= { optixSdhSysSynEntry 5 }

    -- 1.3.6.1.4.1.2011.2.25.4.10.48.1.1.1.6
    optixSdhSysSynWorkMode OBJECT-TYPE
        SYNTAX INTEGER
        {
            trace(1),
            keep(2),
            free(3)
        }
        MAX-ACCESS read-only
        STATUS current
        DESCRIPTION
            "This parameter specifies work mode. 1: trace, 2: keep, 3: free"
        ::= { optixSdhSysSynEntry 6 }

    -- 1.3.6.1.4.1.2011.2.25.4.10.48.1.1.1.7
    optixSdhSysSyn24HourKeepMode OBJECT-TYPE
        SYNTAX Unsigned32
        MAX-ACCESS read-write
        STATUS current
        DESCRIPTION
            "This parameter specifies 24 hour keep mode. 0: normal outdata, 1: last data holding"
        ::= { optixSdhSysSynEntry 7 }

    -- 1.3.6.1.4.1.2011.2.25.4.10.48.1.1.1.8
    optixSdhSynProtectSynRvtMode OBJECT-TYPE
        SYNTAX INTEGER
        {
            enable(1),
            disable(0)
        }
        MAX-ACCESS read-write
        STATUS current
        DESCRIPTION
            "This parameter specifies synchronize source degression switch enable state. 0: disable, 1: enable"
        ::= { optixSdhSysSynEntry 8 }

    -- 1.3.6.1.4.1.2011.2.25.4.10.48.1.1.1.9
    optixSdhSynProtectSynWtrTime OBJECT-TYPE
        SYNTAX Unsigned32
        MAX-ACCESS read-write
        STATUS current
        DESCRIPTION
            "This parameter specifies synchronize source wait to recover time. Value range: 0 to 12 (unit: minute)."
        ::= { optixSdhSysSynEntry 9 }

    -- 1.3.6.1.4.1.2011.2.25.4.10.48.1.1.1.10
    optixSysSynPriTableCLkNumber OBJECT-TYPE
        SYNTAX Unsigned32
        MAX-ACCESS read-write
        STATUS current
        DESCRIPTION
            "This parameter specifies the ssm protocol pri table clock number."
        ::= { optixSdhSysSynEntry 10 }

    -- 1.3.6.1.4.1.2011.2.25.4.10.48.1.1.1.11
    optixSysSynPriTableCLkList OBJECT-TYPE
        SYNTAX OCTET STRING
        MAX-ACCESS read-write
        STATUS current
        DESCRIPTION
            "This parameter specifies the ssm protocol pri table clock list."
        ::= { optixSdhSysSynEntry 11 }

    -- 1.3.6.1.4.1.2011.2.25.4.10.48.1.1.1.12
    optixSdhSysSynCurSynS1Value OBJECT-TYPE
        SYNTAX INTEGER
        {
            qlUnknown(0),
            qlPrc(2),
            qlSsua(4),
            qlSsub(8),
            qlSec(11),
            qlDnu(15)
        }
        MAX-ACCESS read-only
        STATUS current
        DESCRIPTION
            "This parameter specifies the s1 value of current synchronize. 0: qlUnknown, 2: qlPrc, 4: qlSsua, 8: qlSsub, 11: qlSec, 15: qlDnu"
        ::= { optixSdhSysSynEntry 12 }

    -- 1.3.6.1.4.1.2011.2.25.4.10.48.1.1.1.14
    optixSynbaddetectObjFlag OBJECT-TYPE
        SYNTAX INTEGER
        {
            enable(1),
            disable(0)
        }
        MAX-ACCESS read-write
        STATUS current
        DESCRIPTION
            "This parameter specifies the enable status of clock source frequency deviationdetection. 1: enable; 0: disable"
        ::= { optixSdhSysSynEntry 14 }

    -- 1.3.6.1.4.1.2011.2.25.4.10.48.1.2
    optixSdhSysSynClassTable OBJECT-TYPE
        SYNTAX SEQUENCE OF OptixSdhSysSynClassEntry
        MAX-ACCESS not-accessible
        STATUS current
        DESCRIPTION
            "This table contains configuration information of system synchronize class"
        ::= { optixSdhSysSynGroup 2 }

    -- 1.3.6.1.4.1.2011.2.25.4.10.48.1.2.1
    optixSdhSysSynClassEntry OBJECT-TYPE
        SYNTAX OptixSdhSysSynClassEntry
        MAX-ACCESS not-accessible
        STATUS current
        DESCRIPTION
            "Entry containing configuration information of system synchronize class"
        INDEX{ optixLogBoardId,optixSdhSysSynId }
        ::= { optixSdhSysSynClassTable 1 }

    OptixSdhSysSynClassEntry ::=
        SEQUENCE {
            optixSdhSysSynId
                Unsigned32,
            optixSdhSynProtectEnable
                INTEGER,
            optixSdhSysSynStatus
                Unsigned32,
            optixSSMExQulity
                Unsigned32,
            optixSdhSysSynS1Value
                INTEGER,
            optixSdhSysSynSubNet
                Unsigned32,
            optixSdhSysSynNodeID
                Unsigned32
        }

    -- 1.3.6.1.4.1.2011.2.25.4.10.48.1.2.1.1
    optixSdhSysSynId OBJECT-TYPE
        SYNTAX Unsigned32
        MAX-ACCESS not-accessible
        STATUS current
        DESCRIPTION
            "This parameter specifies synchronize source. Value range: 0x01ff0001 to 0x06ff0006 with 0x00f00001, 0x00f00002, and 0x00f10001."
        ::= { optixSdhSysSynClassEntry 1 }

    -- 1.3.6.1.4.1.2011.2.25.4.10.48.1.2.1.2
    optixSdhSynProtectEnable OBJECT-TYPE
        SYNTAX INTEGER
        {
            enable(1),
            disable(0)
        }
        MAX-ACCESS read-write
        STATUS current
        DESCRIPTION
            "This parameter specifies synchronizesource enable state. 0: disable, 1: enable"
        ::= { optixSdhSysSynClassEntry 2 }

    -- 1.3.6.1.4.1.2011.2.25.4.10.48.1.2.1.3
    optixSdhSysSynStatus OBJECT-TYPE
        SYNTAX Unsigned32
        MAX-ACCESS read-only
        STATUS current
        DESCRIPTION
            "This parameter specifies synchronize source status. 0: invalid, 1: valid"
        ::= { optixSdhSysSynClassEntry 3 }

    -- 1.3.6.1.4.1.2011.2.25.4.10.48.1.2.1.4
    optixSSMExQulity OBJECT-TYPE
        SYNTAX Unsigned32
        MAX-ACCESS read-write
        STATUS current
        DESCRIPTION
            "This parameter specifies the ssm protocol s1 qulity. Value range: 0x00, 0x02, 0x04, 0x08, 0x0b, 0x0f, and 0xff."
        ::= { optixSdhSysSynClassEntry 4 }

    -- 1.3.6.1.4.1.2011.2.25.4.10.48.1.2.1.5
    optixSdhSysSynS1Value OBJECT-TYPE
        SYNTAX INTEGER
        {
            qlUnknown(0),
            qlPrc(2),
            qlSsua(4),
            qlSsub(8),
            qlSec(11),
            qlDnu(15)
        }
        MAX-ACCESS read-only
        STATUS current
        DESCRIPTION
            "This parameter specifies the s1 value of all synchronize in pri-table. 0: qlUnknown, 2: qlPrc, 4: qlSsua, 8: qlSsub, 11: qlSec, 15: qlDnu"
        ::= { optixSdhSysSynClassEntry 5 }

    -- 1.3.6.1.4.1.2011.2.25.4.10.48.1.2.1.6
    optixSdhSysSynSubNet OBJECT-TYPE
        SYNTAX Unsigned32
        MAX-ACCESS read-write
        STATUS current
        DESCRIPTION
            "This parameter specifies the sub net id. Value range: 0 to 255."
        ::= { optixSdhSysSynClassEntry 6 }

    -- 1.3.6.1.4.1.2011.2.25.4.10.48.1.2.1.7
    optixSdhSysSynNodeID OBJECT-TYPE
        SYNTAX Unsigned32
        MAX-ACCESS read-write
        STATUS current
        DESCRIPTION
            "This parameter specifies the node id. Value range: 0x00 to 0x0f."
        ::= { optixSdhSysSynClassEntry 7 }

    -- 1.3.6.1.4.1.2011.2.25.4.10.48.1.3
    optixSdhSysSynMember OBJECT IDENTIFIER ::= { optixSdhSysSynGroup 3 }

    -- 1.3.6.1.4.1.2011.2.25.4.10.48.1.3.1
    optixSdhSysSynFromSyn OBJECT-TYPE
        SYNTAX Unsigned32
        MAX-ACCESS accessible-for-notify
        STATUS current
        DESCRIPTION
            "This parameter indicates the ID of the old synchronous clock source."
        ::= { optixSdhSysSynMember 1 }

    -- 1.3.6.1.4.1.2011.2.25.4.10.48.1.3.2
    optixSdhSysSynToSyn OBJECT-TYPE
        SYNTAX Unsigned32
        MAX-ACCESS accessible-for-notify
        STATUS current
        DESCRIPTION
            "This parameter indicates the OD of the new synchronous clock source."
        ::= { optixSdhSysSynMember 2 }

    -- 1.3.6.1.4.1.2011.2.25.4.10.48.1.3.3
    optixSdhSysSynSwitchState OBJECT-TYPE
        SYNTAX INTEGER
        {
            auto(1),
            man(2),
            force(3)
        }
        MAX-ACCESS accessible-for-notify
        STATUS current
        DESCRIPTION
            "This parameter indicates the switching mode of the synchronous clock source. 0x01:auto,0x02:man,0x03:force."
        ::= { optixSdhSysSynMember 3 }

    -- 1.3.6.1.4.1.2011.2.25.4.10.48.1.3.4
    optixSdhSysSynPriTableId OBJECT-TYPE
        SYNTAX INTEGER
        {
            synTbl(0),
            fir2mTbl(1),
            sec2mTbl(2)
        }
        MAX-ACCESS accessible-for-notify
        STATUS current
        DESCRIPTION
            "This parameter indicates the type of the clock source priority table. 0x00:syntbl,0x01:fir-2m-tbl,0x02:sec-2m-tbl."
        ::= { optixSdhSysSynMember 4 }

    -- 1.3.6.1.4.1.2011.2.25.4.10.48.1.3.5
    optixSdhSysSynNum OBJECT-TYPE
        SYNTAX Unsigned32
        MAX-ACCESS accessible-for-notify
        STATUS current
        DESCRIPTION
            "This parameter indicates the ID of the synchronous clock source."
        ::= { optixSdhSysSynMember 5 }

    -- 1.3.6.1.4.1.2011.2.25.4.10.48.1.3.6
    optixSdhSysSynFromSsm OBJECT-TYPE
        SYNTAX INTEGER
        {
            qlUnknown(0),
            qlPrc(2),
            qlSsua(4),
            qlSsub(8),
            qlSec(11),
            qlDnu(15)
        }
        MAX-ACCESS accessible-for-notify
        STATUS current
        DESCRIPTION
            "This parameter indicates the quality information of old SSM.0: qlUnknown, 2: qlPrc, 4: qlSsua, 8: qlSsub, 11: qlSec, 15: qlDnu."
        ::= { optixSdhSysSynMember 6 }

    -- 1.3.6.1.4.1.2011.2.25.4.10.48.1.3.7
    optixSdhSysSynToSsm OBJECT-TYPE
        SYNTAX INTEGER
        {
            qlUnknown(0),
            qlPrc(2),
            qlSsua(4),
            qlSsub(8),
            qlSec(11),
            qlDnu(15)
        }
        MAX-ACCESS accessible-for-notify
        STATUS current
        DESCRIPTION
            "This parameter indicates the quality information of new SSM.0: qlUnknown, 2: qlPrc, 4: qlSsua, 8: qlSsub, 11: qlSec, 15: qlDnu."
        ::= { optixSdhSysSynMember 7 }

    -- 1.3.6.1.4.1.2011.2.25.4.10.48.1.3.8
    optixSdhSysSynManual OBJECT-TYPE
        SYNTAX Unsigned32
        MAX-ACCESS accessible-for-notify
        STATUS current
        DESCRIPTION
            "This parameter indicates whether to manually change the quality information.1:manule,0:no manule."
        ::= { optixSdhSysSynMember 8 }

    -- 1.3.6.1.4.1.2011.2.25.4.10.48.1.4
    optixSdhSysSynEvent OBJECT IDENTIFIER ::= { optixSdhSysSynGroup 4 }

    -- 1.3.6.1.4.1.2011.2.25.4.10.48.1.4.1
    optixSdhSysSynSwitchTrap NOTIFICATION-TYPE
        OBJECTS{ optixSdhSysSynFromSyn,optixSdhSysSynToSyn,optixSdhSysSynSwitchState,optixSdhSysSynPriTableId }
        STATUS current
        DESCRIPTION
            "This parameter indicates the switching event of the synchronous clock source."
        ::= { optixSdhSysSynEvent 1 }

    -- 1.3.6.1.4.1.2011.2.25.4.10.48.1.4.2
    optixSdhSysSynSsmChangeTrap NOTIFICATION-TYPE
        OBJECTS{ optixSdhSysSynNum,optixSdhSysSynFromSsm,optixSdhSysSynManual,optixSdhSysSynToSsm }
        STATUS current
        DESCRIPTION
            "This parameter indicates the quality change event of the synchronous clock source."
        ::= { optixSdhSysSynEvent 2 }

END
