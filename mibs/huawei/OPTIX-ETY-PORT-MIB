-- OPTIX-ETY-PORT-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-ETY-PORT-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        ;

    optixEtyPort MODULE-IDENTITY
        LAST-UPDATED "201204240000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies ety interface cleared information"
        REVISION "201204240000Z"
        DESCRIPTION
            "The initial revision of this MIB module."
        REVISION "201204240000Z"
        DESCRIPTION
            "The initial revision of this MIB module."
        ::={ optixProvisionPtn 18 }

    -- 1.3.6.1.4.1.2011.2.25.4.50.18.1
    optixEtyPortGroup OBJECT IDENTIFIER ::= { optixEtyPort 1 }

    -- 1.3.6.1.4.1.2011.2.25.4.50.18.1.1
    optixEtyPortGroupTable OBJECT-TYPE
        SYNTAX SEQUENCE OF OptixEtyPortGroupEntry
        MAX-ACCESS not-accessible
        STATUS current
        DESCRIPTION
            "This table describes the ETH interface information on devices."
        ::= { optixEtyPortGroup 1 }

    -- 1.3.6.1.4.1.2011.2.25.4.50.18.1.1.1
    optixEtyPortGroupEntry OBJECT-TYPE
        SYNTAX OptixEtyPortGroupEntry
        MAX-ACCESS not-accessible
        STATUS current
        DESCRIPTION
            "This entry describes the ETH interface information on devices."
        INDEX{ optixEtyBoardId,optixEtySubBdId,optixEtyPortId }
        ::= { optixEtyPortGroupTable 1 }

    OptixEtyPortGroupEntry ::=
        SEQUENCE {
            optixEtyBoardId
                Unsigned32,
            optixEtySubBdId
                Unsigned32,
            optixEtyPortId
                Unsigned32,
            optixEtyPortMngStatus
                INTEGER,
            optixEtyPortSpeed
                INTEGER,
            optixEtyPortOperStatus
                INTEGER
        }

    -- 1.3.6.1.4.1.2011.2.25.4.50.18.1.1.1.1
    optixEtyBoardId OBJECT-TYPE
        SYNTAX Unsigned32
        MAX-ACCESS not-accessible
        STATUS current
        DESCRIPTION
            "This object indicates the slot ID of the ETH board. Value range on RTN equipment: 1 to 6."
        ::= { optixEtyPortGroupEntry 1 }

    -- 1.3.6.1.4.1.2011.2.25.4.50.18.1.1.1.2
    optixEtySubBdId OBJECT-TYPE
        SYNTAX Unsigned32
        MAX-ACCESS not-accessible
        STATUS current
        DESCRIPTION
            "This object indicates the ETH subboard ID. The value is 255."
        ::= { optixEtyPortGroupEntry 2 }

    -- 1.3.6.1.4.1.2011.2.25.4.50.18.1.1.1.3
    optixEtyPortId OBJECT-TYPE
        SYNTAX Unsigned32
        MAX-ACCESS not-accessible
        STATUS current
        DESCRIPTION
            "This object indicates the ETH port number. Value range for EM6T/EM6F ports: 1 to 6. Value range for EFP8 ports: 1 to 8."
        ::= { optixEtyPortGroupEntry 3 }

    -- 1.3.6.1.4.1.2011.2.25.4.50.18.1.1.1.4
    optixEtyPortMngStatus OBJECT-TYPE
        SYNTAX INTEGER
        {
            enable(1),
            disable(0)
        }
        MAX-ACCESS read-only
        STATUS current
        DESCRIPTION
            "This object indicates the administration status of the ETH interface. 0: disable, 1: enable"
        ::= { optixEtyPortGroupEntry 4 }

    -- 1.3.6.1.4.1.2011.2.25.4.50.18.1.1.1.5
    optixEtyPortSpeed OBJECT-TYPE
        SYNTAX INTEGER
        {
            auto(0),
            tenmhalf(1),
            tenmfull(2),
            hundredmhalf(3),
            hundredmfull(4),
            thousandmhalf(5),
            thousandmfull(6),
            tengfulllan(7),
            tengfullwan(8),
            negotiating(255)
        }
        MAX-ACCESS read-only
        STATUS current
        DESCRIPTION
            "This object indicates the ETH port rate. 0: auto, 1: tenmhalf, 2: tenmfull, 3: hundredmhalf, 4: hundredmfull, 5: thousandmhalf, 6: thousandmfull, 7: tengfulllan, 8: tengfullwan, 255: negotiating"
        ::= { optixEtyPortGroupEntry 5 }

    -- 1.3.6.1.4.1.2011.2.25.4.50.18.1.1.1.6
    optixEtyPortOperStatus OBJECT-TYPE
        SYNTAX INTEGER
        {
            down(0),
            up(1)
        }
        MAX-ACCESS read-only
        STATUS current
        DESCRIPTION
            "This object indicates the running status of the ETH interface."
        ::= { optixEtyPortGroupEntry 6 }

END
