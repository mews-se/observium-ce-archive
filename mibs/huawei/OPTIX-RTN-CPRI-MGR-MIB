-- OPTIX-RTN-CPRI-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-CPRI-MGR-MIB DEFINITIONS ::= BEGIN
    IMPORTS
        optixProvisionRtn
            FROM OPTIX-OID-MIB
        optixRtnBoardID,optixRtnSubCardID,optixRtnPortID
            FROM OPTIX-RTN-IFBOARD-ATTRIB-MIB
        Unsigned32,MODULE-IDENTITY,OBJECT-TYPE
            FROM SNMPv2-SMI
        ;

    optixRtnCPRIMgr MODULE-IDENTITY
        LAST-UPDATED "201403131919Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query parameters for the CPRI function of IF boards, including the active cpri mode, and query the cpri mode."
        REVISION "201403131919Z"
        DESCRIPTION
            "The initial revision of this MIB module."
        ::={ optixProvisionRtn 16 }

    -- 1.3.6.1.4.1.2011.2.25.4.40.16.1
    optixBoardCpriAttr OBJECT IDENTIFIER ::= { optixRtnCPRIMgr 1 }

    -- 1.3.6.1.4.1.2011.2.25.4.40.16.1.5
    optixRtnCPRIPortGeneralAttribNewTable OBJECT-TYPE
        SYNTAX SEQUENCE OF OptixRtnCPRIPortGeneralAttribNewEntry
        MAX-ACCESS not-accessible
        STATUS current
        DESCRIPTION
            "Describes general attributes of an IF board, including the cpri status."
        ::= { optixBoardCpriAttr 5 }

    -- 1.3.6.1.4.1.2011.2.25.4.40.16.1.5.1
    optixRtnCPRIPortGeneralAttribNewEntry OBJECT-TYPE
        SYNTAX OptixRtnCPRIPortGeneralAttribNewEntry
        MAX-ACCESS not-accessible
        STATUS current
        DESCRIPTION
            "Indicates the management entry for the general attributes of an CPRI port."
        INDEX{ optixRtnBoardID,optixRtnSubCardID,optixRtnPortID }
        ::= { optixRtnCPRIPortGeneralAttribNewTable 1 }

    OptixRtnCPRIPortGeneralAttribNewEntry ::=
        SEQUENCE {
            optixRtnCpriPortModeNew
                OCTET STRING,
            optixRtnCpriPortSpeedNew
                OCTET STRING
        }

    -- 1.3.6.1.4.1.2011.2.25.4.40.16.1.5.1.1
    optixRtnCpriPortModeNew OBJECT-TYPE
        SYNTAX OCTET STRING
        MAX-ACCESS read-only
        STATUS current
        DESCRIPTION
            "query cpri mode.
380:
cpri(1)
nocpri(2)

380H/380HN:
cpri(1)
none(2)
obsai(3)"
        ::= { optixRtnCPRIPortGeneralAttribNewEntry 1 }

    -- 1.3.6.1.4.1.2011.2.25.4.40.16.1.5.1.2
    optixRtnCpriPortSpeedNew OBJECT-TYPE
        SYNTAX OCTET STRING
        MAX-ACCESS read-only
        STATUS current
        DESCRIPTION
            "the cpri speed.
380:
cpri1p25(1)
cpri2p5(2)

380H/380HN:
cpri-1p25compress(0)
cpri-1p25transparent(1)
cpri-2p5compress(2)
cpri-2p5transparent(3)
cpri-3gcompress(4)
cpri-3gtransparent(5)
cpri-5gcompress(6)
cpri-5gtransparent(7)
cpri-6gcompress(8)
cpri-6gtransparent(9)
cpri-9p8compress(10)
cpri-9p8transparent(11)
obsai-1p5(12)
obsai-3g(13)"
        ::= { optixRtnCPRIPortGeneralAttribNewEntry 2 }

    -- 1.3.6.1.4.1.2011.2.25.4.40.16.1.4
    optixRtnCPRIPortActiveTable OBJECT-TYPE
        SYNTAX SEQUENCE OF OptixRtnCPRIPortActiveEntry
        MAX-ACCESS not-accessible
        STATUS current
        DESCRIPTION
            "Table of active cpri mode"
        ::= { optixBoardCpriAttr 4 }

    -- 1.3.6.1.4.1.2011.2.25.4.40.16.1.4.1
    optixRtnCPRIPortActiveEntry OBJECT-TYPE
        SYNTAX OptixRtnCPRIPortActiveEntry
        MAX-ACCESS not-accessible
        STATUS current
        DESCRIPTION
            "active cpri mode"
        INDEX{ optixRtnBoardID,optixRtnSubCardID,optixRtnPortID }
        ::= { optixRtnCPRIPortActiveTable 1 }

    OptixRtnCPRIPortActiveEntry ::=
        SEQUENCE {
            optixRtnCpriPortActiveStatus
                INTEGER
        }

    -- 1.3.6.1.4.1.2011.2.25.4.40.16.1.4.1.1
    optixRtnCpriPortActiveStatus OBJECT-TYPE
        SYNTAX INTEGER
        {
            active(1)
        }
        MAX-ACCESS read-write
        STATUS current
        DESCRIPTION
            "active cpri mode"
        ::= { optixRtnCPRIPortActiveEntry 1 }

    -- 1.3.6.1.4.1.2011.2.25.4.40.16.1.2
    optixRtnCpriPortDelayAndJitterTable OBJECT-TYPE
        SYNTAX SEQUENCE OF OptixRtnCpriPortDelayAndJitterEntry
        MAX-ACCESS not-accessible
        STATUS current
        DESCRIPTION
            "Start the delay and jitter test of the CPRI port."
        ::= { optixBoardCpriAttr 2 }

    -- 1.3.6.1.4.1.2011.2.25.4.40.16.1.2.1
    optixRtnCpriPortDelayAndJitterEntry OBJECT-TYPE
        SYNTAX OptixRtnCpriPortDelayAndJitterEntry
        MAX-ACCESS not-accessible
        STATUS current
        DESCRIPTION
            "Entry to start the delay and jitter test of the CPRI port."
        INDEX{ optixRtnBoardID,optixRtnSubCardID,optixRtnPortID }
        ::= { optixRtnCpriPortDelayAndJitterTable 1 }

    OptixRtnCpriPortDelayAndJitterEntry ::=
        SEQUENCE {
            optixRtnCpriAccessType
                INTEGER,
            optixRtnCpriPortDelay
                Unsigned32,
            optixRtnCpriPortJitter
                Unsigned32,
            optixRtnCpriPortStartStatus
                INTEGER
        }

    -- 1.3.6.1.4.1.2011.2.25.4.40.16.1.2.1.1
    optixRtnCpriAccessType OBJECT-TYPE
        SYNTAX INTEGER
        {
            bbu(1),
            rru(2)
        }
        MAX-ACCESS read-only
        STATUS current
        DESCRIPTION
            "CPRI access-side type, BBU or RRU. 1: BBU; 2: RRU"
        ::= { optixRtnCpriPortDelayAndJitterEntry 1 }

    -- 1.3.6.1.4.1.2011.2.25.4.40.16.1.2.1.2
    optixRtnCpriPortDelay OBJECT-TYPE
        SYNTAX Unsigned32
        MAX-ACCESS read-only
        STATUS current
        DESCRIPTION
            "CPRI port delay"
        ::= { optixRtnCpriPortDelayAndJitterEntry 2 }

    -- 1.3.6.1.4.1.2011.2.25.4.40.16.1.2.1.3
    optixRtnCpriPortJitter OBJECT-TYPE
        SYNTAX Unsigned32
        MAX-ACCESS read-only
        STATUS current
        DESCRIPTION
            "CPRI port jitter"
        ::= { optixRtnCpriPortDelayAndJitterEntry 3 }

    -- 1.3.6.1.4.1.2011.2.25.4.40.16.1.2.1.4
    optixRtnCpriPortStartStatus OBJECT-TYPE
        SYNTAX INTEGER
        {
            start(1),
            invalid(-1)
        }
        MAX-ACCESS read-write
        STATUS current
        DESCRIPTION
            "Start the CPRI delay and jitter test."
        ::= { optixRtnCpriPortDelayAndJitterEntry 4 }

    -- 1.3.6.1.4.1.2011.2.25.4.40.16.1.3
    optixRtnCpriBerthTable OBJECT-TYPE
        SYNTAX SEQUENCE OF OptixRtnCpriBerthEntry
        MAX-ACCESS not-accessible
        STATUS current
        DESCRIPTION
            "Query the bit error threshold of the CPRI port."
        ::= { optixBoardCpriAttr 3 }

    -- 1.3.6.1.4.1.2011.2.25.4.40.16.1.3.1
    optixRtnCpriBerthEntry OBJECT-TYPE
        SYNTAX OptixRtnCpriBerthEntry
        MAX-ACCESS not-accessible
        STATUS current
        DESCRIPTION
            "Entry to query the bit error threshold of the CPRI port."
        INDEX{ optixRtnBoardID,optixRtnSubCardID,optixRtnPortID }
        ::= { optixRtnCpriBerthTable 1 }

    OptixRtnCpriBerthEntry ::=
        SEQUENCE {
            optixRtnCpriPortBerth
                Unsigned32
        }

    -- 1.3.6.1.4.1.2011.2.25.4.40.16.1.3.1.1
    optixRtnCpriPortBerth OBJECT-TYPE
        SYNTAX Unsigned32
        MAX-ACCESS read-write
        STATUS current
        DESCRIPTION
            "Bit error threshold of the CPRI port"
        ::= { optixRtnCpriBerthEntry 1 }

END
