-- OPTIX-RTN-MIMO-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-MIMO-MGR-MIB DEFINITIONS ::= BEGIN
    IMPORTS
        OBJECT-GROUP,MODULE-COMPLIANCE
            FROM SNMPv2-CONF
        Unsigned32,OBJECT-TYPE,MODULE-IDENTITY,Integer32
            FROM SNMPv2-SMI
        TEXTUAL-CONVENTION
            FROM SNMPv2-TC
        optixRtnOduIndex1,optixRtnOduIndex2
            FROM OPTIX-RTN-ODU-MGR-MIB
        optixProvisionRtn
            FROM OPTIX-OID-MIB
        optixRtnMimoBid,optixRtnMimoSubid,optixRtnMimoPortid,OPTIXRtnEnableStateType,optixRtnIndex1,optixRtnIndex2,optixRtnIndex3,optixRtnIndex4
            FROM OPTIX-RTN-GENNERAL-MIB
        ;

    optixRtnMimoParaMgr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query IF board related parameters required in radio link configuration and preventive maintenance, including the IF board modulation mode, bandwidth, AM management, and link identifier."
        REVISION "201204160935Z"
        DESCRIPTION
            "The initial revision of this MIB module1."
        ::={ optixProvisionRtn 6 }

    OPTIXRtnMimoBandWidthType ::= TEXTUAL-CONVENTION
        STATUS current
        DESCRIPTION
            "Indicates the IF bandwidth supported by MIMO."
        SYNTAX INTEGER
        { 
            bw28M(4),
            bw40M(5),
            bw56M(6),
            bw28MACCP(31),
            bw56MACCP(32),
        }

    OPTIXRtnModulateModeType ::= TEXTUAL-CONVENTION
        STATUS current
        DESCRIPTION
            "Describes the modulation mode supported by an IF board. Values: 1: QPSK 2: 16QAM 3: 32QAM 4: 64QAM 5: 128QAM 6: 256QAM 22: BPSK250M 23: BPSK500M 24: BPSK750M 25: BPSK1000M 26: BPSK1500M 27: BPSK2000M -1: null"
        SYNTAX INTEGER
        {
            modeClear(0),
            modeQPSK(1),
            mode16QAM(2),
            mode32QAM(3),
            mode64QAM(4),
            mode128QAM(5),
            mode256QAM(6),
            mode512QAM(7),
            mode1024QAM(8),
            modeQPSKSTRONG(9),
            mode16QAMSTRONG(10),
            mode1024QAMLIGHT(12),
            mode2048QAM(13),
            mode4096QAM(20),
            modeNULL(-1)
        }

    OPTIXRtnBoardType ::= TEXTUAL-CONVENTION
        STATUS current
        DESCRIPTION
            "Describes the board type of peer NE,shxa2: 2454,shuf3: 2484,v1shua2: 3343,mxuf4: 3344,sxa3: 3372,dmc5a: 3415,dmc4b: 3416,mxui5: 3442"
        SYNTAX INTEGER
        {
            shxa2(2454),
            shuf3(2484),
            v1shua2(3343),
            mxuf4(3344),
            sxa3(3372),
            dmc5a(3415),
            dmc4b(3416),
            mxui5(3442)
        }

    -- 1.3.6.1.4.1.2011.2.25.4.40.6.10
    optixRtnMimoPara OBJECT IDENTIFIER ::= { optixRtnMimoParaMgr 10 }

    -- 1.3.6.1.4.1.2011.2.25.4.40.6.10.240
    optixRtnMimo4P4GroupTable OBJECT-TYPE
        SYNTAX SEQUENCE OF OptixRtnMimo4P4GroupEntry
        MAX-ACCESS not-accessible
        STATUS current
        DESCRIPTION
            "Indicates the MIMO work group"
        ::= { optixRtnMimoPara 240 }

    -- 1.3.6.1.4.1.2011.2.25.4.40.6.10.240.1
    optixRtnMimo4P4GroupEntry OBJECT-TYPE
        SYNTAX OptixRtnMimo4P4GroupEntry
        MAX-ACCESS not-accessible
        STATUS current
        DESCRIPTION
            "Indicates the MIMO work group"
        INDEX{ optixRtnGroupID }
        ::= { optixRtnMimo4P4GroupTable 1 }

    OptixRtnMimo4P4GroupEntry ::=
        SEQUENCE {
            optixRtnGroupID
                INTEGER,
            optixRtnGroupType
                INTEGER,
            optixRtnNePos4P1
                INTEGER,
            optixRtnBoardID4P1
                Unsigned32,
            optixRtnSubCardID4P1
                Unsigned32,
            optixRtnPortID4P1
                Unsigned32,
            optixRtnPolar4P1
                Unsigned32,
            optixRtnNePos4P2
                INTEGER,
            optixRtnBoardID4P2
                Unsigned32,
            optixRtnSubCardID4P2
                Unsigned32,
            optixRtnPortID4P2
                Unsigned32,
            optixRtnPolar4P2
                Unsigned32,
            optixRtnNePos4P3
                INTEGER,
            optixRtnBoardID4P3
                Unsigned32,
            optixRtnSubCardID4P3
                Unsigned32,
            optixRtnPortID4P3
                Unsigned32,
            optixRtnPolar4P3
                Unsigned32,
            optixRtnNePos4P4
                INTEGER,
            optixRtnBoardID4P4
                Unsigned32,
            optixRtnSubCardID4P4
                Unsigned32,
            optixRtnPortID4P4
                Unsigned32,
            optixRtnPolar4P4
                Unsigned32,
            optixRtnMimoIfDelAdjNePg
                INTEGER
        }

    -- 1.3.6.1.4.1.2011.2.25.4.40.6.10.240.1.1
    optixRtnGroupID OBJECT-TYPE
        SYNTAX INTEGER
        {
            master(1),
            slave(2)
        }
        MAX-ACCESS not-accessible
        STATUS current
        DESCRIPTION
            "Indicates the MIMO work group ID."
        ::= { optixRtnMimo4P4GroupEntry 1 }

    -- 1.3.6.1.4.1.2011.2.25.4.40.6.10.240.1.2
    optixRtnGroupType OBJECT-TYPE
        SYNTAX INTEGER
        {
            cascade2p2(0),
            cascade4p4(1),
            inner2p2(2),
            inner4p4(3)
        }
        MAX-ACCESS read-create
        STATUS current
        DESCRIPTION
            "Indicates the MIMO work group type"
        ::= { optixRtnMimo4P4GroupEntry 2 }

    -- 1.3.6.1.4.1.2011.2.25.4.40.6.10.240.1.3
    optixRtnNePos4P1 OBJECT-TYPE
        SYNTAX INTEGER
        {
            local(0),
            neighbour(1)
        }
        MAX-ACCESS read-create
        STATUS current
        DESCRIPTION
            "Indicates the local or peer end.
	    1: local
	    2: neighbour"
        ::= { optixRtnMimo4P4GroupEntry 3 }

    -- 1.3.6.1.4.1.2011.2.25.4.40.6.10.240.1.4
    optixRtnBoardID4P1 OBJECT-TYPE
        SYNTAX Unsigned32
        MAX-ACCESS read-create
        STATUS current
        DESCRIPTION
            "Indicates the slot ID."
        ::= { optixRtnMimo4P4GroupEntry 4 }

    -- 1.3.6.1.4.1.2011.2.25.4.40.6.10.240.1.5
    optixRtnSubCardID4P1 OBJECT-TYPE
        SYNTAX Unsigned32
        MAX-ACCESS read-create
        STATUS current
        DESCRIPTION
            "Indicates the subboard ID."
        ::= { optixRtnMimo4P4GroupEntry 5 }

    -- 1.3.6.1.4.1.2011.2.25.4.40.6.10.240.1.6
    optixRtnPortID4P1 OBJECT-TYPE
        SYNTAX Unsigned32
        MAX-ACCESS read-create
        STATUS current
        DESCRIPTION
            "Indicates the port ID."
        ::= { optixRtnMimo4P4GroupEntry 6 }

    -- 1.3.6.1.4.1.2011.2.25.4.40.6.10.240.1.7
    optixRtnPolar4P1 OBJECT-TYPE
        SYNTAX Unsigned32
        {
            h1(1),
            v1(2),
            h2(3),
            v2(4),
            null(255)
        }
        MAX-ACCESS read-create
        STATUS current
        DESCRIPTION
            "Indicates the polarization direction.
	    1: h1
	    2: v1
	    3: h2
	    4: v2"
        ::= { optixRtnMimo4P4GroupEntry 7 }

    -- 1.3.6.1.4.1.2011.2.25.4.40.6.10.240.1.8
    optixRtnNePos4P2 OBJECT-TYPE
        SYNTAX INTEGER
        {
            local(0),
            neighbour(1)
        }
        MAX-ACCESS read-create
        STATUS current
        DESCRIPTION
            "Indicates the local or peer end.
	    1: local
	    2: neighbour"
        ::= { optixRtnMimo4P4GroupEntry 8 }

    -- 1.3.6.1.4.1.2011.2.25.4.40.6.10.240.1.9
    optixRtnBoardID4P2 OBJECT-TYPE
        SYNTAX Unsigned32
        MAX-ACCESS read-create
        STATUS current
        DESCRIPTION
            "Indicates the slot ID."
        ::= { optixRtnMimo4P4GroupEntry 9 }

    -- 1.3.6.1.4.1.2011.2.25.4.40.6.10.240.1.10
    optixRtnSubCardID4P2 OBJECT-TYPE
        SYNTAX Unsigned32
        MAX-ACCESS read-create
        STATUS current
        DESCRIPTION
            "Indicates the subboard ID."
        ::= { optixRtnMimo4P4GroupEntry 10 }

    -- 1.3.6.1.4.1.2011.2.25.4.40.6.10.240.1.11
    optixRtnPortID4P2 OBJECT-TYPE
        SYNTAX Unsigned32
        MAX-ACCESS read-create
        STATUS current
        DESCRIPTION
            "Indicates the port ID."
        ::= { optixRtnMimo4P4GroupEntry 11 }

    -- 1.3.6.1.4.1.2011.2.25.4.40.6.10.240.1.12
    optixRtnPolar4P2 OBJECT-TYPE
        SYNTAX Unsigned32
        {
            h1(1),
            v1(2),
            h2(3),
            v2(4),
            null(255)
        }
        MAX-ACCESS read-create
        STATUS current
        DESCRIPTION
            "Indicates the polarization direction.
	    1: h1
	    2: v1
	    3: h2
	    4: v2"
        ::= { optixRtnMimo4P4GroupEntry 12 }

    -- 1.3.6.1.4.1.2011.2.25.4.40.6.10.240.1.13
    optixRtnNePos4P3 OBJECT-TYPE
        SYNTAX INTEGER
        {
            local(0),
            neighbour(1)
        }
        MAX-ACCESS read-create
        STATUS current
        DESCRIPTION
            "Indicates the local or peer end.
	    1: local
	    2: neighbour"
        ::= { optixRtnMimo4P4GroupEntry 13 }

    -- 1.3.6.1.4.1.2011.2.25.4.40.6.10.240.1.14
    optixRtnBoardID4P3 OBJECT-TYPE
        SYNTAX Unsigned32
        MAX-ACCESS read-create
        STATUS current
        DESCRIPTION
            "Indicates the slot ID."
        ::= { optixRtnMimo4P4GroupEntry 14 }

    -- 1.3.6.1.4.1.2011.2.25.4.40.6.10.240.1.15
    optixRtnSubCardID4P3 OBJECT-TYPE
        SYNTAX Unsigned32
        MAX-ACCESS read-create
        STATUS current
        DESCRIPTION
            "Indicates the subboard ID."
        ::= { optixRtnMimo4P4GroupEntry 15 }

    -- 1.3.6.1.4.1.2011.2.25.4.40.6.10.240.1.16
    optixRtnPortID4P3 OBJECT-TYPE
        SYNTAX Unsigned32
        MAX-ACCESS read-create
        STATUS current
        DESCRIPTION
            "Indicates the port ID."
        ::= { optixRtnMimo4P4GroupEntry 16 }

    -- 1.3.6.1.4.1.2011.2.25.4.40.6.10.240.1.17
    optixRtnPolar4P3 OBJECT-TYPE
        SYNTAX Unsigned32
        {
            h1(1),
            v1(2),
            h2(3),
            v2(4),
            null(255)
        }
        MAX-ACCESS read-create
        STATUS current
        DESCRIPTION
            "Indicates the polarization direction.
	    1: h1
	    2: v1
	    3: h2
	    4: v2"
        ::= { optixRtnMimo4P4GroupEntry 17 }

    -- 1.3.6.1.4.1.2011.2.25.4.40.6.10.240.1.18
    optixRtnNePos4P4 OBJECT-TYPE
        SYNTAX INTEGER
        {
            local(0),
            neighbour(1)
        }
        MAX-ACCESS read-create
        STATUS current
        DESCRIPTION
            "Indicates the local or peer end.
	    1: local
	    2: neighbour"
        ::= { optixRtnMimo4P4GroupEntry 18 }

    -- 1.3.6.1.4.1.2011.2.25.4.40.6.10.240.1.19
    optixRtnBoardID4P4 OBJECT-TYPE
        SYNTAX Unsigned32
        MAX-ACCESS read-create
        STATUS current
        DESCRIPTION
            "Indicates the slot ID."
        ::= { optixRtnMimo4P4GroupEntry 19 }

    -- 1.3.6.1.4.1.2011.2.25.4.40.6.10.240.1.20
    optixRtnSubCardID4P4 OBJECT-TYPE
        SYNTAX Unsigned32
        MAX-ACCESS read-create
        STATUS current
        DESCRIPTION
            "Indicates the subboard ID."
        ::= { optixRtnMimo4P4GroupEntry 20 }

    -- 1.3.6.1.4.1.2011.2.25.4.40.6.10.240.1.21
    optixRtnPortID4P4 OBJECT-TYPE
        SYNTAX Unsigned32
        MAX-ACCESS read-create
        STATUS current
        DESCRIPTION
            "Indicates the port ID."
        ::= { optixRtnMimo4P4GroupEntry 21 }

    -- 1.3.6.1.4.1.2011.2.25.4.40.6.10.240.1.22
    optixRtnPolar4P4 OBJECT-TYPE
        SYNTAX Unsigned32
        {
            h1(1),
            v1(2),
            h2(3),
            v2(4),
            null(255)
        }
        MAX-ACCESS read-create
        STATUS current
        DESCRIPTION
            "Indicates the polarization direction.
	    1: h1
	    2: v1
	    3: h2
	    4: v2"
        ::= { optixRtnMimo4P4GroupEntry 22 }

    -- 1.3.6.1.4.1.2011.2.25.4.40.6.10.240.1.23
    optixRtnMimoIfDelAdjNePg OBJECT-TYPE
        SYNTAX INTEGER
        {
            false(0),
            true(1)
        }
        MAX-ACCESS read-create
        STATUS current
        DESCRIPTION
            "Indicates whether to delete configurations of the adjacent NE.
	    0: false
	    1: true"
        ::= { optixRtnMimo4P4GroupEntry 23 }

    -- 1.3.6.1.4.1.2011.2.25.4.40.6.10.250
    optixRtnMimo2P2GroupTable OBJECT-TYPE
        SYNTAX SEQUENCE OF OptixRtnMimo2P2GroupEntry
        MAX-ACCESS not-accessible
        STATUS current
        DESCRIPTION
            "Indicates the MIMO work group"
        ::= { optixRtnMimoPara 250 }

    -- 1.3.6.1.4.1.2011.2.25.4.40.6.10.250.1
    optixRtnMimo2P2GroupEntry OBJECT-TYPE
        SYNTAX OptixRtnMimo2P2GroupEntry
        MAX-ACCESS not-accessible
        STATUS current
        DESCRIPTION
            "Indicates the MIMO work group"
        INDEX{ optixRtn2P2GroupID }
        ::= { optixRtnMimo2P2GroupTable 1 }

    OptixRtnMimo2P2GroupEntry ::=
        SEQUENCE {
            optixRtn2P2GroupID
                INTEGER,
            optixRtn2P2GroupType
                INTEGER,
            optixRtnNePos2P1
                INTEGER,
            optixRtnBoardID2P1
                Unsigned32,
            optixRtnSubCardID2P1
                Unsigned32,
            optixRtnPortID2P1
                Unsigned32,
            optixRtnPolar2P1
                Unsigned32,
            optixRtnNePos2P2
                INTEGER,
            optixRtnBoardID2P2
                Unsigned32,
            optixRtnSubCardID2P2
                Unsigned32,
            optixRtnPortID2P2
                Unsigned32,
            optixRtnPolar2P2
                Unsigned32,
            optixRtnIfDelAdjNePg
                INTEGER
        }

    -- 1.3.6.1.4.1.2011.2.25.4.40.6.10.250.1.1
    optixRtn2P2GroupID OBJECT-TYPE
        SYNTAX INTEGER
        {
            master(1),
            slave(2)
        }
        MAX-ACCESS not-accessible
        STATUS current
        DESCRIPTION
            "Indicates the MIMO work group ID."
        ::= { optixRtnMimo2P2GroupEntry 1 }

    -- 1.3.6.1.4.1.2011.2.25.4.40.6.10.250.1.2
    optixRtn2P2GroupType OBJECT-TYPE
        SYNTAX INTEGER
        {
            cascade2p2(0),
            cascade4p4(1),
            inner2p2(2)
        }
        MAX-ACCESS read-create
        STATUS current
        DESCRIPTION
            "Indicates the MIMO work group type"
        ::= { optixRtnMimo2P2GroupEntry 2 }

    -- 1.3.6.1.4.1.2011.2.25.4.40.6.10.250.1.3
    optixRtnNePos2P1 OBJECT-TYPE
        SYNTAX INTEGER
        {
            local(0),
            neighbour(1)
        }
        MAX-ACCESS read-create
        STATUS current
        DESCRIPTION
            "Indicates the local or peer end.
	    1: local
	    2: neighbour"
        ::= { optixRtnMimo2P2GroupEntry 3 }

    -- 1.3.6.1.4.1.2011.2.25.4.40.6.10.250.1.4
    optixRtnBoardID2P1 OBJECT-TYPE
        SYNTAX Unsigned32
        MAX-ACCESS read-create
        STATUS current
        DESCRIPTION
            "Indicates the slot ID."
        ::= { optixRtnMimo2P2GroupEntry 4 }

    -- 1.3.6.1.4.1.2011.2.25.4.40.6.10.250.1.5
    optixRtnSubCardID2P1 OBJECT-TYPE
        SYNTAX Unsigned32
        MAX-ACCESS read-create
        STATUS current
        DESCRIPTION
            "Indicates the subboard ID."
        ::= { optixRtnMimo2P2GroupEntry 5 }

    -- 1.3.6.1.4.1.2011.2.25.4.40.6.10.250.1.6
    optixRtnPortID2P1 OBJECT-TYPE
        SYNTAX Unsigned32
        MAX-ACCESS read-create
        STATUS current
        DESCRIPTION
            "Indicates the port ID."
        ::= { optixRtnMimo2P2GroupEntry 6 }

    -- 1.3.6.1.4.1.2011.2.25.4.40.6.10.250.1.7
    optixRtnPolar2P1 OBJECT-TYPE
        SYNTAX Unsigned32
        {
            h1(1),
            v1(2),
            h2(3),
            v2(4),
            null(255)
        }
        MAX-ACCESS read-create
        STATUS current
        DESCRIPTION
            "Indicates the polarization direction.
	    1: h1
	    2: v1
	    3: h2
	    4: v2"
        ::= { optixRtnMimo2P2GroupEntry 7 }

    -- 1.3.6.1.4.1.2011.2.25.4.40.6.10.250.1.8
    optixRtnNePos2P2 OBJECT-TYPE
        SYNTAX INTEGER
        {
            local(0),
            neighbour(1)
        }
        MAX-ACCESS read-create
        STATUS current
        DESCRIPTION
            "Indicates the local or peer end.
	    1: local
	    2: neighbour"
        ::= { optixRtnMimo2P2GroupEntry 8 }

    -- 1.3.6.1.4.1.2011.2.25.4.40.6.10.250.1.9
    optixRtnBoardID2P2 OBJECT-TYPE
        SYNTAX Unsigned32
        MAX-ACCESS read-create
        STATUS current
        DESCRIPTION
            "Indicates the slot ID."
        ::= { optixRtnMimo2P2GroupEntry 9 }

    -- 1.3.6.1.4.1.2011.2.25.4.40.6.10.250.1.10
    optixRtnSubCardID2P2 OBJECT-TYPE
        SYNTAX Unsigned32
        MAX-ACCESS read-create
        STATUS current
        DESCRIPTION
            "Indicates the subboard ID."
        ::= { optixRtnMimo2P2GroupEntry 10 }

    -- 1.3.6.1.4.1.2011.2.25.4.40.6.10.250.1.11
    optixRtnPortID2P2 OBJECT-TYPE
        SYNTAX Unsigned32
        MAX-ACCESS read-create
        STATUS current
        DESCRIPTION
            "Indicates the port ID."
        ::= { optixRtnMimo2P2GroupEntry 11 }

    -- 1.3.6.1.4.1.2011.2.25.4.40.6.10.250.1.12
    optixRtnPolar2P2 OBJECT-TYPE
        SYNTAX Unsigned32
        {
            h1(1),
            v1(2),
            h2(3),
            v2(4),
	    null(255)
        }
        MAX-ACCESS read-create
        STATUS current
        DESCRIPTION
            "Indicates the polarization direction.
	    1: h1
	    2: v1
	    3: h2
	    4: v2"
        ::= { optixRtnMimo2P2GroupEntry 12 }

    -- 1.3.6.1.4.1.2011.2.25.4.40.6.10.250.1.13
    optixRtnIfDelAdjNePg OBJECT-TYPE
        SYNTAX INTEGER
        {
            false(0),
            true(1)
        }
        MAX-ACCESS read-create
        STATUS current
        DESCRIPTION
            "Indicates whether to delete configurations of the adjacent NE.
	    0: false
	    1: true"
        ::= { optixRtnMimo2P2GroupEntry 13 }

    -- 1.3.6.1.4.1.2011.2.25.4.40.6.10.260
    optixRtnMimoOduTable OBJECT-TYPE
        SYNTAX SEQUENCE OF OptixRtnMimoOduEntry
        MAX-ACCESS not-accessible
        STATUS current
        DESCRIPTION
            "Indicates the configuration for ODUs in a MIMO work group"
        ::= { optixRtnMimoPara 260 }

    -- 1.3.6.1.4.1.2011.2.25.4.40.6.10.260.1
    optixRtnMimoOduEntry OBJECT-TYPE
        SYNTAX OptixRtnMimoOduEntry
        MAX-ACCESS not-accessible
        STATUS current
        DESCRIPTION
            "Indicates the configuration for ODUs in a MIMO work group"
        INDEX{ optixRtnMimoGroupNum }
        ::= { optixRtnMimoOduTable 1 }

    OptixRtnMimoOduEntry ::=
        SEQUENCE {
            optixRtnMimoGroupNum
                Unsigned32,
            optixRtnMimoOduMaxTSL
                Integer32,
            optixRtnMimoOduTxFreq
                Unsigned32,
            optixRtnMimoOduTxPower
                Integer32,
            optixRtnMimoOduWorkState
                INTEGER,
            optixRtnMimoOduTRSpacing
                Unsigned32
        }

    -- 1.3.6.1.4.1.2011.2.25.4.40.6.10.260.1.1
    optixRtnMimoGroupNum OBJECT-TYPE
        SYNTAX Unsigned32
        MAX-ACCESS not-accessible
        STATUS current
        DESCRIPTION
            "Indicates the MIMO work group ID."
        ::= { optixRtnMimoOduEntry 1 }

    -- 1.3.6.1.4.1.2011.2.25.4.40.6.10.260.1.2
    optixRtnMimoOduMaxTSL OBJECT-TYPE
        SYNTAX Integer32
        MAX-ACCESS read-create
        STATUS current
        DESCRIPTION
            "Indicates the maximum transmit power of an ODU."
        ::= { optixRtnMimoOduEntry 2 }

    -- 1.3.6.1.4.1.2011.2.25.4.40.6.10.260.1.3
    optixRtnMimoOduTxFreq OBJECT-TYPE
        SYNTAX Unsigned32
        MAX-ACCESS read-create
        STATUS current
        DESCRIPTION
            "Indicates the transmit frequency in the unit of KHz."
        ::= { optixRtnMimoOduEntry 3 }

    -- 1.3.6.1.4.1.2011.2.25.4.40.6.10.260.1.4
    optixRtnMimoOduTxPower OBJECT-TYPE
        SYNTAX Integer32
        MAX-ACCESS read-create
        STATUS current
        DESCRIPTION
            "Indicates the transmit power of the ODU."
        ::= { optixRtnMimoOduEntry 4 }

    -- 1.3.6.1.4.1.2011.2.25.4.40.6.10.260.1.5
    optixRtnMimoOduWorkState OBJECT-TYPE
        SYNTAX INTEGER
        {
            unmute(1),
            mute(0)
        }
        MAX-ACCESS read-create
        STATUS current
        DESCRIPTION
            "Indicates whether the ODU is muted or unmated."
        ::= { optixRtnMimoOduEntry 5 }

    -- 1.3.6.1.4.1.2011.2.25.4.40.6.10.260.1.6
    optixRtnMimoOduTRSpacing OBJECT-TYPE
        SYNTAX Unsigned32
        MAX-ACCESS read-create
        STATUS current
        DESCRIPTION
            "Indicates the T/R spacing for the ODU."
        ::= { optixRtnMimoOduEntry 6 }

    -- 1.3.6.1.4.1.2011.2.25.4.40.6.10.270
    optixRtnMimoIfAtribTable OBJECT-TYPE
        SYNTAX SEQUENCE OF OptixRtnMimoIfAtribEntry
        MAX-ACCESS not-accessible
        STATUS current
        DESCRIPTION
            "Indicates the configuration for a MIMO work group"
        ::= { optixRtnMimoPara 270 }

    -- 1.3.6.1.4.1.2011.2.25.4.40.6.10.270.1
    optixRtnMimoIfAtribEntry OBJECT-TYPE
        SYNTAX OptixRtnMimoIfAtribEntry
        MAX-ACCESS not-accessible
        STATUS current
        DESCRIPTION
            "Indicates the configuration for a MIMO work group"
        INDEX{ optixRtnGroupID }
        ::= { optixRtnMimoIfAtribTable 1 }

    OptixRtnMimoIfAtribEntry ::=
        SEQUENCE {
            optixRtnMimoGPIndex
                Unsigned32,
            optixRtnMimoBandWidth
                OPTIXRtnMimoBandWidthType,
            optixRtnMimoAcmEn
                INTEGER,
            optixRtnMimoBottomMod
                OPTIXRtnModulateModeType,
            optixRtnMimoPeakMod
                OPTIXRtnModulateModeType,
            optixRtnMimoManualMod
                OPTIXRtnModulateModeType,
            optixRtnMimoAtpcEn
                INTEGER
        }

    -- 1.3.6.1.4.1.2011.2.25.4.40.6.10.270.1.1
    optixRtnMimoGPIndex OBJECT-TYPE
        SYNTAX Unsigned32
        MAX-ACCESS not-accessible
        STATUS current
        DESCRIPTION
            "Indicates the MIMO work group ID."
        ::= { optixRtnMimoIfAtribEntry 1 }

    -- 1.3.6.1.4.1.2011.2.25.4.40.6.10.270.1.2
    optixRtnMimoBandWidth OBJECT-TYPE
        SYNTAX OPTIXRtnMimoBandWidthType
        MAX-ACCESS read-create
        STATUS current
        DESCRIPTION
            "Indicates the channel bandwidth."
        ::= { optixRtnMimoIfAtribEntry 2 }

    -- 1.3.6.1.4.1.2011.2.25.4.40.6.10.270.1.3
    optixRtnMimoAcmEn OBJECT-TYPE
        SYNTAX INTEGER
        {
            disable(0),
            enable(1)
        }
        MAX-ACCESS read-create
        STATUS current
        DESCRIPTION
            "Indicates whether the ACM function is enabled.
	    0: disable
	    1: enable
	    default:enable"
        ::= { optixRtnMimoIfAtribEntry 3 }

    -- 1.3.6.1.4.1.2011.2.25.4.40.6.10.270.1.4
    optixRtnMimoBottomMod OBJECT-TYPE
        SYNTAX OPTIXRtnModulateModeType
        MAX-ACCESS read-create
        STATUS current
        DESCRIPTION
            "Indicates the guaranteed-capacity mode."
        ::= { optixRtnMimoIfAtribEntry 4 }

    -- 1.3.6.1.4.1.2011.2.25.4.40.6.10.270.1.5
    optixRtnMimoPeakMod OBJECT-TYPE
        SYNTAX OPTIXRtnModulateModeType
        MAX-ACCESS read-create
        STATUS current
        DESCRIPTION
            "Indicates the full-capacity mode."
        ::= { optixRtnMimoIfAtribEntry 5 }

    -- 1.3.6.1.4.1.2011.2.25.4.40.6.10.270.1.6
    optixRtnMimoManualMod OBJECT-TYPE
        SYNTAX OPTIXRtnModulateModeType
        MAX-ACCESS read-create
        STATUS current
        DESCRIPTION
            "Indicate the manually-specified-capacity mode."
        ::= { optixRtnMimoIfAtribEntry 6 }

    -- 1.3.6.1.4.1.2011.2.25.4.40.6.10.270.1.7
    optixRtnMimoAtpcEn OBJECT-TYPE
        SYNTAX INTEGER
        {
            disable(0),
            enable(1)
        }
        MAX-ACCESS read-create
        STATUS current
        DESCRIPTION
            "Indicates whether the ATPC function is enabled in a MIMO work group.
	    0: Disable
	    1: Enable"
        ::= { optixRtnMimoIfAtribEntry 7 }

    -- 1.3.6.1.4.1.2011.2.25.4.40.6.10.290
    optixRtnMimoXPITable OBJECT-TYPE
        SYNTAX SEQUENCE OF OptixRtnMimoXPIEntry
        MAX-ACCESS not-accessible
        STATUS current
        DESCRIPTION
            "Indicates to query the XPI value"
        ::= { optixRtnMimoPara 290 }

    -- 1.3.6.1.4.1.2011.2.25.4.40.6.10.290.1
    optixRtnMimoXPIEntry OBJECT-TYPE
        SYNTAX OptixRtnMimoXPIEntry
        MAX-ACCESS not-accessible
        STATUS current
        DESCRIPTION
            "Indicates to query the XPI value"
        INDEX{ optixRtnGroupID }
        ::= { optixRtnMimoXPITable 1 }

    OptixRtnMimoXPIEntry ::=
        SEQUENCE {
            optixRtnXPIBoardID
                Unsigned32,
            optixRtnOffsideNeID
                Unsigned32,
            optixRtnOffsideNeBid
                Unsigned32,
            optixRtnXPIValue
                OCTET STRING
        }

    -- 1.3.6.1.4.1.2011.2.25.4.40.6.10.290.1.1
    optixRtnXPIBoardID OBJECT-TYPE
        SYNTAX Unsigned32
        MAX-ACCESS read-write
        STATUS current
        DESCRIPTION
            "Indicates the slot ID."
        ::= { optixRtnMimoXPIEntry 1 }

    -- 1.3.6.1.4.1.2011.2.25.4.40.6.10.290.1.2
    optixRtnOffsideNeID OBJECT-TYPE
        SYNTAX Unsigned32
        MAX-ACCESS read-write
        STATUS current
        DESCRIPTION
            "Indicates the peer NE ID."
        ::= { optixRtnMimoXPIEntry 2 }

    -- 1.3.6.1.4.1.2011.2.25.4.40.6.10.290.1.3
    optixRtnOffsideNeBid OBJECT-TYPE
        SYNTAX Unsigned32
        MAX-ACCESS read-write
        STATUS current
        DESCRIPTION
            "Indicates the slot ID of a board on the peer NE."
        ::= { optixRtnMimoXPIEntry 3 }

    -- 1.3.6.1.4.1.2011.2.25.4.40.6.10.290.1.4
    optixRtnXPIValue OBJECT-TYPE
        SYNTAX OCTET STRING
        MAX-ACCESS read-only
        STATUS current
        DESCRIPTION
            "Indicates the XPI value"
        ::= { optixRtnMimoXPIEntry 4 }

    -- 1.3.6.1.4.1.2011.2.25.4.40.6.10.300
    optixRtnMimo2P2SyncCfgTable OBJECT-TYPE
        SYNTAX SEQUENCE OF OptixRtnMimo2P2SyncCfgEntry
        MAX-ACCESS not-accessible
        STATUS current
        DESCRIPTION
            "Indicates to synchronize MIMO configurations of the local NE to the adjacent NE"
        ::= { optixRtnMimoPara 300 }

    -- 1.3.6.1.4.1.2011.2.25.4.40.6.10.300.1
    optixRtnMimo2P2SyncCfgEntry OBJECT-TYPE
        SYNTAX OptixRtnMimo2P2SyncCfgEntry
        MAX-ACCESS not-accessible
        STATUS current
        DESCRIPTION
            "Indicates to synchronize MIMO configurations of the local NE to the adjacent NE"
        INDEX{ optixRtn2P2SyncCfgGroupID }
        ::= { optixRtnMimo2P2SyncCfgTable 1 }

    OptixRtnMimo2P2SyncCfgEntry ::=
        SEQUENCE {
            optixRtn2P2SyncCfgGroupID
                Unsigned32,
            optixRtnSyncCfgBoardID
                Unsigned32,
            optixRtnSyncCfgSubCardID
                Unsigned32,
            optixRtnSyncCfgPortID
                Unsigned32,
            optixRtnSyncCfgPolar
                INTEGER
        }

    -- 1.3.6.1.4.1.2011.2.25.4.40.6.10.300.1.1
    optixRtn2P2SyncCfgGroupID OBJECT-TYPE
        SYNTAX Unsigned32
        MAX-ACCESS not-accessible
        STATUS current
        DESCRIPTION
            "Indicates the MIMO work group ID."
        ::= { optixRtnMimo2P2SyncCfgEntry 1 }

    -- 1.3.6.1.4.1.2011.2.25.4.40.6.10.300.1.2
    optixRtnSyncCfgBoardID OBJECT-TYPE
        SYNTAX Unsigned32
        MAX-ACCESS read-create
        STATUS current
        DESCRIPTION
            "Indicates the slot ID."
        ::= { optixRtnMimo2P2SyncCfgEntry 2 }

    -- 1.3.6.1.4.1.2011.2.25.4.40.6.10.300.1.3
    optixRtnSyncCfgSubCardID OBJECT-TYPE
        SYNTAX Unsigned32
        MAX-ACCESS read-create
        STATUS current
        DESCRIPTION
            "Indicates the subboard ID."
        ::= { optixRtnMimo2P2SyncCfgEntry 3 }

    -- 1.3.6.1.4.1.2011.2.25.4.40.6.10.300.1.4
    optixRtnSyncCfgPortID OBJECT-TYPE
        SYNTAX Unsigned32
        MAX-ACCESS read-create
        STATUS current
        DESCRIPTION
            "Indicates the port ID."
        ::= { optixRtnMimo2P2SyncCfgEntry 4 }

    -- 1.3.6.1.4.1.2011.2.25.4.40.6.10.300.1.5
    optixRtnSyncCfgPolar OBJECT-TYPE
        SYNTAX INTEGER
        {
            h1(1),
            v1(2),
            h2(3),
            v2(4)
        }
        MAX-ACCESS read-create
        STATUS current
        DESCRIPTION
            "Indicates the polarization direction.
	    1: h1
	    2: v1
	    3: h2
	    4: v2"
        ::= { optixRtnMimo2P2SyncCfgEntry 5 }

    -- 1.3.6.1.4.1.2011.2.25.4.40.6.10.310
    optixRtnMimo4P4SyncCfgTable OBJECT-TYPE
        SYNTAX SEQUENCE OF OptixRtnMimo4P4SyncCfgEntry
        MAX-ACCESS not-accessible
        STATUS current
        DESCRIPTION
            "Indicates to synchronize MIMO configurations of the local NE to the adjacent NE"
        ::= { optixRtnMimoPara 310 }

    -- 1.3.6.1.4.1.2011.2.25.4.40.6.10.310.1
    optixRtnMimo4P4SyncCfgEntry OBJECT-TYPE
        SYNTAX OptixRtnMimo4P4SyncCfgEntry
        MAX-ACCESS not-accessible
        STATUS current
        DESCRIPTION
            "Indicates to synchronize MIMO configurations of the local NE to the adjacent NE"
        INDEX{ optixRtn2P2SyncCfgGroupID }
        ::= { optixRtnMimo4P4SyncCfgTable 1 }

    OptixRtnMimo4P4SyncCfgEntry ::=
        SEQUENCE {
            optixRtn4P4SyncCfgGroupID
                Unsigned32,
            optixRtnSyncCfgBoardID2P1
                Unsigned32,
            optixRtnSyncCfgSubCardID2P1
                Unsigned32,
            optixRtnSyncCfgPortID2P1
                Unsigned32,
            optixRtnSyncCfgPolar2P1
                INTEGER,
            optixRtnSyncCfgBoardID2P2
                Unsigned32,
            optixRtnSyncCfgSubCardID2P2
                Unsigned32,
            optixRtnSyncCfgPortID2P2
                Unsigned32,
            optixRtnSyncCfgPolar2P2
                INTEGER
        }

    -- 1.3.6.1.4.1.2011.2.25.4.40.6.10.310.1.1
    optixRtn4P4SyncCfgGroupID OBJECT-TYPE
        SYNTAX Unsigned32
        MAX-ACCESS not-accessible
        STATUS current
        DESCRIPTION
            "Indicates the MIMO work group ID."
        ::= { optixRtnMimo4P4SyncCfgEntry 1 }

    -- 1.3.6.1.4.1.2011.2.25.4.40.6.10.310.1.2
    optixRtnSyncCfgBoardID2P1 OBJECT-TYPE
        SYNTAX Unsigned32
        MAX-ACCESS read-create
        STATUS current
        DESCRIPTION
            "Indicates the slot ID."
        ::= { optixRtnMimo4P4SyncCfgEntry 2 }

    -- 1.3.6.1.4.1.2011.2.25.4.40.6.10.310.1.3
    optixRtnSyncCfgSubCardID2P1 OBJECT-TYPE
        SYNTAX Unsigned32
        MAX-ACCESS read-create
        STATUS current
        DESCRIPTION
            "Indicates the subboard ID."
        ::= { optixRtnMimo4P4SyncCfgEntry 3 }

    -- 1.3.6.1.4.1.2011.2.25.4.40.6.10.310.1.4
    optixRtnSyncCfgPortID2P1 OBJECT-TYPE
        SYNTAX Unsigned32
        MAX-ACCESS read-create
        STATUS current
        DESCRIPTION
            "Indicates the port ID."
        ::= { optixRtnMimo4P4SyncCfgEntry 4 }

    -- 1.3.6.1.4.1.2011.2.25.4.40.6.10.310.1.5
    optixRtnSyncCfgPolar2P1 OBJECT-TYPE
        SYNTAX INTEGER
        {
            h1(1),
            v1(2),
            h2(3),
            v2(4)
        }
        MAX-ACCESS read-create
        STATUS current
        DESCRIPTION
            "Indicates the polarization direction.
	    1: h1
	    2: v1
	    3: h2
	    4: v2"
        ::= { optixRtnMimo4P4SyncCfgEntry 5 }

    -- 1.3.6.1.4.1.2011.2.25.4.40.6.10.310.1.6
    optixRtnSyncCfgBoardID2P2 OBJECT-TYPE
        SYNTAX Unsigned32
        MAX-ACCESS read-create
        STATUS current
        DESCRIPTION
            "Indicates the slot ID."
        ::= { optixRtnMimo4P4SyncCfgEntry 6 }

    -- 1.3.6.1.4.1.2011.2.25.4.40.6.10.310.1.7
    optixRtnSyncCfgSubCardID2P2 OBJECT-TYPE
        SYNTAX Unsigned32
        MAX-ACCESS read-create
        STATUS current
        DESCRIPTION
            "Indicates the subboard ID."
        ::= { optixRtnMimo4P4SyncCfgEntry 7 }

    -- 1.3.6.1.4.1.2011.2.25.4.40.6.10.310.1.8
    optixRtnSyncCfgPortID2P2 OBJECT-TYPE
        SYNTAX Unsigned32
        MAX-ACCESS read-create
        STATUS current
        DESCRIPTION
            "Indicates the port ID."
        ::= { optixRtnMimo4P4SyncCfgEntry 8 }

    -- 1.3.6.1.4.1.2011.2.25.4.40.6.10.310.1.9
    optixRtnSyncCfgPolar2P2 OBJECT-TYPE
        SYNTAX INTEGER
        {
            h1(1),
            v1(2),
            h2(3),
            v2(4)
        }
        MAX-ACCESS read-create
        STATUS current
        DESCRIPTION
            "Indicates the polarization direction.
	    1: h1
	    2: v1
	    3: h2
	    4: v2"
        ::= { optixRtnMimo4P4SyncCfgEntry 9 }

    -- 1.3.6.1.4.1.2011.2.25.4.40.6.10.320
    optixRtnMimoAdjoinNeinfoTable OBJECT-TYPE
        SYNTAX SEQUENCE OF OptixRtnMimoAdjoinNeinfoEntry
        MAX-ACCESS not-accessible
        STATUS current
        DESCRIPTION
            "Indicates to query the cascading NEs in a MIMO work group"
        ::= { optixRtnMimoPara 320 }

    -- 1.3.6.1.4.1.2011.2.25.4.40.6.10.320.1
    optixRtnMimoAdjoinNeinfoEntry OBJECT-TYPE
        SYNTAX OptixRtnMimoAdjoinNeinfoEntry
        MAX-ACCESS not-accessible
        STATUS current
        DESCRIPTION
            "Indicates to query the cascading NEs in a MIMO work group"
        INDEX{ optixRtnMimoBid,optixRtnMimoSubid, optixRtnMimoPortid }
        ::= { optixRtnMimoAdjoinNeinfoTable 1 }

    OptixRtnMimoAdjoinNeinfoEntry ::=
        SEQUENCE {
            optixRtnMimoNeighbourNeID
                Unsigned32,
            optixRtnMimoNeighbourNEName
                OCTET STRING,
            optixRtnMimoNeighbourNEBoardType
                OPTIXRtnBoardType
            
        }

    -- 1.3.6.1.4.1.2011.2.25.4.40.6.10.320.1.1
    optixRtnMimoNeighbourNeID OBJECT-TYPE
        SYNTAX Unsigned32
        MAX-ACCESS read-only
        STATUS current
        DESCRIPTION
            "Indicates the ID of the adjacent NE"
        ::= { optixRtnMimoAdjoinNeinfoEntry 1 }

    -- 1.3.6.1.4.1.2011.2.25.4.40.6.10.320.1.2
    optixRtnMimoNeighbourNEName OBJECT-TYPE
        SYNTAX OCTET STRING
        MAX-ACCESS read-only
        STATUS current
        DESCRIPTION
            "Indicates the name of the adjacent NE"
        ::= { optixRtnMimoAdjoinNeinfoEntry 2 }

    -- 1.3.6.1.4.1.2011.2.25.4.40.6.10.320.1.3
    optixRtnMimoNeighbourNEBoardType OBJECT-TYPE
        SYNTAX OPTIXRtnBoardType
        MAX-ACCESS read-only
        STATUS current
        DESCRIPTION
            "Indicates board type of the adjacent NE"
        ::= { optixRtnMimoAdjoinNeinfoEntry 3 }

    -- 1.3.6.1.4.1.2011.2.25.4.40.6.10.321
    optixRtnMimoAdjoinExtNeinfoTable OBJECT-TYPE
        SYNTAX SEQUENCE OF OptixRtnMimoAdjoinExtNeinfoEntry
        MAX-ACCESS not-accessible
        STATUS current
        DESCRIPTION
            "Indicates to query the cascading NEs in a MIMO work group"
        ::= { optixRtnMimoPara 321 }

    -- 1.3.6.1.4.1.2011.2.25.4.40.6.10.321.1
    optixRtnMimoAdjoinExtNeinfoEntry OBJECT-TYPE
        SYNTAX OptixRtnMimoAdjoinExtNeinfoEntry
        MAX-ACCESS not-accessible
        STATUS current
        DESCRIPTION
            "Indicates to query the cascading NEs in a MIMO work group"
        INDEX{ optixRtnMimoGroupID }
        ::= { optixRtnMimoAdjoinExtNeinfoTable 1 }

    OptixRtnMimoAdjoinExtNeinfoEntry ::=
        SEQUENCE {
            optixRtnMimoGroupID
                INTEGER,
	       optixRtnMimoNeBoardID
                Unsigned32,
            optixRtnMimoNeSubCardID
                Unsigned32,
            optixRtnMimoNePortID
                Unsigned32,	
            optixRtnMimoNeighbourNeId
                Unsigned32,
            optixRtnMimoNeighbourNeName
                OCTET STRING,
            optixRtnMimoNeighbourNeBoardType
                OPTIXRtnBoardType,		
	    optixRtnMimoNeighbourNeADJID
                Unsigned32,		
            optixRtnMimoNeighbourNeBoardID
                Unsigned32,
            optixRtnMimoNeighbourNeSubCardID
                Unsigned32,
            optixRtnMimoNeighbourNePortID
                Unsigned32
        }

    -- 1.3.6.1.4.1.2011.2.25.4.40.6.10.321.1.1
    optixRtnMimoGroupID OBJECT-TYPE
        SYNTAX INTEGER
        {
            master(1),
            slave(2)
        }
        MAX-ACCESS not-accessible
        STATUS current
        DESCRIPTION
            "Indicates the MIMO work group ID."
        ::= { optixRtnMimoAdjoinExtNeinfoEntry 1 }
	
    -- 1.3.6.1.4.1.2011.2.25.4.40.6.10.321.1.2
    optixRtnMimoNeBoardID OBJECT-TYPE
        SYNTAX Unsigned32
        MAX-ACCESS read-only
        STATUS current
        DESCRIPTION
            "Indicates the slot ID of the  NE"
        ::= { optixRtnMimoAdjoinExtNeinfoEntry 2}

    -- 1.3.6.1.4.1.2011.2.25.4.40.6.10.321.1.3
    optixRtnMimoNeSubCardID OBJECT-TYPE
        SYNTAX Unsigned32
        MAX-ACCESS read-only
        STATUS current
        DESCRIPTION
            "Indicates the subboard ID of the  NE"
        ::= { optixRtnMimoAdjoinExtNeinfoEntry 3}

    -- 1.3.6.1.4.1.2011.2.25.4.40.6.10.321.1.4
    optixRtnMimoNePortID OBJECT-TYPE
        SYNTAX Unsigned32
        MAX-ACCESS read-only
        STATUS current
        DESCRIPTION
            "Indicates the port ID of the  NE"
        ::= { optixRtnMimoAdjoinExtNeinfoEntry 4 }
	
    -- 1.3.6.1.4.1.2011.2.25.4.40.6.10.321.1.5
    optixRtnMimoNeighbourNeId OBJECT-TYPE
        SYNTAX Unsigned32
        MAX-ACCESS read-only
        STATUS current
        DESCRIPTION
            "Indicates the ID of the adjacent NE"
        ::= { optixRtnMimoAdjoinExtNeinfoEntry 5 }

    -- 1.3.6.1.4.1.2011.2.25.4.40.6.10.321.1.6
    optixRtnMimoNeighbourNeName OBJECT-TYPE
        SYNTAX OCTET STRING
        MAX-ACCESS read-only
        STATUS current
        DESCRIPTION
            "Indicates the name of the adjacent NE"
        ::= { optixRtnMimoAdjoinExtNeinfoEntry 6 }

    -- 1.3.6.1.4.1.2011.2.25.4.40.6.10.321.1.7
    optixRtnMimoNeighbourNeBoardType OBJECT-TYPE
        SYNTAX OPTIXRtnBoardType
        MAX-ACCESS read-only
        STATUS current
        DESCRIPTION
            "Indicates board type of the adjacent NE"
        ::= { optixRtnMimoAdjoinExtNeinfoEntry 7 }
		
    -- 1.3.6.1.4.1.2011.2.25.4.40.6.10.321.1.8
    optixRtnMimoNeighbourNeADJID OBJECT-TYPE
        SYNTAX Unsigned32
        MAX-ACCESS read-only
        STATUS current
        DESCRIPTION
            "Indicates the mimo ID of the adjacent NE"
        ::= { optixRtnMimoAdjoinExtNeinfoEntry 8 }
	
    -- 1.3.6.1.4.1.2011.2.25.4.40.6.10.321.1.9
    optixRtnMimoNeighbourNeBoardID OBJECT-TYPE
        SYNTAX Unsigned32
        MAX-ACCESS read-only
        STATUS current
        DESCRIPTION
            "Indicates the slot ID of the adjacent NE"
        ::= { optixRtnMimoAdjoinExtNeinfoEntry 9 }

    -- 1.3.6.1.4.1.2011.2.25.4.40.6.10.321.1.10
    optixRtnMimoNeighbourNeSubCardID OBJECT-TYPE
        SYNTAX Unsigned32
        MAX-ACCESS read-only
        STATUS current
        DESCRIPTION
            "Indicates the subboard ID of the adjacent NE"
        ::= { optixRtnMimoAdjoinExtNeinfoEntry 10}

    -- 1.3.6.1.4.1.2011.2.25.4.40.6.10.321.1.11
    optixRtnMimoNeighbourNePortID OBJECT-TYPE
        SYNTAX Unsigned32
        MAX-ACCESS read-only
        STATUS current
        DESCRIPTION
            "Indicates the port ID of the adjacent NE"
        ::= { optixRtnMimoAdjoinExtNeinfoEntry 11}

    -- 1.3.6.1.4.1.2011.2.25.4.40.6.10.330
    optixRtnMimoXPIExtTable OBJECT-TYPE
        SYNTAX SEQUENCE OF OptixRtnMimoXPIExtEntry
        MAX-ACCESS not-accessible
        STATUS current
        DESCRIPTION
            "Indicates to query the XPI value"
        ::= { optixRtnMimoPara 330 }

    -- 1.3.6.1.4.1.2011.2.25.4.40.6.10.330.1
    optixRtnMimoXPIExtEntry OBJECT-TYPE
        SYNTAX OptixRtnMimoXPIExtEntry
        MAX-ACCESS not-accessible
        STATUS current
        DESCRIPTION
            "Indicates to query the XPI value"
        INDEX{ optixRtnGroupID }
        ::= { optixRtnMimoXPIExtTable 1 }

    OptixRtnMimoXPIExtEntry ::=
        SEQUENCE {
            optixRtnXPIExtBoardIDIndex
                Unsigned32,
            optixRtnXPIValueExt
                OCTET STRING
        }

    -- 1.3.6.1.4.1.2011.2.25.4.40.6.10.330.1.1
    optixRtnXPIExtBoardIDIndex OBJECT-TYPE
        SYNTAX Unsigned32
        MAX-ACCESS not-accessible
        STATUS current
        DESCRIPTION
            "Indicates the slot ID."
        ::= { optixRtnMimoXPIExtEntry 1 }

    -- 1.3.6.1.4.1.2011.2.25.4.40.6.10.330.1.2
    optixRtnXPIValueExt OBJECT-TYPE
        SYNTAX OCTET STRING
        MAX-ACCESS read-only
        STATUS current
        DESCRIPTION
            "Indicates the XPI Ext value"
        ::= { optixRtnMimoXPIExtEntry 2}

END
