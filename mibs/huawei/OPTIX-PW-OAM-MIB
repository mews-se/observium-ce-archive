-- OPTIX-PW-OAM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PW-OAM-MIB DEFINITIONS ::= BEGIN
    IMPORTS
        OBJECT-GROUP,MODULE-COMPLIANCE
            FROM SNMPv2-CONF
        MODULE-IDENTITY,OBJECT-TYPE,Unsigned32,Integer32,IpAddress
            FROM SNMPv2-SMI
        RowStatus
            FROM SNMPv2-TC
        optixProvisionPtn
            FROM OPTIX-OID-MIB
        ;

    optixPWOamMod MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage the MPLS PW OAM. The PW OAM provides complete fault detection and identification mechanism and network performance monitoringat the PW layer. Based on the OAM check result, the equipment determines whether to trigger protection switching. The PW OAM enables quick faultdetection and identificationand service protection."
        REVISION "201204170000Z"
        DESCRIPTION
            "Initial version of this MIB module"
        ::={ optixProvisionPtn 7 }

    -- 1.3.6.1.4.1.2011.2.25.4.50.7.1
    optixPWOamObject OBJECT IDENTIFIER ::= { optixPWOamMod 1 }

    -- 1.3.6.1.4.1.2011.2.25.4.50.7.1.1
    optixPWOamTable OBJECT-TYPE
        SYNTAX SEQUENCE OF OptixPWOamEntry
        MAX-ACCESS not-accessible
        STATUS current
        DESCRIPTION
            "Thistable is used to configure PW OAM attributes, including the PW OAM enable status, detection mode, CC detection mode, and SD/SF thresholds."
        ::= { optixPWOamObject 1 }

    -- 1.3.6.1.4.1.2011.2.25.4.50.7.1.1.1
    optixPWOamEntry OBJECT-TYPE
        SYNTAX OptixPWOamEntry
        MAX-ACCESS not-accessible
        STATUS current
        DESCRIPTION
            "Thisentry is used to manage PW OAM attributes."
        INDEX{ optixPWOamIndex }
        ::= { optixPWOamTable 1 }

    OptixPWOamEntry ::=
        SEQUENCE {
            optixPWOamIndex
                Unsigned32,
            optixPWOamEnable
                INTEGER,
            optixPWOamCheckWay
                INTEGER,
            optixPWOamCcType
                INTEGER,
            optixPWOamCcTime
                Unsigned32,
            optixPWOamSf
                Unsigned32,
            optixPWOamSd
                Unsigned32,
            optixPWOamPeerLsrId
                IpAddress,
            optixPWOamPeerPwId
                Unsigned32,
            optixPWOamStandard
                INTEGER
        }

    -- 1.3.6.1.4.1.2011.2.25.4.50.7.1.1.1.1
    optixPWOamIndex OBJECT-TYPE
        SYNTAX Unsigned32
        MAX-ACCESS not-accessible
        STATUS current
        DESCRIPTION
            "This object indicates the PW OAM index, ranging from 1 to 0x00ffffff."
        ::= { optixPWOamEntry 1 }

    -- 1.3.6.1.4.1.2011.2.25.4.50.7.1.1.1.2
    optixPWOamEnable OBJECT-TYPE
        SYNTAX INTEGER
        {
            disable(0),
            enable(1)
        }
        MAX-ACCESS read-write
        STATUS current
        DESCRIPTION
            "This object indicates whether the OAM is enabled. 1: enable 0: disable"
        DEFVAL{ 0 }
        ::= { optixPWOamEntry 2 }

    -- 1.3.6.1.4.1.2011.2.25.4.50.7.1.1.1.3
    optixPWOamCheckWay OBJECT-TYPE
        SYNTAX INTEGER
        {
            auto(1),
            manual(2)
        }
        MAX-ACCESS read-write
        STATUS current
        DESCRIPTION
            "This object indicates the OAM detection mode. 1: auto 2: manual"
        DEFVAL{ 1 }
        ::= { optixPWOamEntry 3 }

    -- 1.3.6.1.4.1.2011.2.25.4.50.7.1.1.1.4
    optixPWOamCcType OBJECT-TYPE
        SYNTAX INTEGER
        {
            cv(1),
            ffd(2)
        }
        MAX-ACCESS read-write
        STATUS current
        DESCRIPTION
            "This object indicates the CC detection packet type. 1: cv (default value) 2: ffd"
        DEFVAL{ 1 }
        ::= { optixPWOamEntry 4 }

    -- 1.3.6.1.4.1.2011.2.25.4.50.7.1.1.1.5
    optixPWOamCcTime OBJECT-TYPE
        SYNTAX Unsigned32(1..7|255)
        MAX-ACCESS read-write
        STATUS current
        DESCRIPTION
            "This object indicates the CC detection packet frequency. When the packet type is cv, the frequency is an invalid value, 0xff. When the packet type is ffd, the valid value of the frequency is as follows: 1: 3.3 ms 2: 10 ms 3: 20 ms 4: 50 ms 5: 100 ms 6: 200 ms 7: 500 ms"
        DEFVAL{ 255 }
        ::= { optixPWOamEntry 5 }

    -- 1.3.6.1.4.1.2011.2.25.4.50.7.1.1.1.6
    optixPWOamSf OBJECT-TYPE
        SYNTAX Unsigned32(0..255)
        MAX-ACCESS read-write
        STATUS current
        DESCRIPTION
            "This object indicates the SF threshold (packet loss rate). Valid values range from 0 to 100."
        DEFVAL{ 0 }
        ::= { optixPWOamEntry 6 }

    -- 1.3.6.1.4.1.2011.2.25.4.50.7.1.1.1.7
    optixPWOamSd OBJECT-TYPE
        SYNTAX Unsigned32(0..255)
        MAX-ACCESS read-write
        STATUS current
        DESCRIPTION
            "This object indicates the SD threshold (packet loss rate). Valid values range from 0 to 100."
        DEFVAL{ 0 }
        ::= { optixPWOamEntry 7 }

    -- 1.3.6.1.4.1.2011.2.25.4.50.7.1.1.1.8
    optixPWOamPeerLsrId OBJECT-TYPE
        SYNTAX IpAddress
        MAX-ACCESS read-write
        STATUS current
        DESCRIPTION
            "This object indicates the LSR ID to receive, which is the LSR ID of the valid MPLS device. 0.0.0.0: indicates that the peer IP address of the local PW is automatically obtained."
        DEFVAL{ 0 }
        ::= { optixPWOamEntry 8 }

    -- 1.3.6.1.4.1.2011.2.25.4.50.7.1.1.1.9
    optixPWOamPeerPwId OBJECT-TYPE
        SYNTAX Unsigned32
        MAX-ACCESS read-write
        STATUS current
        DESCRIPTION
            "This object indicates the remote PW ID, which is a valid MPLS PW ID. 0: indicates that the ID of the local PW is automatically obtained."
        DEFVAL{ 0 }
        ::= { optixPWOamEntry 9 }

    -- 1.3.6.1.4.1.2011.2.25.4.50.7.1.1.1.10
    optixPWOamStandard OBJECT-TYPE
        SYNTAX INTEGER
        {
            y1711(1),
            y1731(2)
        }
        MAX-ACCESS read-write
        STATUS current
        DESCRIPTION
            "This object indicates the OAM protocol standard&amp;nbsp; 1: 1711 2: 1731"
        DEFVAL{ 1 }
        ::= { optixPWOamEntry 10 }

    -- 1.3.6.1.4.1.2011.2.25.4.50.7.1.2
    optixPWOamStateTable OBJECT-TYPE
        SYNTAX SEQUENCE OF OptixPWOamStateEntry
        MAX-ACCESS not-accessible
        STATUS current
        DESCRIPTION
            "Thistable is used to query the PW OAM status."
        ::= { optixPWOamObject 2 }

    -- 1.3.6.1.4.1.2011.2.25.4.50.7.1.2.1
    optixPWOamStateEntry OBJECT-TYPE
        SYNTAX OptixPWOamStateEntry
        MAX-ACCESS not-accessible
        STATUS current
        DESCRIPTION
            "Thisentry is used to manage the PW OAM status."
        INDEX{ optixPWOamIndex,optixPWOamDirection }
        ::= { optixPWOamStateTable 1 }

    OptixPWOamStateEntry ::=
        SEQUENCE {
            optixPWOamDirection
                INTEGER,
            optixPWOamState
                INTEGER,
            optixPWOamDefectType
                INTEGER,
            optixPWOamUnavailableTime
                Unsigned32,
            optixPWOamDefectPosition
                IpAddress
        }

    -- 1.3.6.1.4.1.2011.2.25.4.50.7.1.2.1.1
    optixPWOamDirection OBJECT-TYPE
        SYNTAX INTEGER
        {
            farend(0),
            nearend(1)
        }
        MAX-ACCESS not-accessible
        STATUS current
        DESCRIPTION
            "For bidirectional MPLS PWs, the status query is performed in two directions, local and remote ends. This object indicates the direction of the PW OAM. The status query is performed in single direction: local or remote end."
        ::= { optixPWOamStateEntry 1 }

    -- 1.3.6.1.4.1.2011.2.25.4.50.7.1.2.1.2
    optixPWOamState OBJECT-TYPE
        SYNTAX INTEGER
        {
            initialstate(0),
            nearendavailable(1),
            nearenddefectavailable(2),
            nearenddefectunavailable(3),
            nearendunavailable(4),
            farendavailable(5),
            farenddefectavailable(6),
            farenddefectunavailable(7),
            farendunavailable(8)
        }
        MAX-ACCESS read-only
        STATUS current
        DESCRIPTION
            "This object indicates the PW OAM status. 0: initialstate, 1: nearendavailable, 2: nearenddefectavailable, 3: nearenddefectunavailable, 4: nearendunavailable, 5: farendavailable, 6: farenddefectavailable, 7: farenddefectunavailable, 8: farendunavailable"
        ::= { optixPWOamStateEntry 2 }

    -- 1.3.6.1.4.1.2011.2.25.4.50.7.1.2.1.3
    optixPWOamDefectType OBJECT-TYPE
        SYNTAX INTEGER
        {
            dserver(1),
            dpeerme(2),
            dlocv(3),
            dttsimismatch(4),
            dttsimismerge(5),
            dexcess(6),
            dunknown(7),
            invalid(255)
        }
        MAX-ACCESS read-only
        STATUS current
        DESCRIPTION
            "This object indicates the defect type of the PW OAM. 1: dserver, 2: dpeerme, 3: dlocv, 4: dttsimismatch, 5: dttsimismerge, 6: dexcess, 7: dunknown, 255: invalid"
        ::= { optixPWOamStateEntry 3 }

    -- 1.3.6.1.4.1.2011.2.25.4.50.7.1.2.1.4
    optixPWOamUnavailableTime OBJECT-TYPE
        SYNTAX Unsigned32
        MAX-ACCESS read-only
        STATUS current
        DESCRIPTION
            "This object indicates the unavailable time of the PW OAM. The time ranges from 0 to 300,000 ms. 4294967295: invalid"
        ::= { optixPWOamStateEntry 4 }

    -- 1.3.6.1.4.1.2011.2.25.4.50.7.1.2.1.5
    optixPWOamDefectPosition OBJECT-TYPE
        SYNTAX IpAddress
        MAX-ACCESS read-only
        STATUS current
        DESCRIPTION
            "This object indicates the position of the PW OAM defect: a node identified by IP address."
        ::= { optixPWOamStateEntry 5 }

END
