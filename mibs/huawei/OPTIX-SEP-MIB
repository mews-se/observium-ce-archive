-- OPTIX-SEP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SEP-MIB DEFINITIONS ::= BEGIN
    IMPORTS
        optixProvisionPtn
            FROM OPTIX-OID-MIB
        OBJECT-GROUP,MODULE-COMPLIANCE
            FROM SNMPv2-CONF
        MODULE-IDENTITY,OBJECT-TYPE,Unsigned32,NOTIFICATION-TYPE,Integer32
            FROM SNMPv2-SMI
        RowStatus
            FROM SNMPv2-TC
        ;

    optixSEPMod MODULE-IDENTITY
        LAST-UPDATED "201704111545Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes SEP information, including SEP configurations, SEP port information, and SEP topology information."
        REVISION "201704111545Z"
        DESCRIPTION
            "Initial version of this MIB module."
        ::={ optixProvisionPtn 36 }

    -- 1.3.6.1.4.1.2011.2.25.4.50.36.1
    optixSEPObject OBJECT IDENTIFIER ::= { optixSEPMod 1 }

    -- 1.3.6.1.4.1.2011.2.25.4.50.36.1.1
    optixSEPConfigInfoTable OBJECT-TYPE
        SYNTAX SEQUENCE OF OptixSEPConfigInfoEntry
        MAX-ACCESS not-accessible
        STATUS current
        DESCRIPTION
            "This table contains configuration information of SEP."
        ::= { optixSEPObject 1 }

    -- 1.3.6.1.4.1.2011.2.25.4.50.36.1.1.1
    optixSEPConfigInfoEntry OBJECT-TYPE
        SYNTAX OptixSEPConfigInfoEntry
        MAX-ACCESS not-accessible
        STATUS current
        DESCRIPTION
            "This entry contains configuration information of SEP."
        INDEX{ optixSEPID }
        ::= { optixSEPConfigInfoTable 1 }

    OptixSEPConfigInfoEntry ::=
        SEQUENCE {
            optixSEPID
                Unsigned32,
            optixSEPCtrVlan
                Unsigned32,
            optixSEPSrvVlanNum
                Unsigned32,
            optixSEPSrvVlanList
                OCTET STRING,
            optixSEPPreemtMode
                INTEGER,
            optixSEPDelayTime
                Unsigned32,
            optixSEPTCInterval
                Unsigned32,
            optixSEPTCNotifyNum
                Unsigned32,
            optixSEPTCNotifyList
                OCTET STRING,
            optixSEPAuthenType
                INTEGER,
            optixSEPAuthenPwd
                OCTET STRING,
            optixSEPBlockMode
                INTEGER,
            optixSEPBlockPortHop
                Unsigned32,
            optixSEPBlockPortSysName
                OCTET STRING,
            optixSEPBlockPortName
                OCTET STRING,
            optixSEPName
                OCTET STRING,
            optixSEPClearPKTCount
                INTEGER,
            optixSEPAddVlanList
                OCTET STRING,
            optixSEPDelVlanList
                OCTET STRING,
            optixSEPSetSysNameType
                Integer32
        }

    -- 1.3.6.1.4.1.2011.2.25.4.50.36.1.1.1.1
    optixSEPID OBJECT-TYPE
        SYNTAX Unsigned32
        MAX-ACCESS not-accessible
        STATUS current
        DESCRIPTION
            "This node indicates the SEP protection ID."
        ::= { optixSEPConfigInfoEntry 1 }

    -- 1.3.6.1.4.1.2011.2.25.4.50.36.1.1.1.2
    optixSEPCtrVlan OBJECT-TYPE
        SYNTAX Unsigned32
        MAX-ACCESS read-write
        STATUS current
        DESCRIPTION
            "This node indicates the SEP control VLAN ID, which ranges from 1 to 4094 and must be different from service VLAN IDs."
        ::= { optixSEPConfigInfoEntry 2 }

    -- 1.3.6.1.4.1.2011.2.25.4.50.36.1.1.1.3
    optixSEPSrvVlanNum OBJECT-TYPE
        SYNTAX Unsigned32
        MAX-ACCESS read-write
        STATUS current
        DESCRIPTION
            "This node indicates the SEP service VLAN quantity, which ranges from 0 to 253. Value 0 indicates that all services on the port are protected."
        ::= { optixSEPConfigInfoEntry 3 }

    -- 1.3.6.1.4.1.2011.2.25.4.50.36.1.1.1.4
    optixSEPSrvVlanList OBJECT-TYPE
        SYNTAX OCTET STRING
        MAX-ACCESS read-write
        STATUS current
        DESCRIPTION
            "This node indicates the SEP service VLAN ID list."
        ::= { optixSEPConfigInfoEntry 4 }

    -- 1.3.6.1.4.1.2011.2.25.4.50.36.1.1.1.5
    optixSEPPreemtMode OBJECT-TYPE
        SYNTAX INTEGER
        {
            nonpreempt(1),
            manual(2),
            delay(3)
        }
        MAX-ACCESS read-write
        STATUS current
        DESCRIPTION
            "This node indicates the SEP preemption mode. Value 1 indicates the non-preemption mode; value 2 indicates the manual preemption mode; value 3 indicates the delay preemption mode. The default value is 1."
        DEFVAL{ 1 }
        ::= { optixSEPConfigInfoEntry 5 }

    -- 1.3.6.1.4.1.2011.2.25.4.50.36.1.1.1.6
    optixSEPDelayTime OBJECT-TYPE
        SYNTAX Unsigned32
        MAX-ACCESS read-write
        STATUS current
        DESCRIPTION
            "This node indicates the SEP preemption hold-off time, in seconds. The value ranges from 15 to 600, and the step is 1. The default value is 15."
        DEFVAL{ 15 }
        ::= { optixSEPConfigInfoEntry 6 }

    -- 1.3.6.1.4.1.2011.2.25.4.50.36.1.1.1.7
    optixSEPTCInterval OBJECT-TYPE
        SYNTAX Unsigned32
        MAX-ACCESS read-write
        STATUS current
        DESCRIPTION
            "This node indicates the SEP TC hold-off time, in seconds. The value ranges from 1 to 10. The default value is 2."
        DEFVAL{ 2 }
        ::= { optixSEPConfigInfoEntry 7 }

    -- 1.3.6.1.4.1.2011.2.25.4.50.36.1.1.1.8
    optixSEPTCNotifyNum OBJECT-TYPE
        SYNTAX Unsigned32
        MAX-ACCESS read-write
        STATUS current
        DESCRIPTION
            "This node indicates the number of SEP nodes to be notified of the SEP TC. The value ranges from 0 to 8. Value 0 indicates that the SEP nodes are not notified."
        ::= { optixSEPConfigInfoEntry 8 }

    -- 1.3.6.1.4.1.2011.2.25.4.50.36.1.1.1.9
    optixSEPTCNotifyList OBJECT-TYPE
        SYNTAX OCTET STRING
        MAX-ACCESS read-write
        STATUS current
        DESCRIPTION
            "This node indicates the list of SEP nodes to be notified of the SEP TC."
        ::= { optixSEPConfigInfoEntry 9 }

    -- 1.3.6.1.4.1.2011.2.25.4.50.36.1.1.1.10
    optixSEPAuthenType OBJECT-TYPE
        SYNTAX INTEGER
        {
            none(0),
            hmacsha256(1)
        }
        MAX-ACCESS read-write
        STATUS current
        DESCRIPTION
            "This node indicates the SEP authentication mode. Value 0 indicates that no authentication is performed; value 1 indicates that the authentication password is encrypted by HMAC-SHA256. The default value is 0."
        DEFVAL{ 0 }
        ::= { optixSEPConfigInfoEntry 10 }

    -- 1.3.6.1.4.1.2011.2.25.4.50.36.1.1.1.11
    optixSEPAuthenPwd OBJECT-TYPE
        SYNTAX OCTET STRING (SIZE(1..64))
        MAX-ACCESS read-write
        STATUS current
        DESCRIPTION
            "This node indicates the SEP authentication password. It is set to a null character string if no authentication is performed and to a character string of 1 to 64 bytes if the authentication password is encrypted by HMAC-SHA256."
        ::= { optixSEPConfigInfoEntry 11 }

    -- 1.3.6.1.4.1.2011.2.25.4.50.36.1.1.1.12
    optixSEPBlockMode OBJECT-TYPE
        SYNTAX INTEGER
        {
            optimal(1),
            middle(2),
            hop(3),
            name(4)
        }
        MAX-ACCESS read-write
        STATUS current
        DESCRIPTION
            "This node indicates the SEP port blocking mode. Value 1 indicates that the port with the highest priority is the blocked port; value 2 indicates that an intermediate port in the SEP segment is the blocked port; value 3 indicates that the blocked port is specified based on the number of hops; value 4 indicates that the blocked port is specified based on the device name and port name."
        ::= { optixSEPConfigInfoEntry 12 }

    -- 1.3.6.1.4.1.2011.2.25.4.50.36.1.1.1.13
    optixSEPBlockPortHop OBJECT-TYPE
        SYNTAX Unsigned32
        MAX-ACCESS read-write
        STATUS current
        DESCRIPTION
            "This node indicates the number of hops of the blocked port when the SEP port blocking mode is hop. This node is valid only when the block mode is hop and is set to 0xffff in other scenarios."
        ::= { optixSEPConfigInfoEntry 13 }

    -- 1.3.6.1.4.1.2011.2.25.4.50.36.1.1.1.14
    optixSEPBlockPortSysName OBJECT-TYPE
        SYNTAX OCTET STRING
        MAX-ACCESS read-write
        STATUS current
        DESCRIPTION
            "This node indicates the system name of the blocking port when the SEP port block mode is name. This node is valid only when the block mode is name and is not processed in other scenarios."
        ::= { optixSEPConfigInfoEntry 14 }

    -- 1.3.6.1.4.1.2011.2.25.4.50.36.1.1.1.15
    optixSEPBlockPortName OBJECT-TYPE
        SYNTAX OCTET STRING
        MAX-ACCESS read-write
        STATUS current
        DESCRIPTION
            "This node indicates the name of the blocking port when the SEP port block mode is name. This node is valid only when the block mode is name and is not processed in other scenarios."
        ::= { optixSEPConfigInfoEntry 15 }

    -- 1.3.6.1.4.1.2011.2.25.4.50.36.1.1.1.16
    optixSEPName OBJECT-TYPE
        SYNTAX OCTET STRING
        MAX-ACCESS read-write
        STATUS current
        DESCRIPTION
            "This node describes the SEP name."
        ::= { optixSEPConfigInfoEntry 16 }

    -- 1.3.6.1.4.1.2011.2.25.4.50.36.1.1.1.17
    optixSEPClearPKTCount OBJECT-TYPE
        SYNTAX INTEGER
        {
            clear(0)
        }
        MAX-ACCESS read-write
        STATUS current
        DESCRIPTION
            "This node indicates whether to clear packet statistics on an SEP port. Value 0 indicates that the packet statistics are cleared."
        ::= { optixSEPConfigInfoEntry 17 }

    -- 1.3.6.1.4.1.2011.2.25.4.50.36.1.1.1.18
    optixSEPAddVlanList OBJECT-TYPE
        SYNTAX OCTET STRING
        MAX-ACCESS read-write
        STATUS current
        DESCRIPTION
            "This node indicates the SEP service VLAN ID list to add."
        ::= { optixSEPConfigInfoEntry 18 }

    -- 1.3.6.1.4.1.2011.2.25.4.50.36.1.1.1.19
    optixSEPDelVlanList OBJECT-TYPE
        SYNTAX OCTET STRING
        MAX-ACCESS read-write
        STATUS current
        DESCRIPTION
            "This node indicates the SEP service VLAN ID list to be deleted."
        ::= { optixSEPConfigInfoEntry 19 }

    -- 1.3.6.1.4.1.2011.2.25.4.50.36.1.1.1.20
    optixSEPSetSysNameType OBJECT-TYPE
        SYNTAX Integer32 (0..1)
        MAX-ACCESS read-write
        STATUS current
        DESCRIPTION
            "Set a name type for the sep system."
        DEFVAL{ 0 }
        ::= { optixSEPConfigInfoEntry 20 }

    -- 1.3.6.1.4.1.2011.2.25.4.50.36.1.2
    optixSEPPortInfoTable OBJECT-TYPE
        SYNTAX SEQUENCE OF OptixSEPPortInfoEntry
        MAX-ACCESS not-accessible
        STATUS current
        DESCRIPTION
            "This table contains information of SEP ports."
        ::= { optixSEPObject 2 }

    -- 1.3.6.1.4.1.2011.2.25.4.50.36.1.2.1
    optixSEPPortInfoEntry OBJECT-TYPE
        SYNTAX OptixSEPPortInfoEntry
        MAX-ACCESS not-accessible
        STATUS current
        DESCRIPTION
            "This entry contains information of SEP ports."
        INDEX{ optixSEPID,optixSEPBoardID,optixSEPSubcard,optixSEPPortID }
        ::= { optixSEPPortInfoTable 1 }

    OptixSEPPortInfoEntry ::=
        SEQUENCE {
            optixSEPBoardID
                Unsigned32,
            optixSEPSubcard
                Unsigned32,
            optixSEPPortID
                Unsigned32,
            optixSEPPortCfgRole
                INTEGER,
            optixSEPPortWorkRole
                INTEGER,
            optixSEPPortPriority
                Unsigned32,
            optixSEPPortState
                INTEGER,
            optixSEPNeiPortSysName
                OCTET STRING,
            optixSEPNeiPortName
                OCTET STRING,
            optixSEPNeiPortMac
                OCTET STRING,
            optixSEPNeiPortID
                Unsigned32,
            optixSEPNeiPortState
                INTEGER,
            optixSEPPortSendNBRTLV
                Unsigned32,
            optixSEPPortSendLSPINFOTLV
                Unsigned32,
            optixSEPPortSendLSPACKTLV
                Unsigned32,
            optixSEPPortSendPREEMPTREGTLV
                Unsigned32,
            optixSEPPortSendPREEMPTACKTLV
                Unsigned32,
            optixSEPPortSendTCNotify
                Unsigned32,
            optixSEPPortSendEPA
                Unsigned32,
            optixSEPPortRecvNBRTLV
                Unsigned32,
            optixSEPPortRecvLSPINFOTLV
                Unsigned32,
            optixSEPPortRecvLSPACKTLV
                Unsigned32,
            optixSEPPortRecvPREEMPTREGTLV
                Unsigned32,
            optixSEPPortRecvPREEMPTACKTLV
                Unsigned32,
            optixSEPPortRecvTCNotify
                Unsigned32,
            optixSEPPortRecvEPA
                Unsigned32,
            optixSEPPortErrPkg
                Unsigned32
        }

    -- 1.3.6.1.4.1.2011.2.25.4.50.36.1.2.1.1
    optixSEPBoardID OBJECT-TYPE
        SYNTAX Unsigned32
        MAX-ACCESS not-accessible
        STATUS current
        DESCRIPTION
            "This node indicates the slot ID of an SEP port."
        ::= { optixSEPPortInfoEntry 1 }

    -- 1.3.6.1.4.1.2011.2.25.4.50.36.1.2.1.2
    optixSEPSubcard OBJECT-TYPE
        SYNTAX Unsigned32
        MAX-ACCESS not-accessible
        STATUS current
        DESCRIPTION
            "This node indicates the subboard ID of an SEP port."
        ::= { optixSEPPortInfoEntry 2 }

    -- 1.3.6.1.4.1.2011.2.25.4.50.36.1.2.1.3
    optixSEPPortID OBJECT-TYPE
        SYNTAX Unsigned32
        MAX-ACCESS not-accessible
        STATUS current
        DESCRIPTION
            "This node indicates the SEP port number."
        ::= { optixSEPPortInfoEntry 3 }

    -- 1.3.6.1.4.1.2011.2.25.4.50.36.1.2.1.4
    optixSEPPortCfgRole OBJECT-TYPE
        SYNTAX INTEGER
        {
            common(16),
            priedge(34),
            secedge(33),
            nonbrpriedge(50),
            nonbrsecedge(49),
            none(255)
        }
        MAX-ACCESS read-only
        STATUS current
        DESCRIPTION
            "This node indicates the configuration role of an SEP port. Value 0x10 indicates a common port; value 0x22 indicates the primary edge port; value 0x21 indicates the secondary edge port; value 0x32 indicates the no-neighbor primary edge port; value 0x31 indicates the no-neighbor secondary edge port; value 0xff indicates an invalid port."
        ::= { optixSEPPortInfoEntry 4 }

    -- 1.3.6.1.4.1.2011.2.25.4.50.36.1.2.1.5
    optixSEPPortWorkRole OBJECT-TYPE
        SYNTAX INTEGER
        {
            common(16),
            priedge(34),
            secedge(33),
            nonbrpriedge(50),
            nonbrsecedge(49),
            none(255)
        }
        MAX-ACCESS read-only
        STATUS current
        DESCRIPTION
            "This node indicates the running role of an SEP port. Value 0x10 indicates a common port; value 0x22 indicates the primary edge port; value 0x21 indicates the secondary edge port; value 0x32 indicates the no-neighbor primary edge port; value 0x31 indicates the no-neighbor secondary edge port; value 0xff indicates an invalid port."
        ::= { optixSEPPortInfoEntry 5 }

    -- 1.3.6.1.4.1.2011.2.25.4.50.36.1.2.1.6
    optixSEPPortPriority OBJECT-TYPE
        SYNTAX Unsigned32
        MAX-ACCESS read-write
        STATUS current
        DESCRIPTION
            "This node indicates the priority of an SEP port."
        ::= { optixSEPPortInfoEntry 6 }

    -- 1.3.6.1.4.1.2011.2.25.4.50.36.1.2.1.7
    optixSEPPortState OBJECT-TYPE
        SYNTAX INTEGER
        {
            discarding(0),
            forwarding(1)
        }
        MAX-ACCESS read-only
        STATUS current
        DESCRIPTION
            "This node indicates the SEP port status. Value 0 indicates discarding; value 1 indicates forwarding."
        ::= { optixSEPPortInfoEntry 7 }

    -- 1.3.6.1.4.1.2011.2.25.4.50.36.1.2.1.8
    optixSEPNeiPortSysName OBJECT-TYPE
        SYNTAX OCTET STRING
        MAX-ACCESS read-only
        STATUS current
        DESCRIPTION
            "This node indicates the system name of the SEP neighbor port. The NE ID is used as the system name."
        ::= { optixSEPPortInfoEntry 8 }

    -- 1.3.6.1.4.1.2011.2.25.4.50.36.1.2.1.9
    optixSEPNeiPortName OBJECT-TYPE
        SYNTAX OCTET STRING
        MAX-ACCESS read-only
        STATUS current
        DESCRIPTION
            "This node indicates the SEP neighbor port name, which is a string in the format of Slot ID/Subboard ID/Port number."
        ::= { optixSEPPortInfoEntry 9 }

    -- 1.3.6.1.4.1.2011.2.25.4.50.36.1.2.1.10
    optixSEPNeiPortMac OBJECT-TYPE
        SYNTAX OCTET STRING
        MAX-ACCESS read-only
        STATUS current
        DESCRIPTION
            "This node indicates the physical address of the SEP neighbor port."
        ::= { optixSEPPortInfoEntry 10 }

    -- 1.3.6.1.4.1.2011.2.25.4.50.36.1.2.1.11
    optixSEPNeiPortID OBJECT-TYPE
        SYNTAX Unsigned32
        MAX-ACCESS read-only
        STATUS current
        DESCRIPTION
            "This node indicates the SEP neighbor port number."
        ::= { optixSEPPortInfoEntry 11 }

    -- 1.3.6.1.4.1.2011.2.25.4.50.36.1.2.1.12
    optixSEPNeiPortState OBJECT-TYPE
        SYNTAX INTEGER
        {
            down(0),
            init(1),
            preup(2),
            up(3),
            conflict(4),
            none(255)
        }
        MAX-ACCESS read-only
        STATUS current
        DESCRIPTION
            "This node indicates the SEP neighbor port status. Value 0 indicates down; value 1 indicates initialized; value 2 indicates preup; value 3 indicates up; value 4 indicates conflict; value 0xff indicates none."
        ::= { optixSEPPortInfoEntry 12 }

    -- 1.3.6.1.4.1.2011.2.25.4.50.36.1.2.1.13
    optixSEPPortSendNBRTLV OBJECT-TYPE
        SYNTAX Unsigned32
        MAX-ACCESS read-only
        STATUS current
        DESCRIPTION
            "This node indicates the statistics on the NBR TLV sent from an SEP port."
        ::= { optixSEPPortInfoEntry 13 }

    -- 1.3.6.1.4.1.2011.2.25.4.50.36.1.2.1.14
    optixSEPPortSendLSPINFOTLV OBJECT-TYPE
        SYNTAX Unsigned32
        MAX-ACCESS read-only
        STATUS current
        DESCRIPTION
            "This node indicates the statistics on the LSP INFO TLV sent from an SEP port."
        ::= { optixSEPPortInfoEntry 14 }

    -- 1.3.6.1.4.1.2011.2.25.4.50.36.1.2.1.15
    optixSEPPortSendLSPACKTLV OBJECT-TYPE
        SYNTAX Unsigned32
        MAX-ACCESS read-only
        STATUS current
        DESCRIPTION
            "This node indicates the statistics on the LSP ACK TLV sent from an SEP port."
        ::= { optixSEPPortInfoEntry 15 }

    -- 1.3.6.1.4.1.2011.2.25.4.50.36.1.2.1.16
    optixSEPPortSendPREEMPTREGTLV OBJECT-TYPE
        SYNTAX Unsigned32
        MAX-ACCESS read-only
        STATUS current
        DESCRIPTION
            "This node indicates the statistics on the PREEMPT REQ TLV sent from an SEP port."
        ::= { optixSEPPortInfoEntry 16 }

    -- 1.3.6.1.4.1.2011.2.25.4.50.36.1.2.1.17
    optixSEPPortSendPREEMPTACKTLV OBJECT-TYPE
        SYNTAX Unsigned32
        MAX-ACCESS read-only
        STATUS current
        DESCRIPTION
            "This node indicates the statistics on the PREEMPT ACK TLV sent from an SEP port."
        ::= { optixSEPPortInfoEntry 17 }

    -- 1.3.6.1.4.1.2011.2.25.4.50.36.1.2.1.18
    optixSEPPortSendTCNotify OBJECT-TYPE
        SYNTAX Unsigned32
        MAX-ACCESS read-only
        STATUS current
        DESCRIPTION
            "This node indicates the statistics on the TC Notify sent from an SEP port."
        ::= { optixSEPPortInfoEntry 18 }

    -- 1.3.6.1.4.1.2011.2.25.4.50.36.1.2.1.19
    optixSEPPortSendEPA OBJECT-TYPE
        SYNTAX Unsigned32
        MAX-ACCESS read-only
        STATUS current
        DESCRIPTION
            "This node indicates the statistics on the EPA sent from an SEP port."
        ::= { optixSEPPortInfoEntry 19 }

    -- 1.3.6.1.4.1.2011.2.25.4.50.36.1.2.1.20
    optixSEPPortRecvNBRTLV OBJECT-TYPE
        SYNTAX Unsigned32
        MAX-ACCESS read-only
        STATUS current
        DESCRIPTION
            "This node indicates the statistics on the NBR TLV received by an SEP port."
        ::= { optixSEPPortInfoEntry 20 }

    -- 1.3.6.1.4.1.2011.2.25.4.50.36.1.2.1.21
    optixSEPPortRecvLSPINFOTLV OBJECT-TYPE
        SYNTAX Unsigned32
        MAX-ACCESS read-only
        STATUS current
        DESCRIPTION
            "This node indicates the statistics on the LSP INFO TLV received by an SEP port."
        ::= { optixSEPPortInfoEntry 21 }

    -- 1.3.6.1.4.1.2011.2.25.4.50.36.1.2.1.22
    optixSEPPortRecvLSPACKTLV OBJECT-TYPE
        SYNTAX Unsigned32
        MAX-ACCESS read-only
        STATUS current
        DESCRIPTION
            "This node indicates the statistics on the LSP ACK TLV received by an SEP port."
        ::= { optixSEPPortInfoEntry 22 }

    -- 1.3.6.1.4.1.2011.2.25.4.50.36.1.2.1.23
    optixSEPPortRecvPREEMPTREGTLV OBJECT-TYPE
        SYNTAX Unsigned32
        MAX-ACCESS read-only
        STATUS current
        DESCRIPTION
            "This node indicates the statistics on the PREEMPT REQ TLV received by an SEP port."
        ::= { optixSEPPortInfoEntry 23 }

    -- 1.3.6.1.4.1.2011.2.25.4.50.36.1.2.1.24
    optixSEPPortRecvPREEMPTACKTLV OBJECT-TYPE
        SYNTAX Unsigned32
        MAX-ACCESS read-only
        STATUS current
        DESCRIPTION
            "This node indicates the statistics on the PREEMPT ACK TLV received by an SEP port."
        ::= { optixSEPPortInfoEntry 24 }

    -- 1.3.6.1.4.1.2011.2.25.4.50.36.1.2.1.25
    optixSEPPortRecvTCNotify OBJECT-TYPE
        SYNTAX Unsigned32
        MAX-ACCESS read-only
        STATUS current
        DESCRIPTION
            "This node indicates the statistics on the TC Notify received by an SEP port."
        ::= { optixSEPPortInfoEntry 25 }

    -- 1.3.6.1.4.1.2011.2.25.4.50.36.1.2.1.26
    optixSEPPortRecvEPA OBJECT-TYPE
        SYNTAX Unsigned32
        MAX-ACCESS read-only
        STATUS current
        DESCRIPTION
            "This node indicates the statistics on the EPA received by an SEP port."
        ::= { optixSEPPortInfoEntry 26 }

    -- 1.3.6.1.4.1.2011.2.25.4.50.36.1.2.1.27
    optixSEPPortErrPkg OBJECT-TYPE
        SYNTAX Unsigned32
        MAX-ACCESS read-only
        STATUS current
        DESCRIPTION
            "This node indicates the statistics on the error packets received by an SEP port."
        ::= { optixSEPPortInfoEntry 27 }

    -- 1.3.6.1.4.1.2011.2.25.4.50.36.1.3
    optixSEPTopoTable OBJECT-TYPE
        SYNTAX SEQUENCE OF OptixSEPTopoEntry
        MAX-ACCESS not-accessible
        STATUS current
        DESCRIPTION
            "This table contains topology information of SEP."
        ::= { optixSEPObject 3 }

    -- 1.3.6.1.4.1.2011.2.25.4.50.36.1.3.1
    optixSEPTopoEntry OBJECT-TYPE
        SYNTAX OptixSEPTopoEntry
        MAX-ACCESS not-accessible
        STATUS current
        DESCRIPTION
            "This entry contains topology information of SEP."
        INDEX{ optixSEPTopoIndex,optixSEPID }
        ::= { optixSEPTopoTable 1 }

    OptixSEPTopoEntry ::=
        SEQUENCE {
            optixSEPTopoIndex
                Unsigned32,
            optixSEPTopoSysName
                OCTET STRING,
            optixSEPTopoPortName
                OCTET STRING,
            optixSEPTopoPortCfgRole
                INTEGER,
            optixSEPTopoPortWorkRole
                INTEGER,
            optixSEPTopoPortMac
                OCTET STRING,
            optixSEPTopoPortID
                Unsigned32,
            optixSEPTopoPortPriority
                Unsigned32,
            optixSEPTopoPortState
                INTEGER,
            optixSEPTopoHop
                Unsigned32,
            optixSEPTopoLinkState
                INTEGER,
            optixSEPTopoBroPortName
                OCTET STRING,
            optixSEPTopoBroPortID
                Unsigned32,
            optixSEPTopoNeiSysName
                OCTET STRING,
            optixSEPTopoNeiPortName
                OCTET STRING,
            optixSEPTopoNeiSysMac
                OCTET STRING,
            optixSEPTopoNeiPortID
                Unsigned32,
            optixSEPTopoNeiState
                INTEGER,
            optixSEPTopoAgeingTime
                Unsigned32,
            optixSEPTopoSerializationNum
                Unsigned32
        }

    -- 1.3.6.1.4.1.2011.2.25.4.50.36.1.3.1.1
    optixSEPTopoIndex OBJECT-TYPE
        SYNTAX Unsigned32
        MAX-ACCESS not-accessible
        STATUS current
        DESCRIPTION
            "This node describes the SEP topology information record index."
        ::= { optixSEPTopoEntry 1 }

    -- 1.3.6.1.4.1.2011.2.25.4.50.36.1.3.1.2
    optixSEPTopoSysName OBJECT-TYPE
        SYNTAX OCTET STRING
        MAX-ACCESS read-only
        STATUS current
        DESCRIPTION
            "This node indicates the system name in the SEP topology information. The NE ID is used as the system name."
        ::= { optixSEPTopoEntry 2 }

    -- 1.3.6.1.4.1.2011.2.25.4.50.36.1.3.1.3
    optixSEPTopoPortName OBJECT-TYPE
        SYNTAX OCTET STRING
        MAX-ACCESS read-only
        STATUS current
        DESCRIPTION
            "This node indicates the port name in the SEP topology information, which is a string in the format of Slot ID/Subboard ID/Port number."
        ::= { optixSEPTopoEntry 3 }

    -- 1.3.6.1.4.1.2011.2.25.4.50.36.1.3.1.4
    optixSEPTopoPortCfgRole OBJECT-TYPE
        SYNTAX INTEGER
        {
            common(16),
            priedge(34),
            secedge(33),
            nonbrpriedge(50),
            nonbrsecedge(49),
            none(255)
        }
        MAX-ACCESS read-only
        STATUS current
        DESCRIPTION
            "This node indicates the port configuration role in the SEP topology information. Value 0x10 indicates a common port; value 0x22 indicates the primary edge port; value 0x21 indicates the secondary edge port; value 0x32 indicates the no-neighbor primary edge port; value 0x31 indicates the no-neighbor secondary edge port; value 0xff indicates an invalid port."
        ::= { optixSEPTopoEntry 4 }

    -- 1.3.6.1.4.1.2011.2.25.4.50.36.1.3.1.5
    optixSEPTopoPortWorkRole OBJECT-TYPE
        SYNTAX INTEGER
        {
            common(16),
            priedge(34),
            secedge(33),
            nonbrpriedge(50),
            nonbrsecedge(49),
            none(255)
        }
        MAX-ACCESS read-only
        STATUS current
        DESCRIPTION
            "This node indicates the port working role in the SEP topology information. Value 0x10 indicates a common port; value 0x22 indicates the primary edge port; value 0x21 indicates the secondary edge port; value 0x32 indicates the no-neighbor primary edge port; value 0x31 indicates the no-neighbor secondary edge port; value 0xff indicates an invalid port."
        ::= { optixSEPTopoEntry 5 }

    -- 1.3.6.1.4.1.2011.2.25.4.50.36.1.3.1.6
    optixSEPTopoPortMac OBJECT-TYPE
        SYNTAX OCTET STRING
        MAX-ACCESS read-only
        STATUS current
        DESCRIPTION
            "This node indicates the port physical address in the SEP topology information."
        ::= { optixSEPTopoEntry 6 }

    -- 1.3.6.1.4.1.2011.2.25.4.50.36.1.3.1.7
    optixSEPTopoPortID OBJECT-TYPE
        SYNTAX Unsigned32
        MAX-ACCESS read-only
        STATUS current
        DESCRIPTION
            "This node indicates the port number in the SEP topology information."
        ::= { optixSEPTopoEntry 7 }

    -- 1.3.6.1.4.1.2011.2.25.4.50.36.1.3.1.8
    optixSEPTopoPortPriority OBJECT-TYPE
        SYNTAX Unsigned32
        MAX-ACCESS read-only
        STATUS current
        DESCRIPTION
            "This node indicates the port priority in the SEP topology information."
        ::= { optixSEPTopoEntry 8 }

    -- 1.3.6.1.4.1.2011.2.25.4.50.36.1.3.1.9
    optixSEPTopoPortState OBJECT-TYPE
        SYNTAX INTEGER
        {
            discarding(0),
            forwarding(1)
        }
        MAX-ACCESS read-only
        STATUS current
        DESCRIPTION
            "This node indicates the port status in the SEP topology information. Value 0 indicates discarding; value 1 indicates forwarding."
        ::= { optixSEPTopoEntry 9 }

    -- 1.3.6.1.4.1.2011.2.25.4.50.36.1.3.1.10
    optixSEPTopoHop OBJECT-TYPE
        SYNTAX Unsigned32
        MAX-ACCESS read-only
        STATUS current
        DESCRIPTION
            "This node indicates the number of hops in the SEP topology information."
        ::= { optixSEPTopoEntry 10 }

    -- 1.3.6.1.4.1.2011.2.25.4.50.36.1.3.1.11
    optixSEPTopoLinkState OBJECT-TYPE
        SYNTAX INTEGER
        {
            down(0),
            up(1)
        }
        MAX-ACCESS read-only
        STATUS current
        DESCRIPTION
            "This node indicates the link status in the SEP topology information. Value 0 indicates down; value 1 indicates up."
        ::= { optixSEPTopoEntry 11 }

    -- 1.3.6.1.4.1.2011.2.25.4.50.36.1.3.1.12
    optixSEPTopoBroPortName OBJECT-TYPE
        SYNTAX OCTET STRING
        MAX-ACCESS read-only
        STATUS current
        DESCRIPTION
            "This node indicates the brother port name in the SEP topology information, which is a string in the format of Slot ID/Subboard ID/Port number."
        ::= { optixSEPTopoEntry 12 }

    -- 1.3.6.1.4.1.2011.2.25.4.50.36.1.3.1.13
    optixSEPTopoBroPortID OBJECT-TYPE
        SYNTAX Unsigned32
        MAX-ACCESS read-only
        STATUS current
        DESCRIPTION
            "This node indicates the brother port number in the SEP topology information."
        ::= { optixSEPTopoEntry 13 }

    -- 1.3.6.1.4.1.2011.2.25.4.50.36.1.3.1.14
    optixSEPTopoNeiSysName OBJECT-TYPE
        SYNTAX OCTET STRING
        MAX-ACCESS read-only
        STATUS current
        DESCRIPTION
            "This node indicates the neighbor system name in the SEP topology information. The NE ID is used as the system name."
        ::= { optixSEPTopoEntry 14 }

    -- 1.3.6.1.4.1.2011.2.25.4.50.36.1.3.1.15
    optixSEPTopoNeiPortName OBJECT-TYPE
        SYNTAX OCTET STRING
        MAX-ACCESS read-only
        STATUS current
        DESCRIPTION
            "This node indicates the neighbor system port name in the SEP topology information."
        ::= { optixSEPTopoEntry 15 }

    -- 1.3.6.1.4.1.2011.2.25.4.50.36.1.3.1.16
    optixSEPTopoNeiSysMac OBJECT-TYPE
        SYNTAX OCTET STRING
        MAX-ACCESS read-only
        STATUS current
        DESCRIPTION
            "This node indicates the physical address of the neighbor system in the SEP topology information."
        ::= { optixSEPTopoEntry 16 }

    -- 1.3.6.1.4.1.2011.2.25.4.50.36.1.3.1.17
    optixSEPTopoNeiPortID OBJECT-TYPE
        SYNTAX Unsigned32
        MAX-ACCESS read-only
        STATUS current
        DESCRIPTION
            "This node indicates the neighbor port number in the SEP topology information."
        ::= { optixSEPTopoEntry 17 }

    -- 1.3.6.1.4.1.2011.2.25.4.50.36.1.3.1.18
    optixSEPTopoNeiState OBJECT-TYPE
        SYNTAX INTEGER
        {
            down(0),
            init(1),
            preup(2),
            up(3),
            conflict(4),
            none(255)
        }
        MAX-ACCESS read-only
        STATUS current
        DESCRIPTION
            "This node indicates the neighbor status in the SEP topology information. Value 0 indicates down; value 1 indicates init; value 2 indicates preup; value 3 indicates up; value 4 indicates conflict; value 0xff indicates none."
        ::= { optixSEPTopoEntry 18 }

    -- 1.3.6.1.4.1.2011.2.25.4.50.36.1.3.1.19
    optixSEPTopoAgeingTime OBJECT-TYPE
        SYNTAX Unsigned32
        MAX-ACCESS read-only
        STATUS current
        DESCRIPTION
            "This node indicates the aging time in the SEP topology information."
        ::= { optixSEPTopoEntry 19 }

    -- 1.3.6.1.4.1.2011.2.25.4.50.36.1.3.1.20
    optixSEPTopoSerializationNum OBJECT-TYPE
        SYNTAX Unsigned32
        MAX-ACCESS read-only
        STATUS current
        DESCRIPTION
            "This node indicates the serial number in the SEP topology information."
        ::= { optixSEPTopoEntry 20 }

    -- 1.3.6.1.4.1.2011.2.25.4.50.36.1.4
    optixSEPCrtTable OBJECT-TYPE
        SYNTAX SEQUENCE OF OptixSEPCrtEntry
        MAX-ACCESS not-accessible
        STATUS current
        DESCRIPTION
            "This table describes the information about SEP creation."
        ::= { optixSEPObject 4 }

    -- 1.3.6.1.4.1.2011.2.25.4.50.36.1.4.1
    optixSEPCrtEntry OBJECT-TYPE
        SYNTAX OptixSEPCrtEntry
        MAX-ACCESS not-accessible
        STATUS current
        DESCRIPTION
            "This entry contains creating information of SEP."
        INDEX{ optixSEPID }
        ::= { optixSEPCrtTable 1 }

    OptixSEPCrtEntry ::=
        SEQUENCE {
            optixSEPAddCtrVlan
                Unsigned32,
            optixSEPEastBoardID
                Unsigned32,
            optixSEPEastSubcard
                Unsigned32,
            optixSEPEastPortID
                Unsigned32,
            optixSEPEastPortRole
                INTEGER,
            optixSEPWestBoardID
                Unsigned32,
            optixSEPWestSubcard
                Unsigned32,
            optixSEPWestPortID
                Unsigned32,
            optixSEPWestPortRole
                INTEGER,
            optixSEPAddSrvVlanNum
                Unsigned32,
            optixSEPAddSrvVlanList
                OCTET STRING,
            optixSEPRowStatus
                RowStatus
        }

    -- 1.3.6.1.4.1.2011.2.25.4.50.36.1.4.1.1
    optixSEPAddCtrVlan OBJECT-TYPE
        SYNTAX Unsigned32
        MAX-ACCESS read-create
        STATUS current
        DESCRIPTION
            "This node indicates the SEP control VLAN ID, which ranges from 1 to 4094 and must be different from service VLAN IDs."
        ::= { optixSEPCrtEntry 1 }

    -- 1.3.6.1.4.1.2011.2.25.4.50.36.1.4.1.2
    optixSEPEastBoardID OBJECT-TYPE
        SYNTAX Unsigned32
        MAX-ACCESS read-create
        STATUS current
        DESCRIPTION
            "This node indicates the slot ID of the SEP east port. Value 0xffff indicates that no east port is available."
        ::= { optixSEPCrtEntry 2 }

    -- 1.3.6.1.4.1.2011.2.25.4.50.36.1.4.1.3
    optixSEPEastSubcard OBJECT-TYPE
        SYNTAX Unsigned32
        MAX-ACCESS read-create
        STATUS current
        DESCRIPTION
            "This node indicates the subboard ID of the SEP east port. Value 0xff indicates that no subboard is available."
        ::= { optixSEPCrtEntry 3 }

    -- 1.3.6.1.4.1.2011.2.25.4.50.36.1.4.1.4
    optixSEPEastPortID OBJECT-TYPE
        SYNTAX Unsigned32
        MAX-ACCESS read-create
        STATUS current
        DESCRIPTION
            "This node indicates the SEP east port number. Value 0xffff indicates that no east port is available."
        ::= { optixSEPCrtEntry 4 }

    -- 1.3.6.1.4.1.2011.2.25.4.50.36.1.4.1.5
    optixSEPEastPortRole OBJECT-TYPE
        SYNTAX INTEGER
        {
            common(16),
            priedge(34),
            secedge(33),
            nonbrpriedge(50),
            nonbrsecedge(49),
            none(255)
        }
        MAX-ACCESS read-create
        STATUS current
        DESCRIPTION
            "This node indicates the role of the SEP east port. Value 0x10 indicates a common port; value 0x22 indicates the primary edge port; value 0x21 indicates the secondary edge port; value 0x32 indicates the no-neighbor primary edge port; value 0x31 indicates the no-neighbor secondary edge port; value 0xff indicates an invalid port."
        ::= { optixSEPCrtEntry 5 }

    -- 1.3.6.1.4.1.2011.2.25.4.50.36.1.4.1.6
    optixSEPWestBoardID OBJECT-TYPE
        SYNTAX Unsigned32
        MAX-ACCESS read-create
        STATUS current
        DESCRIPTION
            "This node indicates the slot ID of the SEP west port. Value 0xffff indicates that no west port is available."
        ::= { optixSEPCrtEntry 6 }

    -- 1.3.6.1.4.1.2011.2.25.4.50.36.1.4.1.7
    optixSEPWestSubcard OBJECT-TYPE
        SYNTAX Unsigned32
        MAX-ACCESS read-create
        STATUS current
        DESCRIPTION
            "This node indicates the subboard ID of the SEP west port. Value 0xff indicates that no subboard is available."
        ::= { optixSEPCrtEntry 7 }

    -- 1.3.6.1.4.1.2011.2.25.4.50.36.1.4.1.8
    optixSEPWestPortID OBJECT-TYPE
        SYNTAX Unsigned32
        MAX-ACCESS read-create
        STATUS current
        DESCRIPTION
            "This node indicates the SEP west port number. Value 0xffff indicates that no west port is available."
        ::= { optixSEPCrtEntry 8 }

    -- 1.3.6.1.4.1.2011.2.25.4.50.36.1.4.1.9
    optixSEPWestPortRole OBJECT-TYPE
        SYNTAX INTEGER
        {
            common(16),
            priedge(34),
            secedge(33),
            nonbrpriedge(50),
            nonbrsecedge(49),
            none(255)
        }
        MAX-ACCESS read-create
        STATUS current
        DESCRIPTION
            "This node indicates the role of the SEP west port. Value 0x10 indicates a common port; value 0x22 indicates the primary edge port; value 0x21 indicates the secondary edge port; value 0x32 indicates the no-neighbor primary edge port; value 0x31 indicates the no-neighbor secondary edge port; value 0xff indicates an invalid port."
        ::= { optixSEPCrtEntry 9 }

    -- 1.3.6.1.4.1.2011.2.25.4.50.36.1.4.1.10
    optixSEPAddSrvVlanNum OBJECT-TYPE
        SYNTAX Unsigned32
        MAX-ACCESS read-create
        STATUS current
        DESCRIPTION
            "This node indicates the SEP service VLAN quantity, which ranges from 0 to 253. Value 0 indicates that all services on the port are protected."
        ::= { optixSEPCrtEntry 10 }

    -- 1.3.6.1.4.1.2011.2.25.4.50.36.1.4.1.11
    optixSEPAddSrvVlanList OBJECT-TYPE
        SYNTAX OCTET STRING
        MAX-ACCESS read-create
        STATUS current
        DESCRIPTION
            "This node indicates the SEP service VLAN ID list."
        ::= { optixSEPCrtEntry 11 }

    -- 1.3.6.1.4.1.2011.2.25.4.50.36.1.4.1.255
    optixSEPRowStatus OBJECT-TYPE
        SYNTAX RowStatus
        MAX-ACCESS read-create
        STATUS current
        DESCRIPTION
            "This node indicates the row status of the SEP creating information table."
        ::= { optixSEPCrtEntry 255 }

    -- 1.3.6.1.4.1.2011.2.25.4.50.36.1.5
    optixSEPTrap OBJECT IDENTIFIER ::= { optixSEPObject 5 }

    -- 1.3.6.1.4.1.2011.2.25.4.50.36.1.5.1
    optixSEPNBRStateChangeEvtTrap NOTIFICATION-TYPE
        STATUS current
        DESCRIPTION
            "This node is used to report the neighbor status change event of SEP."
        ::= { optixSEPTrap 1 }

    -- 1.3.6.1.4.1.2011.2.25.4.50.36.1.5.2
    optixSEPFWDStateChangeEvtTrap NOTIFICATION-TYPE
        STATUS current
        DESCRIPTION
            "This node is used to report the forwarding status change event of an SEP port."
        ::= { optixSEPTrap 2 }

    -- 1.3.6.1.4.1.2011.2.25.4.50.36.1.6
    optixSEPEvtTrapMember OBJECT IDENTIFIER ::= { optixSEPObject 6 }

    -- 1.3.6.1.4.1.2011.2.25.4.50.36.1.6.1
    optixSEPEvtTrapSepID OBJECT-TYPE
        SYNTAX Unsigned32
        MAX-ACCESS accessible-for-notify
        STATUS current
        DESCRIPTION
            "This node indicates the ID of an SEP protected instance."
        ::= { optixSEPEvtTrapMember 1 }

    -- 1.3.6.1.4.1.2011.2.25.4.50.36.1.6.2
    optixSEPEvtTrapBoard OBJECT-TYPE
        SYNTAX Unsigned32
        MAX-ACCESS accessible-for-notify
        STATUS current
        DESCRIPTION
            "This node indicates the slot ID of an SEP port."
        ::= { optixSEPEvtTrapMember 2 }

    -- 1.3.6.1.4.1.2011.2.25.4.50.36.1.6.3
    optixSEPEvtTrapSubCard OBJECT-TYPE
        SYNTAX Unsigned32
        MAX-ACCESS accessible-for-notify
        STATUS current
        DESCRIPTION
            "This node indicates the subboard ID of an SEP port."
        ::= { optixSEPEvtTrapMember 3 }

    -- 1.3.6.1.4.1.2011.2.25.4.50.36.1.6.4
    optixSEPEvtTrapPort OBJECT-TYPE
        SYNTAX Unsigned32
        MAX-ACCESS accessible-for-notify
        STATUS current
        DESCRIPTION
            "This node indicates the SEP port number."
        ::= { optixSEPEvtTrapMember 4 }

    -- 1.3.6.1.4.1.2011.2.25.4.50.36.1.6.5
    optixSEPEvtTrapNBRState OBJECT-TYPE
        SYNTAX INTEGER
        {
            down(0),
            init(1),
            preup(2),
            up(3),
            conflict(4),
            none(255)
        }
        MAX-ACCESS accessible-for-notify
        STATUS current
        DESCRIPTION
            "This object indicates the SEP neighbor port status. Value 0 indicates down; value 1 indicates initialized; value 2 indicates preup; value 3 indicates up; value 4 indicates conflict; value 0xff indicates none."
        ::= { optixSEPEvtTrapMember 5 }

    -- 1.3.6.1.4.1.2011.2.25.4.50.36.1.6.6
    optixSEPEvtTrapFWDState OBJECT-TYPE
        SYNTAX INTEGER
        {
            discarding(0),
            forwarding(1)
        }
        MAX-ACCESS accessible-for-notify
        STATUS current
        DESCRIPTION
            "This node indicates the SEP port status. Value 0 indicates discarding; value 1 indicates forwarding."
        ::= { optixSEPEvtTrapMember 6 }

END
