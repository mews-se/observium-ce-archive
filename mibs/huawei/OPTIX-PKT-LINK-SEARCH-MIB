-- OPTIX-PKT-LINK-SEARCH-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-LINK-SEARCH-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        optixPortId
            FROM OPTIX-PORT-MANAGE-MIB
        ;

    optixPktLinkSearch MODULE-IDENTITY
        LAST-UPDATED "201212051642Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the QOS service configuration information of device"
        REVISION "201212051642Z"
        DESCRIPTION
            "The initial revision of this MIB module1."
        ::={ optixProvisionPtn 16 }

    -- 1.3.6.1.4.1.2011.2.25.4.50.16.1
    optixPktLinkSearchtGroup OBJECT IDENTIFIER ::= { optixPktLinkSearch 1 }

    -- 1.3.6.1.4.1.2011.2.25.4.50.16.1.1
    optixLinkSearchTable OBJECT-TYPE
        SYNTAX SEQUENCE OF OptixLinkSearchEntry
        MAX-ACCESS not-accessible
        STATUS current
        DESCRIPTION
            "This table describes the basic QoS port schedualing configurations."
        ::= { optixPktLinkSearchtGroup 1 }

    -- 1.3.6.1.4.1.2011.2.25.4.50.16.1.1.1
    optixLinkSearchEntry OBJECT-TYPE
        SYNTAX OptixLinkSearchEntry
        MAX-ACCESS not-accessible
        STATUS current
        DESCRIPTION
            "This entry describes the basic QoS port schedualing configurations."
        INDEX{ optixLogBoardId,optixLogSubCardId,optixPortId }
        ::= { optixLinkSearchTable 1 }

    OptixLinkSearchEntry ::=
        SEQUENCE {
            optixLinkSearchTxNeId
                Unsigned32,
            optixLinkSearchTxPortType
                INTEGER,
            optixLinkSearchTxBoardId
                Unsigned32,
            optixLinkSearchTxSubId
                Unsigned32,
            optixLinkSearchTxPortId
                Unsigned32,
            optixLinkSearchTxSlotVlan
                Unsigned32,
            optixLinkSearchRxNeId
                Unsigned32,
            optixLinkSearchRxPortType
                Unsigned32,
            optixLinkSearchRxBoardId
                Unsigned32,
            optixLinkSearchRxSubId
                Unsigned32,
            optixLinkSearchRxPortId
                Unsigned32,
            optixLinkSearchRxSlotVlan
                Unsigned32,
            optixLinkSearchStartStatus
                INTEGER
        }

    -- 1.3.6.1.4.1.2011.2.25.4.50.16.1.1.1.1
    optixLinkSearchTxNeId OBJECT-TYPE
        SYNTAX Unsigned32
        MAX-ACCESS read-only
        STATUS current
        DESCRIPTION
            "This object indicates the QoS port schedualing direction of the QoS module. NEID"
        ::= { optixLinkSearchEntry 1 }

    -- 1.3.6.1.4.1.2011.2.25.4.50.16.1.1.1.2
    optixLinkSearchTxPortType OBJECT-TYPE
        SYNTAX INTEGER
        {
            pos(1),
            cStm(2),
            e1(3),
            eth(4),
            vlan(5),
            ifport(6),
            xdsl(7)
        }
        MAX-ACCESS read-only
        STATUS current
        DESCRIPTION
            "This object indicates the QoS port schedualing config cir of the QoS module. 1: POS, 2: cSTM, 3: E1, 4: ETH, 5: VLAN, 6: ifport, 7: xDSL"
        ::= { optixLinkSearchEntry 2 }

    -- 1.3.6.1.4.1.2011.2.25.4.50.16.1.1.1.3
    optixLinkSearchTxBoardId OBJECT-TYPE
        SYNTAX Unsigned32
        MAX-ACCESS read-only
        STATUS current
        DESCRIPTION
            "This object indicates the QoS port schedualing cbs of the QoS module. Value range: 1 to 0xffffffff. Board IDs vary on different equipment."
        ::= { optixLinkSearchEntry 3 }

    -- 1.3.6.1.4.1.2011.2.25.4.50.16.1.1.1.4
    optixLinkSearchTxSubId OBJECT-TYPE
        SYNTAX Unsigned32
        MAX-ACCESS read-only
        STATUS current
        DESCRIPTION
            "This object indicates the QoS port schedualing config pir of the QoS module. Value range: 1 to 255."
        ::= { optixLinkSearchEntry 4 }

    -- 1.3.6.1.4.1.2011.2.25.4.50.16.1.1.1.5
    optixLinkSearchTxPortId OBJECT-TYPE
        SYNTAX Unsigned32
        MAX-ACCESS read-only
        STATUS current
        DESCRIPTION
            "This object indicates the QoS port schedualing config pbs of the QoS module. Value range: 1 to 0xffffffff."
        ::= { optixLinkSearchEntry 5 }

    -- 1.3.6.1.4.1.2011.2.25.4.50.16.1.1.1.6
    optixLinkSearchTxSlotVlan OBJECT-TYPE
        SYNTAX Unsigned32
        MAX-ACCESS read-only
        STATUS current
        DESCRIPTION
            "This object indicates the QoS port schedualing policy id of the QoS module. Value range for VLAN: 1 to 4096. Value range for VC-12: 1 to 63."
        ::= { optixLinkSearchEntry 6 }

    -- 1.3.6.1.4.1.2011.2.25.4.50.16.1.1.1.7
    optixLinkSearchRxNeId OBJECT-TYPE
        SYNTAX Unsigned32
        MAX-ACCESS read-only
        STATUS current
        DESCRIPTION
            "This object indicates the QoS port row status."
        ::= { optixLinkSearchEntry 7 }

    -- 1.3.6.1.4.1.2011.2.25.4.50.16.1.1.1.8
    optixLinkSearchRxPortType OBJECT-TYPE
        SYNTAX Unsigned32
        MAX-ACCESS read-only
        STATUS current
        DESCRIPTION
            "This object indicates the QoS port schedualing config cir of the QoS module. 1: POS, 2: cSTM, 3: E1, 4: ETH, 5: VLAN, 6: ifport, 7: xDSL"
        ::= { optixLinkSearchEntry 8 }

    -- 1.3.6.1.4.1.2011.2.25.4.50.16.1.1.1.9
    optixLinkSearchRxBoardId OBJECT-TYPE
        SYNTAX Unsigned32
        MAX-ACCESS read-only
        STATUS current
        DESCRIPTION
            "This object indicates the QoS port schedualing cbs of the QoS module. Value range: 1 to 0xffffffff. Board IDs vary on different equipment."
        ::= { optixLinkSearchEntry 9 }

    -- 1.3.6.1.4.1.2011.2.25.4.50.16.1.1.1.10
    optixLinkSearchRxSubId OBJECT-TYPE
        SYNTAX Unsigned32
        MAX-ACCESS read-only
        STATUS current
        DESCRIPTION
            "This object indicates the QoS port schedualing config pir of the QoS module. Value range: 1 to 255."
        ::= { optixLinkSearchEntry 10 }

    -- 1.3.6.1.4.1.2011.2.25.4.50.16.1.1.1.11
    optixLinkSearchRxPortId OBJECT-TYPE
        SYNTAX Unsigned32
        MAX-ACCESS read-only
        STATUS current
        DESCRIPTION
            "This object indicates the QoS port schedualing config pbs of the QoS module. Value range: 1 to 0xffffffff."
        ::= { optixLinkSearchEntry 11 }

    -- 1.3.6.1.4.1.2011.2.25.4.50.16.1.1.1.12
    optixLinkSearchRxSlotVlan OBJECT-TYPE
        SYNTAX Unsigned32
        MAX-ACCESS read-only
        STATUS current
        DESCRIPTION
            "This object indicates the QoS port schedualing policy id of the QoS module. Value range for VLAN: 1 to 4096. Value range for VC-12: 1 to 63."
        ::= { optixLinkSearchEntry 12 }

    -- 1.3.6.1.4.1.2011.2.25.4.50.16.1.1.1.13
    optixLinkSearchStartStatus OBJECT-TYPE
        SYNTAX INTEGER
        {
            invalied(0),
            enable(1)
        }
        MAX-ACCESS read-write
        STATUS current
        DESCRIPTION
            "This object start the QoS port schedualing of the QoS module. 0: invalid, 1: enable"
        ::= { optixLinkSearchEntry 13 }

END
