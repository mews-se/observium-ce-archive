-- OPTIX-PKT-CES-ACR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-CES-ACR-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,NOTIFICATION-TYPE
            FROM SNMPv2-SMI
        optixLogBoardId,optixLogSubCardId
            FROM OPTIX-BOARD-MANAGE-MIB
        optixUnitoUniAtmSrvIndex
            FROM OPTIX-ATMIMA-MIB
        RowStatus
            FROM SNMPv2-TC
        ;

    optixPktCesAcr MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies configuration information of CES ACR"
        REVISION "201204200000Z"
        DESCRIPTION
            "The initial revision of this MIB module1."
        ::={ optixProvisionPtn 24 }

    -- 1.3.6.1.4.1.2011.2.25.4.50.24.8
    optixPktCesAcrGroup OBJECT IDENTIFIER ::= { optixPktCesAcr 8 }

    -- 1.3.6.1.4.1.2011.2.25.4.50.24.8.1
    optixCesAcrModeTable OBJECT-TYPE
        SYNTAX SEQUENCE OF OptixCesAcrModeEntry
        MAX-ACCESS not-accessible
        STATUS current
        DESCRIPTION
            "This table describes the configurations of the CES ACR clock mode."
        ::= { optixPktCesAcrGroup 1 }

    -- 1.3.6.1.4.1.2011.2.25.4.50.24.8.1.1
    optixCesAcrModeEntry OBJECT-TYPE
        SYNTAX OptixCesAcrModeEntry
        MAX-ACCESS not-accessible
        STATUS current
        DESCRIPTION
            "Thisentry describes the configurations of the CES ACR clock mode."
        INDEX{ optixLogBoardId,optixLogSubCardId,optixCesAcrid,optixCesAcrHPId,optixCesAcrLPId }
        ::= { optixCesAcrModeTable 1 }

    OptixCesAcrModeEntry ::=
        SEQUENCE {
            optixCesAcrid
                Unsigned32,
            optixCesAcrHPId
                Unsigned32,
            optixCesAcrLPId
                Unsigned32,
            optixCesAcrClockMode
                INTEGER
        }

    -- 1.3.6.1.4.1.2011.2.25.4.50.24.8.1.1.1
    optixCesAcrid OBJECT-TYPE
        SYNTAX Unsigned32
        MAX-ACCESS not-accessible
        STATUS current
        DESCRIPTION
            "This object indicates the CES ACR ID."
        ::= { optixCesAcrModeEntry 1 }

    -- 1.3.6.1.4.1.2011.2.25.4.50.24.8.1.1.2
    optixCesAcrHPId OBJECT-TYPE
        SYNTAX Unsigned32
        MAX-ACCESS not-accessible
        STATUS current
        DESCRIPTION
            "This object indicates the higher order path ID of the CES ACR. The value range:1 to 0xffff"
        ::= { optixCesAcrModeEntry 2 }

    -- 1.3.6.1.4.1.2011.2.25.4.50.24.8.1.1.3
    optixCesAcrLPId OBJECT-TYPE
        SYNTAX Unsigned32
        MAX-ACCESS not-accessible
        STATUS current
        DESCRIPTION
            "This object indicates the lower order path ID of the CES ACR.The value range:1 to 0xffff"
        ::= { optixCesAcrModeEntry 3 }

    -- 1.3.6.1.4.1.2011.2.25.4.50.24.8.1.1.4
    optixCesAcrClockMode OBJECT-TYPE
        SYNTAX INTEGER
        {
            null(0),
            line(1),
            system(2)
        }
        MAX-ACCESS read-write
        STATUS current
        DESCRIPTION
            "This object indicates the CES ACR clock mode. 0: null, 1: line, 2: system"
        ::= { optixCesAcrModeEntry 4 }

    -- 1.3.6.1.4.1.2011.2.25.4.50.24.8.2
    optixCesAcrSourceTable OBJECT-TYPE
        SYNTAX SEQUENCE OF OptixCesAcrSourceEntry
        MAX-ACCESS not-accessible
        STATUS current
        DESCRIPTION
            "This table describes the configurations of the CES ACR clock source."
        ::= { optixPktCesAcrGroup 2 }

    -- 1.3.6.1.4.1.2011.2.25.4.50.24.8.2.1
    optixCesAcrSourceEntry OBJECT-TYPE
        SYNTAX OptixCesAcrSourceEntry
        MAX-ACCESS not-accessible
        STATUS current
        DESCRIPTION
            "This entry describes the configurations of the CES ACR clock source."
        INDEX{ optixCesAcrSTGBid,optixCesAcrSTGDomainID }
        ::= { optixCesAcrSourceTable 1 }

    OptixCesAcrSourceEntry ::=
        SEQUENCE {
            optixCesAcrSTGBid
                Unsigned32,
            optixCesAcrSTGDomainID
                INTEGER,
            optixCesAcrPwIndex
                Unsigned32,
            optixCesAcrRealPwIndex
                Unsigned32,
            optixCesAcrSourceBid
                Unsigned32,
            optixCesAcrSourceSubid
                Unsigned32,
            optixCesAcrSourcePid
                Unsigned32,
            optixCesAcrSourceRowStatus
                RowStatus
        }

    -- 1.3.6.1.4.1.2011.2.25.4.50.24.8.2.1.1
    optixCesAcrSTGBid OBJECT-TYPE
        SYNTAX Unsigned32
        MAX-ACCESS not-accessible
        STATUS current
        DESCRIPTION
            "This object indicates the STG slot ID."
        ::= { optixCesAcrSourceEntry 1 }

    -- 1.3.6.1.4.1.2011.2.25.4.50.24.8.2.1.2
    optixCesAcrSTGDomainID OBJECT-TYPE
        SYNTAX INTEGER
        {
            all(0),
            cesacr1(1),
            cesacr2(2),
            cesacr3(3),
            cesacr4(4)
        }
        MAX-ACCESS not-accessible
        STATUS current
        DESCRIPTION
            "This object indicates the STG domain number. 0: all, 1: cesacr1, 2: cesacr2, 3: cesacr3, 4: cesacr4"
        ::= { optixCesAcrSourceEntry 2 }

    -- 1.3.6.1.4.1.2011.2.25.4.50.24.8.2.1.3
    optixCesAcrPwIndex OBJECT-TYPE
        SYNTAX Unsigned32
        MAX-ACCESS read-create
        STATUS current
        DESCRIPTION
            "This object indicates the PW index of the CES ACR. Value range: 1~0xFFFFFFFF."
        ::= { optixCesAcrSourceEntry 3 }

    -- 1.3.6.1.4.1.2011.2.25.4.50.24.8.2.1.4
    optixCesAcrRealPwIndex OBJECT-TYPE
        SYNTAX Unsigned32
        MAX-ACCESS read-only
        STATUS current
        DESCRIPTION
            "This object indicates the actual PW index of the CES ACR. Value range: 1~0xFFFFFFFF."
        ::= { optixCesAcrSourceEntry 4 }

    -- 1.3.6.1.4.1.2011.2.25.4.50.24.8.2.1.5
    optixCesAcrSourceBid OBJECT-TYPE
        SYNTAX Unsigned32
        MAX-ACCESS not-accessible
        STATUS current
        DESCRIPTION
            "This object indicates the slot ID of the board to which the ACR clock is bound."
        ::= { optixCesAcrSourceEntry 5 }

    -- 1.3.6.1.4.1.2011.2.25.4.50.24.8.2.1.6
    optixCesAcrSourceSubid OBJECT-TYPE
        SYNTAX Unsigned32
        MAX-ACCESS not-accessible
        STATUS current
        DESCRIPTION
            "This object indicates the subboard ID of the board to which the ACR clock is bound."
        ::= { optixCesAcrSourceEntry 6 }

    -- 1.3.6.1.4.1.2011.2.25.4.50.24.8.2.1.7
    optixCesAcrSourcePid OBJECT-TYPE
        SYNTAX Unsigned32
        MAX-ACCESS not-accessible
        STATUS current
        DESCRIPTION
            "This object indicates the port number of the board to which the ACR clock is bound."
        ::= { optixCesAcrSourceEntry 7 }

    -- 1.3.6.1.4.1.2011.2.25.4.50.24.8.2.1.255
    optixCesAcrSourceRowStatus OBJECT-TYPE
        SYNTAX RowStatus
        MAX-ACCESS read-create
        STATUS current
        DESCRIPTION
            "This object describes the configurations of the CES ACR clock row status."
        ::= { optixCesAcrSourceEntry 255 }

    -- 1.3.6.1.4.1.2011.2.25.4.50.24.8.3
    optixCesAcrTrackStatusTable OBJECT-TYPE
        SYNTAX SEQUENCE OF OptixCesAcrTrackStatusEntry
        MAX-ACCESS not-accessible
        STATUS current
        DESCRIPTION
            "This table describes the configurations of the clock tracing status."
        ::= { optixPktCesAcrGroup 3 }

    -- 1.3.6.1.4.1.2011.2.25.4.50.24.8.3.1
    optixCesAcrTrackStatusEntry OBJECT-TYPE
        SYNTAX OptixCesAcrTrackStatusEntry
        MAX-ACCESS not-accessible
        STATUS current
        DESCRIPTION
            "Thisentry describes the configurations of the clock tracking status."
        INDEX{ optixLogBoardId,optixLogSubCardId,optixCesAcrClkId }
        ::= { optixCesAcrTrackStatusTable 1 }

    OptixCesAcrTrackStatusEntry ::=
        SEQUENCE {
            optixCesAcrClkId
                Unsigned32,
            optixCesAcrTrackMode
                INTEGER,
            optixCesAcrLockMode
                INTEGER
        }

    -- 1.3.6.1.4.1.2011.2.25.4.50.24.8.3.1.1
    optixCesAcrClkId OBJECT-TYPE
        SYNTAX Unsigned32
        MAX-ACCESS not-accessible
        STATUS current
        DESCRIPTION
            "This object indicates the ACR clock ID."
        ::= { optixCesAcrTrackStatusEntry 1 }

    -- 1.3.6.1.4.1.2011.2.25.4.50.24.8.3.1.2
    optixCesAcrTrackMode OBJECT-TYPE
        SYNTAX INTEGER
        {
            track(1),
            keep(2),
            free(3)
        }
        MAX-ACCESS read-only
        STATUS current
        DESCRIPTION
            "This object indicates the CES ACR tracking status. 1: track, 2: keep, 3: free"
        ::= { optixCesAcrTrackStatusEntry 2 }

    -- 1.3.6.1.4.1.2011.2.25.4.50.24.8.3.1.3
    optixCesAcrLockMode OBJECT-TYPE
        SYNTAX INTEGER
        {
            unlock(0),
            lock(1)
        }
        MAX-ACCESS read-only
        STATUS current
        DESCRIPTION
            "This object indicates the CES ACR locking mode. 0: unlock, 1: lock"
        ::= { optixCesAcrTrackStatusEntry 3 }

    -- 1.3.6.1.4.1.2011.2.25.4.50.24.8.4
    optixCesAcrSdhRetimingClkSrcTable OBJECT-TYPE
        SYNTAX SEQUENCE OF OptixCesAcrSdhRetimingClkSrcEntry
        MAX-ACCESS not-accessible
        STATUS current
        DESCRIPTION
            "This table describes the configurations of the SDH retimingclock source."
        ::= { optixPktCesAcrGroup 4 }

    -- 1.3.6.1.4.1.2011.2.25.4.50.24.8.4.1
    optixCesAcrSdhRetimingClkSrcEntry OBJECT-TYPE
        SYNTAX OptixCesAcrSdhRetimingClkSrcEntry
        MAX-ACCESS not-accessible
        STATUS current
        DESCRIPTION
            "This entry describes the configurations of the SDH retiming clock source."
        INDEX{ optixCesAcrSTGBid }
        ::= { optixCesAcrSdhRetimingClkSrcTable 1 }

    OptixCesAcrSdhRetimingClkSrcEntry ::=
        SEQUENCE {
            optixCesAcrSdhLockMode
                INTEGER,
            optixCesAcrSdhSubboardId
                Unsigned32,
            optixCesAcrSdhPortId
                Unsigned32
        }

    -- 1.3.6.1.4.1.2011.2.25.4.50.24.8.4.1.1
    optixCesAcrSdhLockMode OBJECT-TYPE
        SYNTAX INTEGER
        {
            master(0),
            slave(1),
            line(2)
        }
        MAX-ACCESS read-write
        STATUS current
        DESCRIPTION
            "This object indicates the SDH retiming clock mode. 0: master, 1: slave, 2: line"
        ::= { optixCesAcrSdhRetimingClkSrcEntry 1 }

    -- 1.3.6.1.4.1.2011.2.25.4.50.24.8.4.1.2
    optixCesAcrSdhSubboardId OBJECT-TYPE
        SYNTAX Unsigned32
        MAX-ACCESS read-write
        STATUS current
        DESCRIPTION
            "This object indicates the suboard ID of the SDH port for the retiming clock mode."
        ::= { optixCesAcrSdhRetimingClkSrcEntry 2 }

    -- 1.3.6.1.4.1.2011.2.25.4.50.24.8.4.1.3
    optixCesAcrSdhPortId OBJECT-TYPE
        SYNTAX Unsigned32
        MAX-ACCESS read-write
        STATUS current
        DESCRIPTION
            "This object indicates the port number of the SDH port for the retiming clock mode."
        ::= { optixCesAcrSdhRetimingClkSrcEntry 3 }

    -- 1.3.6.1.4.1.2011.2.25.4.50.24.8.5
    optixCesAcrSdhportE1ClkRvtSrcTable OBJECT-TYPE
        SYNTAX SEQUENCE OF OptixCesAcrSdhportE1ClkRvtSrcEntry
        MAX-ACCESS not-accessible
        STATUS current
        DESCRIPTION
            "This table describes the revertive source of the E1 clockof the SDH port."
        ::= { optixPktCesAcrGroup 5 }

    -- 1.3.6.1.4.1.2011.2.25.4.50.24.8.5.1
    optixCesAcrSdhportE1ClkRvtSrcEntry OBJECT-TYPE
        SYNTAX OptixCesAcrSdhportE1ClkRvtSrcEntry
        MAX-ACCESS not-accessible
        STATUS current
        DESCRIPTION
            "Thisentry describes the revertive source of the E1 clockof the SDH port."
        INDEX{ optixLogBoardId,optixLogSubCardId,optixCesAcrSdhportE1ClkSrc }
        ::= { optixCesAcrSdhportE1ClkRvtSrcTable 1 }

    OptixCesAcrSdhportE1ClkRvtSrcEntry ::=
        SEQUENCE {
            optixCesAcrSdhportE1ClkSrc
                Unsigned32,
            optxiCesAcrSdhportE1ClkRvtSrcPortId
                Unsigned32,
            optxiCesAcrSdhportE1ClkRvtSrcHP
                Unsigned32,
            optxiCesAcrSdhportE1ClkRvtSrcLP
                Unsigned32
        }

    -- 1.3.6.1.4.1.2011.2.25.4.50.24.8.5.1.1
    optixCesAcrSdhportE1ClkSrc OBJECT-TYPE
        SYNTAX Unsigned32
        MAX-ACCESS not-accessible
        STATUS current
        DESCRIPTION
            "This object indicates the E1 clock source."
        ::= { optixCesAcrSdhportE1ClkRvtSrcEntry 1 }

    -- 1.3.6.1.4.1.2011.2.25.4.50.24.8.5.1.2
    optxiCesAcrSdhportE1ClkRvtSrcPortId OBJECT-TYPE
        SYNTAX Unsigned32
        MAX-ACCESS read-write
        STATUS current
        DESCRIPTION
            "This object indicates the port number of the E1 clock source."
        ::= { optixCesAcrSdhportE1ClkRvtSrcEntry 2 }

    -- 1.3.6.1.4.1.2011.2.25.4.50.24.8.5.1.3
    optxiCesAcrSdhportE1ClkRvtSrcHP OBJECT-TYPE
        SYNTAX Unsigned32
        MAX-ACCESS read-write
        STATUS current
        DESCRIPTION
            "This object indicates the higher order path ID of the E1 clock source.The value range:1 to 0xffff"
        ::= { optixCesAcrSdhportE1ClkRvtSrcEntry 3 }

    -- 1.3.6.1.4.1.2011.2.25.4.50.24.8.5.1.4
    optxiCesAcrSdhportE1ClkRvtSrcLP OBJECT-TYPE
        SYNTAX Unsigned32
        MAX-ACCESS read-write
        STATUS current
        DESCRIPTION
            "This object indicates the lower order path ID of the E1 clock source.The value range:1 to 0xffff"
        ::= { optixCesAcrSdhportE1ClkRvtSrcEntry 4 }

    -- 1.3.6.1.4.1.2011.2.25.4.50.24.8.6
    optixCesAcrSourceMember OBJECT IDENTIFIER ::= { optixPktCesAcrGroup 6 }

    -- 1.3.6.1.4.1.2011.2.25.4.50.24.8.6.1
    optixCesAcrSTGBidTrapInfo OBJECT-TYPE
        SYNTAX Unsigned32
        MAX-ACCESS accessible-for-notify
        STATUS current
        DESCRIPTION
            "This object indicates the STG slot ID."
        ::= { optixCesAcrSourceMember 1 }

    -- 1.3.6.1.4.1.2011.2.25.4.50.24.8.6.2
    optixCesAcrSTGDomainTrapInfo OBJECT-TYPE
        SYNTAX INTEGER
        {
            all(0),
            cesacr1(1),
            cesacr2(2),
            cesacr3(3),
            cesacr4(4)
        }
        MAX-ACCESS accessible-for-notify
        STATUS current
        DESCRIPTION
            "This object indicates the STG domain number. 0: all, 1: cesacr1, 2: cesacr2, 3: cesacr3, 4: cesacr4"
        ::= { optixCesAcrSourceMember 2 }

    -- 1.3.6.1.4.1.2011.2.25.4.50.24.8.6.3
    optixCesAcrRealPwIndexTrapInfo OBJECT-TYPE
        SYNTAX Unsigned32
        MAX-ACCESS accessible-for-notify
        STATUS current
        DESCRIPTION
            "This object indicates the actual PW index of the CES ACR."
        ::= { optixCesAcrSourceMember 3 }

    -- 1.3.6.1.4.1.2011.2.25.4.50.24.8.7
    optixCesAcrSourceEvent OBJECT IDENTIFIER ::= { optixPktCesAcrGroup 7 }

    -- 1.3.6.1.4.1.2011.2.25.4.50.24.8.7.1
    optixCesAcrSourceTrap NOTIFICATION-TYPE
        OBJECTS{ optixCesAcrRealPwIndexTrapInfo,optixCesAcrSTGDomainTrapInfo,optixCesAcrSTGBidTrapInfo }
        STATUS current
        DESCRIPTION
            "This Trap describes the configurations of the CES ACR clock Event."
        ::= { optixCesAcrSourceEvent 1 }

    -- 1.3.6.1.4.1.2011.2.25.4.50.24.8.8
    optixCesAcrBindSourceTable OBJECT-TYPE
        SYNTAX SEQUENCE OF OptixCesAcrBindSourceEntry
        MAX-ACCESS not-accessible
        STATUS current
        DESCRIPTION
            "This table describes the configurations of the CES ACR clock source."
        ::= { optixPktCesAcrGroup 8 }

    -- 1.3.6.1.4.1.2011.2.25.4.50.24.8.8.1
    optixCesAcrBindSourceEntry OBJECT-TYPE
        SYNTAX OptixCesAcrBindSourceEntry
        MAX-ACCESS not-accessible
        STATUS current
        DESCRIPTION
            "This object indicates the STG domain number."
        INDEX{ optixCesAcrBindSTGBid,optixCesAcrBindSTGDomain,optixCesAcrBindSourceBid,optixCesAcrBindSourceSubid,optixCesAcrBindSourcePid }
        ::= { optixCesAcrBindSourceTable 1 }

    OptixCesAcrBindSourceEntry ::=
        SEQUENCE {
            optixCesAcrBindSTGBid
                Unsigned32,
            optixCesAcrBindSTGDomain
                INTEGER,
            optixCesAcrBindSourceBid
                Unsigned32,
            optixCesAcrBindSourceSubid
                Unsigned32,
            optixCesAcrBindSourcePid
                Unsigned32,
            optixCesAcrBindSourceRowStatus
                RowStatus
        }

    -- 1.3.6.1.4.1.2011.2.25.4.50.24.8.8.1.1
    optixCesAcrBindSTGBid OBJECT-TYPE
        SYNTAX Unsigned32
        MAX-ACCESS not-accessible
        STATUS current
        DESCRIPTION
            "This object indicates the STG slot ID."
        ::= { optixCesAcrBindSourceEntry 1 }

    -- 1.3.6.1.4.1.2011.2.25.4.50.24.8.8.1.2
    optixCesAcrBindSTGDomain OBJECT-TYPE
        SYNTAX INTEGER
        {
            syn(1),
            cesacr1(2),
            cesacr2(3),
            cesacr3(4),
            cesacr4(5),
            topacr1(6),
            topdiff1(7),
            topdiff2(8),
            topdiff3(9)
        }
        MAX-ACCESS not-accessible
        STATUS current
        DESCRIPTION
            "This object indicates the STG domain number. 1: syn, 2: cesacr1, 3: cesacr2, 4: cesacr3, 5: cesacr4, 6: topacr1, 7: topdiff1, 8: topdiff2, 9: topdiff3"
        ::= { optixCesAcrBindSourceEntry 2 }

    -- 1.3.6.1.4.1.2011.2.25.4.50.24.8.8.1.3
    optixCesAcrBindSourceBid OBJECT-TYPE
        SYNTAX Unsigned32
        MAX-ACCESS not-accessible
        STATUS current
        DESCRIPTION
            "This object indicates theslot ID of the board to which the ACR clock is bound."
        ::= { optixCesAcrBindSourceEntry 3 }

    -- 1.3.6.1.4.1.2011.2.25.4.50.24.8.8.1.4
    optixCesAcrBindSourceSubid OBJECT-TYPE
        SYNTAX Unsigned32
        MAX-ACCESS not-accessible
        STATUS current
        DESCRIPTION
            "This object indicates the subboard ID of the board to which the ACR clock is bound."
        ::= { optixCesAcrBindSourceEntry 4 }

    -- 1.3.6.1.4.1.2011.2.25.4.50.24.8.8.1.5
    optixCesAcrBindSourcePid OBJECT-TYPE
        SYNTAX Unsigned32
        MAX-ACCESS not-accessible
        STATUS current
        DESCRIPTION
            "This object indicates the port number of the board to which the ACR clock is bound."
        ::= { optixCesAcrBindSourceEntry 5 }

    -- 1.3.6.1.4.1.2011.2.25.4.50.24.8.8.1.255
    optixCesAcrBindSourceRowStatus OBJECT-TYPE
        SYNTAX RowStatus
        MAX-ACCESS read-create
        STATUS current
        DESCRIPTION
            "This object describes the configurations of the CES ACR clock row status."
        ::= { optixCesAcrBindSourceEntry 255 }

    -- 1.3.6.1.4.1.2011.2.25.4.50.24.8.9
    optixCesAcrBindSourceExTable OBJECT-TYPE
        SYNTAX SEQUENCE OF OptixCesAcrBindSourceExEntry
        MAX-ACCESS not-accessible
        STATUS current
        DESCRIPTION
            "This table describes the expanded configurations of the CES ACR clock source bind port."
        ::= { optixPktCesAcrGroup 9 }

    -- 1.3.6.1.4.1.2011.2.25.4.50.24.8.9.1
    optixCesAcrBindSourceExEntry OBJECT-TYPE
        SYNTAX OptixCesAcrBindSourceExEntry
        MAX-ACCESS not-accessible
        STATUS current
        DESCRIPTION
            "This entry describes the expanded configurations of the CES ACR clock source bind port."
        INDEX{ optixCesAcrBindSTGBid,optixCesAcrBindSTGDomain,optixCesAcrBindSourceBid,optixCesAcrBindSourceSubid,optixCesAcrBindSourcePid,optixCesAcrBindSourceExVC4,optixCesAcrBindSourceExVC12 }
        ::= { optixCesAcrBindSourceExTable 1 }

    OptixCesAcrBindSourceExEntry ::=
        SEQUENCE {
            optixCesAcrBindSourceExVC4
                Unsigned32,
            optixCesAcrBindSourceExVC12
                Unsigned32,
            optixCesAcrBindSourceExRowStatus
                RowStatus
        }

    -- 1.3.6.1.4.1.2011.2.25.4.50.24.8.9.1.1
    optixCesAcrBindSourceExVC4 OBJECT-TYPE
        SYNTAX Unsigned32
        MAX-ACCESS not-accessible
        STATUS current
        DESCRIPTION
            "This object describes the VC4 path id."
        ::= { optixCesAcrBindSourceExEntry 1 }

    -- 1.3.6.1.4.1.2011.2.25.4.50.24.8.9.1.2
    optixCesAcrBindSourceExVC12 OBJECT-TYPE
        SYNTAX Unsigned32
        MAX-ACCESS not-accessible
        STATUS current
        DESCRIPTION
            "This object describes the VC12 path id."
        ::= { optixCesAcrBindSourceExEntry 2 }

    -- 1.3.6.1.4.1.2011.2.25.4.50.24.8.9.1.255
    optixCesAcrBindSourceExRowStatus OBJECT-TYPE
        SYNTAX RowStatus
        MAX-ACCESS read-create
        STATUS current
        DESCRIPTION
            "This object describes the row status in the expanded configurations of the CES ACR clock source bind port."
        ::= { optixCesAcrBindSourceExEntry 255 }

    -- 1.3.6.1.4.1.2011.2.25.4.50.24.8.10
    optixCesAcrE1SendClkTable OBJECT-TYPE
        SYNTAX SEQUENCE OF OptixCesAcrE1SendClkEntry
        MAX-ACCESS not-accessible
        STATUS current
        DESCRIPTION
            "This table describes the E1 clock info."
        ::= { optixPktCesAcrGroup 10 }

    -- 1.3.6.1.4.1.2011.2.25.4.50.24.8.10.1
    optixCesAcrE1SendClkEntry OBJECT-TYPE
        SYNTAX OptixCesAcrE1SendClkEntry
        MAX-ACCESS not-accessible
        STATUS current
        DESCRIPTION
            "This Entry describes the E1 clock info."
        INDEX{ optixCesAcrid }
        ::= { optixCesAcrE1SendClkTable 1 }

    OptixCesAcrE1SendClkEntry ::=
        SEQUENCE {
            optixCesAcrSendSTGBid
                Unsigned32,
            optixCesAcrSendSTGID
                Unsigned32
        }

    -- 1.3.6.1.4.1.2011.2.25.4.50.24.8.10.1.1
    optixCesAcrSendSTGBid OBJECT-TYPE
        SYNTAX Unsigned32
        MAX-ACCESS read-write
        STATUS current
        DESCRIPTION
            "This object indicates the clock board ID."
        ::= { optixCesAcrE1SendClkEntry 1 }

    -- 1.3.6.1.4.1.2011.2.25.4.50.24.8.10.1.2
    optixCesAcrSendSTGID OBJECT-TYPE
        SYNTAX Unsigned32
        MAX-ACCESS read-write
        STATUS current
        DESCRIPTION
            "This object indicates the E1 clock ID."
        ::= { optixCesAcrE1SendClkEntry 2 }

    -- 1.3.6.1.4.1.2011.2.25.4.50.24.8.11
    optixCesAcrE1SourceTable OBJECT-TYPE
        SYNTAX SEQUENCE OF OptixCesAcrE1SourceEntry
        MAX-ACCESS not-accessible
        STATUS current
        DESCRIPTION
            "This table describes the configurations of the CES ACR E1 clock source"
        ::= { optixPktCesAcrGroup 11 }

    -- 1.3.6.1.4.1.2011.2.25.4.50.24.8.11.1
    optixCesAcrE1SourceEntry OBJECT-TYPE
        SYNTAX OptixCesAcrE1SourceEntry
        MAX-ACCESS not-accessible
        STATUS current
        DESCRIPTION
            "This Entry describes the configurations of the CES ACR E1 clock source"
        INDEX{ optixCesAcrSendSTGBid,optixCesAcrSendSTGID }
        ::= { optixCesAcrE1SourceTable 1 }

    OptixCesAcrE1SourceEntry ::=
        SEQUENCE {
            optixCesAcrE1SourceBid
                Unsigned32,
            optixCesAcrE1SourceSubid
                Unsigned32,
            optixCesAcrE1SourcePid
                Unsigned32,
            optxiCesAcrE1SourceHP
                Unsigned32,
            optxiCesAcrE1sourceLP
                Unsigned32,
            optixCesAcrE1SourceRowStatus
                RowStatus
        }

    -- 1.3.6.1.4.1.2011.2.25.4.50.24.8.11.1.1
    optixCesAcrE1SourceBid OBJECT-TYPE
        SYNTAX Unsigned32
        MAX-ACCESS read-create
        STATUS current
        DESCRIPTION
            "This object indicates the board ID bounded with the ACR E1 clock."
        ::= { optixCesAcrE1SourceEntry 1 }

    -- 1.3.6.1.4.1.2011.2.25.4.50.24.8.11.1.2
    optixCesAcrE1SourceSubid OBJECT-TYPE
        SYNTAX Unsigned32
        MAX-ACCESS read-create
        STATUS current
        DESCRIPTION
            "This object indicates the subboard ID of the board to which the ACR E1 clock is bound."
        ::= { optixCesAcrE1SourceEntry 2 }

    -- 1.3.6.1.4.1.2011.2.25.4.50.24.8.11.1.3
    optixCesAcrE1SourcePid OBJECT-TYPE
        SYNTAX Unsigned32
        MAX-ACCESS read-create
        STATUS current
        DESCRIPTION
            "This object indicates the port number of the board to which the ACR E1 clock is bound."
        ::= { optixCesAcrE1SourceEntry 3 }

    -- 1.3.6.1.4.1.2011.2.25.4.50.24.8.11.1.4
    optxiCesAcrE1SourceHP OBJECT-TYPE
        SYNTAX Unsigned32
        MAX-ACCESS read-create
        STATUS current
        DESCRIPTION
            "This object indicates the higher order path ID of the E1 clock source.The value range:1 to 0xffff"
        ::= { optixCesAcrE1SourceEntry 4 }

    -- 1.3.6.1.4.1.2011.2.25.4.50.24.8.11.1.5
    optxiCesAcrE1sourceLP OBJECT-TYPE
        SYNTAX Unsigned32
        MAX-ACCESS read-create
        STATUS current
        DESCRIPTION
            "This object indicates the lower order path ID of the E1 clock source. Value range:1 to 0xffff"
        ::= { optixCesAcrE1SourceEntry 5 }

    -- 1.3.6.1.4.1.2011.2.25.4.50.24.8.11.1.255
    optixCesAcrE1SourceRowStatus OBJECT-TYPE
        SYNTAX RowStatus
        MAX-ACCESS read-create
        STATUS current
        DESCRIPTION
            "This object describes the configurations of the ACR E1 clock row status."
        ::= { optixCesAcrE1SourceEntry 255 }

END
