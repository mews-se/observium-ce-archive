-- OPTIX-GLOBAL-MON-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-MON-MIB DEFINITIONS ::= BEGIN
    IMPORTS
        optixCommonGlobal
            FROM OPTIX-OID-MIB
        DateAndTime
            FROM SNMPv2-TC
        Unsigned32,MODULE-IDENTITY,OBJECT-TYPE
            FROM SNMPv2-SMI
        ;

    optixGlobalMON MODULE-IDENTITY
        LAST-UPDATED "201607011131Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "MON module"
        REVISION "201607011131Z"
        DESCRIPTION
            "The initial version"
        ::={ optixCommonGlobal 7 }

    -- 1.3.6.1.4.1.2011.2.25.3.40.7.1
    optixLanguageCodeManager OBJECT IDENTIFIER ::= { optixGlobalMON 1 }

    -- 1.3.6.1.4.1.2011.2.25.3.40.7.1.1
    optixLanguageCode OBJECT-TYPE
        SYNTAX INTEGER
        {
            default(0),
            gbk(1),
            iso88591(2),
            utf8(3)
        }
        MAX-ACCESS read-write
        STATUS current
        DESCRIPTION
            "Language type."
        ::= { optixLanguageCodeManager 1 }

    -- 1.3.6.1.4.1.2011.2.25.3.40.7.2
    optixDataAndTimeManager OBJECT IDENTIFIER ::= { optixGlobalMON 2 }

    -- 1.3.6.1.4.1.2011.2.25.3.40.7.2.1
    optixTimezoneGroup OBJECT IDENTIFIER ::= { optixDataAndTimeManager 1 }

    -- 1.3.6.1.4.1.2011.2.25.3.40.7.2.1.1
    optixTimezone OBJECT-TYPE
        SYNTAX OCTET STRING
        MAX-ACCESS read-write
        STATUS current
        DESCRIPTION
            "time zone."
        ::= { optixTimezoneGroup 1 }

    -- 1.3.6.1.4.1.2011.2.25.3.40.7.2.1.2
    optixRegion OBJECT-TYPE
        SYNTAX OCTET STRING
        MAX-ACCESS read-write
        STATUS current
        DESCRIPTION
            "region."
        ::= { optixTimezoneGroup 2 }

    -- 1.3.6.1.4.1.2011.2.25.3.40.7.2.2
    optixDaylightSavingTime OBJECT IDENTIFIER ::= { optixDataAndTimeManager 2 }

    -- 1.3.6.1.4.1.2011.2.25.3.40.7.2.2.1
    optixDaylightSavingTimeSwitch OBJECT-TYPE
        SYNTAX INTEGER
        {
            disable(0),
            enable(1)
        }
        MAX-ACCESS read-write
        STATUS current
        DESCRIPTION
            "Daylight save time switch."
        ::= { optixDaylightSavingTime 1 }

    -- 1.3.6.1.4.1.2011.2.25.3.40.7.2.2.2
    optixDaylightSavingTimeBeginAdjustMode OBJECT-TYPE
        SYNTAX INTEGER
        {
            date(0),
            weekbackward(2),
            weekforward(1)
        }
        MAX-ACCESS read-write
        STATUS current
        DESCRIPTION
            "Begin adjustment mode."
        ::= { optixDaylightSavingTime 2 }

    -- 1.3.6.1.4.1.2011.2.25.3.40.7.2.2.3
    optixDaylightSavingTimeEndAdjustMode OBJECT-TYPE
        SYNTAX INTEGER
        {
            date(0),
            weekbackward(2),
            weekforward(1)
        }
        MAX-ACCESS read-write
        STATUS current
        DESCRIPTION
            "End adjustment mode."
        ::= { optixDaylightSavingTime 3 }

    -- 1.3.6.1.4.1.2011.2.25.3.40.7.2.2.4
    optixDaylightSavingTimeAdjustMinute OBJECT-TYPE
        SYNTAX INTEGER (0..120)
        MAX-ACCESS read-write
        STATUS current
        DESCRIPTION
            "Adjusted minutes."
        ::= { optixDaylightSavingTime 4 }

    -- 1.3.6.1.4.1.2011.2.25.3.40.7.2.2.5
    optixDaylightSavingTimeStartDate OBJECT-TYPE
        SYNTAX DateAndTime
        MAX-ACCESS read-write
        STATUS current
        DESCRIPTION
            "start date."
        ::= { optixDaylightSavingTime 5 }

    -- 1.3.6.1.4.1.2011.2.25.3.40.7.2.2.6
    optixDaylightSavingTimeStartWeek OBJECT-TYPE
        SYNTAX INTEGER (1..5)
        MAX-ACCESS read-write
        STATUS current
        DESCRIPTION
            "Start week."
        ::= { optixDaylightSavingTime 6 }

    -- 1.3.6.1.4.1.2011.2.25.3.40.7.2.2.7
    optixDaylightSavingTimeStartWeekday OBJECT-TYPE
        SYNTAX INTEGER
        {
            sunday(0),
            monday(1),
            thusday(2),
            wednesday(3),
            thursday(4),
            friday(5),
            saturday(6)
        }
        MAX-ACCESS read-write
        STATUS current
        DESCRIPTION
            "Start weekday."
        ::= { optixDaylightSavingTime 7 }

    -- 1.3.6.1.4.1.2011.2.25.3.40.7.2.2.8
    optixDaylightSavingTimeEndDate OBJECT-TYPE
        SYNTAX DateAndTime
        MAX-ACCESS read-write
        STATUS current
        DESCRIPTION
            "end date."
        ::= { optixDaylightSavingTime 8 }

    -- 1.3.6.1.4.1.2011.2.25.3.40.7.2.2.9
    optixDaylightSavingTimeEndWeek OBJECT-TYPE
        SYNTAX INTEGER (1..5)
        MAX-ACCESS read-write
        STATUS current
        DESCRIPTION
            "End week."
        ::= { optixDaylightSavingTime 9 }

    -- 1.3.6.1.4.1.2011.2.25.3.40.7.2.2.10
    optixDaylightSavingTimeEndWeekday OBJECT-TYPE
        SYNTAX INTEGER
        {
            sunday(0),
            monday(1),
            thusday(2),
            wednesday(3),
            thursday(4),
            friday(5),
            saturday(6)
        }
        MAX-ACCESS read-write
        STATUS current
        DESCRIPTION
            "End weekday."
        ::= { optixDaylightSavingTime 10 }

    -- 1.3.6.1.4.1.2011.2.25.3.40.7.2.2.11
    optixDaylightSavingTimeState OBJECT-TYPE
        SYNTAX INTEGER
        {
            false(0),
            true(1)
        }
        MAX-ACCESS read-only
        STATUS current
        DESCRIPTION
            "Saving time state."
        ::= { optixDaylightSavingTime 11 }

    -- 1.3.6.1.4.1.2011.2.25.3.40.7.2.3
    optixSystemDateAndTimeGroup OBJECT IDENTIFIER ::= { optixDataAndTimeManager 3 }

    -- 1.3.6.1.4.1.2011.2.25.3.40.7.2.3.1
    optixSystemDateAndTime OBJECT-TYPE
        SYNTAX DateAndTime
        MAX-ACCESS read-write
        STATUS current
        DESCRIPTION
            "system time."
        ::= { optixSystemDateAndTimeGroup 1 }

    -- 1.3.6.1.4.1.2011.2.25.3.40.7.2.3.2
    optixDateAndTimeLocalization OBJECT-TYPE
        SYNTAX INTEGER
        {
            disable(0),
            enableFrom1990(1),
            enableFrom1970(2)
        }
        MAX-ACCESS read-only
        STATUS current
        DESCRIPTION
            "Local time."
        ::= { optixSystemDateAndTimeGroup 2 }

    -- 1.3.6.1.4.1.2011.2.25.3.40.7.3
    optixInitializeSystem OBJECT IDENTIFIER ::= { optixGlobalMON 3 }

    -- 1.3.6.1.4.1.2011.2.25.3.40.7.3.1
    optixBoardId OBJECT-TYPE
        SYNTAX Unsigned32 (0..65535)
        MAX-ACCESS read-write
        STATUS current
        DESCRIPTION
            "Board slot ID."
        ::= { optixInitializeSystem 1 }

    -- 1.3.6.1.4.1.2011.2.25.3.40.7.3.2
    optixResetMode OBJECT-TYPE
        SYNTAX INTEGER
        {
            cold(0),
            warm(1),
            dberase(2),
            dswdl(3),
            swdlall(4),
            beraseall(5),
            dbfdl(6),
            swdlne(9)
        }
        MAX-ACCESS read-write
        STATUS current
        DESCRIPTION
            "Reset mode."
        ::= { optixInitializeSystem 2 }

END
