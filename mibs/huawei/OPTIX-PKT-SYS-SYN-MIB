-- OPTIX-PKT-SYS-SYN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-SYS-SYN-MIB DEFINITIONS ::= BEGIN
    IMPORTS
        optixProvisionPtn
            FROM OPTIX-OID-MIB
        OBJECT-GROUP,MODULE-COMPLIANCE
            FROM SNMPv2-CONF
        Gauge32,MODULE-IDENTITY,Unsigned32,OBJECT-TYPE
            FROM SNMPv2-SMI
        optixLogBoardId
            FROM OPTIX-BOARD-MANAGE-MIB
        RowStatus
            FROM SNMPv2-TC
        ;

    optixpktSYSsyn MODULE-IDENTITY
        LAST-UPDATED "201401211534Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations ofsystem clock source management."
        REVISION "201401211534Z"
        DESCRIPTION
            "The initial revision of this MIB module1."
        ::={ optixProvisionPtn 35 }

    -- 1.3.6.1.4.1.2011.2.25.4.50.35.1
    optixpktSYSsynGroup OBJECT IDENTIFIER ::= { optixpktSYSsyn 1 }

    -- 1.3.6.1.4.1.2011.2.25.4.50.35.1.1
    optixpktSYSsynTable OBJECT-TYPE
        SYNTAX SEQUENCE OF OptixpktSYSsynEntry
        MAX-ACCESS not-accessible
        STATUS current
        DESCRIPTION
            "This table contains configuration information of system clock sources."
        ::= { optixpktSYSsynGroup 1 }

    -- 1.3.6.1.4.1.2011.2.25.4.50.35.1.1.1
    optixpktSYSsynEntry OBJECT-TYPE
        SYNTAX OptixpktSYSsynEntry
        MAX-ACCESS not-accessible
        STATUS current
        DESCRIPTION
            "This table contains configuration information of system clock sources."
        INDEX{ optixLogBoardId }
        ::= { optixpktSYSsynTable 1 }

    OptixpktSYSsynEntry ::=
        SEQUENCE {
            optixpktSYSsynCurSyn
                Unsigned32,
            optixpktSYSCurSynS1Value
                INTEGER,
            optixpktSYSsynPriTableCLkList
                OCTET STRING,
            optixpktSYSsyn24HourKeepMode
                Unsigned32,
            optixpktSYSsynSwState
                INTEGER,
            optixpktsynProtectSynWtrTime
                Unsigned32,
            optixpktSYSclkpllLockstate
                INTEGER,
            optixpktSysSynWorkMode
                INTEGER
        }

    -- 1.3.6.1.4.1.2011.2.25.4.50.35.1.1.1.1
    optixpktSYSsynCurSyn OBJECT-TYPE
        SYNTAX Unsigned32
        MAX-ACCESS read-only
        STATUS current
        DESCRIPTION
            "This parameter specifies current SDH clock source. Value range: 0x01ff0001 to 0x06ff0006 with 0x00f00001, 0x00f00002, and 0x00f10001."
        ::= { optixpktSYSsynEntry 1 }

    -- 1.3.6.1.4.1.2011.2.25.4.50.35.1.1.1.2
    optixpktSYSCurSynS1Value OBJECT-TYPE
        SYNTAX INTEGER
        {
            qlUnknown(0),
            qlPrc(2),
            qlSsua(4),
            qlSsub(8),
            qlSec(11),
            qlDnu(15)
        }
        MAX-ACCESS read-only
        STATUS current
        DESCRIPTION
            "This parameter specifies the s1 value of the current clock source. 0: qlUnknown, 2: qlPrc, 4: qlSsua, 8: qlSsub, 11: qlSec, 15: qlDnu"
        ::= { optixpktSYSsynEntry 2 }

    -- 1.3.6.1.4.1.2011.2.25.4.50.35.1.1.1.3
    optixpktSYSsynPriTableCLkList OBJECT-TYPE
        SYNTAX OCTET STRING
        MAX-ACCESS read-write
        STATUS current
        DESCRIPTION
            "This parameter specifies the list of clock source priorities."
        ::= { optixpktSYSsynEntry 3 }

    -- 1.3.6.1.4.1.2011.2.25.4.50.35.1.1.1.4
    optixpktSYSsyn24HourKeepMode OBJECT-TYPE
        SYNTAX Unsigned32
        MAX-ACCESS read-write
        STATUS current
        DESCRIPTION
            "This parameter specifies the 24 hour keep mode of SDH clock sources. 0: disable, 1: enable"
        ::= { optixpktSYSsynEntry 4 }

    -- 1.3.6.1.4.1.2011.2.25.4.50.35.1.1.1.5
    optixpktSYSsynSwState OBJECT-TYPE
        SYNTAX INTEGER
        {
            synAuto(0),
            synMan(1),
            synForce(2)
        }
        MAX-ACCESS read-only
        STATUS current
        DESCRIPTION
            "This parameter specifies the switching state. 0: synAuto, 1: synMan, 2: synForce"
        ::= { optixpktSYSsynEntry 5 }

    -- 1.3.6.1.4.1.2011.2.25.4.50.35.1.1.1.6
    optixpktsynProtectSynWtrTime OBJECT-TYPE
        SYNTAX Unsigned32
        MAX-ACCESS read-write
        STATUS current
        DESCRIPTION
            "This parameter specifies the clock source WTR time. Value range: 0 to 12 (unit: minute)."
        ::= { optixpktSYSsynEntry 6 }

    -- 1.3.6.1.4.1.2011.2.25.4.50.35.1.1.1.7
    optixpktSYSclkpllLockstate OBJECT-TYPE
        SYNTAX INTEGER
        {
            unlock(0),
            lock(1)
        }
        MAX-ACCESS read-only
        STATUS current
        DESCRIPTION
            "This parameter specifies the system clock PLL lock state."
        ::= { optixpktSYSsynEntry 7 }

    -- 1.3.6.1.4.1.2011.2.25.4.50.35.1.1.1.8
    optixpktSysSynWorkMode OBJECT-TYPE
        SYNTAX INTEGER
        {
            trace(1),
            keep(2),
            free(3)
        }
        MAX-ACCESS read-only
        STATUS current
        DESCRIPTION
            "This parameter specifies working mode. 1: trace, 2: keep, 3: free"
        ::= { optixpktSYSsynEntry 8 }

    -- 1.3.6.1.4.1.2011.2.25.4.50.35.1.2
    optixpktSYSsynClassTable OBJECT-TYPE
        SYNTAX SEQUENCE OF OptixpktSYSsynClassEntry
        MAX-ACCESS not-accessible
        STATUS current
        DESCRIPTION
            "This table contains configuration information of system clock lists."
        ::= { optixpktSYSsynGroup 2 }

    -- 1.3.6.1.4.1.2011.2.25.4.50.35.1.2.1
    optixpktSYSsynClassEntry OBJECT-TYPE
        SYNTAX OptixpktSYSsynClassEntry
        MAX-ACCESS not-accessible
        STATUS current
        DESCRIPTION
            "This entry containing configuration information of system clock lists."
        INDEX{ optixLogBoardId,optixpktSYSsynCurSyn }
        ::= { optixpktSYSsynClassTable 1 }

    OptixpktSYSsynClassEntry ::=
        SEQUENCE {
            optixpktSSMExQulity
                Unsigned32,
            optixpktsysSSMEnableFlag
                INTEGER,
            optixpktSSMsynClkIdMode
                INTEGER,
            optixpktSYSsynStatus
                Unsigned32,
            optixpktsynProtectEnable
                INTEGER,
            optixpktsysSynSubNet
                Unsigned32,
            optixpktsysSynNodeID
                Unsigned32,
            optixpktsysSynS1Mode
                INTEGER,
            optixpktsysSynSw
                Unsigned32
        }

    -- 1.3.6.1.4.1.2011.2.25.4.50.35.1.2.1.1
    optixpktSSMExQulity OBJECT-TYPE
        SYNTAX Unsigned32
        MAX-ACCESS read-write
        STATUS current
        DESCRIPTION
            "This parameter specifies the SSM protocol configuration of the clock source. Value range: 0x00, 0x02, 0x04, 0x08, 0x0b, 0x0f, and 0xff."
        ::= { optixpktSYSsynClassEntry 1 }

    -- 1.3.6.1.4.1.2011.2.25.4.50.35.1.2.1.2
    optixpktsysSSMEnableFlag OBJECT-TYPE
        SYNTAX INTEGER
        {
            permit(1),
            forbid(0)
        }
        MAX-ACCESS read-write
        STATUS current
        DESCRIPTION
            "This object indicates the enable status of the SSM protocol. 1: permit, 0: forbid"
        ::= { optixpktSYSsynClassEntry 2 }

    -- 1.3.6.1.4.1.2011.2.25.4.50.35.1.2.1.3
    optixpktSSMsynClkIdMode OBJECT-TYPE
        SYNTAX INTEGER
        {
            permit(1),
            forbid(0)
        }
        MAX-ACCESS read-write
        STATUS current
        DESCRIPTION
            "This object indicates the enable status of forbidding the output of SSM protocol clock ID. 1: permit, 0: forbid"
        ::= { optixpktSYSsynClassEntry 3 }

    -- 1.3.6.1.4.1.2011.2.25.4.50.35.1.2.1.4
    optixpktSYSsynStatus OBJECT-TYPE
        SYNTAX Unsigned32
        MAX-ACCESS read-only
        STATUS current
        DESCRIPTION
            "This parameter specifies the clock source status. 0: invalid, 1: valid"
        ::= { optixpktSYSsynClassEntry 4 }

    -- 1.3.6.1.4.1.2011.2.25.4.50.35.1.2.1.5
    optixpktsynProtectEnable OBJECT-TYPE
        SYNTAX INTEGER
        {
            enable(1),
            disable(0)
        }
        MAX-ACCESS read-write
        STATUS current
        DESCRIPTION
            "This parameter specifies the clock source protection enable status. 0: disable, 1: enable"
        ::= { optixpktSYSsynClassEntry 5 }

    -- 1.3.6.1.4.1.2011.2.25.4.50.35.1.2.1.6
    optixpktsysSynSubNet OBJECT-TYPE
        SYNTAX Unsigned32
        MAX-ACCESS read-write
        STATUS current
        DESCRIPTION
            "This parameter specifies the subnet ID. Value range: 0 to 255."
        ::= { optixpktSYSsynClassEntry 6 }

    -- 1.3.6.1.4.1.2011.2.25.4.50.35.1.2.1.7
    optixpktsysSynNodeID OBJECT-TYPE
        SYNTAX Unsigned32
        MAX-ACCESS read-write
        STATUS current
        DESCRIPTION
            "This parameter specifies the node ID. Value range: 0x00 to 0x0f."
        ::= { optixpktSYSsynClassEntry 7 }

    -- 1.3.6.1.4.1.2011.2.25.4.50.35.1.2.1.8
    optixpktsysSynS1Mode OBJECT-TYPE
        SYNTAX INTEGER
        {
            qlUnknown(0),
            qlPrc(2),
            qlSsua(4),
            qlSsub(8),
            qlSec(11),
            qlDnu(15)
        }
        MAX-ACCESS read-only
        STATUS current
        DESCRIPTION
            "This node represents the clock source's S1 byte value: qlUnknown(0), qlPrc(2), qlSsua(4), qlSsub(8), qlSec(11), or qlDnu(15)."
        ::= { optixpktSYSsynClassEntry 8 }

    -- 1.3.6.1.4.1.2011.2.25.4.50.35.1.2.1.9
    optixpktsysSynSw OBJECT-TYPE
        SYNTAX Unsigned32
        MAX-ACCESS read-write
        STATUS current
        DESCRIPTION
            "This node indicates switching or clearing the clock source: 0-clea, 1-manual, 2-force."
        ::= { optixpktSYSsynClassEntry 9 }

    -- 1.3.6.1.4.1.2011.2.25.4.50.35.1.3
    optixpktSynGroupTable OBJECT-TYPE
        SYNTAX SEQUENCE OF OptixpktSynGroupEntry
        MAX-ACCESS not-accessible
        STATUS current
        DESCRIPTION
            "Configuration information of the system clock source group"
        ::= { optixpktSYSsynGroup 3 }

    -- 1.3.6.1.4.1.2011.2.25.4.50.35.1.3.1
    optixpktSynGroupEntry OBJECT-TYPE
        SYNTAX OptixpktSynGroupEntry
        MAX-ACCESS not-accessible
        STATUS current
        DESCRIPTION
            "Entry to the configuration information of the system clock source group"
        INDEX{ optixpktSynBoardID,optixpktSynGroupid }
        ::= { optixpktSynGroupTable 1 }

    OptixpktSynGroupEntry ::=
        SEQUENCE {
            optixpktSynBoardID
                Unsigned32,
            optixpktSynGroupid
                Unsigned32,
            optixpktSynGroupSysNum
                Unsigned32,
            optixpktSynGroupSysList
                OCTET STRING,
            optixpktSynGroupRowStatus
                RowStatus
        }

    -- 1.3.6.1.4.1.2011.2.25.4.50.35.1.3.1.1
    optixpktSynBoardID OBJECT-TYPE
        SYNTAX Unsigned32
        MAX-ACCESS not-accessible
        STATUS current
        DESCRIPTION
            "System control board ID in a clock source group"
        ::= { optixpktSynGroupEntry 1 }

    -- 1.3.6.1.4.1.2011.2.25.4.50.35.1.3.1.2
    optixpktSynGroupid OBJECT-TYPE
        SYNTAX Unsigned32
        MAX-ACCESS not-accessible
        STATUS current
        DESCRIPTION
            "Clock source group ID"
        ::= { optixpktSynGroupEntry 2 }

    -- 1.3.6.1.4.1.2011.2.25.4.50.35.1.3.1.3
    optixpktSynGroupSysNum OBJECT-TYPE
        SYNTAX Unsigned32
        MAX-ACCESS read-create
        STATUS current
        DESCRIPTION
            "Number of clock sources in a clock source group"
        ::= { optixpktSynGroupEntry 3 }

    -- 1.3.6.1.4.1.2011.2.25.4.50.35.1.3.1.4
    optixpktSynGroupSysList OBJECT-TYPE
        SYNTAX OCTET STRING
        MAX-ACCESS read-create
        STATUS current
        DESCRIPTION
            "Clock source list"
        ::= { optixpktSynGroupEntry 4 }

    -- 1.3.6.1.4.1.2011.2.25.4.50.35.1.3.1.255
    optixpktSynGroupRowStatus OBJECT-TYPE
        SYNTAX RowStatus
        MAX-ACCESS read-create
        STATUS current
        DESCRIPTION
            "Row status of the clock source group"
        ::= { optixpktSynGroupEntry 255 }

    -- 1.3.6.1.4.1.2011.2.25.4.50.35.2
    optixpktSYSsynNeGroup OBJECT IDENTIFIER ::= { optixpktSYSsyn 2 }

    -- 1.3.6.1.4.1.2011.2.25.4.50.35.2.1
    optixpktSYSsynCnorvt OBJECT-TYPE
        SYNTAX INTEGER
        {
            enable(1),
            disable(0)
        }
        MAX-ACCESS read-write
        STATUS current
        DESCRIPTION
            "This node describes whether the clock switching by the descending order of priorities is enabled."
        ::= { optixpktSYSsynNeGroup 1 }

    -- 1.3.6.1.4.1.2011.2.25.4.50.35.2.2
    optixpktSYSsynQlunknowValue1 OBJECT-TYPE
        SYNTAX INTEGER
        {
            qlUnknown(0),
            qlPrc(2),
            qlSsua(4),
            qlSsub(8),
            qlSec(11),
            qlDnu(15)
        }
        MAX-ACCESS read-write
        STATUS current
        DESCRIPTION
            "The node describes the QL_UNKNOW-represented quality level 1."
        ::= { optixpktSYSsynNeGroup 2 }

    -- 1.3.6.1.4.1.2011.2.25.4.50.35.2.3
    optixpktSYSsynQlunknowValue2 OBJECT-TYPE
        SYNTAX INTEGER
        {
            qlUnknown(0),
            qlPrc(2),
            qlSsua(4),
            qlSsub(8),
            qlSec(11),
            qlDnu(15)
        }
        MAX-ACCESS read-write
        STATUS current
        DESCRIPTION
            "The node describes the QL_UNKNOW-represented quality level 2."
        ::= { optixpktSYSsynNeGroup 3 }

END
