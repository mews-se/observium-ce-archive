-- OPTIX-PKT-PORT-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-PORT-MIB DEFINITIONS ::= BEGIN
    IMPORTS
        optixProvisionPtn
            FROM OPTIX-OID-MIB
        OBJECT-GROUP,MODULE-COMPLIANCE
            FROM SNMPv2-CONF
        optixLogBoardId,optixLogSubCardId
            FROM OPTIX-BOARD-MANAGE-MIB
        Unsigned32,OBJECT-TYPE,MODULE-IDENTITY,IpAddress,NOTIFICATION-TYPE
            FROM SNMPv2-SMI
        MacAddress,RowStatus,DateAndTime
            FROM SNMPv2-TC
        optixPortId
            FROM OPTIX-PORT-MANAGE-MIB
        ;

    optixPktPort MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of device"
        REVISION "201204200000Z"
        DESCRIPTION
            "The initial revision of this MIB module1."
        ::={ optixProvisionPtn 52 }

    -- 1.3.6.1.4.1.2011.2.25.4.50.52.1
    optixPktPortGroup OBJECT IDENTIFIER ::= { optixPktPort 1 }

    -- 1.3.6.1.4.1.2011.2.25.4.50.52.1.1
    optixEthPortTable OBJECT-TYPE
        SYNTAX SEQUENCE OF OptixEthPortEntry
        MAX-ACCESS not-accessible
        STATUS current
        DESCRIPTION
            "This table contains basic configuration information of ETH port"
        ::= { optixPktPortGroup 1 }

    -- 1.3.6.1.4.1.2011.2.25.4.50.52.1.1.1
    optixEthPortEntry OBJECT-TYPE
        SYNTAX OptixEthPortEntry
        MAX-ACCESS not-accessible
        STATUS current
        DESCRIPTION
            "Entry containins basic configuration information of ETH port"
        INDEX{ optixLogBoardId,optixLogSubCardId,optixEthPortId }
        ::= { optixEthPortTable 1 }

    OptixEthPortEntry ::=
        SEQUENCE {
            optixEthPortId
                Unsigned32,
            optixEthPortEncapType
                INTEGER,
            optixEthPortMtu
                Unsigned32,
            optixEthPortWorkMode
                INTEGER,
            optixEthPortEn
                INTEGER,
            optixEthPortPtnWorkMode
                INTEGER,
            optixEthPortPhyFCState
                INTEGER,
            optixEthPortPtnMacLoop
                INTEGER,
            optixEthPortPtnPhyLoop
                INTEGER,
            optixEthPortFcMode
                INTEGER,
            optixEthPortAutoFcMode
                INTEGER,
            optixEthPortOpif
                INTEGER,
            optixEthPortSamplingId
                Unsigned32,
            optixEthPortRxRate
                OCTET STRING,
            optixEthPortTxRate
                OCTET STRING,
            optixEthPortRealFc
                INTEGER,
            optixEthPortMdimode
                INTEGER,
            optixEthPortEnable
                INTEGER,
            optixEthPortVlanId
                Unsigned32,
            optixEthPortVlanPri
                Unsigned32,
            optixEthPortTag
                INTEGER,
            optixEthPortQinqId
                Unsigned32,
            optixEthPortMac
                OCTET STRING,
            optixEthPortLoopEn
                INTEGER,
            optixEthPortBlockEn
                INTEGER,
            optixEthPortWatchFlowEn
                INTEGER,
            optixEthPortWatchFlowTime
                Unsigned32,
            optixEthPortBroadBateenEn
                INTEGER,
            optixEthPortBroadBateen
                Unsigned32,
            optixEthPortAutoneg
                INTEGER,
            optixEthPortWatchRateEn
                INTEGER,
            optixEthPortOpticalDir
                INTEGER,
            optixEthPortJitterEnableState
                INTEGER,
            optixEthPortPhyErrDetectState
                INTEGER,
            optixEthPortErrorFlag
                Unsigned32,
            optixEthPortLevelMode
                INTEGER,
            optixEthPortUpDownStauts
                INTEGER,
            optixHybridMinBandWidth
                Unsigned32,
            optixHybridMaxBandWidth
                Unsigned32,
            optixEthPortPoeEnable
                INTEGER,
            optixEthPortRealPoeEnable
                INTEGER,
            optixHybridL3HoldOffTime
                Unsigned32,
            optixEthPortBerDetectState
                INTEGER,
            optixEthPortPacketLostEXC
                INTEGER,
            optixEthPortPacketLostSD
                INTEGER,
            optixEthPortBerSwitchState
                INTEGER,
            optixEthPortBerSwitchType
                INTEGER,
            optixEthPortbdbateabsth
                Unsigned32,
            optixEthPortBwuSwatChenableState
                INTEGER,
            optixEthPortPoeMode
                INTEGER,
            optixEthPortRowStatus
                RowStatus
        }

    -- 1.3.6.1.4.1.2011.2.25.4.50.52.1.1.1.1
    optixEthPortId OBJECT-TYPE
        SYNTAX Unsigned32
        MAX-ACCESS not-accessible
        STATUS current
        DESCRIPTION
            "This parameter specifies the eth port index"
        ::= { optixEthPortEntry 1 }

    -- 1.3.6.1.4.1.2011.2.25.4.50.52.1.1.1.2
    optixEthPortEncapType OBJECT-TYPE
        SYNTAX INTEGER
        {
            null(0),
            cTag(1),
            sTag(2),
            iTag(3),
            atm(4),
            ppp(5)
        }
        MAX-ACCESS read-create
        STATUS current
        DESCRIPTION
            "This parameter specifies the eth port encaptype. 0: null, 1: cTag, 2: sTag, 3: iTag, 4: atm, 5: ppp"
        ::= { optixEthPortEntry 2 }

    -- 1.3.6.1.4.1.2011.2.25.4.50.52.1.1.1.3
    optixEthPortMtu OBJECT-TYPE
        SYNTAX Unsigned32
        MAX-ACCESS read-create
        STATUS current
        DESCRIPTION
            "This parameter specifies the eth port MTU. Value range: 1518 to 9600."
        ::= { optixEthPortEntry 3 }

    -- 1.3.6.1.4.1.2011.2.25.4.50.52.1.1.1.4
    optixEthPortWorkMode OBJECT-TYPE
        SYNTAX INTEGER
        {
            auto(0),
            snmp10mhalf(1),
            snmp10mfull(2),
            snmp100mhalf(3),
            snmp100mfull(4),
            snmp1000mhalf(5),
            snmp1000mfull(6),
            snmp10gfulllan(7),
            snmp10gfullwan(8),
            snmp2500mfull(14),
            negotiating(255)
        }
        MAX-ACCESS read-create
        STATUS current
        DESCRIPTION
            "This parameter specifies the eth port work mode. 0: auto, 1: snmp10mhalf, 2: snmp10mfull, 3: snmp100mhalf, 4: snmp100mfull, 5: snmp1000mhalf, 6: snmp1000mfull, 7: snmp10gfulllan, 8: snmp10gfullwan, 14: snmp2500mfull, 255: negotiating"
        ::= { optixEthPortEntry 4 }

    -- 1.3.6.1.4.1.2011.2.25.4.50.52.1.1.1.5
    optixEthPortEn OBJECT-TYPE
        SYNTAX INTEGER
        {
            enable(1),
            disable(0)
        }
        MAX-ACCESS read-only
        STATUS current
        DESCRIPTION
            "This parameter specifies the eth port phy enable. 0: disable, 1: enable"
        ::= { optixEthPortEntry 5 }

    -- 1.3.6.1.4.1.2011.2.25.4.50.52.1.1.1.6
    optixEthPortPtnWorkMode OBJECT-TYPE
        SYNTAX INTEGER
        {
            auto(0),
            snmp10mhalf(1),
            snmp10mfull(2),
            snmp100mhalf(3),
            snmp100mfull(4),
            snmp1000mhalf(5),
            snmp1000mfull(6),
            snmp10gfulllan(7),
            snmp10gfullwan(8),
            negotiating(255)
        }
        MAX-ACCESS read-only
        STATUS current
        DESCRIPTION
            "This parameter specifies the eth port phy work mode. 0: auto, 1: snmp10mhalf, 2: snmp10mfull, 3: snmp100mhalf, 4: snmp100mfull, 5: snmp1000mhalf, 6: snmp1000mfull, 7: snmp10gfulllan, 8: snmp10gfullwan, 255: negotiating"
        ::= { optixEthPortEntry 6 }

    -- 1.3.6.1.4.1.2011.2.25.4.50.52.1.1.1.7
    optixEthPortPhyFCState OBJECT-TYPE
        SYNTAX INTEGER
        {
            disable(0),
            enable(1),
            send(2),
            recv(3)
        }
        MAX-ACCESS read-only
        STATUS current
        DESCRIPTION
            "This parameter specifies the eth port phy flow control state. 0: disable, 1: enable, 2: send, 3: recv"
        ::= { optixEthPortEntry 7 }

    -- 1.3.6.1.4.1.2011.2.25.4.50.52.1.1.1.8
    optixEthPortPtnMacLoop OBJECT-TYPE
        SYNTAX INTEGER
        {
            noloop(0),
            inloop(1),
            outloop(2)
        }
        MAX-ACCESS read-create
        STATUS current
        DESCRIPTION
            "This parameter specifies the eth port mac loop type. 0: noloop, 1: inloop, 2: outloop"
        ::= { optixEthPortEntry 8 }

    -- 1.3.6.1.4.1.2011.2.25.4.50.52.1.1.1.9
    optixEthPortPtnPhyLoop OBJECT-TYPE
        SYNTAX INTEGER
        {
            noloop(0),
            inloop(1),
            outloop(2)
        }
        MAX-ACCESS read-create
        STATUS current
        DESCRIPTION
            "This parameter specifies the eth port phy loop type. 0: noloop, 1: inloop, 2: outloop"
        ::= { optixEthPortEntry 9 }

    -- 1.3.6.1.4.1.2011.2.25.4.50.52.1.1.1.10
    optixEthPortFcMode OBJECT-TYPE
        SYNTAX INTEGER
        {
            disable(0),
            enable(1),
            send(2),
            recv(3)
        }
        MAX-ACCESS read-create
        STATUS current
        DESCRIPTION
            "This parameter specifies the eth port fc mode. 0: disable, 1: enable, 2: send, 3: recv"
        ::= { optixEthPortEntry 10 }

    -- 1.3.6.1.4.1.2011.2.25.4.50.52.1.1.1.11
    optixEthPortAutoFcMode OBJECT-TYPE
        SYNTAX INTEGER
        {
            disable(0),
            asym(1),
            sym(2),
            asymSym(3)
        }
        MAX-ACCESS read-create
        STATUS current
        DESCRIPTION
            "This parameter specifies the eth port fc mode auto. 0: disable, 1: asym, 2: sym, 3: asymSym"
        ::= { optixEthPortEntry 11 }

    -- 1.3.6.1.4.1.2011.2.25.4.50.52.1.1.1.12
    optixEthPortOpif OBJECT-TYPE
        SYNTAX INTEGER
        {
            none(0),
            singleMode(1),
            multiMode(2),
            electrical(3)
        }
        MAX-ACCESS read-only
        STATUS current
        DESCRIPTION
            "This parameter specifies the eth port opif type. 0: none, 1: singleMode, 2: multiMode, 3: electrical"
        ::= { optixEthPortEntry 12 }

    -- 1.3.6.1.4.1.2011.2.25.4.50.52.1.1.1.13
    optixEthPortSamplingId OBJECT-TYPE
        SYNTAX Unsigned32
        MAX-ACCESS read-only
        STATUS current
        DESCRIPTION
            "This parameter specifies the eth port receive rate"
        ::= { optixEthPortEntry 13 }

    -- 1.3.6.1.4.1.2011.2.25.4.50.52.1.1.1.14
    optixEthPortRxRate OBJECT-TYPE
        SYNTAX OCTET STRING (SIZE(0..256))
        MAX-ACCESS read-only
        STATUS current
        DESCRIPTION
            "This parameter specifies the eth port receive rate"
        ::= { optixEthPortEntry 14 }

    -- 1.3.6.1.4.1.2011.2.25.4.50.52.1.1.1.15
    optixEthPortTxRate OBJECT-TYPE
        SYNTAX OCTET STRING (SIZE(0..256))
        MAX-ACCESS read-only
        STATUS current
        DESCRIPTION
            "This parameter specifies the eth port send rate"
        ::= { optixEthPortEntry 15 }

    -- 1.3.6.1.4.1.2011.2.25.4.50.52.1.1.1.16
    optixEthPortRealFc OBJECT-TYPE
        SYNTAX INTEGER
        {
            disable(0),
            enable(1),
            send(2),
            recv(3)
        }
        MAX-ACCESS read-only
        STATUS current
        DESCRIPTION
            "This parameter specifies the eth port real fc mode result. 0: disable, 1: enable, 2: send, 3: recv"
        ::= { optixEthPortEntry 16 }

    -- 1.3.6.1.4.1.2011.2.25.4.50.52.1.1.1.17
    optixEthPortMdimode OBJECT-TYPE
        SYNTAX INTEGER
        {
            mdix(0),
            auto(1),
            mdi(2)
        }
        MAX-ACCESS read-create
        STATUS current
        DESCRIPTION
            "This parameter specifies the eth port mdi mode. 0: mdix, 1: auto, 2: mdi"
        ::= { optixEthPortEntry 17 }

    -- 1.3.6.1.4.1.2011.2.25.4.50.52.1.1.1.18
    optixEthPortEnable OBJECT-TYPE
        SYNTAX INTEGER
        {
            enable(1),
            disable(0)
        }
        MAX-ACCESS read-create
        STATUS current
        DESCRIPTION
            "This parameter specifies the eth port enable. 0: disable, 1: enable"
        ::= { optixEthPortEntry 18 }

    -- 1.3.6.1.4.1.2011.2.25.4.50.52.1.1.1.19
    optixEthPortVlanId OBJECT-TYPE
        SYNTAX Unsigned32
        MAX-ACCESS read-create
        STATUS current
        DESCRIPTION
            "This parameter specifies the eth port vlan ID. Value range: 0 to 4095."
        ::= { optixEthPortEntry 19 }

    -- 1.3.6.1.4.1.2011.2.25.4.50.52.1.1.1.20
    optixEthPortVlanPri OBJECT-TYPE
        SYNTAX Unsigned32
        MAX-ACCESS read-create
        STATUS current
        DESCRIPTION
            "This parameter specifies the eth port vlan pri. Value range: 0 to 7. A larger value indicates a higher priority."
        ::= { optixEthPortEntry 20 }

    -- 1.3.6.1.4.1.2011.2.25.4.50.52.1.1.1.21
    optixEthPortTag OBJECT-TYPE
        SYNTAX INTEGER
        {
            access(0),
            tagAware(1),
            hybrid(2),
            snmp0xff(255)
        }
        MAX-ACCESS read-create
        STATUS current
        DESCRIPTION
            "This parameter specifies the eth port tag. 0: access, 1: tagAware, 2: hybrid, 255: snmp0xff"
        ::= { optixEthPortEntry 21 }

    -- 1.3.6.1.4.1.2011.2.25.4.50.52.1.1.1.22
    optixEthPortQinqId OBJECT-TYPE
        SYNTAX Unsigned32
        MAX-ACCESS read-create
        STATUS current
        DESCRIPTION
            "This parameter specifies the eth port qinq"
        ::= { optixEthPortEntry 22 }

    -- 1.3.6.1.4.1.2011.2.25.4.50.52.1.1.1.23
    optixEthPortMac OBJECT-TYPE
        SYNTAX OCTET STRING (SIZE(0..32))
        MAX-ACCESS read-create
        STATUS current
        DESCRIPTION
            "This parameter specifies the eth port mac address"
        ::= { optixEthPortEntry 23 }

    -- 1.3.6.1.4.1.2011.2.25.4.50.52.1.1.1.24
    optixEthPortLoopEn OBJECT-TYPE
        SYNTAX INTEGER
        {
            enable(1),
            disable(0)
        }
        MAX-ACCESS read-create
        STATUS current
        DESCRIPTION
            "This parameter specifies the eth port loop enable. 0: disable, 1: enable"
        ::= { optixEthPortEntry 24 }

    -- 1.3.6.1.4.1.2011.2.25.4.50.52.1.1.1.25
    optixEthPortBlockEn OBJECT-TYPE
        SYNTAX INTEGER
        {
            enable(1),
            disable(0)
        }
        MAX-ACCESS read-create
        STATUS current
        DESCRIPTION
            "This parameter specifies the eth port block after loop. 0: disable, 1: enable"
        ::= { optixEthPortEntry 25 }

    -- 1.3.6.1.4.1.2011.2.25.4.50.52.1.1.1.26
    optixEthPortWatchFlowEn OBJECT-TYPE
        SYNTAX INTEGER
        {
            enable(1),
            disable(0)
        }
        MAX-ACCESS read-create
        STATUS current
        DESCRIPTION
            "This parameter specifies the eth port watch flow enable. 0: disable, 1: enable"
        ::= { optixEthPortEntry 26 }

    -- 1.3.6.1.4.1.2011.2.25.4.50.52.1.1.1.27
    optixEthPortWatchFlowTime OBJECT-TYPE
        SYNTAX Unsigned32
        MAX-ACCESS read-create
        STATUS current
        DESCRIPTION
            "This parameter specifies the eth port watch flow time"
        ::= { optixEthPortEntry 27 }

    -- 1.3.6.1.4.1.2011.2.25.4.50.52.1.1.1.28
    optixEthPortBroadBateenEn OBJECT-TYPE
        SYNTAX INTEGER
        {
            enable(1),
            disable(0)
        }
        MAX-ACCESS read-create
        STATUS current
        DESCRIPTION
            "This parameter specifies the eth port broadbateen enable. 0: disable, 1: enable"
        ::= { optixEthPortEntry 28 }

    -- 1.3.6.1.4.1.2011.2.25.4.50.52.1.1.1.29
    optixEthPortBroadBateen OBJECT-TYPE
        SYNTAX Unsigned32
        MAX-ACCESS read-create
        STATUS current
        DESCRIPTION
            "This parameter specifies the eth port broadbateen"
        ::= { optixEthPortEntry 29 }

    -- 1.3.6.1.4.1.2011.2.25.4.50.52.1.1.1.30
    optixEthPortAutoneg OBJECT-TYPE
        SYNTAX INTEGER
        {
            snmp10mhalf(1),
            snmp10mfull(2),
            snmp100mhalf(3),
            snmp100mfull(4),
            snmp1000mhalf(5),
            snmp1000mfull(6),
            null(255)
        }
        MAX-ACCESS read-create
        STATUS current
        DESCRIPTION
            "This parameter specifies the eth port autoneg. 1: snmp10mhalf, 2: snmp10mfull, 3: snmp100mhalf, 4: snmp100mfull, 5: snmp1000mhalf, 6: snmp1000mfull, 255: null"
        ::= { optixEthPortEntry 30 }

    -- 1.3.6.1.4.1.2011.2.25.4.50.52.1.1.1.31
    optixEthPortWatchRateEn OBJECT-TYPE
        SYNTAX INTEGER
        {
            enable(1),
            disable(0)
        }
        MAX-ACCESS read-create
        STATUS current
        DESCRIPTION
            "This parameter specifies the eth port watch rate enable. 0: disable, 1: enable"
        ::= { optixEthPortEntry 31 }

    -- 1.3.6.1.4.1.2011.2.25.4.50.52.1.1.1.32
    optixEthPortOpticalDir OBJECT-TYPE
        SYNTAX INTEGER
        {
            none(0),
            sglfbr(1),
            dblfbr(2)
        }
        MAX-ACCESS read-only
        STATUS current
        DESCRIPTION
            "This parameter specifies the eth port optical direction. 0: none, 1: sglfbr, 2: dblfbr"
        ::= { optixEthPortEntry 32 }

    -- 1.3.6.1.4.1.2011.2.25.4.50.52.1.1.1.33
    optixEthPortJitterEnableState OBJECT-TYPE
        SYNTAX INTEGER
        {
            disable(0),
            enable(1)
        }
        MAX-ACCESS read-create
        STATUS current
        DESCRIPTION
            "This parameter specifies the eth port enable status of jitter optimization. 0: disable, 1: enable"
        ::= { optixEthPortEntry 33 }

    -- 1.3.6.1.4.1.2011.2.25.4.50.52.1.1.1.34
    optixEthPortPhyErrDetectState OBJECT-TYPE
        SYNTAX INTEGER
        {
            disable(0),
            enable(1)
        }
        MAX-ACCESS read-create
        STATUS current
        DESCRIPTION
            "This parameter specifies the eth port enable status of PHY erroneous detection. 0: disable, 1: enable"
        ::= { optixEthPortEntry 34 }

    -- 1.3.6.1.4.1.2011.2.25.4.50.52.1.1.1.35
    optixEthPortErrorFlag OBJECT-TYPE
        SYNTAX Unsigned32
        MAX-ACCESS read-only
        STATUS current
        DESCRIPTION
            "This parameter specifies the eth port flag of PHY mistake"
        ::= { optixEthPortEntry 35 }

    -- 1.3.6.1.4.1.2011.2.25.4.50.52.1.1.1.36
    optixEthPortLevelMode OBJECT-TYPE
        SYNTAX INTEGER
        {
            level1(1),
            level2(2),
            level3(3),
            level2Level3(4)
        }
        MAX-ACCESS read-create
        STATUS current
        DESCRIPTION
            "This parameter specifies the eth port mode. 1: level1, 2: level2, 3: level3, 4: level2Level3"
        ::= { optixEthPortEntry 36 }

    -- 1.3.6.1.4.1.2011.2.25.4.50.52.1.1.1.37
    optixEthPortUpDownStauts OBJECT-TYPE
        SYNTAX INTEGER
        {
            down(0),
            up(1)
        }
        MAX-ACCESS read-only
        STATUS current
        DESCRIPTION
            "This parameter specifies the up down status of port. 0: down, 1: up"
        ::= { optixEthPortEntry 37 }

    -- 1.3.6.1.4.1.2011.2.25.4.50.52.1.1.1.38
    optixHybridMinBandWidth OBJECT-TYPE
        SYNTAX Unsigned32
        MAX-ACCESS read-only
        STATUS current
        DESCRIPTION
            "This parameter specifies hybrid port min bandwidth"
        ::= { optixEthPortEntry 38 }

    -- 1.3.6.1.4.1.2011.2.25.4.50.52.1.1.1.39
    optixHybridMaxBandWidth OBJECT-TYPE
        SYNTAX Unsigned32
        MAX-ACCESS read-only
        STATUS current
        DESCRIPTION
            "This parameter specifies hybrid port max bandwidth"
        ::= { optixEthPortEntry 39 }

    -- 1.3.6.1.4.1.2011.2.25.4.50.52.1.1.1.40
    optixEthPortPoeEnable OBJECT-TYPE
        SYNTAX INTEGER
        {
            auto(2),
            enable(1),
            disable(0)
        }
        MAX-ACCESS read-create
        STATUS current
        DESCRIPTION
            "This parameter specifies the eth port enable status of poe. 0: disable, 1: enable"
        ::= { optixEthPortEntry 40 }

    -- 1.3.6.1.4.1.2011.2.25.4.50.52.1.1.1.41
    optixEthPortRealPoeEnable OBJECT-TYPE
        SYNTAX INTEGER
        {
            enable(1),
            disable(0)
        }
        MAX-ACCESS read-only
        STATUS current
        DESCRIPTION
            "This parameter specifies the eth port real enable status of poe"
        ::= { optixEthPortEntry 41 }

    -- 1.3.6.1.4.1.2011.2.25.4.50.52.1.1.1.42
    optixHybridL3HoldOffTime OBJECT-TYPE
        SYNTAX Unsigned32
        MAX-ACCESS read-create
        STATUS current
        DESCRIPTION
            "This parameter specifies hybrid port Hold off time"
        ::= { optixEthPortEntry 42 }

    -- 1.3.6.1.4.1.2011.2.25.4.50.52.1.1.1.43
    optixEthPortBerDetectState OBJECT-TYPE
        SYNTAX INTEGER
        {
            disable(0),
            enable(1)
        }
        MAX-ACCESS read-create
        STATUS current
        DESCRIPTION
            "This parameter indicates whether the bit error detection function is enabled."
        ::= { optixEthPortEntry 43 }

    -- 1.3.6.1.4.1.2011.2.25.4.50.52.1.1.1.44
    optixEthPortPacketLostEXC OBJECT-TYPE
        SYNTAX INTEGER
        {
            null(0),
            tenToPower2(2),
            tenToPower3(3),
            tenToPower4(4),
            tenToPower5(5)
        }
        MAX-ACCESS read-create
        STATUS current
        DESCRIPTION
            "This parameter specifies the threshold of PacketLostEXC."
        ::= { optixEthPortEntry 44 }

    -- 1.3.6.1.4.1.2011.2.25.4.50.52.1.1.1.45
    optixEthPortPacketLostSD OBJECT-TYPE
        SYNTAX INTEGER
        {
            null(0),
            tenToPower5(5),
            tenToPower6(6),
            tenToPower7(7),
            tenToPower8(8),
            tenToPower9(9)
        }
        MAX-ACCESS read-create
        STATUS current
        DESCRIPTION
            "This parameter specifies the threshold of PacketLostSD."
        ::= { optixEthPortEntry 45 }

    -- 1.3.6.1.4.1.2011.2.25.4.50.52.1.1.1.46
    optixEthPortBerSwitchState OBJECT-TYPE
        SYNTAX INTEGER
        {
            disable(0),
            enable(1)
        }
        MAX-ACCESS read-create
        STATUS current
        DESCRIPTION
            "This parameter indicates whether the bit-error-triggered switching is enabled."
        ::= { optixEthPortEntry 46 }

    -- 1.3.6.1.4.1.2011.2.25.4.50.52.1.1.1.47
    optixEthPortBerSwitchType OBJECT-TYPE
        SYNTAX INTEGER
        {
            sf(0),
            sd(1)
        }
        MAX-ACCESS read-create
        STATUS current
        DESCRIPTION
            "This parameter indicates the type of the bit-error-triggered switching."
        ::= { optixEthPortEntry 47 }

    -- 1.3.6.1.4.1.2011.2.25.4.50.52.1.1.1.48
    optixEthPortbdbateabsth OBJECT-TYPE
        SYNTAX Unsigned32
        MAX-ACCESS read-create
        STATUS current
        DESCRIPTION
            "This object indicates the threshold of the broadcast packet suppression absolute value."
        ::= { optixEthPortEntry 48 }

    -- 1.3.6.1.4.1.2011.2.25.4.50.52.1.1.1.49
    optixEthPortBwuSwatChenableState OBJECT-TYPE
        SYNTAX INTEGER
        {
            disable(0),
            enable(1)
        }
        MAX-ACCESS read-create
        STATUS current
        DESCRIPTION
            "This object indicates the enable status of monitoring port historical bandwidth usage."
        ::= { optixEthPortEntry 49 }

    -- 1.3.6.1.4.1.2011.2.25.4.50.52.1.1.1.50
    optixEthPortPoeMode OBJECT-TYPE
        SYNTAX INTEGER
        {
            poe(0),
            poeplus(1)
        }
        MAX-ACCESS read-create
        STATUS current
        DESCRIPTION
            "This parameter specifies the PoE mode of the Ethernet port. 0: PoE; 1: PoE plus"
        ::= { optixEthPortEntry 50 }

    -- 1.3.6.1.4.1.2011.2.25.4.50.52.1.1.1.255
    optixEthPortRowStatus OBJECT-TYPE
        SYNTAX RowStatus
        MAX-ACCESS read-create
        STATUS current
        DESCRIPTION
            "This parameter specifies the eth port row status"
        ::= { optixEthPortEntry 255 }

    -- 1.3.6.1.4.1.2011.2.25.4.50.52.1.2
    optixVlanPortTable OBJECT-TYPE
        SYNTAX SEQUENCE OF OptixVlanPortEntry
        MAX-ACCESS not-accessible
        STATUS current
        DESCRIPTION
            "This table contains basic configuration information of VLAN port"
        ::= { optixPktPortGroup 2 }

    -- 1.3.6.1.4.1.2011.2.25.4.50.52.1.2.1
    optixVlanPortEntry OBJECT-TYPE
        SYNTAX OptixVlanPortEntry
        MAX-ACCESS not-accessible
        STATUS current
        DESCRIPTION
            "This table contains basic configuration information of VLAN port"
        INDEX{ optixLogBoardId,optixLogSubCardId,optixVlanPortId }
        ::= { optixVlanPortTable 1 }

    OptixVlanPortEntry ::=
        SEQUENCE {
            optixVlanPortId
                Unsigned32,
            optixVlanPortVportType
                INTEGER,
            optixVlanPortBoardId
                Unsigned32,
            optixVlanPortSubID
                Unsigned32,
            optixVlanPortPortId
                Unsigned32,
            optixVlanPortVlan
                Unsigned32,
            optixVlanPortLevelMode
                INTEGER,
            optixVlanIfPortVlan
                Unsigned32,
            optixVlanPortRowStatus
                RowStatus
        }

    -- 1.3.6.1.4.1.2011.2.25.4.50.52.1.2.1.1
    optixVlanPortId OBJECT-TYPE
        SYNTAX Unsigned32
        MAX-ACCESS not-accessible
        STATUS current
        DESCRIPTION
            "This parameter specifies the VLAN port index. Value range: 0x2800 to 0x2FFF,0x9100 to 0x94FF."
        ::= { optixVlanPortEntry 1 }

    -- 1.3.6.1.4.1.2011.2.25.4.50.52.1.2.1.2
    optixVlanPortVportType OBJECT-TYPE
        SYNTAX INTEGER
        {
            eoa(1),
            vlan(2),
            eoadsl(3),
            eoefm(4),
            eoatm(5),
            vlanif(12)
        }
        MAX-ACCESS read-create
        STATUS current
        DESCRIPTION
            "This parameter specifies the virtual port type for VLAN ports. 1: eoa, 2: vlan, 3: eoadsl, 4: eoefm, 5: eoatm, 12: vlanif"
        ::= { optixVlanPortEntry 2 }

    -- 1.3.6.1.4.1.2011.2.25.4.50.52.1.2.1.3
    optixVlanPortBoardId OBJECT-TYPE
        SYNTAX Unsigned32
        MAX-ACCESS read-create
        STATUS current
        DESCRIPTION
            "This parameter specifies the vlan port board id"
        ::= { optixVlanPortEntry 3 }

    -- 1.3.6.1.4.1.2011.2.25.4.50.52.1.2.1.4
    optixVlanPortSubID OBJECT-TYPE
        SYNTAX Unsigned32
        MAX-ACCESS read-create
        STATUS current
        DESCRIPTION
            "This parameter specifies the vlan port subcard id"
        ::= { optixVlanPortEntry 4 }

    -- 1.3.6.1.4.1.2011.2.25.4.50.52.1.2.1.5
    optixVlanPortPortId OBJECT-TYPE
        SYNTAX Unsigned32
        MAX-ACCESS read-create
        STATUS current
        DESCRIPTION
            "This parameter specifies the vlan port port id"
        ::= { optixVlanPortEntry 5 }

    -- 1.3.6.1.4.1.2011.2.25.4.50.52.1.2.1.6
    optixVlanPortVlan OBJECT-TYPE
        SYNTAX Unsigned32
        MAX-ACCESS read-create
        STATUS current
        DESCRIPTION
            "This parameter specifies the vlan port vlan. Value range: 1 to 4094."
        ::= { optixVlanPortEntry 6 }

    -- 1.3.6.1.4.1.2011.2.25.4.50.52.1.2.1.7
    optixVlanPortLevelMode OBJECT-TYPE
        SYNTAX INTEGER
        {
            level1(1),
            level2(2),
            level3(3),
            level2Level3(4)
        }
        MAX-ACCESS read-create
        STATUS current
        DESCRIPTION
            "This parameter specifies the vlan port mode. 1: level1, 2: level2, 3: level3, 4: level2Level3"
        ::= { optixVlanPortEntry 7 }

    -- 1.3.6.1.4.1.2011.2.25.4.50.52.1.2.1.8
    optixVlanIfPortVlan OBJECT-TYPE
        SYNTAX Unsigned32
        MAX-ACCESS read-create
        STATUS current
        DESCRIPTION
            "This parameter specifies VLAN IDs configured for VLAN-IF member ports. Value range: 1 to 4094."
        ::= { optixVlanPortEntry 8 }

    -- 1.3.6.1.4.1.2011.2.25.4.50.52.1.2.1.255
    optixVlanPortRowStatus OBJECT-TYPE
        SYNTAX RowStatus
        MAX-ACCESS read-create
        STATUS current
        DESCRIPTION
            "This parameter specifies the vlan port row status"
        ::= { optixVlanPortEntry 255 }

    -- 1.3.6.1.4.1.2011.2.25.4.50.52.1.3
    optixAtmPortTable OBJECT-TYPE
        SYNTAX SEQUENCE OF OptixAtmPortEntry
        MAX-ACCESS not-accessible
        STATUS current
        DESCRIPTION
            "This table contains basic configuration information of ATM port"
        ::= { optixPktPortGroup 3 }

    -- 1.3.6.1.4.1.2011.2.25.4.50.52.1.3.1
    optixAtmPortEntry OBJECT-TYPE
        SYNTAX OptixAtmPortEntry
        MAX-ACCESS not-accessible
        STATUS current
        DESCRIPTION
            "This table contains basic configuration information of ATM port"
        INDEX{ optixLogBoardId,optixLogSubCardId,optixAtmPortId }
        ::= { optixAtmPortTable 1 }

    OptixAtmPortEntry ::=
        SEQUENCE {
            optixAtmPortId
                Unsigned32,
            optixAtmPortLoop
                INTEGER,
            optixAtmPortType
                INTEGER,
            optixAtmPortCellEn
                INTEGER,
            optixAtmPortMinVpi
                Unsigned32,
            optixAtmPortMaxVpi
                Unsigned32,
            optixAtmPortMinVci
                Unsigned32,
            optixAtmPortMaxVci
                Unsigned32,
            optixAtmPortVccVpi
                Unsigned32,
            optixAtmPortEncapType
                INTEGER,
            optixAtmPortLevelMode
                INTEGER,
            optixAtmPortRowStatus
                RowStatus
        }

    -- 1.3.6.1.4.1.2011.2.25.4.50.52.1.3.1.1
    optixAtmPortId OBJECT-TYPE
        SYNTAX Unsigned32
        MAX-ACCESS not-accessible
        STATUS current
        DESCRIPTION
            "This parameter specifies the atm port id"
        ::= { optixAtmPortEntry 1 }

    -- 1.3.6.1.4.1.2011.2.25.4.50.52.1.3.1.2
    optixAtmPortLoop OBJECT-TYPE
        SYNTAX INTEGER
        {
            noloop(0),
            inloop(1),
            outloop(2)
        }
        MAX-ACCESS read-create
        STATUS current
        DESCRIPTION
            "This parameter specifies the atm port loop mode. 0: noloop, 1: inloop, 2: outloop"
        ::= { optixAtmPortEntry 2 }

    -- 1.3.6.1.4.1.2011.2.25.4.50.52.1.3.1.3
    optixAtmPortType OBJECT-TYPE
        SYNTAX INTEGER
        {
            uni(1),
            nni(2)
        }
        MAX-ACCESS read-create
        STATUS current
        DESCRIPTION
            "This parameter specifies the atm port type. 1: UNI, 2: NNI"
        ::= { optixAtmPortEntry 3 }

    -- 1.3.6.1.4.1.2011.2.25.4.50.52.1.3.1.4
    optixAtmPortCellEn OBJECT-TYPE
        SYNTAX INTEGER
        {
            enable(1),
            disable(0)
        }
        MAX-ACCESS read-create
        STATUS current
        DESCRIPTION
            "This parameter specifies the atm port cell enable. 0: disable, 1: enable"
        ::= { optixAtmPortEntry 4 }

    -- 1.3.6.1.4.1.2011.2.25.4.50.52.1.3.1.5
    optixAtmPortMinVpi OBJECT-TYPE
        SYNTAX Unsigned32
        MAX-ACCESS read-create
        STATUS current
        DESCRIPTION
            "This parameter specifies the atm port min vpi. Value range: 0 to 0xfff and 0xffff. The value 0xffff indicates that the minimum value is not limited. This parameter is reserved and the default value is 0xffff."
        ::= { optixAtmPortEntry 5 }

    -- 1.3.6.1.4.1.2011.2.25.4.50.52.1.3.1.6
    optixAtmPortMaxVpi OBJECT-TYPE
        SYNTAX Unsigned32
        MAX-ACCESS read-create
        STATUS current
        DESCRIPTION
            "This parameter specifies the atm port max vpi. Value range: 0 to 0xfff and 0xffff. The value 0xffff indicates that the maximum value is not limited. This parameter is reserved and the default value is 0xffff."
        ::= { optixAtmPortEntry 6 }

    -- 1.3.6.1.4.1.2011.2.25.4.50.52.1.3.1.7
    optixAtmPortMinVci OBJECT-TYPE
        SYNTAX Unsigned32
        MAX-ACCESS read-create
        STATUS current
        DESCRIPTION
            "This parameter specifies the atm port min vci. Value range: 0 to 0xffff and 0xffffffff. The value 0xffffffff indicates that the minimum value is not limited. The default value is 0xffffffff."
        ::= { optixAtmPortEntry 7 }

    -- 1.3.6.1.4.1.2011.2.25.4.50.52.1.3.1.8
    optixAtmPortMaxVci OBJECT-TYPE
        SYNTAX Unsigned32
        MAX-ACCESS read-create
        STATUS current
        DESCRIPTION
            "This parameter specifies the atm port max vci Value range: 0 to 0xffff and 0xffffffff. The value 0xffffffff indicates that the maximum value is not limited. The default value is 0xffffffff."
        ::= { optixAtmPortEntry 8 }

    -- 1.3.6.1.4.1.2011.2.25.4.50.52.1.3.1.9
    optixAtmPortVccVpi OBJECT-TYPE
        SYNTAX Unsigned32
        MAX-ACCESS read-create
        STATUS current
        DESCRIPTION
            "This paramater specifies the atm port vcc vpi. Value range fro OSN 1099/OSN 3900: 0 to 64."
        ::= { optixAtmPortEntry 9 }

    -- 1.3.6.1.4.1.2011.2.25.4.50.52.1.3.1.10
    optixAtmPortEncapType OBJECT-TYPE
        SYNTAX INTEGER
        {
            null(0),
            cTag(1),
            sTag(2),
            iTag(3),
            atm(4),
            ppp(5)
        }
        MAX-ACCESS read-only
        STATUS current
        DESCRIPTION
            "This parameter specifies the atm port encaptype. 0: null, 1: cTag, 2: sTag, 3: iTag, 4: atm, 5: ppp"
        ::= { optixAtmPortEntry 10 }

    -- 1.3.6.1.4.1.2011.2.25.4.50.52.1.3.1.11
    optixAtmPortLevelMode OBJECT-TYPE
        SYNTAX INTEGER
        {
            level1(1),
            level2(2),
            level3(3),
            level2Level3(4)
        }
        MAX-ACCESS read-create
        STATUS current
        DESCRIPTION
            "This parameter specifies the Atm Port mode. 1: level1, 2: level2, 3: level3, 4: level2Level3"
        ::= { optixAtmPortEntry 11 }

    -- 1.3.6.1.4.1.2011.2.25.4.50.52.1.3.1.255
    optixAtmPortRowStatus OBJECT-TYPE
        SYNTAX RowStatus
        MAX-ACCESS read-create
        STATUS current
        DESCRIPTION
            "This paramater specifies the atm port row status"
        ::= { optixAtmPortEntry 255 }

    -- 1.3.6.1.4.1.2011.2.25.4.50.52.1.4
    optixMLPPPTable OBJECT-TYPE
        SYNTAX SEQUENCE OF OptixMLPPPEntry
        MAX-ACCESS not-accessible
        STATUS current
        DESCRIPTION
            "This table contains basic configuration information of ML-PPP"
        ::= { optixPktPortGroup 4 }

    -- 1.3.6.1.4.1.2011.2.25.4.50.52.1.4.1
    optixMLPPPEntry OBJECT-TYPE
        SYNTAX OptixMLPPPEntry
        MAX-ACCESS not-accessible
        STATUS current
        DESCRIPTION
            "Entry containins basic configuration information of ML-PPP"
        INDEX{ optixMLPPPId }
        ::= { optixMLPPPTable 1 }

    OptixMLPPPEntry ::=
        SEQUENCE {
            optixMLPPPId
                Unsigned32,
            optixMLPPPMinMemNum
                Unsigned32,
            optixMLPPPDelayCheckEn
                INTEGER,
            optixMLPPPDelay
                Unsigned32,
            optixMLPPPBoardId
                Unsigned32,
            optixMLPPPSubId
                Unsigned32,
            optixMLPPPPortId
                OCTET STRING,
            optixMLPPPState
                INTEGER,
            optixMLPPPNegotIp
                IpAddress,
            optixMLPPPNegotMask
                Unsigned32,
            optixMLPPPSeqNumType
                INTEGER,
            optixMLPPPFragsize
                Unsigned32,
            optixMLPPPSendSpeed
                Unsigned32,
            optixMLPPPReciveSpeed
                Unsigned32,
            optixMLPPPOSICPType
                INTEGER,
            optixMLPPPMtu
                Unsigned32,
            optixMLPPPLevelMode
                INTEGER,
            optixMLPPPResetState
                INTEGER,
            optixMLPPPRowStatus
                RowStatus
        }

    -- 1.3.6.1.4.1.2011.2.25.4.50.52.1.4.1.1
    optixMLPPPId OBJECT-TYPE
        SYNTAX Unsigned32
        MAX-ACCESS not-accessible
        STATUS current
        DESCRIPTION
            "This parameter specifies ML-PPP id"
        ::= { optixMLPPPEntry 1 }

    -- 1.3.6.1.4.1.2011.2.25.4.50.52.1.4.1.2
    optixMLPPPMinMemNum OBJECT-TYPE
        SYNTAX Unsigned32
        MAX-ACCESS read-create
        STATUS current
        DESCRIPTION
            "This parameter specifies ML-PPP min member number"
        ::= { optixMLPPPEntry 2 }

    -- 1.3.6.1.4.1.2011.2.25.4.50.52.1.4.1.3
    optixMLPPPDelayCheckEn OBJECT-TYPE
        SYNTAX INTEGER
        {
            disable(0),
            enable(1),
            none(255)
        }
        MAX-ACCESS read-create
        STATUS current
        DESCRIPTION
            "This parameter specifies ML-PPP delay check enable. 0: disable, 1: enable, 255: none"
        ::= { optixMLPPPEntry 3 }

    -- 1.3.6.1.4.1.2011.2.25.4.50.52.1.4.1.4
    optixMLPPPDelay OBJECT-TYPE
        SYNTAX Unsigned32
        MAX-ACCESS read-create
        STATUS current
        DESCRIPTION
            "This parameter specifies ML-PPP delay"
        ::= { optixMLPPPEntry 4 }

    -- 1.3.6.1.4.1.2011.2.25.4.50.52.1.4.1.5
    optixMLPPPBoardId OBJECT-TYPE
        SYNTAX Unsigned32
        MAX-ACCESS read-only
        STATUS current
        DESCRIPTION
            "This parameter specifies ML-PPP board id"
        ::= { optixMLPPPEntry 5 }

    -- 1.3.6.1.4.1.2011.2.25.4.50.52.1.4.1.6
    optixMLPPPSubId OBJECT-TYPE
        SYNTAX Unsigned32
        MAX-ACCESS read-only
        STATUS current
        DESCRIPTION
            "This parameter specifies ML-PPP subcard id"
        ::= { optixMLPPPEntry 6 }

    -- 1.3.6.1.4.1.2011.2.25.4.50.52.1.4.1.7
    optixMLPPPPortId OBJECT-TYPE
        SYNTAX OCTET STRING
        MAX-ACCESS read-only
        STATUS current
        DESCRIPTION
            "This parameter specifies ML-PPP port id"
        ::= { optixMLPPPEntry 7 }

    -- 1.3.6.1.4.1.2011.2.25.4.50.52.1.4.1.8
    optixMLPPPState OBJECT-TYPE
        SYNTAX INTEGER
        {
            up(1),
            down(2)
        }
        MAX-ACCESS read-only
        STATUS current
        DESCRIPTION
            "This parameter specifies ML-PPP state. 1: up, 2: down"
        ::= { optixMLPPPEntry 8 }

    -- 1.3.6.1.4.1.2011.2.25.4.50.52.1.4.1.9
    optixMLPPPNegotIp OBJECT-TYPE
        SYNTAX IpAddress
        MAX-ACCESS read-only
        STATUS current
        DESCRIPTION
            "This parameter specifies ML-PPP negot ip"
        ::= { optixMLPPPEntry 9 }

    -- 1.3.6.1.4.1.2011.2.25.4.50.52.1.4.1.10
    optixMLPPPNegotMask OBJECT-TYPE
        SYNTAX Unsigned32
        MAX-ACCESS read-only
        STATUS current
        DESCRIPTION
            "This parameter specifies ML-PPP negot mask"
        ::= { optixMLPPPEntry 10 }

    -- 1.3.6.1.4.1.2011.2.25.4.50.52.1.4.1.11
    optixMLPPPSeqNumType OBJECT-TYPE
        SYNTAX INTEGER
        {
            huawei(0),
            short(1),
            long(2)
        }
        MAX-ACCESS read-create
        STATUS current
        DESCRIPTION
            "This parameter specifies ML-PPP SEQNUM type. 0: huawei, 1: short, 2: long"
        ::= { optixMLPPPEntry 11 }

    -- 1.3.6.1.4.1.2011.2.25.4.50.52.1.4.1.12
    optixMLPPPFragsize OBJECT-TYPE
        SYNTAX Unsigned32
        MAX-ACCESS read-create
        STATUS current
        DESCRIPTION
            "This parameter specifies ML-PPP frag size"
        ::= { optixMLPPPEntry 12 }

    -- 1.3.6.1.4.1.2011.2.25.4.50.52.1.4.1.13
    optixMLPPPSendSpeed OBJECT-TYPE
        SYNTAX Unsigned32
        MAX-ACCESS read-only
        STATUS current
        DESCRIPTION
            "This parameter specifies ML-PPP send speed"
        ::= { optixMLPPPEntry 13 }

    -- 1.3.6.1.4.1.2011.2.25.4.50.52.1.4.1.14
    optixMLPPPReciveSpeed OBJECT-TYPE
        SYNTAX Unsigned32
        MAX-ACCESS read-only
        STATUS current
        DESCRIPTION
            "This parameter specifies ML-PPP recive speed"
        ::= { optixMLPPPEntry 14 }

    -- 1.3.6.1.4.1.2011.2.25.4.50.52.1.4.1.15
    optixMLPPPOSICPType OBJECT-TYPE
        SYNTAX INTEGER
        {
            disable(0),
            enable(1)
        }
        MAX-ACCESS read-only
        STATUS current
        DESCRIPTION
            "This parameter specifies ML-PPP OSICP type. 0: disable, 1: enable"
        ::= { optixMLPPPEntry 15 }

    -- 1.3.6.1.4.1.2011.2.25.4.50.52.1.4.1.16
    optixMLPPPMtu OBJECT-TYPE
        SYNTAX Unsigned32
        MAX-ACCESS read-create
        STATUS current
        DESCRIPTION
            "This parameter specifies the MLPPP port MTU"
        ::= { optixMLPPPEntry 16 }

    -- 1.3.6.1.4.1.2011.2.25.4.50.52.1.4.1.17
    optixMLPPPLevelMode OBJECT-TYPE
        SYNTAX INTEGER
        {
            level1(1),
            level2(2),
            level3(3),
            level2Level3(4)
        }
        MAX-ACCESS read-create
        STATUS current
        DESCRIPTION
            "This parameter specifies the MLPPP mode. 1: level1, 2: level2, 3: level3, 4: level2Level3"
        ::= { optixMLPPPEntry 17 }

    -- 1.3.6.1.4.1.2011.2.25.4.50.52.1.4.1.18
    optixMLPPPResetState OBJECT-TYPE
        SYNTAX INTEGER
        {
            null(0)
        }
        MAX-ACCESS read-create
        STATUS current
        DESCRIPTION
            "This parameter specifies the MLPPP reset state. 0: null"
        ::= { optixMLPPPEntry 18 }

    -- 1.3.6.1.4.1.2011.2.25.4.50.52.1.4.1.255
    optixMLPPPRowStatus OBJECT-TYPE
        SYNTAX RowStatus
        MAX-ACCESS read-create
        STATUS current
        DESCRIPTION
            "This parameter specifies ML-PPP row status"
        ::= { optixMLPPPEntry 255 }

    -- 1.3.6.1.4.1.2011.2.25.4.50.52.1.5
    optixL3PortTable OBJECT-TYPE
        SYNTAX SEQUENCE OF OptixL3PortEntry
        MAX-ACCESS not-accessible
        STATUS current
        DESCRIPTION
            "This table contains basic configuration information of L3 Port"
        ::= { optixPktPortGroup 5 }

    -- 1.3.6.1.4.1.2011.2.25.4.50.52.1.5.1
    optixL3PortEntry OBJECT-TYPE
        SYNTAX OptixL3PortEntry
        MAX-ACCESS not-accessible
        STATUS current
        DESCRIPTION
            "Entry containins basic configuration information of L3 Port"
        INDEX{ optixLogBoardId,optixLogSubCardId,optixL3PortId }
        ::= { optixL3PortTable 1 }

    OptixL3PortEntry ::=
        SEQUENCE {
            optixL3PortId
                Unsigned32,
            optixL3PortIpMode
                INTEGER,
            optixL3PortIpAddr
                IpAddress,
            optixL3PortIpMask
                IpAddress,
            optixL3PortBrwIpBoardId
                Unsigned32,
            optixL3PortBrwIpSubId
                Unsigned32,
            optixL3PortBrwIpPortId
                Unsigned32,
            optixL3PortMplsEnable
                INTEGER,
            optixL3PortArpAgeTime
                Unsigned32,
            optixL3PortArpFullFlag
                INTEGER,
            optixL3PortMtu
                Unsigned32,
            optixL3PortRowStatus
                RowStatus
        }

    -- 1.3.6.1.4.1.2011.2.25.4.50.52.1.5.1.1
    optixL3PortId OBJECT-TYPE
        SYNTAX Unsigned32
        MAX-ACCESS not-accessible
        STATUS current
        DESCRIPTION
            "This parameter specifies the L3 port id"
        ::= { optixL3PortEntry 1 }

    -- 1.3.6.1.4.1.2011.2.25.4.50.52.1.5.1.2
    optixL3PortIpMode OBJECT-TYPE
        SYNTAX INTEGER
        {
            dsgt(1),
            brwne(2),
            brwpt(3)
        }
        MAX-ACCESS read-create
        STATUS current
        DESCRIPTION
            "This parameter specifies the L3 port ip mode. 1: dsgt, 2: brwne, 3: brwpt"
        ::= { optixL3PortEntry 2 }

    -- 1.3.6.1.4.1.2011.2.25.4.50.52.1.5.1.3
    optixL3PortIpAddr OBJECT-TYPE
        SYNTAX IpAddress
        MAX-ACCESS read-create
        STATUS current
        DESCRIPTION
            "This parameter specifies the L3 port ip address. Value range in in dotted decimal notation: 0.0.0.0 to 255.255.255.255."
        ::= { optixL3PortEntry 3 }

    -- 1.3.6.1.4.1.2011.2.25.4.50.52.1.5.1.4
    optixL3PortIpMask OBJECT-TYPE
        SYNTAX IpAddress
        MAX-ACCESS read-create
        STATUS current
        DESCRIPTION
            "This parameter specifies the L3 port ip mask. Value range in in dotted decimal notation: 0.0.0.0 to 255.255.255.255."
        ::= { optixL3PortEntry 4 }

    -- 1.3.6.1.4.1.2011.2.25.4.50.52.1.5.1.5
    optixL3PortBrwIpBoardId OBJECT-TYPE
        SYNTAX Unsigned32
        MAX-ACCESS read-create
        STATUS current
        DESCRIPTION
            "This parameter specifies the L3 port ip borrow ip board id"
        ::= { optixL3PortEntry 5 }

    -- 1.3.6.1.4.1.2011.2.25.4.50.52.1.5.1.6
    optixL3PortBrwIpSubId OBJECT-TYPE
        SYNTAX Unsigned32
        MAX-ACCESS read-create
        STATUS current
        DESCRIPTION
            "This parameter specifies the L3 port ip borrow ip port id"
        ::= { optixL3PortEntry 6 }

    -- 1.3.6.1.4.1.2011.2.25.4.50.52.1.5.1.7
    optixL3PortBrwIpPortId OBJECT-TYPE
        SYNTAX Unsigned32
        MAX-ACCESS read-create
        STATUS current
        DESCRIPTION
            "This parameter specifies the L3 port ip borrow subbd id"
        ::= { optixL3PortEntry 7 }

    -- 1.3.6.1.4.1.2011.2.25.4.50.52.1.5.1.8
    optixL3PortMplsEnable OBJECT-TYPE
        SYNTAX INTEGER
        {
            disable(0),
            enable(1)
        }
        MAX-ACCESS read-create
        STATUS current
        DESCRIPTION
            "This parameter specifies the L3 port mpls enable. 0: disable, 1: enable"
        ::= { optixL3PortEntry 8 }

    -- 1.3.6.1.4.1.2011.2.25.4.50.52.1.5.1.9
    optixL3PortArpAgeTime OBJECT-TYPE
        SYNTAX Unsigned32
        MAX-ACCESS read-create
        STATUS current
        DESCRIPTION
            "This parameter specifies the L3 port arp age time. Value range: 1 to 1440 (unit: minute)"
        ::= { optixL3PortEntry 9 }

    -- 1.3.6.1.4.1.2011.2.25.4.50.52.1.5.1.10
    optixL3PortArpFullFlag OBJECT-TYPE
        SYNTAX INTEGER
        {
            no(0),
            yes(1)
        }
        MAX-ACCESS read-only
        STATUS current
        DESCRIPTION
            "This parameter specifies the L3 port arp Full flag"
        ::= { optixL3PortEntry 10 }

    -- 1.3.6.1.4.1.2011.2.25.4.50.52.1.5.1.11
    optixL3PortMtu OBJECT-TYPE
        SYNTAX Unsigned32
        MAX-ACCESS read-create
        STATUS current
        DESCRIPTION
            "This parameter specifies the L3 port mtu. Value range:46 to 9600, default:1500"
        ::= { optixL3PortEntry 11 }

    -- 1.3.6.1.4.1.2011.2.25.4.50.52.1.5.1.255
    optixL3PortRowStatus OBJECT-TYPE
        SYNTAX RowStatus
        MAX-ACCESS read-create
        STATUS current
        DESCRIPTION
            "This parameter specifies the L3 port row status"
        ::= { optixL3PortEntry 255 }

    -- 1.3.6.1.4.1.2011.2.25.4.50.52.1.6
    optixE1Table OBJECT-TYPE
        SYNTAX SEQUENCE OF OptixE1Entry
        MAX-ACCESS not-accessible
        STATUS current
        DESCRIPTION
            "This table contains configuration information of E1 port"
        ::= { optixPktPortGroup 6 }

    -- 1.3.6.1.4.1.2011.2.25.4.50.52.1.6.1
    optixE1Entry OBJECT-TYPE
        SYNTAX OptixE1Entry
        MAX-ACCESS not-accessible
        STATUS current
        DESCRIPTION
            "Entry containing configuration information of E1 port"
        INDEX{ optixLogBoardId,optixLogSubCardId,optixE1PortId }
        ::= { optixE1Table 1 }

    OptixE1Entry ::=
        SEQUENCE {
            optixE1PortId
                Unsigned32,
            optixE1RetimingMode
                INTEGER,
            optixE1LinkCode
                INTEGER,
            optixE1Frm
                INTEGER,
            optixE1Eq
                INTEGER,
            optixE1UserSlotNum
                Unsigned32,
            optixE1Loop
                INTEGER,
            optixE1PrbsDir
                INTEGER,
            optixE1PrbsFrm
                INTEGER,
            optixE1TestType
                INTEGER,
            optixE1StartDataTime
                DateAndTime,
            optixE1EndDataTime
                DateAndTime,
            optixE1Progress
                Unsigned32,
            optixE1RealTestPeriod
                Unsigned32,
            optixE1DataTypeNum
                Unsigned32,
            optixE1Type1
                Unsigned32,
            optixE1TestType2
                Unsigned32,
            optixE1Result1
                Unsigned32,
            optixE1TestResult2
                Unsigned32,
            optixE1EncapType
                INTEGER,
            optixE1Mtu
                Unsigned32,
            optixE1LevelMode
                INTEGER,
            optixE1BittestPrbsDir
                INTEGER,
            optixE1BittestPrbsFrm
                INTEGER,
            optixE1BittestType
                INTEGER,
            optixE1BittestStartDateTime
                DateAndTime,
            optixE1BittestRealTestPeriod
                Unsigned32,
            optixE1BittestStartPeriod
                Unsigned32,
            optixE1BittestTestResult1
                OCTET STRING,
            optixE1BittestTestResult2
                OCTET STRING,
            optixE1BittestTestResult3
                OCTET STRING,
            optixE1TestAction
                INTEGER,
            optixE1TestTime
                Unsigned32,
            optixE1TestType3
                Unsigned32,
            optixE1TestResult3
                Unsigned32,
            optixE1TestType4
                Unsigned32,
            optixE1TestResult4
                Unsigned32,
            optixE1TestType5
                Unsigned32,
            optixE1TestResult5
                Unsigned32,
            optixE1TestType6
                Unsigned32,
            optixE1TestResult6
                Unsigned32,
            optixE1BerTH
                INTEGER,
            optixE1AisCheck
                INTEGER,
            optixE1RowStatus
                RowStatus
        }

    -- 1.3.6.1.4.1.2011.2.25.4.50.52.1.6.1.1
    optixE1PortId OBJECT-TYPE
        SYNTAX Unsigned32
        MAX-ACCESS not-accessible
        STATUS current
        DESCRIPTION
            "This parameter specifies the E1 port id"
        ::= { optixE1Entry 1 }

    -- 1.3.6.1.4.1.2011.2.25.4.50.52.1.6.1.2
    optixE1RetimingMode OBJECT-TYPE
        SYNTAX INTEGER
        {
            master(0),
            slave(1),
            line(2)
        }
        MAX-ACCESS read-create
        STATUS current
        DESCRIPTION
            "This parameter specifies E1 port retiming mode. 0: master, 1: slave, 2: line"
        ::= { optixE1Entry 2 }

    -- 1.3.6.1.4.1.2011.2.25.4.50.52.1.6.1.3
    optixE1LinkCode OBJECT-TYPE
        SYNTAX INTEGER
        {
            hdb3(0)
        }
        MAX-ACCESS read-create
        STATUS current
        DESCRIPTION
            "This parameter specifies E1 port linkcode. 0: hdb3"
        ::= { optixE1Entry 3 }

    -- 1.3.6.1.4.1.2011.2.25.4.50.52.1.6.1.4
    optixE1Frm OBJECT-TYPE
        SYNTAX INTEGER
        {
            unframe(0),
            doubleFrame(1),
            crc4Multiframe(2)
        }
        MAX-ACCESS read-create
        STATUS current
        DESCRIPTION
            "This parameter specifies E1 port frame struct. 0: unframe, 1: doubleFrame, 2: crc4Multiframe"
        ::= { optixE1Entry 4 }

    -- 1.3.6.1.4.1.2011.2.25.4.50.52.1.6.1.5
    optixE1Eq OBJECT-TYPE
        SYNTAX INTEGER
        {
            snmp75(1),
            snmp120(2)
        }
        MAX-ACCESS read-only
        STATUS current
        DESCRIPTION
            "This parameter specifies E1 port cable resistance value. 1: snmp75, 2: snmp120"
        ::= { optixE1Entry 5 }

    -- 1.3.6.1.4.1.2011.2.25.4.50.52.1.6.1.6
    optixE1UserSlotNum OBJECT-TYPE
        SYNTAX Unsigned32
        MAX-ACCESS read-create
        STATUS current
        DESCRIPTION
            "This parameter specifies E1 user slot number"
        ::= { optixE1Entry 6 }

    -- 1.3.6.1.4.1.2011.2.25.4.50.52.1.6.1.7
    optixE1Loop OBJECT-TYPE
        SYNTAX INTEGER
        {
            noloop(0),
            inloop(1),
            outloop(2)
        }
        MAX-ACCESS read-create
        STATUS current
        DESCRIPTION
            "This parameter specifies E1 port loop mode. 0: noloop, 1: inloop, 2: outloop"
        ::= { optixE1Entry 7 }

    -- 1.3.6.1.4.1.2011.2.25.4.50.52.1.6.1.8
    optixE1PrbsDir OBJECT-TYPE
        SYNTAX INTEGER
        {
            uni(0),
            nni(1)
        }
        MAX-ACCESS read-create
        STATUS current
        DESCRIPTION
            "This parameter specifies E1 port prbs dir. 0: UNI, 1: NNI"
        ::= { optixE1Entry 8 }

    -- 1.3.6.1.4.1.2011.2.25.4.50.52.1.6.1.9
    optixE1PrbsFrm OBJECT-TYPE
        SYNTAX INTEGER
        {
            unFrame(0),
            frame(1)
        }
        MAX-ACCESS read-create
        STATUS current
        DESCRIPTION
            "This parameter specifies E1 port prbs frm. 0: unFrame, 1: frame"
        ::= { optixE1Entry 9 }

    -- 1.3.6.1.4.1.2011.2.25.4.50.52.1.6.1.10
    optixE1TestType OBJECT-TYPE
        SYNTAX INTEGER
        {
            shortTerm(1),
            longTerm(2),
            longlongTerm(3)
        }
        MAX-ACCESS read-create
        STATUS current
        DESCRIPTION
            "This parameter specifies E1 port test type. 1: shortTerm, 2: longTerm, 3: longTerm"
        ::= { optixE1Entry 10 }

    -- 1.3.6.1.4.1.2011.2.25.4.50.52.1.6.1.11
    optixE1StartDataTime OBJECT-TYPE
        SYNTAX DateAndTime
        MAX-ACCESS read-only
        STATUS current
        DESCRIPTION
            "This parameter specifies E1 port start data time"
        ::= { optixE1Entry 11 }

    -- 1.3.6.1.4.1.2011.2.25.4.50.52.1.6.1.12
    optixE1EndDataTime OBJECT-TYPE
        SYNTAX DateAndTime
        MAX-ACCESS read-only
        STATUS current
        DESCRIPTION
            "This parameter specifies E1 port end data time"
        ::= { optixE1Entry 12 }

    -- 1.3.6.1.4.1.2011.2.25.4.50.52.1.6.1.13
    optixE1Progress OBJECT-TYPE
        SYNTAX Unsigned32
        MAX-ACCESS read-only
        STATUS current
        DESCRIPTION
            "This parameter specifies E1 port progress. Value range: 1 to 100 (unit: %)"
        ::= { optixE1Entry 13 }

    -- 1.3.6.1.4.1.2011.2.25.4.50.52.1.6.1.14
    optixE1RealTestPeriod OBJECT-TYPE
        SYNTAX Unsigned32
        MAX-ACCESS read-only
        STATUS current
        DESCRIPTION
            "This parameter specifies E1 port real test period"
        ::= { optixE1Entry 14 }

    -- 1.3.6.1.4.1.2011.2.25.4.50.52.1.6.1.15
    optixE1DataTypeNum OBJECT-TYPE
        SYNTAX Unsigned32
        MAX-ACCESS read-only
        STATUS current
        DESCRIPTION
            "This parameter specifies E1 port data type number"
        ::= { optixE1Entry 15 }

    -- 1.3.6.1.4.1.2011.2.25.4.50.52.1.6.1.16
    optixE1Type1 OBJECT-TYPE
        SYNTAX Unsigned32
        MAX-ACCESS read-only
        STATUS current
        DESCRIPTION
            "This parameter specifies E1 port type 1"
        ::= { optixE1Entry 16 }

    -- 1.3.6.1.4.1.2011.2.25.4.50.52.1.6.1.17
    optixE1TestType2 OBJECT-TYPE
        SYNTAX Unsigned32
        MAX-ACCESS read-only
        STATUS current
        DESCRIPTION
            "This parameter specifies E1 port type 2"
        ::= { optixE1Entry 17 }

    -- 1.3.6.1.4.1.2011.2.25.4.50.52.1.6.1.18
    optixE1Result1 OBJECT-TYPE
        SYNTAX Unsigned32
        MAX-ACCESS read-only
        STATUS current
        DESCRIPTION
            "This parameter specifies E1 port test result 1"
        ::= { optixE1Entry 18 }

    -- 1.3.6.1.4.1.2011.2.25.4.50.52.1.6.1.19
    optixE1TestResult2 OBJECT-TYPE
        SYNTAX Unsigned32
        MAX-ACCESS read-only
        STATUS current
        DESCRIPTION
            "This parameter specifies E1 port test result 2"
        ::= { optixE1Entry 19 }

    -- 1.3.6.1.4.1.2011.2.25.4.50.52.1.6.1.20
    optixE1EncapType OBJECT-TYPE
        SYNTAX INTEGER
        {
            null(0),
            cTag(1),
            sTag(2),
            iTag(3),
            atm(4),
            ppp(5)
        }
        MAX-ACCESS read-create
        STATUS current
        DESCRIPTION
            "This parameter specifies the e1 port encaptype. 0: null, 1: cTag, 2: sTag, 3: iTag, 4: atm, 5: ppp"
        ::= { optixE1Entry 20 }

    -- 1.3.6.1.4.1.2011.2.25.4.50.52.1.6.1.21
    optixE1Mtu OBJECT-TYPE
        SYNTAX Unsigned32
        MAX-ACCESS read-create
        STATUS current
        DESCRIPTION
            "This parameter specifies the E1 MTU"
        ::= { optixE1Entry 21 }

    -- 1.3.6.1.4.1.2011.2.25.4.50.52.1.6.1.22
    optixE1LevelMode OBJECT-TYPE
        SYNTAX INTEGER
        {
            level1(1),
            level2(2),
            level3(3),
            level2Level3(4)
        }
        MAX-ACCESS read-create
        STATUS current
        DESCRIPTION
            "This parameter specifies the E1 port mode. 1: level1, 2: level2, 3: level3, 4: level2Level3"
        ::= { optixE1Entry 22 }

    -- 1.3.6.1.4.1.2011.2.25.4.50.52.1.6.1.23
    optixE1BittestPrbsDir OBJECT-TYPE
        SYNTAX INTEGER
        {
            uni(0),
            nni(1)
        }
        MAX-ACCESS read-create
        STATUS current
        DESCRIPTION
            "This parameter specifies E1 port prbs dir. 0: UNI, 1: NNI"
        ::= { optixE1Entry 23 }

    -- 1.3.6.1.4.1.2011.2.25.4.50.52.1.6.1.24
    optixE1BittestPrbsFrm OBJECT-TYPE
        SYNTAX INTEGER
        {
            unFrame(0),
            frame(1)
        }
        MAX-ACCESS read-create
        STATUS current
        DESCRIPTION
            "This parameter specifies E1 port prbs frm. 0: unFrame, 1: frame"
        ::= { optixE1Entry 24 }

    -- 1.3.6.1.4.1.2011.2.25.4.50.52.1.6.1.25
    optixE1BittestType OBJECT-TYPE
        SYNTAX INTEGER
        {
            shortTerm(1),
            longTerm(2),
            longlongTerm(3)
        }
        MAX-ACCESS read-create
        STATUS current
        DESCRIPTION
            "This parameter specifies the E1 port bittest type. 1: shortTerm, 2: longTerm, 3: longTerm"
        ::= { optixE1Entry 25 }

    -- 1.3.6.1.4.1.2011.2.25.4.50.52.1.6.1.26
    optixE1BittestStartDateTime OBJECT-TYPE
        SYNTAX DateAndTime
        MAX-ACCESS read-only
        STATUS current
        DESCRIPTION
            "This parameter specifies the E1 port bittest date and time"
        ::= { optixE1Entry 26 }

    -- 1.3.6.1.4.1.2011.2.25.4.50.52.1.6.1.27
    optixE1BittestRealTestPeriod OBJECT-TYPE
        SYNTAX Unsigned32
        MAX-ACCESS read-only
        STATUS current
        DESCRIPTION
            "This parameter specifies the E1 port bittest real test period"
        ::= { optixE1Entry 27 }

    -- 1.3.6.1.4.1.2011.2.25.4.50.52.1.6.1.28
    optixE1BittestStartPeriod OBJECT-TYPE
        SYNTAX Unsigned32
        MAX-ACCESS read-only
        STATUS current
        DESCRIPTION
            "This parameter specifies the E1 port bittest start period"
        ::= { optixE1Entry 28 }

    -- 1.3.6.1.4.1.2011.2.25.4.50.52.1.6.1.29
    optixE1BittestTestResult1 OBJECT-TYPE
        SYNTAX OCTET STRING
        MAX-ACCESS read-only
        STATUS current
        DESCRIPTION
            "This parameter specifies the E1 port bittest result(part 1)"
        ::= { optixE1Entry 29 }

    -- 1.3.6.1.4.1.2011.2.25.4.50.52.1.6.1.30
    optixE1BittestTestResult2 OBJECT-TYPE
        SYNTAX OCTET STRING
        MAX-ACCESS read-only
        STATUS current
        DESCRIPTION
            "This parameter specifies the E1 port bittest result(part 2)"
        ::= { optixE1Entry 30 }

    -- 1.3.6.1.4.1.2011.2.25.4.50.52.1.6.1.31
    optixE1BittestTestResult3 OBJECT-TYPE
        SYNTAX OCTET STRING
        MAX-ACCESS read-only
        STATUS current
        DESCRIPTION
            "This parameter specifies the E1 port bittest result(part 3)"
        ::= { optixE1Entry 31 }

    -- 1.3.6.1.4.1.2011.2.25.4.50.52.1.6.1.32
    optixE1TestAction OBJECT-TYPE
        SYNTAX INTEGER
        {
            stop(0),
            start(1),
            null(255)
        }
        MAX-ACCESS read-create
        STATUS current
        DESCRIPTION
            "This parameter specifies E1 port test set Begin time. 0: stop, 1: start, 255: null"
        ::= { optixE1Entry 32 }

    -- 1.3.6.1.4.1.2011.2.25.4.50.52.1.6.1.33
    optixE1TestTime OBJECT-TYPE
        SYNTAX Unsigned32
        MAX-ACCESS read-create
        STATUS current
        DESCRIPTION
            "This parameter specifies E1 port test set End Time"
        ::= { optixE1Entry 33 }

    -- 1.3.6.1.4.1.2011.2.25.4.50.52.1.6.1.34
    optixE1TestType3 OBJECT-TYPE
        SYNTAX Unsigned32
        MAX-ACCESS read-only
        STATUS current
        DESCRIPTION
            "This parameter specifies E1 port type 3."
        ::= { optixE1Entry 34 }

    -- 1.3.6.1.4.1.2011.2.25.4.50.52.1.6.1.35
    optixE1TestResult3 OBJECT-TYPE
        SYNTAX Unsigned32
        MAX-ACCESS read-only
        STATUS current
        DESCRIPTION
            "This parameter specifies E1 port test result 3"
        ::= { optixE1Entry 35 }

    -- 1.3.6.1.4.1.2011.2.25.4.50.52.1.6.1.36
    optixE1TestType4 OBJECT-TYPE
        SYNTAX Unsigned32
        MAX-ACCESS read-only
        STATUS current
        DESCRIPTION
            "This parameter specifies E1 port type 4"
        ::= { optixE1Entry 36 }

    -- 1.3.6.1.4.1.2011.2.25.4.50.52.1.6.1.37
    optixE1TestResult4 OBJECT-TYPE
        SYNTAX Unsigned32
        MAX-ACCESS read-only
        STATUS current
        DESCRIPTION
            "This parameter specifies E1 port test result 4"
        ::= { optixE1Entry 37 }

    -- 1.3.6.1.4.1.2011.2.25.4.50.52.1.6.1.38
    optixE1TestType5 OBJECT-TYPE
        SYNTAX Unsigned32
        MAX-ACCESS read-only
        STATUS current
        DESCRIPTION
            "This parameter specifies E1 port type 5"
        ::= { optixE1Entry 38 }

    -- 1.3.6.1.4.1.2011.2.25.4.50.52.1.6.1.39
    optixE1TestResult5 OBJECT-TYPE
        SYNTAX Unsigned32
        MAX-ACCESS read-only
        STATUS current
        DESCRIPTION
            "his parameter specifies E1 port test result 5"
        ::= { optixE1Entry 39 }

    -- 1.3.6.1.4.1.2011.2.25.4.50.52.1.6.1.40
    optixE1TestType6 OBJECT-TYPE
        SYNTAX Unsigned32
        MAX-ACCESS read-only
        STATUS current
        DESCRIPTION
            "This parameter specifies E1 port type 6"
        ::= { optixE1Entry 40 }

    -- 1.3.6.1.4.1.2011.2.25.4.50.52.1.6.1.41
    optixE1TestResult6 OBJECT-TYPE
        SYNTAX Unsigned32
        MAX-ACCESS read-only
        STATUS current
        DESCRIPTION
            "This parameter specifies E1 port test result 6"
        ::= { optixE1Entry 41 }

    -- 1.3.6.1.4.1.2011.2.25.4.50.52.1.6.1.42
    optixE1BerTH OBJECT-TYPE
        SYNTAX INTEGER
        {
            e9(1),
            e8(2),
            e7(3),
            e6(4),
            e5(5),
            e4(6),
            e3(7)
        }
        MAX-ACCESS read-create
        STATUS current
        DESCRIPTION
            "This object indicates the level of the upper BER threshold of E1 links."
        ::= { optixE1Entry 42 }

    -- 1.3.6.1.4.1.2011.2.25.4.50.52.1.6.1.43
    optixE1AisCheck OBJECT-TYPE
        SYNTAX INTEGER
        {
            disable(0),
            enable(1)
        }
        MAX-ACCESS read-create
        STATUS current
        DESCRIPTION
            "This object indicates the status of the Ais alarm."
        ::= { optixE1Entry 43 }

    -- 1.3.6.1.4.1.2011.2.25.4.50.52.1.6.1.255
    optixE1RowStatus OBJECT-TYPE
        SYNTAX RowStatus
        MAX-ACCESS read-create
        STATUS current
        DESCRIPTION
            "This parameter specifies E1 port row status"
        ::= { optixE1Entry 255 }

    -- 1.3.6.1.4.1.2011.2.25.4.50.52.1.7
    optixSPV4Table OBJECT-TYPE
        SYNTAX SEQUENCE OF OptixSPV4Entry
        MAX-ACCESS not-accessible
        STATUS current
        DESCRIPTION
            "This table contains configuration information of serial port"
        ::= { optixPktPortGroup 7 }

    -- 1.3.6.1.4.1.2011.2.25.4.50.52.1.7.1
    optixSPV4Entry OBJECT-TYPE
        SYNTAX OptixSPV4Entry
        MAX-ACCESS not-accessible
        STATUS current
        DESCRIPTION
            "Entry containing configuration information of serial port"
        INDEX{ optixLogBoardId,optixLogSubCardId,optixSPV4Id }
        ::= { optixSPV4Table 1 }

    OptixSPV4Entry ::=
        SEQUENCE {
            optixSPV4Id
                Unsigned32,
            optixSPV4PortId
                Unsigned32,
            optixSPV4Num
                Unsigned32,
            optixSPV4List
                OCTET STRING,
            optixSPV4EncapType
                INTEGER,
            optixSPV4LevelMode
                INTEGER,
            optixSPV4Mtu
                Unsigned32,
            optixSPV4RowStatus
                RowStatus
        }

    -- 1.3.6.1.4.1.2011.2.25.4.50.52.1.7.1.1
    optixSPV4Id OBJECT-TYPE
        SYNTAX Unsigned32
        MAX-ACCESS not-accessible
        STATUS current
        DESCRIPTION
            "This parameter specifies the serial port ID"
        ::= { optixSPV4Entry 1 }

    -- 1.3.6.1.4.1.2011.2.25.4.50.52.1.7.1.2
    optixSPV4PortId OBJECT-TYPE
        SYNTAX Unsigned32
        MAX-ACCESS read-create
        STATUS current
        DESCRIPTION
            "This parameter specifies physical port id"
        ::= { optixSPV4Entry 2 }

    -- 1.3.6.1.4.1.2011.2.25.4.50.52.1.7.1.3
    optixSPV4Num OBJECT-TYPE
        SYNTAX Unsigned32
        MAX-ACCESS read-create
        STATUS current
        DESCRIPTION
            "This parameter specifies serial port number"
        ::= { optixSPV4Entry 3 }

    -- 1.3.6.1.4.1.2011.2.25.4.50.52.1.7.1.4
    optixSPV4List OBJECT-TYPE
        SYNTAX OCTET STRING
        MAX-ACCESS read-create
        STATUS current
        DESCRIPTION
            "This parameter specifies serial port list"
        ::= { optixSPV4Entry 4 }

    -- 1.3.6.1.4.1.2011.2.25.4.50.52.1.7.1.5
    optixSPV4EncapType OBJECT-TYPE
        SYNTAX INTEGER
        {
            null(0),
            cTag(1),
            sTag(2),
            iTag(3),
            atm(4),
            ppp(5)
        }
        MAX-ACCESS read-create
        STATUS current
        DESCRIPTION
            "This parameter specifies the specifies serial port encaptype. 0: null, 1: cTag, 2: sTag, 3: iTag, 4: atm, 5: ppp"
        ::= { optixSPV4Entry 5 }

    -- 1.3.6.1.4.1.2011.2.25.4.50.52.1.7.1.6
    optixSPV4LevelMode OBJECT-TYPE
        SYNTAX INTEGER
        {
            level1(1),
            level2(2),
            level3(3),
            level2Level3(4)
        }
        MAX-ACCESS read-create
        STATUS current
        DESCRIPTION
            "This parameter specifies the specifies serial port mode. 1: level1, 2: level2, 3: level3, 4: level2Level3"
        ::= { optixSPV4Entry 6 }

    -- 1.3.6.1.4.1.2011.2.25.4.50.52.1.7.1.7
    optixSPV4Mtu OBJECT-TYPE
        SYNTAX Unsigned32
        MAX-ACCESS read-create
        STATUS current
        DESCRIPTION
            "This parameter specifies the SPV4 MTU"
        ::= { optixSPV4Entry 7 }

    -- 1.3.6.1.4.1.2011.2.25.4.50.52.1.7.1.255
    optixSPV4RowStatus OBJECT-TYPE
        SYNTAX RowStatus
        MAX-ACCESS read-create
        STATUS current
        DESCRIPTION
            "This parameter specifies serial port row status"
        ::= { optixSPV4Entry 255 }

    -- 1.3.6.1.4.1.2011.2.25.4.50.52.1.8
    optixSPVC12Table OBJECT-TYPE
        SYNTAX SEQUENCE OF OptixSPVC12Entry
        MAX-ACCESS not-accessible
        STATUS current
        DESCRIPTION
            "This table contains configuration information of serial port vc12"
        ::= { optixPktPortGroup 8 }

    -- 1.3.6.1.4.1.2011.2.25.4.50.52.1.8.1
    optixSPVC12Entry OBJECT-TYPE
        SYNTAX OptixSPVC12Entry
        MAX-ACCESS not-accessible
        STATUS current
        DESCRIPTION
            "Entry containing configuration information of serial port vc12"
        INDEX{ optixLogBoardId,optixLogSubCardId,optixSPVC12Id }
        ::= { optixSPVC12Table 1 }

    OptixSPVC12Entry ::=
        SEQUENCE {
            optixSPVC12Id
                Unsigned32,
            optixSPVC12HP
                Unsigned32,
            optixSPVC12LP
                Unsigned32,
            optixSPVC1264kNum
                Unsigned32,
            optixSPVC1264kList
                Unsigned32,
            optixSPVC12RowStatus
                RowStatus
        }

    -- 1.3.6.1.4.1.2011.2.25.4.50.52.1.8.1.1
    optixSPVC12Id OBJECT-TYPE
        SYNTAX Unsigned32
        MAX-ACCESS not-accessible
        STATUS current
        DESCRIPTION
            "This parameter sepcifies physical port of vc12"
        ::= { optixSPVC12Entry 1 }

    -- 1.3.6.1.4.1.2011.2.25.4.50.52.1.8.1.2
    optixSPVC12HP OBJECT-TYPE
        SYNTAX Unsigned32
        MAX-ACCESS read-only
        STATUS current
        DESCRIPTION
            "This parameter sepcifies HP of serial port vc12"
        ::= { optixSPVC12Entry 2 }

    -- 1.3.6.1.4.1.2011.2.25.4.50.52.1.8.1.3
    optixSPVC12LP OBJECT-TYPE
        SYNTAX Unsigned32
        MAX-ACCESS read-only
        STATUS current
        DESCRIPTION
            "This parameter sepcifies LP of serial port vc12"
        ::= { optixSPVC12Entry 3 }

    -- 1.3.6.1.4.1.2011.2.25.4.50.52.1.8.1.4
    optixSPVC1264kNum OBJECT-TYPE
        SYNTAX Unsigned32
        MAX-ACCESS read-only
        STATUS current
        DESCRIPTION
            "This parameter sepcifies 64k numbert of serial port vc 12"
        ::= { optixSPVC12Entry 4 }

    -- 1.3.6.1.4.1.2011.2.25.4.50.52.1.8.1.5
    optixSPVC1264kList OBJECT-TYPE
        SYNTAX Unsigned32
        MAX-ACCESS read-only
        STATUS current
        DESCRIPTION
            "This parameter sepcifies 64k list of serial port vc 12"
        ::= { optixSPVC12Entry 5 }

    -- 1.3.6.1.4.1.2011.2.25.4.50.52.1.8.1.255
    optixSPVC12RowStatus OBJECT-TYPE
        SYNTAX RowStatus
        MAX-ACCESS read-only
        STATUS current
        DESCRIPTION
            "This parameter sepcifies SP VC12 row status"
        ::= { optixSPVC12Entry 255 }

    -- 1.3.6.1.4.1.2011.2.25.4.50.52.1.9
    optixE1EventMember OBJECT IDENTIFIER ::= { optixPktPortGroup 9 }

    -- 1.3.6.1.4.1.2011.2.25.4.50.52.1.9.1
    optixE1BIDTrapInfo OBJECT-TYPE
        SYNTAX Unsigned32
        MAX-ACCESS accessible-for-notify
        STATUS current
        DESCRIPTION
            "This parameter specifies the E1 Board id"
        ::= { optixE1EventMember 1 }

    -- 1.3.6.1.4.1.2011.2.25.4.50.52.1.9.2
    optixE1SubIdTrapInfo OBJECT-TYPE
        SYNTAX Unsigned32
        MAX-ACCESS accessible-for-notify
        STATUS current
        DESCRIPTION
            "This parameter specifies the E1 Sub id"
        ::= { optixE1EventMember 2 }

    -- 1.3.6.1.4.1.2011.2.25.4.50.52.1.9.3
    optixE1PIdTrapInfo OBJECT-TYPE
        SYNTAX Unsigned32
        MAX-ACCESS accessible-for-notify
        STATUS current
        DESCRIPTION
            "This parameter specifies the E1 port id"
        ::= { optixE1EventMember 3 }

    -- 1.3.6.1.4.1.2011.2.25.4.50.52.1.9.4
    optixE1TimeStampTrapInfo OBJECT-TYPE
        SYNTAX Unsigned32
        MAX-ACCESS accessible-for-notify
        STATUS current
        DESCRIPTION
            "This parameter specifies the E1 port id"
        ::= { optixE1EventMember 4 }

    -- 1.3.6.1.4.1.2011.2.25.4.50.52.1.9.5
    optixE1PRBSDIRTrapInfo OBJECT-TYPE
        SYNTAX INTEGER
        {
            uni(0),
            nni(1)
        }
        MAX-ACCESS accessible-for-notify
        STATUS current
        DESCRIPTION
            "This parameter specifies the E1 PRBS-DIR. 0: UNI, 1: NNI"
        ::= { optixE1EventMember 5 }

    -- 1.3.6.1.4.1.2011.2.25.4.50.52.1.9.6
    optixE1PRBSFRMTrapInfo OBJECT-TYPE
        SYNTAX INTEGER
        {
            unFrame(0),
            frame(1)
        }
        MAX-ACCESS accessible-for-notify
        STATUS current
        DESCRIPTION
            "This parameter specifies the E1 PRBS-FRM. 0: unFrame, 1: frame"
        ::= { optixE1EventMember 6 }

    -- 1.3.6.1.4.1.2011.2.25.4.50.52.1.9.7
    optixE1TestTypeTrapInfo OBJECT-TYPE
        SYNTAX INTEGER
        {
            shortTerm(1),
            longTerm(2),
            longlongTerm(3)
        }
        MAX-ACCESS accessible-for-notify
        STATUS current
        DESCRIPTION
            "This parameter specifies the E1 test Type. 1: shortTerm, 2: longTerm, 3: longTerm"
        ::= { optixE1EventMember 7 }

    -- 1.3.6.1.4.1.2011.2.25.4.50.52.1.9.8
    optixE1StartDataTimeTrapInfo OBJECT-TYPE
        SYNTAX DateAndTime
        MAX-ACCESS accessible-for-notify
        STATUS current
        DESCRIPTION
            "This parameter specifies the E1 Start Data Time"
        ::= { optixE1EventMember 8 }

    -- 1.3.6.1.4.1.2011.2.25.4.50.52.1.9.9
    optixE1EndDataTimeTrapInfo OBJECT-TYPE
        SYNTAX DateAndTime
        MAX-ACCESS accessible-for-notify
        STATUS current
        DESCRIPTION
            "This parameter specifies the E1 End Data Time"
        ::= { optixE1EventMember 9 }

    -- 1.3.6.1.4.1.2011.2.25.4.50.52.1.9.10
    optixE1ProressTrapInfo OBJECT-TYPE
        SYNTAX Unsigned32
        MAX-ACCESS accessible-for-notify
        STATUS current
        DESCRIPTION
            "This parameter specifies the E1 Proress"
        ::= { optixE1EventMember 10 }

    -- 1.3.6.1.4.1.2011.2.25.4.50.52.1.9.11
    optixE1RealTestPeriodTrapInfo OBJECT-TYPE
        SYNTAX Unsigned32
        MAX-ACCESS accessible-for-notify
        STATUS current
        DESCRIPTION
            "This parameter specifies the E1 Real Test Period"
        ::= { optixE1EventMember 11 }

    -- 1.3.6.1.4.1.2011.2.25.4.50.52.1.9.12
    optixE1DatatypeNumTrapInfo OBJECT-TYPE
        SYNTAX Unsigned32
        MAX-ACCESS accessible-for-notify
        STATUS current
        DESCRIPTION
            "This parameter specifies the E1 DatatypeNum"
        ::= { optixE1EventMember 12 }

    -- 1.3.6.1.4.1.2011.2.25.4.50.52.1.9.13
    optixE1Type1TrapInfo OBJECT-TYPE
        SYNTAX Unsigned32
        MAX-ACCESS accessible-for-notify
        STATUS current
        DESCRIPTION
            "This parameter specifies the E1 Type1"
        ::= { optixE1EventMember 13 }

    -- 1.3.6.1.4.1.2011.2.25.4.50.52.1.9.14
    optixE1TestResult1TrapInfo OBJECT-TYPE
        SYNTAX Unsigned32
        MAX-ACCESS accessible-for-notify
        STATUS current
        DESCRIPTION
            "This parameter specifies the E1 Test Result1"
        ::= { optixE1EventMember 14 }

    -- 1.3.6.1.4.1.2011.2.25.4.50.52.1.9.15
    optixE1Type2TrapInfo OBJECT-TYPE
        SYNTAX Unsigned32
        MAX-ACCESS accessible-for-notify
        STATUS current
        DESCRIPTION
            "This parameter specifies the E1 type2"
        ::= { optixE1EventMember 15 }

    -- 1.3.6.1.4.1.2011.2.25.4.50.52.1.9.16
    optixE1TestResult2TrapInfo OBJECT-TYPE
        SYNTAX Unsigned32
        MAX-ACCESS accessible-for-notify
        STATUS current
        DESCRIPTION
            "This parameter specifies the E1 test Reasult2"
        ::= { optixE1EventMember 16 }

    -- 1.3.6.1.4.1.2011.2.25.4.50.52.1.9.17
    optixE1Type3TrapInfo OBJECT-TYPE
        SYNTAX Unsigned32
        MAX-ACCESS accessible-for-notify
        STATUS current
        DESCRIPTION
            "This parameter specifies E1 port type 3."
        ::= { optixE1EventMember 17 }

    -- 1.3.6.1.4.1.2011.2.25.4.50.52.1.9.18
    optixE1TestResult3TrapInfo OBJECT-TYPE
        SYNTAX Unsigned32
        MAX-ACCESS accessible-for-notify
        STATUS current
        DESCRIPTION
            "This parameter specifies E1 port test result 3."
        ::= { optixE1EventMember 18 }

    -- 1.3.6.1.4.1.2011.2.25.4.50.52.1.9.19
    optixE1Type4TrapInfo OBJECT-TYPE
        SYNTAX Unsigned32
        MAX-ACCESS accessible-for-notify
        STATUS current
        DESCRIPTION
            "This parameter specifies E1 port type 4."
        ::= { optixE1EventMember 19 }

    -- 1.3.6.1.4.1.2011.2.25.4.50.52.1.9.20
    optixE1TestResult4TrapInfo OBJECT-TYPE
        SYNTAX Unsigned32
        MAX-ACCESS accessible-for-notify
        STATUS current
        DESCRIPTION
            "This parameter specifies E1 port test result 4."
        ::= { optixE1EventMember 20 }

    -- 1.3.6.1.4.1.2011.2.25.4.50.52.1.9.21
    optixE1Type5TrapInfo OBJECT-TYPE
        SYNTAX Unsigned32
        MAX-ACCESS accessible-for-notify
        STATUS current
        DESCRIPTION
            "This parameter specifies E1 port type 5."
        ::= { optixE1EventMember 21 }

    -- 1.3.6.1.4.1.2011.2.25.4.50.52.1.9.22
    optixE1TestResult5TrapInfo OBJECT-TYPE
        SYNTAX Unsigned32
        MAX-ACCESS accessible-for-notify
        STATUS current
        DESCRIPTION
            "This parameter specifies E1 port test result 5."
        ::= { optixE1EventMember 22 }

    -- 1.3.6.1.4.1.2011.2.25.4.50.52.1.9.23
    optixE1Type6TrapInfo OBJECT-TYPE
        SYNTAX Unsigned32
        MAX-ACCESS accessible-for-notify
        STATUS current
        DESCRIPTION
            "This parameter specifies E1 port type 6."
        ::= { optixE1EventMember 23 }

    -- 1.3.6.1.4.1.2011.2.25.4.50.52.1.9.24
    optixE1TestResult6TrapInfo OBJECT-TYPE
        SYNTAX Unsigned32
        MAX-ACCESS accessible-for-notify
        STATUS current
        DESCRIPTION
            "This parameter specifies E1 port test result 6."
        ::= { optixE1EventMember 24 }

    -- 1.3.6.1.4.1.2011.2.25.4.50.52.1.10
    optixE1Event OBJECT IDENTIFIER ::= { optixPktPortGroup 10 }

    -- 1.3.6.1.4.1.2011.2.25.4.50.52.1.10.1
    optixE1Trap NOTIFICATION-TYPE
        OBJECTS{ optixE1TestResult2TrapInfo,optixE1Type2TrapInfo,optixE1TestResult1TrapInfo,optixE1Type1TrapInfo,optixE1DatatypeNumTrapInfo,optixE1RealTestPeriodTrapInfo,optixE1ProressTrapInfo,optixE1EndDataTimeTrapInfo,optixE1StartDataTimeTrapInfo,optixE1TestTypeTrapInfo,optixE1PRBSFRMTrapInfo,optixE1PRBSDIRTrapInfo,optixE1TimeStampTrapInfo,optixE1PIdTrapInfo,optixE1SubIdTrapInfo,optixE1BIDTrapInfo,optixE1Type3TrapInfo,optixE1TestResult3TrapInfo,optixE1Type4TrapInfo,optixE1TestResult4TrapInfo,optixE1Type5TrapInfo,optixE1TestResult5TrapInfo,optixE1Type6TrapInfo,optixE1TestResult6TrapInfo }
        STATUS current
        DESCRIPTION
            "This trap contains the bit error test event reported by E1 port."
        ::= { optixE1Event 1 }

    -- 1.3.6.1.4.1.2011.2.25.4.50.52.1.11
    optixAddMLPPPMemberTable OBJECT-TYPE
        SYNTAX SEQUENCE OF OptixAddMLPPPMemberEntry
        MAX-ACCESS not-accessible
        STATUS current
        DESCRIPTION
            "This table contains basic configuration information of ML-PPP"
        ::= { optixPktPortGroup 11 }

    -- 1.3.6.1.4.1.2011.2.25.4.50.52.1.11.1
    optixAddMLPPPMemberEntry OBJECT-TYPE
        SYNTAX OptixAddMLPPPMemberEntry
        MAX-ACCESS not-accessible
        STATUS current
        DESCRIPTION
            "Entry containins basic configuration information of ML-PPP"
        INDEX{ optixAddMLPPPMemberMLPPPId,optixAddMLPPPMemberBoardId,optixAddMLPPPMemberSubId,optixAddMLPPPMemberPortId }
        ::= { optixAddMLPPPMemberTable 1 }

    OptixAddMLPPPMemberEntry ::=
        SEQUENCE {
            optixAddMLPPPMemberMLPPPId
                Unsigned32,
            optixAddMLPPPMemberBoardId
                Unsigned32,
            optixAddMLPPPMemberPortId
                Unsigned32,
            optixAddMLPPPMemberSubId
                Unsigned32,
            optixAddMLPPPMemberRowStatus
                RowStatus
        }

    -- 1.3.6.1.4.1.2011.2.25.4.50.52.1.11.1.1
    optixAddMLPPPMemberMLPPPId OBJECT-TYPE
        SYNTAX Unsigned32
        MAX-ACCESS not-accessible
        STATUS current
        DESCRIPTION
            "This parameter specifies ML-PPP id"
        ::= { optixAddMLPPPMemberEntry 1 }

    -- 1.3.6.1.4.1.2011.2.25.4.50.52.1.11.1.2
    optixAddMLPPPMemberBoardId OBJECT-TYPE
        SYNTAX Unsigned32
        MAX-ACCESS not-accessible
        STATUS current
        DESCRIPTION
            "This parameter specifies ML-PPP board id"
        ::= { optixAddMLPPPMemberEntry 2 }

    -- 1.3.6.1.4.1.2011.2.25.4.50.52.1.11.1.3
    optixAddMLPPPMemberPortId OBJECT-TYPE
        SYNTAX Unsigned32
        MAX-ACCESS not-accessible
        STATUS current
        DESCRIPTION
            "This parameter specifies ML-PPP port id"
        ::= { optixAddMLPPPMemberEntry 3 }

    -- 1.3.6.1.4.1.2011.2.25.4.50.52.1.11.1.5
    optixAddMLPPPMemberSubId OBJECT-TYPE
        SYNTAX Unsigned32
        MAX-ACCESS not-accessible
        STATUS current
        DESCRIPTION
            "This parameter specifies ML-PPP subcard id"
        ::= { optixAddMLPPPMemberEntry 5 }

    -- 1.3.6.1.4.1.2011.2.25.4.50.52.1.11.1.255
    optixAddMLPPPMemberRowStatus OBJECT-TYPE
        SYNTAX RowStatus
        MAX-ACCESS read-create
        STATUS current
        DESCRIPTION
            "This parameter specifies ML-PPP row status"
        ::= { optixAddMLPPPMemberEntry 255 }

    -- 1.3.6.1.4.1.2011.2.25.4.50.52.1.12
    optixVC12Table OBJECT-TYPE
        SYNTAX SEQUENCE OF OptixVC12Entry
        MAX-ACCESS not-accessible
        STATUS current
        DESCRIPTION
            "This table contains configuration information of VC12 bit test"
        ::= { optixPktPortGroup 12 }

    -- 1.3.6.1.4.1.2011.2.25.4.50.52.1.12.1
    optixVC12Entry OBJECT-TYPE
        SYNTAX OptixVC12Entry
        MAX-ACCESS not-accessible
        STATUS current
        DESCRIPTION
            "Entry containing configuration information of VC12 bit test"
        INDEX{ optixLogBoardId,optixLogSubCardId,optixVC12pid,optixVC12HpId,optixVC12LpId }
        ::= { optixVC12Table 1 }

    OptixVC12Entry ::=
        SEQUENCE {
            optixVC12pid
                Unsigned32,
            optixVC12HpId
                Unsigned32,
            optixVC12LpId
                Unsigned32,
            optixVC12PrbsDir
                INTEGER,
            optixVC12PrbsFrm
                INTEGER,
            optixVC12Action
                INTEGER,
            optixVC12Type
                INTEGER,
            optixVC12Time
                INTEGER,
            optixVC12StartDateTime
                DateAndTime,
            optixVC12RealTestPri
                Unsigned32,
            optixVC12StartPeriod
                Unsigned32,
            optixVC12Result1
                OCTET STRING,
            optixVC12Result2
                OCTET STRING,
            optixVC12Result3
                OCTET STRING
        }

    -- 1.3.6.1.4.1.2011.2.25.4.50.52.1.12.1.1
    optixVC12pid OBJECT-TYPE
        SYNTAX Unsigned32
        MAX-ACCESS not-accessible
        STATUS current
        DESCRIPTION
            "Entry containing port id of VC12 bit test"
        ::= { optixVC12Entry 1 }

    -- 1.3.6.1.4.1.2011.2.25.4.50.52.1.12.1.2
    optixVC12HpId OBJECT-TYPE
        SYNTAX Unsigned32
        MAX-ACCESS not-accessible
        STATUS current
        DESCRIPTION
            "This parameter specifies the VC4 id"
        ::= { optixVC12Entry 2 }

    -- 1.3.6.1.4.1.2011.2.25.4.50.52.1.12.1.3
    optixVC12LpId OBJECT-TYPE
        SYNTAX Unsigned32
        MAX-ACCESS not-accessible
        STATUS current
        DESCRIPTION
            "This parameter specifies the VC12 id"
        ::= { optixVC12Entry 3 }

    -- 1.3.6.1.4.1.2011.2.25.4.50.52.1.12.1.4
    optixVC12PrbsDir OBJECT-TYPE
        SYNTAX INTEGER
        {
            uni(0),
            nni(1)
        }
        MAX-ACCESS read-write
        STATUS current
        DESCRIPTION
            "This parameter specifies bit test prbs dir. 0: UNI, 1: NNI"
        ::= { optixVC12Entry 4 }

    -- 1.3.6.1.4.1.2011.2.25.4.50.52.1.12.1.5
    optixVC12PrbsFrm OBJECT-TYPE
        SYNTAX INTEGER
        {
            unFrame(0),
            frame(1)
        }
        MAX-ACCESS read-write
        STATUS current
        DESCRIPTION
            "This parameter specifies bit test prbs frm. 0: unFrame, 1: frame"
        ::= { optixVC12Entry 5 }

    -- 1.3.6.1.4.1.2011.2.25.4.50.52.1.12.1.6
    optixVC12Action OBJECT-TYPE
        SYNTAX INTEGER
        {
            stop(0),
            start(1),
            invalid(255)
        }
        MAX-ACCESS read-write
        STATUS current
        DESCRIPTION
            "This parameter specifies the bit test start control. 0: stop, 1: start, 255: invalid"
        ::= { optixVC12Entry 6 }

    -- 1.3.6.1.4.1.2011.2.25.4.50.52.1.12.1.7
    optixVC12Type OBJECT-TYPE
        SYNTAX INTEGER
        {
            shortTerm(1),
            longTerm(2),
            longlongTerm(3)
        }
        MAX-ACCESS read-write
        STATUS current
        DESCRIPTION
            "This parameter specifies the bit test type. 1: shortTerm, 2: longTerm, 3: longTerm"
        ::= { optixVC12Entry 7 }

    -- 1.3.6.1.4.1.2011.2.25.4.50.52.1.12.1.8
    optixVC12Time OBJECT-TYPE
        SYNTAX INTEGER
        {
            invalid(0)
        }
        MAX-ACCESS read-write
        STATUS current
        DESCRIPTION
            "This parameter specifies the bit test time. 0: invalid"
        ::= { optixVC12Entry 8 }

    -- 1.3.6.1.4.1.2011.2.25.4.50.52.1.12.1.9
    optixVC12StartDateTime OBJECT-TYPE
        SYNTAX DateAndTime
        MAX-ACCESS read-only
        STATUS current
        DESCRIPTION
            "This parameter specifies the bit test start date time"
        ::= { optixVC12Entry 9 }

    -- 1.3.6.1.4.1.2011.2.25.4.50.52.1.12.1.10
    optixVC12RealTestPri OBJECT-TYPE
        SYNTAX Unsigned32
        MAX-ACCESS read-only
        STATUS current
        DESCRIPTION
            "This parameter specifies the bit test real test period"
        ::= { optixVC12Entry 10 }

    -- 1.3.6.1.4.1.2011.2.25.4.50.52.1.12.1.11
    optixVC12StartPeriod OBJECT-TYPE
        SYNTAX Unsigned32
        MAX-ACCESS read-only
        STATUS current
        DESCRIPTION
            "This parameter specifies the bit test start test period"
        ::= { optixVC12Entry 11 }

    -- 1.3.6.1.4.1.2011.2.25.4.50.52.1.12.1.12
    optixVC12Result1 OBJECT-TYPE
        SYNTAX OCTET STRING
        MAX-ACCESS read-only
        STATUS current
        DESCRIPTION
            "This parameter specifies the first part of bit test result"
        ::= { optixVC12Entry 12 }

    -- 1.3.6.1.4.1.2011.2.25.4.50.52.1.12.1.13
    optixVC12Result2 OBJECT-TYPE
        SYNTAX OCTET STRING
        MAX-ACCESS read-only
        STATUS current
        DESCRIPTION
            "This parameter specifies the second part of bit test result"
        ::= { optixVC12Entry 13 }

    -- 1.3.6.1.4.1.2011.2.25.4.50.52.1.12.1.14
    optixVC12Result3 OBJECT-TYPE
        SYNTAX OCTET STRING
        MAX-ACCESS read-only
        STATUS current
        DESCRIPTION
            "This parameter specifies the third part of bit test result"
        ::= { optixVC12Entry 14 }

    -- 1.3.6.1.4.1.2011.2.25.4.50.52.1.13
    optixCL2HTable OBJECT-TYPE
        SYNTAX SEQUENCE OF OptixCL2HEntry
        MAX-ACCESS not-accessible
        STATUS current
        DESCRIPTION
            "This table describes basic information about starting to capture headers of L2 packets."
        ::= { optixPktPortGroup 13 }

    -- 1.3.6.1.4.1.2011.2.25.4.50.52.1.13.1
    optixCL2HEntry OBJECT-TYPE
        SYNTAX OptixCL2HEntry
        MAX-ACCESS not-accessible
        STATUS current
        DESCRIPTION
            "This entry contains basic configuration information of Start Capture Header of L2 Layer"
        INDEX{ optixLogBoardId,optixLogSubCardId,optixEthPortId,optixCL2HMode,optixCL2HNum,optixCL2HLength,optixCL2HDirection,optixCL2HAgeTime,optixCL2HConditionMask,optixCL2HSourceMAC,optixCL2HSourceMACWC,optixCL2HDestinationMAC,optixCL2HDestinationMACWC,optixCL2HOutVlan,optixCL2HOutVlanWC,optixCL2HInnerVlan,optixCL2HInnerVlanWC,optixCL2HEthernetType,optixCL2HEthernetTypeWC }
        ::= { optixCL2HTable 1 }

    OptixCL2HEntry ::=
        SEQUENCE {
            optixCL2HStart
                INTEGER,
            optixCL2HMode
                INTEGER,
            optixCL2HNum
                Unsigned32,
            optixCL2HLength
                Unsigned32,
            optixCL2HDirection
                INTEGER,
            optixCL2HConditionMask
                Unsigned32,
            optixCL2HSourceMAC
                MacAddress,
            optixCL2HSourceMACWC
                MacAddress,
            optixCL2HDestinationMAC
                MacAddress,
            optixCL2HDestinationMACWC
                MacAddress,
            optixCL2HOutVlan
                Unsigned32,
            optixCL2HOutVlanWC
                Unsigned32,
            optixCL2HInnerVlan
                Unsigned32,
            optixCL2HInnerVlanWC
                Unsigned32,
            optixCL2HEthernetType
                Unsigned32,
            optixCL2HEthernetTypeWC
                Unsigned32,
            optixCL2HAgeTime
                Unsigned32,
            optixCL2ProhdrStart
                INTEGER,
            optixCL2HOffSetIndex
                Unsigned32,
            optixCL2HMatchLength
                Unsigned32,
            optixCL2HMatchRule
                OCTET STRING
        }

    -- 1.3.6.1.4.1.2011.2.25.4.50.52.1.13.1.1
    optixCL2HStart OBJECT-TYPE
        SYNTAX INTEGER
        {
            start(1)
        }
        MAX-ACCESS read-write
        STATUS current
        DESCRIPTION
            "This parameter indicates that capturing headers of L2 packets starts."
        ::= { optixCL2HEntry 1 }

    -- 1.3.6.1.4.1.2011.2.25.4.50.52.1.13.1.2
    optixCL2HMode OBJECT-TYPE
        SYNTAX INTEGER
        {
            once(0),
            continuance(1)
        }
        MAX-ACCESS not-accessible
        STATUS current
        DESCRIPTION
            "This parameter specifies a capture mode."
        DEFVAL{ 0 }
        ::= { optixCL2HEntry 2 }

    -- 1.3.6.1.4.1.2011.2.25.4.50.52.1.13.1.3
    optixCL2HNum OBJECT-TYPE
        SYNTAX Unsigned32 (1..1000)
        MAX-ACCESS not-accessible
        STATUS current
        DESCRIPTION
            "This parameter indicates the number of captured packets."
        DEFVAL{ 100 }
        ::= { optixCL2HEntry 3 }

    -- 1.3.6.1.4.1.2011.2.25.4.50.52.1.13.1.4
    optixCL2HLength OBJECT-TYPE
        SYNTAX Unsigned32 (16..74)
        MAX-ACCESS not-accessible
        STATUS current
        DESCRIPTION
            "This parameter indicates the length of the packet header."
        DEFVAL{ 16 }
        ::= { optixCL2HEntry 4 }

    -- 1.3.6.1.4.1.2011.2.25.4.50.52.1.13.1.5
    optixCL2HDirection OBJECT-TYPE
        SYNTAX INTEGER
        {
            ingress(0),
            egress(1)
        }
        MAX-ACCESS not-accessible
        STATUS current
        DESCRIPTION
            "This parameter specifies the direction in which packets' headers are captured."
        DEFVAL{ 0 }
        ::= { optixCL2HEntry 5 }

    -- 1.3.6.1.4.1.2011.2.25.4.50.52.1.13.1.6
    optixCL2HConditionMask OBJECT-TYPE
        SYNTAX Unsigned32
        MAX-ACCESS not-accessible
        STATUS current
        DESCRIPTION
            "This parameter specifies a mask for header capturing conditions."
        ::= { optixCL2HEntry 6 }

    -- 1.3.6.1.4.1.2011.2.25.4.50.52.1.13.1.7
    optixCL2HSourceMAC OBJECT-TYPE
        SYNTAX MacAddress
        MAX-ACCESS not-accessible
        STATUS current
        DESCRIPTION
            "This parameter specifies a source MAC address."
        ::= { optixCL2HEntry 7 }

    -- 1.3.6.1.4.1.2011.2.25.4.50.52.1.13.1.8
    optixCL2HSourceMACWC OBJECT-TYPE
        SYNTAX MacAddress
        MAX-ACCESS not-accessible
        STATUS current
        DESCRIPTION
            "This parameter specifies a wildcard character for source MAC addresses."
        ::= { optixCL2HEntry 8 }

    -- 1.3.6.1.4.1.2011.2.25.4.50.52.1.13.1.9
    optixCL2HDestinationMAC OBJECT-TYPE
        SYNTAX MacAddress
        MAX-ACCESS not-accessible
        STATUS current
        DESCRIPTION
            "This parameter specifies a destination MAC address."
        ::= { optixCL2HEntry 9 }

    -- 1.3.6.1.4.1.2011.2.25.4.50.52.1.13.1.10
    optixCL2HDestinationMACWC OBJECT-TYPE
        SYNTAX MacAddress
        MAX-ACCESS not-accessible
        STATUS current
        DESCRIPTION
            "This parameter specifies a wildcard character for destination MAC addresses."
        ::= { optixCL2HEntry 10 }

    -- 1.3.6.1.4.1.2011.2.25.4.50.52.1.13.1.11
    optixCL2HOutVlan OBJECT-TYPE
        SYNTAX Unsigned32 (0..4095)
        MAX-ACCESS not-accessible
        STATUS current
        DESCRIPTION
            "This parameter specifies an outer VLAN ID."
        ::= { optixCL2HEntry 11 }

    -- 1.3.6.1.4.1.2011.2.25.4.50.52.1.13.1.12
    optixCL2HOutVlanWC OBJECT-TYPE
        SYNTAX Unsigned32
        MAX-ACCESS not-accessible
        STATUS current
        DESCRIPTION
            "This parameter specifies a wildcard character for outer VLAN IDs."
        DEFVAL{ 0 }
        ::= { optixCL2HEntry 12 }

    -- 1.3.6.1.4.1.2011.2.25.4.50.52.1.13.1.13
    optixCL2HInnerVlan OBJECT-TYPE
        SYNTAX Unsigned32 (0..4095)
        MAX-ACCESS not-accessible
        STATUS current
        DESCRIPTION
            "This parameter specifies an inner VLAN ID."
        ::= { optixCL2HEntry 13 }

    -- 1.3.6.1.4.1.2011.2.25.4.50.52.1.13.1.14
    optixCL2HInnerVlanWC OBJECT-TYPE
        SYNTAX Unsigned32
        MAX-ACCESS not-accessible
        STATUS current
        DESCRIPTION
            "This parameter specifies a wildcard character for inner VLAN IDs."
        DEFVAL{ 0 }
        ::= { optixCL2HEntry 14 }

    -- 1.3.6.1.4.1.2011.2.25.4.50.52.1.13.1.15
    optixCL2HEthernetType OBJECT-TYPE
        SYNTAX Unsigned32
        MAX-ACCESS not-accessible
        STATUS current
        DESCRIPTION
            "This parameter specifies an Ethernet type."
        DEFVAL{ 0 }
        ::= { optixCL2HEntry 15 }

    -- 1.3.6.1.4.1.2011.2.25.4.50.52.1.13.1.16
    optixCL2HEthernetTypeWC OBJECT-TYPE
        SYNTAX Unsigned32
        MAX-ACCESS not-accessible
        STATUS current
        DESCRIPTION
            "This parameter specifies a wildcard character for Ethernet types."
        DEFVAL{ 0 }
        ::= { optixCL2HEntry 16 }

    -- 1.3.6.1.4.1.2011.2.25.4.50.52.1.13.1.17
    optixCL2HAgeTime OBJECT-TYPE
        SYNTAX Unsigned32
        MAX-ACCESS not-accessible
        STATUS current
        DESCRIPTION
            "This parameter specifies the aging time of capturing packet headers."
        DEFVAL{ 600 }
        ::= { optixCL2HEntry 17 }

    -- 1.3.6.1.4.1.2011.2.25.4.50.52.1.13.1.18
    optixCL2ProhdrStart OBJECT-TYPE
        SYNTAX INTEGER
        {
            start(1)
        }
        MAX-ACCESS read-write
        STATUS current
        DESCRIPTION
            "This parameter indicates that capturing headers of L2 protocol packets starts."
        ::= { optixCL2HEntry 18 }

    -- 1.3.6.1.4.1.2011.2.25.4.50.52.1.13.1.19
    optixCL2HOffSetIndex OBJECT-TYPE
        SYNTAX Unsigned32
        MAX-ACCESS read-write
        STATUS current
        DESCRIPTION
            "This parameter indicates the offset index of capturing packet headers."
        ::= { optixCL2HEntry 19 }

    -- 1.3.6.1.4.1.2011.2.25.4.50.52.1.13.1.20
    optixCL2HMatchLength OBJECT-TYPE
        SYNTAX Unsigned32
        MAX-ACCESS read-write
        STATUS current
        DESCRIPTION
            "This parameter specifies the match length of capturing packet headers."
        ::= { optixCL2HEntry 20 }

    -- 1.3.6.1.4.1.2011.2.25.4.50.52.1.13.1.21
    optixCL2HMatchRule OBJECT-TYPE
        SYNTAX OCTET STRING
        MAX-ACCESS read-write
        STATUS current
        DESCRIPTION
            "This parameter specifies the match rule of capturing packet headers."
        ::= { optixCL2HEntry 21 }

    -- 1.3.6.1.4.1.2011.2.25.4.50.52.1.14
    optixCL3HTable OBJECT-TYPE
        SYNTAX SEQUENCE OF OptixCL3HEntry
        MAX-ACCESS not-accessible
        STATUS current
        DESCRIPTION
            "This table describes basic information about starting to capture headers of L3 packets."
        ::= { optixPktPortGroup 14 }

    -- 1.3.6.1.4.1.2011.2.25.4.50.52.1.14.1
    optixCL3HEntry OBJECT-TYPE
        SYNTAX OptixCL3HEntry
        MAX-ACCESS not-accessible
        STATUS current
        DESCRIPTION
            "This entry contains basic configuration information of Start Capture Header of L3 Layer"
        INDEX{ optixLogBoardId,optixLogSubCardId,optixEthPortId,optixCL2HMode,optixCL2HNum,optixCL2HLength,optixCL2HDirection,optixCL2HAgeTime,optixCL2HConditionMask,optixCL3HSrcIP,optixCL3HSrcIPWC,optixCL3HDestinationIP,optixCL3HDestinationIPWC,optixCL3HTOS,optixCL3HTOSWC,optixCL3HProtocolType,optixCL3HProtocolTypeWC,optixCL3HICMPType,optixCL3HICMPTypeWC,optixCL3HTCPSrcPortID,optixCL3HTCPSrcPortIDWC,optixCL3HTCPDstPortID,optixCL3HTCPDstPortIDWC,optixCL2HDestinationMAC,optixCL2HDestinationMACWC,optixCL2HSourceMAC,optixCL2HSourceMACWC }
        ::= { optixCL3HTable 1 }

    OptixCL3HEntry ::=
        SEQUENCE {
            optixCL3HStart
                INTEGER,
            optixCL3HSrcIP
                IpAddress,
            optixCL3HSrcIPWC
                IpAddress,
            optixCL3HDestinationIP
                IpAddress,
            optixCL3HDestinationIPWC
                IpAddress,
            optixCL3HTOS
                Unsigned32,
            optixCL3HTOSWC
                Unsigned32,
            optixCL3HProtocolType
                Unsigned32,
            optixCL3HProtocolTypeWC
                Unsigned32,
            optixCL3HICMPType
                Unsigned32,
            optixCL3HICMPTypeWC
                Unsigned32,
            optixCL3HTCPSrcPortID
                Unsigned32,
            optixCL3HTCPSrcPortIDWC
                Unsigned32,
            optixCL3HTCPDstPortID
                Unsigned32,
            optixCL3HTCPDstPortIDWC
                Unsigned32,
            optixCL3HOffSetIndex
                Unsigned32,
            optixCL3HMatchLength
                Unsigned32,
            optixCL3HMatchRule
                OCTET STRING
        }

    -- 1.3.6.1.4.1.2011.2.25.4.50.52.1.14.1.1
    optixCL3HStart OBJECT-TYPE
        SYNTAX INTEGER
        {
            start(1)
        }
        MAX-ACCESS read-write
        STATUS current
        DESCRIPTION
            "This parameter indicates that capturing headers of L3 packets starts."
        ::= { optixCL3HEntry 1 }

    -- 1.3.6.1.4.1.2011.2.25.4.50.52.1.14.1.2
    optixCL3HSrcIP OBJECT-TYPE
        SYNTAX IpAddress
        MAX-ACCESS not-accessible
        STATUS current
        DESCRIPTION
            "This parameter specifies a source IP address."
        ::= { optixCL3HEntry 2 }

    -- 1.3.6.1.4.1.2011.2.25.4.50.52.1.14.1.3
    optixCL3HSrcIPWC OBJECT-TYPE
        SYNTAX IpAddress
        MAX-ACCESS not-accessible
        STATUS current
        DESCRIPTION
            "This parameter specifies a wildcard character for source IP addresses."
        ::= { optixCL3HEntry 3 }

    -- 1.3.6.1.4.1.2011.2.25.4.50.52.1.14.1.4
    optixCL3HDestinationIP OBJECT-TYPE
        SYNTAX IpAddress
        MAX-ACCESS not-accessible
        STATUS current
        DESCRIPTION
            "This parameter specifies a destination IP address."
        ::= { optixCL3HEntry 4 }

    -- 1.3.6.1.4.1.2011.2.25.4.50.52.1.14.1.5
    optixCL3HDestinationIPWC OBJECT-TYPE
        SYNTAX IpAddress
        MAX-ACCESS not-accessible
        STATUS current
        DESCRIPTION
            "This parameter specifies a wildcard character for destination IP addresses."
        ::= { optixCL3HEntry 5 }

    -- 1.3.6.1.4.1.2011.2.25.4.50.52.1.14.1.6
    optixCL3HTOS OBJECT-TYPE
        SYNTAX Unsigned32
        MAX-ACCESS not-accessible
        STATUS current
        DESCRIPTION
            "This parameter specifies a TOS."
        ::= { optixCL3HEntry 6 }

    -- 1.3.6.1.4.1.2011.2.25.4.50.52.1.14.1.7
    optixCL3HTOSWC OBJECT-TYPE
        SYNTAX Unsigned32
        MAX-ACCESS not-accessible
        STATUS current
        DESCRIPTION
            "This parameter specifies a wildcard character for TOSs."
        ::= { optixCL3HEntry 7 }

    -- 1.3.6.1.4.1.2011.2.25.4.50.52.1.14.1.8
    optixCL3HProtocolType OBJECT-TYPE
        SYNTAX Unsigned32
        MAX-ACCESS not-accessible
        STATUS current
        DESCRIPTION
            "This parameter specifies a protocol type."
        ::= { optixCL3HEntry 8 }

    -- 1.3.6.1.4.1.2011.2.25.4.50.52.1.14.1.9
    optixCL3HProtocolTypeWC OBJECT-TYPE
        SYNTAX Unsigned32
        MAX-ACCESS not-accessible
        STATUS current
        DESCRIPTION
            "This parameter specifies a wildcard character for protocol types."
        ::= { optixCL3HEntry 9 }

    -- 1.3.6.1.4.1.2011.2.25.4.50.52.1.14.1.10
    optixCL3HICMPType OBJECT-TYPE
        SYNTAX Unsigned32
        MAX-ACCESS not-accessible
        STATUS current
        DESCRIPTION
            "This parameter specifies an ICMP type."
        ::= { optixCL3HEntry 10 }

    -- 1.3.6.1.4.1.2011.2.25.4.50.52.1.14.1.11
    optixCL3HICMPTypeWC OBJECT-TYPE
        SYNTAX Unsigned32
        MAX-ACCESS not-accessible
        STATUS current
        DESCRIPTION
            "This parameter specifies a wildcard character for ICMP types."
        ::= { optixCL3HEntry 11 }

    -- 1.3.6.1.4.1.2011.2.25.4.50.52.1.14.1.12
    optixCL3HTCPSrcPortID OBJECT-TYPE
        SYNTAX Unsigned32
        MAX-ACCESS not-accessible
        STATUS current
        DESCRIPTION
            "This parameter specifies the ID of a TCP source port."
        ::= { optixCL3HEntry 12 }

    -- 1.3.6.1.4.1.2011.2.25.4.50.52.1.14.1.13
    optixCL3HTCPSrcPortIDWC OBJECT-TYPE
        SYNTAX Unsigned32
        MAX-ACCESS not-accessible
        STATUS current
        DESCRIPTION
            "This parameter specifies a wildcard character for IDs of TCP source ports."
        ::= { optixCL3HEntry 13 }

    -- 1.3.6.1.4.1.2011.2.25.4.50.52.1.14.1.14
    optixCL3HTCPDstPortID OBJECT-TYPE
        SYNTAX Unsigned32
        MAX-ACCESS not-accessible
        STATUS current
        DESCRIPTION
            "This parameter specifies the ID of a TCP destination port."
        ::= { optixCL3HEntry 14 }

    -- 1.3.6.1.4.1.2011.2.25.4.50.52.1.14.1.15
    optixCL3HTCPDstPortIDWC OBJECT-TYPE
        SYNTAX Unsigned32
        MAX-ACCESS not-accessible
        STATUS current
        DESCRIPTION
            "This parameter specifies a wildcard character for IDs of TCP destination ports."
        ::= { optixCL3HEntry 15 }

    -- 1.3.6.1.4.1.2011.2.25.4.50.52.1.14.1.16
    optixCL3HOffSetIndex OBJECT-TYPE
        SYNTAX Unsigned32
        MAX-ACCESS read-write
        STATUS current
        DESCRIPTION
            "This parameter indicates the offset index of capturing packet headers."
        ::= { optixCL3HEntry 16 }

    -- 1.3.6.1.4.1.2011.2.25.4.50.52.1.14.1.17
    optixCL3HMatchLength OBJECT-TYPE
        SYNTAX Unsigned32
        MAX-ACCESS read-write
        STATUS current
        DESCRIPTION
            "This parameter specifies the match length of capturing packet headers."
        ::= { optixCL3HEntry 17 }

    -- 1.3.6.1.4.1.2011.2.25.4.50.52.1.14.1.18
    optixCL3HMatchRule OBJECT-TYPE
        SYNTAX OCTET STRING
        MAX-ACCESS read-write
        STATUS current
        DESCRIPTION
            "This parameter specifies the match rule of capturing packet headers."
        ::= { optixCL3HEntry 18 }

    -- 1.3.6.1.4.1.2011.2.25.4.50.52.1.15
    optixPortCaptureHeaderTable OBJECT-TYPE
        SYNTAX SEQUENCE OF OptixPortCaptureHeaderEntry
        MAX-ACCESS not-accessible
        STATUS current
        DESCRIPTION
            "This table describes basic information about stopping packet header capturing on a port."
        ::= { optixPktPortGroup 15 }

    -- 1.3.6.1.4.1.2011.2.25.4.50.52.1.15.1
    optixPortCaptureHeaderEntry OBJECT-TYPE
        SYNTAX OptixPortCaptureHeaderEntry
        MAX-ACCESS not-accessible
        STATUS current
        DESCRIPTION
            "This entry describes basic information about stopping packet header capturing on a port."
        INDEX{ optixLogBoardId,optixLogSubCardId,optixEthPortId }
        ::= { optixPortCaptureHeaderTable 1 }

    OptixPortCaptureHeaderEntry ::=
        SEQUENCE {
            optixPortCaptureHeaderStop
                INTEGER,
            optixPortCapHeaderStopType
                INTEGER,
            optixPortCapHeaderStopDirect
                INTEGER
        }

    -- 1.3.6.1.4.1.2011.2.25.4.50.52.1.15.1.1
    optixPortCaptureHeaderStop OBJECT-TYPE
        SYNTAX INTEGER
        {
            stop(0)
        }
        MAX-ACCESS read-write
        STATUS current
        DESCRIPTION
            "This parameter indicates that packet header capturing stops on a port."
        ::= { optixPortCaptureHeaderEntry 1 }

    -- 1.3.6.1.4.1.2011.2.25.4.50.52.1.15.1.2
    optixPortCapHeaderStopType OBJECT-TYPE
        SYNTAX INTEGER
        {
            service(0),
            protocol(1)
        }
        MAX-ACCESS read-write
        STATUS current
        DESCRIPTION
            "This parameter indicates the type of captured packets."
        ::= { optixPortCaptureHeaderEntry 2 }

    -- 1.3.6.1.4.1.2011.2.25.4.50.52.1.15.1.3
    optixPortCapHeaderStopDirect OBJECT-TYPE
        SYNTAX INTEGER
        {
            ingress(0),
            egress(1)
        }
        MAX-ACCESS read-write
        STATUS current
        DESCRIPTION
            "This parameter indicates the direction of captured packets on a port."
        DEFVAL{ 0 }
        ::= { optixPortCaptureHeaderEntry 3 }

    -- 1.3.6.1.4.1.2011.2.25.4.50.52.1.16
    optixETHMgrPacketEventMember OBJECT IDENTIFIER ::= { optixPktPortGroup 16 }

    -- 1.3.6.1.4.1.2011.2.25.4.50.52.1.16.1
    optixETHMgrPacketBIDTrapInfo OBJECT-TYPE
        SYNTAX Unsigned32
        MAX-ACCESS accessible-for-notify
        STATUS current
        DESCRIPTION
            "This parameter specifies the board ID of an Ethernet port."
        ::= { optixETHMgrPacketEventMember 1 }

    -- 1.3.6.1.4.1.2011.2.25.4.50.52.1.16.2
    optixETHMgrPacketSubIDTrapInfo OBJECT-TYPE
        SYNTAX Unsigned32
        MAX-ACCESS accessible-for-notify
        STATUS current
        DESCRIPTION
            "This parameter specifies the subboard ID of an Ethernet port."
        ::= { optixETHMgrPacketEventMember 2 }

    -- 1.3.6.1.4.1.2011.2.25.4.50.52.1.16.3
    optixETHMgrPacketPIDTrapInfo OBJECT-TYPE
        SYNTAX Unsigned32
        MAX-ACCESS accessible-for-notify
        STATUS current
        DESCRIPTION
            "This parameter specifies the ID of an Ethernet port."
        ::= { optixETHMgrPacketEventMember 3 }

    -- 1.3.6.1.4.1.2011.2.25.4.50.52.1.16.4
    optixETHMgrPacketAllNumTrapInfo OBJECT-TYPE
        SYNTAX OCTET STRING
        MAX-ACCESS accessible-for-notify
        STATUS current
        DESCRIPTION
            "This parameter indicates the number of packets captured by the chip."
        ::= { optixETHMgrPacketEventMember 4 }

    -- 1.3.6.1.4.1.2011.2.25.4.50.52.1.16.5
    optixETHMgrPacketHeadNumTrapInfo OBJECT-TYPE
        SYNTAX Unsigned32
        MAX-ACCESS accessible-for-notify
        STATUS current
        DESCRIPTION
            "This parameter indicates the number of captured packet headers."
        ::= { optixETHMgrPacketEventMember 5 }

    -- 1.3.6.1.4.1.2011.2.25.4.50.52.1.16.6
    optixETHMgrPacketEndTagTrapInfo OBJECT-TYPE
        SYNTAX Unsigned32
        MAX-ACCESS accessible-for-notify
        STATUS current
        DESCRIPTION
            "This parameter specifies a flag for the ending of packet capturing."
        ::= { optixETHMgrPacketEventMember 6 }

    -- 1.3.6.1.4.1.2011.2.25.4.50.52.1.16.7
    optixETHMgrPacketHeadLenTrapInfo OBJECT-TYPE
        SYNTAX Unsigned32
        MAX-ACCESS accessible-for-notify
        STATUS current
        DESCRIPTION
            "This parameter indicates the length of the packet header."
        ::= { optixETHMgrPacketEventMember 7 }

    -- 1.3.6.1.4.1.2011.2.25.4.50.52.1.16.8
    optixETHMgrPacketPayload OBJECT-TYPE
        SYNTAX OCTET STRING
        MAX-ACCESS accessible-for-notify
        STATUS current
        DESCRIPTION
            "This parameter indicates the packet payload."
        ::= { optixETHMgrPacketEventMember 8 }

    -- 1.3.6.1.4.1.2011.2.25.4.50.52.1.16.9
    optixETHMgrPacketTypeTrapInfo OBJECT-TYPE
        SYNTAX INTEGER
        {
            service(0),
            protocol(1)
        }
        MAX-ACCESS accessible-for-notify
        STATUS current
        DESCRIPTION
            "This parameter specifies the packet type of captured packets."
        ::= { optixETHMgrPacketEventMember 9 }

    -- 1.3.6.1.4.1.2011.2.25.4.50.52.1.16.10
    optixETHMgrPacketDirectTrapInfo OBJECT-TYPE
        SYNTAX INTEGER
        {
            ingress(0),
            egress(1)
        }
        MAX-ACCESS accessible-for-notify
        STATUS current
        DESCRIPTION
            "This parameter specifies the direction of captured packets on a port."
        DEFVAL{ 0 }
        ::= { optixETHMgrPacketEventMember 10 }

    -- 1.3.6.1.4.1.2011.2.25.4.50.52.1.17
    optixNeCaptureHeaderStop OBJECT-TYPE
        SYNTAX INTEGER
        {
            stop(0)
        }
        MAX-ACCESS read-write
        STATUS current
        DESCRIPTION
            "This parameter specifies whether packet header capturing on an entire NE is stopped."
        ::= { optixPktPortGroup 17 }

    -- 1.3.6.1.4.1.2011.2.25.4.50.52.1.18
    optixETHMgrPacketEvent OBJECT IDENTIFIER ::= { optixPktPortGroup 18 }

    -- 1.3.6.1.4.1.2011.2.25.4.50.52.1.18.1
    optixETHMgrPacketTrap NOTIFICATION-TYPE
        OBJECTS{ optixETHMgrPacketBIDTrapInfo,optixETHMgrPacketSubIDTrapInfo,optixETHMgrPacketPIDTrapInfo,optixETHMgrPacketTypeTrapInfo,optixETHMgrPacketDirectTrapInfo,optixETHMgrPacketAllNumTrapInfo,optixETHMgrPacketHeadNumTrapInfo,optixETHMgrPacketEndTagTrapInfo,optixETHMgrPacketHeadLenTrapInfo,optixETHMgrPacketPayload }
        STATUS current
        DESCRIPTION
            "This trap describes the packet header capturing event."
        ::= { optixETHMgrPacketEvent 1 }

    -- 1.3.6.1.4.1.2011.2.25.4.50.52.1.19
    optixPktPortLogicStateChangeTrapMember OBJECT IDENTIFIER ::= { optixPktPortGroup 19 }

    -- 1.3.6.1.4.1.2011.2.25.4.50.52.1.19.1
    optixPktPortLogicStateBID OBJECT-TYPE
        SYNTAX Unsigned32
        MAX-ACCESS accessible-for-notify
        STATUS current
        DESCRIPTION
            "This object indicates the slot ID."
        ::= { optixPktPortLogicStateChangeTrapMember 1 }

    -- 1.3.6.1.4.1.2011.2.25.4.50.52.1.19.2
    optixPktPortLogicStatesubBID OBJECT-TYPE
        SYNTAX Unsigned32
        MAX-ACCESS accessible-for-notify
        STATUS current
        DESCRIPTION
            "This object indicates the subcard ID."
        ::= { optixPktPortLogicStateChangeTrapMember 2 }

    -- 1.3.6.1.4.1.2011.2.25.4.50.52.1.19.3
    optixPktPortLogicStatePID OBJECT-TYPE
        SYNTAX Unsigned32
        MAX-ACCESS accessible-for-notify
        STATUS current
        DESCRIPTION
            "This object indicates the port ID."
        ::= { optixPktPortLogicStateChangeTrapMember 3 }

    -- 1.3.6.1.4.1.2011.2.25.4.50.52.1.19.4
    optixPktPortLogicStateChange OBJECT-TYPE
        SYNTAX INTEGER
        {
            down(0),
            up(1),
            invalid(255)
        }
        MAX-ACCESS accessible-for-notify
        STATUS current
        DESCRIPTION
            "This object indicates the change state."
        ::= { optixPktPortLogicStateChangeTrapMember 4 }

    -- 1.3.6.1.4.1.2011.2.25.4.50.52.1.20
    optixPerAlmTHTable OBJECT-TYPE
        SYNTAX SEQUENCE OF OptixPerAlmTHEntry
        MAX-ACCESS not-accessible
        STATUS current
        DESCRIPTION
            "This table contains basic configuration of the optical power threshold."
        ::= { optixPktPortGroup 20 }

    -- 1.3.6.1.4.1.2011.2.25.4.50.52.1.20.1
    optixPerAlmTHEntry OBJECT-TYPE
        SYNTAX OptixPerAlmTHEntry
        MAX-ACCESS not-accessible
        STATUS current
        DESCRIPTION
            "This entry contains basic configuration of the optical power threshold."
        INDEX{ optixLogBoardId,optixLogSubCardId,optixPortId,optixPerAlmTHPathID,optixPerAlmTHtype }
        ::= { optixPerAlmTHTable 1 }

    OptixPerAlmTHEntry ::=
        SEQUENCE {
            optixPerAlmTHPathID
                Unsigned32,
            optixPerAlmTHtype
                Unsigned32,
            optixPerAlmTHhigh
                INTEGER,
            optixPerAlmTHLow
                INTEGER
        }

    -- 1.3.6.1.4.1.2011.2.25.4.50.52.1.20.1.1
    optixPerAlmTHPathID OBJECT-TYPE
        SYNTAX Unsigned32
        MAX-ACCESS not-accessible
        STATUS current
        DESCRIPTION
            "This object specifies the path ID."
        ::= { optixPerAlmTHEntry 1 }

    -- 1.3.6.1.4.1.2011.2.25.4.50.52.1.20.1.2
    optixPerAlmTHtype OBJECT-TYPE
        SYNTAX Unsigned32
        MAX-ACCESS not-accessible
        STATUS current
        DESCRIPTION
            "This object specifies the performance ID."
        ::= { optixPerAlmTHEntry 2 }

    -- 1.3.6.1.4.1.2011.2.25.4.50.52.1.20.1.3
    optixPerAlmTHhigh OBJECT-TYPE
        SYNTAX INTEGER
        MAX-ACCESS read-write
        STATUS current
        DESCRIPTION
            "This object specifies the upper threshold."
        ::= { optixPerAlmTHEntry 3 }

    -- 1.3.6.1.4.1.2011.2.25.4.50.52.1.20.1.4
    optixPerAlmTHLow OBJECT-TYPE
        SYNTAX INTEGER
        MAX-ACCESS read-write
        STATUS current
        DESCRIPTION
            "This object specifies the lower threshold."
        ::= { optixPerAlmTHEntry 4 }

    -- 1.3.6.1.4.1.2011.2.25.4.50.52.1.21
    optixPktPortLogicStateChangeEvent OBJECT IDENTIFIER ::= { optixPktPortGroup 21 }

    -- 1.3.6.1.4.1.2011.2.25.4.50.52.1.21.1
    optixPktPortLogicStateChangeTrap NOTIFICATION-TYPE
        OBJECTS{ optixPktPortLogicStateBID,optixPktPortLogicStatesubBID,optixPktPortLogicStatePID,optixPktPortLogicStateChange }
        STATUS current
        DESCRIPTION
            "This trap describes the logical status event information of a port."
        ::= { optixPktPortLogicStateChangeEvent 1 }

    -- 1.3.6.1.4.1.2011.2.25.4.50.52.1.22
    optixPktPortbwuswatchfluxTable OBJECT-TYPE
        SYNTAX SEQUENCE OF OptixPktPortbwuswatchfluxEntry
        MAX-ACCESS not-accessible
        STATUS current
        DESCRIPTION
            "This table contains the historical bandwidth usage of ports."
        ::= { optixPktPortGroup 22 }

    -- 1.3.6.1.4.1.2011.2.25.4.50.52.1.22.1
    optixPktPortbwuswatchfluxEntry OBJECT-TYPE
        SYNTAX OptixPktPortbwuswatchfluxEntry
        MAX-ACCESS not-accessible
        STATUS current
        DESCRIPTION
            "This entry contains the historical bandwidth usage of ports."
        INDEX{ optixLogBoardId,optixLogSubCardId,optixPortId,optixPktPortbwuStartTime,optixPktPortbwuEndTime,optixPktPortbwuTimelist }
        ::= { optixPktPortbwuswatchfluxTable 1 }

    OptixPktPortbwuswatchfluxEntry ::=
        SEQUENCE {
            optixPktPortbwuStartTime
                DateAndTime,
            optixPktPortbwuEndTime
                DateAndTime,
            optixPktPortbwuTimelist
                Unsigned32,
            optixPktPortbwurealStartTime
                DateAndTime,
            optixPktPortbwuDataFlag
                Unsigned32,
            optixPktPortbwuRxDataUS
                Unsigned32,
            optixPktPortbwuTxDataUS
                Unsigned32
        }

    -- 1.3.6.1.4.1.2011.2.25.4.50.52.1.22.1.1
    optixPktPortbwuStartTime OBJECT-TYPE
        SYNTAX DateAndTime
        MAX-ACCESS not-accessible
        STATUS current
        DESCRIPTION
            "This object indicates the historical bandwidth usage of a port."
        ::= { optixPktPortbwuswatchfluxEntry 1 }

    -- 1.3.6.1.4.1.2011.2.25.4.50.52.1.22.1.2
    optixPktPortbwuEndTime OBJECT-TYPE
        SYNTAX DateAndTime
        MAX-ACCESS not-accessible
        STATUS current
        DESCRIPTION
            "This object indicates the end time of port historical bandwidth use."
        ::= { optixPktPortbwuswatchfluxEntry 2 }

    -- 1.3.6.1.4.1.2011.2.25.4.50.52.1.22.1.3
    optixPktPortbwuTimelist OBJECT-TYPE
        SYNTAX Unsigned32
        MAX-ACCESS not-accessible
        STATUS current
        DESCRIPTION
            "This object indicates the list of port historical bandwidth usage."
        ::= { optixPktPortbwuswatchfluxEntry 3 }

    -- 1.3.6.1.4.1.2011.2.25.4.50.52.1.22.1.4
    optixPktPortbwurealStartTime OBJECT-TYPE
        SYNTAX DateAndTime
        MAX-ACCESS read-only
        STATUS current
        DESCRIPTION
            "This object indicates the start time of port historical bandwidth use."
        ::= { optixPktPortbwuswatchfluxEntry 4 }

    -- 1.3.6.1.4.1.2011.2.25.4.50.52.1.22.1.5
    optixPktPortbwuDataFlag OBJECT-TYPE
        SYNTAX Unsigned32
        MAX-ACCESS read-only
        STATUS current
        DESCRIPTION
            "This object indicates whether the port historical bandwidth usage data is available. 0: No usage data is available; 1: Usage data is available."
        ::= { optixPktPortbwuswatchfluxEntry 5 }

    -- 1.3.6.1.4.1.2011.2.25.4.50.52.1.22.1.6
    optixPktPortbwuRxDataUS OBJECT-TYPE
        SYNTAX Unsigned32
        MAX-ACCESS read-only
        STATUS current
        DESCRIPTION
            "This object indicates the receive-end data of port historical bandwidth usage."
        ::= { optixPktPortbwuswatchfluxEntry 6 }

    -- 1.3.6.1.4.1.2011.2.25.4.50.52.1.22.1.7
    optixPktPortbwuTxDataUS OBJECT-TYPE
        SYNTAX Unsigned32
        MAX-ACCESS read-only
        STATUS current
        DESCRIPTION
            "This object indicates the transmit-end data of port historical bandwidth usage."
        ::= { optixPktPortbwuswatchfluxEntry 7 }

    -- 1.3.6.1.4.1.2011.2.25.4.50.52.1.23
    optixPktPortBWWatchFluxTable OBJECT-TYPE
        SYNTAX SEQUENCE OF OptixPktPortBWWatchFluxEntry
        MAX-ACCESS not-accessible
        STATUS current
        DESCRIPTION
            "This table describes the historical physical traffic of ports."
        ::= { optixPktPortGroup 23 }

    -- 1.3.6.1.4.1.2011.2.25.4.50.52.1.23.1
    optixPktPortBWWatchFluxEntry OBJECT-TYPE
        SYNTAX OptixPktPortBWWatchFluxEntry
        MAX-ACCESS not-accessible
        STATUS current
        DESCRIPTION
            "This entry describes the historical physical traffic of ports."
        INDEX{ optixLogBoardId,optixLogSubCardId,optixPortId,optixPktPortbwuStartTime,optixPktPortbwuEndTime,optixPktPortbwuTimelist }
        ::= { optixPktPortBWWatchFluxTable 1 }

    OptixPktPortBWWatchFluxEntry ::=
        SEQUENCE {
            optixPktPortBWRealStartTime
                DateAndTime,
            optixPktPortBWDataFlag
                Unsigned32,
            optixPktPortBWRxDataUS
                Unsigned32,
            optixPktPortBWTxDataUS
                Unsigned32
        }

    -- 1.3.6.1.4.1.2011.2.25.4.50.52.1.23.1.1
    optixPktPortBWRealStartTime OBJECT-TYPE
        SYNTAX DateAndTime
        MAX-ACCESS read-only
        STATUS current
        DESCRIPTION
            "This object indicates the start time of port historical physical flow."
        ::= { optixPktPortBWWatchFluxEntry 1 }

    -- 1.3.6.1.4.1.2011.2.25.4.50.52.1.23.1.2
    optixPktPortBWDataFlag OBJECT-TYPE
        SYNTAX Unsigned32
        MAX-ACCESS read-only
        STATUS current
        DESCRIPTION
            "This object indicates whether the port historical physical flow is available. 0: No usage data is available; 1: Usage data is available."
        ::= { optixPktPortBWWatchFluxEntry 2 }

    -- 1.3.6.1.4.1.2011.2.25.4.50.52.1.23.1.3
    optixPktPortBWRxDataUS OBJECT-TYPE
        SYNTAX Unsigned32
        MAX-ACCESS read-only
        STATUS current
        DESCRIPTION
            "This object indicates the receive-end data of port historical physical flow ."
        ::= { optixPktPortBWWatchFluxEntry 3 }

    -- 1.3.6.1.4.1.2011.2.25.4.50.52.1.23.1.4
    optixPktPortBWTxDataUS OBJECT-TYPE
        SYNTAX Unsigned32
        MAX-ACCESS read-only
        STATUS current
        DESCRIPTION
            "This object indicates the transmit-end data of port historical physical flow."
        ::= { optixPktPortBWWatchFluxEntry 4 }

    -- 1.3.6.1.4.1.2011.2.25.4.50.52.1.24
    optixPktPortRMONWatchFluxTable OBJECT-TYPE
        SYNTAX SEQUENCE OF OptixPktPortRMONWatchFluxEntry
        MAX-ACCESS not-accessible
        STATUS current
        DESCRIPTION
            "This table describes the traffic of ports at any given time."
        ::= { optixPktPortGroup 24 }

    -- 1.3.6.1.4.1.2011.2.25.4.50.52.1.24.1
    optixPktPortRMONWatchFluxEntry OBJECT-TYPE
        SYNTAX OptixPktPortRMONWatchFluxEntry
        MAX-ACCESS not-accessible
        STATUS current
        DESCRIPTION
            "This entry describes the traffic of ports at any given time."
        INDEX{ optixLogBoardId,optixLogSubCardId,optixPortId,optixPktPortbwuStartTime,optixPktPortbwuEndTime,optixPktPortbwuTimelist }
        ::= { optixPktPortRMONWatchFluxTable 1 }

    OptixPktPortRMONWatchFluxEntry ::=
        SEQUENCE {
            optixPktPortRMONRealStartTime
                DateAndTime,
            optixPktPortRMONDataFlag
                Unsigned32,
            optixPktPortRMONRxDataUS
                Unsigned32,
            optixPktPortRMONTxDataUS
                Unsigned32
        }

    -- 1.3.6.1.4.1.2011.2.25.4.50.52.1.24.1.1
    optixPktPortRMONRealStartTime OBJECT-TYPE
        SYNTAX DateAndTime
        MAX-ACCESS read-only
        STATUS current
        DESCRIPTION
            "This object indicates the start time of port flow."
        ::= { optixPktPortRMONWatchFluxEntry 1 }

    -- 1.3.6.1.4.1.2011.2.25.4.50.52.1.24.1.2
    optixPktPortRMONDataFlag OBJECT-TYPE
        SYNTAX Unsigned32
        MAX-ACCESS read-only
        STATUS current
        DESCRIPTION
            "This object indicates whether the port flow is available. 0: No usage data is available; 1: Usage data is available."
        ::= { optixPktPortRMONWatchFluxEntry 2 }

    -- 1.3.6.1.4.1.2011.2.25.4.50.52.1.24.1.3
    optixPktPortRMONRxDataUS OBJECT-TYPE
        SYNTAX Unsigned32
        MAX-ACCESS read-only
        STATUS current
        DESCRIPTION
            "This object indicates the receive-end data of port flow ."
        ::= { optixPktPortRMONWatchFluxEntry 3 }

    -- 1.3.6.1.4.1.2011.2.25.4.50.52.1.24.1.4
    optixPktPortRMONTxDataUS OBJECT-TYPE
        SYNTAX Unsigned32
        MAX-ACCESS read-only
        STATUS current
        DESCRIPTION
            "This object indicates the transmit-end data of port flow."
        ::= { optixPktPortRMONWatchFluxEntry 4 }

    -- 1.3.6.1.4.1.2011.2.25.4.50.52.1.25
    optixEthPortExtTable OBJECT-TYPE
        SYNTAX SEQUENCE OF OptixEthPortExtEntry
        MAX-ACCESS not-accessible
        STATUS current
        DESCRIPTION
            "This table contains basic configuration information of an ETH port."
        ::= { optixPktPortGroup 25 }

    -- 1.3.6.1.4.1.2011.2.25.4.50.52.1.25.1
    optixEthPortExtEntry OBJECT-TYPE
        SYNTAX OptixEthPortExtEntry
        MAX-ACCESS not-accessible
        STATUS current
        DESCRIPTION
            "This entry contains basic configuration information of an ETH port."
        INDEX{ optixLogBoardId,optixLogSubCardId,optixPortId }
        ::= { optixEthPortExtTable 1 }

    OptixEthPortExtEntry ::=
        SEQUENCE {
            optixEthPortholdupstate
                INTEGER,
            optixEthPortRemarkstate
                INTEGER,
            optixEthPortAutoBroadBaTh
                Unsigned32,
            optixEthPortAutoBroadBaRealTh
                Unsigned32,
            optixEthPortAutoBroadBaRealEn
                INTEGER,
            optixEthPortUniDirMode
                INTEGER,
            optixEthPortDefForwardType
                INTEGER,
            optixEthPortPacketColor
                INTEGER,
            optixEthPortLagLinkAggrePortPri
                Unsigned32,
            optixEthPortBwwatchEnable
                INTEGER,
            optixEthPortDelayWatchEn
                INTEGER,
            optixEthPortWaveWorkBand
                INTEGER,
            optixEthPortGetWaveNum
                Unsigned32,
        }

    -- 1.3.6.1.4.1.2011.2.25.4.50.52.1.25.1.1
    optixEthPortholdupstate OBJECT-TYPE
        SYNTAX INTEGER
        {
            disable(0),
            enable(1)
        }
        MAX-ACCESS read-write
        STATUS current
        DESCRIPTION
            "This parameter specifies the forcible-up state of an ETH port. 0: disable, 1: enable"
        ::= { optixEthPortExtEntry 1 }

    -- 1.3.6.1.4.1.2011.2.25.4.50.52.1.25.1.2
    optixEthPortRemarkstate OBJECT-TYPE
        SYNTAX INTEGER
        {
            disable(0),
            enable(1)
        }
        MAX-ACCESS read-write
        STATUS current
        DESCRIPTION
            "This parameter specifies the demapping enable status of an ETH port.0:disable,1:enable"
        ::= { optixEthPortExtEntry 2 }

    -- 1.3.6.1.4.1.2011.2.25.4.50.52.1.25.1.3
    optixEthPortAutoBroadBaTh OBJECT-TYPE
        SYNTAX Unsigned32
        MAX-ACCESS read-write
        STATUS current
        DESCRIPTION
            "This parameter indicates the threshold (%) for automatic broadcast packet suppression of PWs."
        ::= { optixEthPortExtEntry 3 }

    -- 1.3.6.1.4.1.2011.2.25.4.50.52.1.25.1.4
    optixEthPortAutoBroadBaRealTh OBJECT-TYPE
        SYNTAX Unsigned32
        MAX-ACCESS read-only
        STATUS current
        DESCRIPTION
            "This parameter indicates the actual threshold (%) for automatic broadcast packet suppression of PWs."
        ::= { optixEthPortExtEntry 4 }

    -- 1.3.6.1.4.1.2011.2.25.4.50.52.1.25.1.5
    optixEthPortAutoBroadBaRealEn OBJECT-TYPE
        SYNTAX INTEGER
        {
            disable(0),
            enable(1)
        }
        MAX-ACCESS read-only
        STATUS current
        DESCRIPTION
            "This parameter indicates whether automatic broadcast packet suppression is enabled for PWs."
        ::= { optixEthPortExtEntry 5 }

    -- 1.3.6.1.4.1.2011.2.25.4.50.52.1.25.1.6
    optixEthPortUniDirMode OBJECT-TYPE
        SYNTAX INTEGER
        {
            disable(0),
            enable(1)
        }
        MAX-ACCESS read-write
        STATUS current
        DESCRIPTION
            "This parameter indicates whether unidirectional operation is enabled for 10G port.0:disable,1:enable."
        ::= { optixEthPortExtEntry 6 }

    -- 1.3.6.1.4.1.2011.2.25.4.50.52.1.25.1.7
    optixEthPortDefForwardType OBJECT-TYPE
        SYNTAX INTEGER
        {
            cs7(1),
            cs6(2),
            ef(3),
            af4(4),
            af3(5),
            af2(6),
            af1(7),
            be(8)
        }
        MAX-ACCESS read-write
        STATUS current
        DESCRIPTION
            "This parameter indicates the default forwarding queue priority of ETH ports. Its value is an integer: cs7 (1), cs6 (2), ef (3), af4 (4), af3 (5), af2 (6), af1 (7), or be (8)."
        ::= { optixEthPortExtEntry 7 }

    -- 1.3.6.1.4.1.2011.2.25.4.50.52.1.25.1.8
    optixEthPortPacketColor OBJECT-TYPE
        SYNTAX INTEGER
        {
            red(1),
            yellow(2),
            green(3)
        }
        MAX-ACCESS read-write
        STATUS current
        DESCRIPTION
            "This parameter indicates the default packet color of an ETH-port forwarding queue: red(1), yellow (2), or green (3)."
        ::= { optixEthPortExtEntry 8 }

    -- 1.3.6.1.4.1.2011.2.25.4.50.52.1.25.1.9
    optixEthPortLagLinkAggrePortPri OBJECT-TYPE
        SYNTAX Unsigned32
        MAX-ACCESS read-write
        STATUS current
        DESCRIPTION
            "This object indicates the priority of the L2 LAG slave port. Value range: 0 to 0xffffffff."
        ::= { optixEthPortExtEntry 9 }

    -- 1.3.6.1.4.1.2011.2.25.4.50.52.1.25.1.10
    optixEthPortBwwatchEnable OBJECT-TYPE
        SYNTAX INTEGER
        {
            enable(1),
            disable(0)
        }
        MAX-ACCESS read-write
        STATUS current
        DESCRIPTION
            "This object indicates the enable status of monitoring port physical bandwidth usage."
        ::= { optixEthPortExtEntry 10 }

    -- 1.3.6.1.4.1.2011.2.25.4.50.52.1.25.1.11
    optixEthPortDelayWatchEn OBJECT-TYPE
        SYNTAX INTEGER
        {
            disable(0),
            enable(1)
        }
        MAX-ACCESS read-write
        STATUS current
        DESCRIPTION
            "This object indicates the enable status of accurate expansion. 0: disable, 1: enable"
        ::= { optixEthPortExtEntry 11 }

    -- 1.3.6.1.4.1.2011.2.25.4.50.52.1.25.1.12
        optixEthPortWaveWorkBand OBJECT-TYPE
        SYNTAX INTEGER
        {
            clband(0),
            cband(1),
            lband(2),
            cband320G(3),
            cbandraman(4),
            lbandraman(5),
            cwdmband(6),
            smcband(7),
            cband96a(8),
            cbandplus(9),
            cband192(10),
            invalid(255)
        }
        MAX-ACCESS read-only
        STATUS current
        DESCRIPTION
            "This parameter is used to query the working band wavelength of a laser."
        ::= { optixEthPortExtEntry 12 }

    -- 1.3.6.1.4.1.2011.2.25.4.50.52.1.25.1.13
        optixEthPortGetWaveNum OBJECT-TYPE
        SYNTAX Unsigned32
        MAX-ACCESS read-only
        STATUS current
        DESCRIPTION
            "This parameter is used to query the number of operating wavelengths of a laser."
        ::= { optixEthPortExtEntry 13 }

    -- 1.3.6.1.4.1.2011.2.25.4.50.52.1.26
    optixAtomGpsPortTable OBJECT-TYPE
        SYNTAX SEQUENCE OF OptixAtomGpsPortEntry
        MAX-ACCESS not-accessible
        STATUS current
        DESCRIPTION
            "This table contains basic configuration information of the GPS port."
        ::= { optixPktPortGroup 26 }

    -- 1.3.6.1.4.1.2011.2.25.4.50.52.1.26.1
    optixAtomGpsPortEntry OBJECT-TYPE
        SYNTAX OptixAtomGpsPortEntry
        MAX-ACCESS not-accessible
        STATUS current
        DESCRIPTION
            "This entry contains basic configuration information of the GPS port."
        INDEX{ optixLogBoardId,optixLogSubCardId,optixPortId }
        ::= { optixAtomGpsPortTable 1 }

    OptixAtomGpsPortEntry ::=
        SEQUENCE {
            optixAtomGpsPortPtpDomainId
                Unsigned32,
            optixAtomGpsPortPtpPri1
                Unsigned32,
            optixAtomGpsPortPtpPri2
                Unsigned32,
            optixAtomGpsPortTimeYear
                Unsigned32,
            optixAtomGpsPortTimeMonth
                Unsigned32,
            optixAtomGpsPortTimeDay
                Unsigned32,
            optixAtomGpsPortTimeHour
                Unsigned32,
            optixAtomGpsPortTimeMinute
                Unsigned32,
            optixAtomGpsPortTimeSecond
                Unsigned32,
            optixAtomGpsPortTimeLockState
                INTEGER,
            optixAtomGpsPortLliteNum
                Unsigned32,
            optixAtomGpsPortLliteId
                OCTET STRING,
            optixAtomGpsPortLliteRatio
                OCTET STRING,
            optixAtomGpsPortSelfHealEn
                INTEGER,
            optixAtomGpsPortFreqLockState
                INTEGER,
            optixAtomGpsPortReStart
                INTEGER
        }

    -- 1.3.6.1.4.1.2011.2.25.4.50.52.1.26.1.1
    optixAtomGpsPortPtpDomainId OBJECT-TYPE
        SYNTAX Unsigned32
        MAX-ACCESS read-write
        STATUS current
        DESCRIPTION
            "This parameter specifies the domain ID of an IEEE 1588 packet sent over the GPS port."
        ::= { optixAtomGpsPortEntry 1 }

    -- 1.3.6.1.4.1.2011.2.25.4.50.52.1.26.1.2
    optixAtomGpsPortPtpPri1 OBJECT-TYPE
        SYNTAX Unsigned32
        MAX-ACCESS read-write
        STATUS current
        DESCRIPTION
            "This parameter specifies priority 1 of an IEEE 1588 packet sent over the GPS port."
        ::= { optixAtomGpsPortEntry 2 }

    -- 1.3.6.1.4.1.2011.2.25.4.50.52.1.26.1.3
    optixAtomGpsPortPtpPri2 OBJECT-TYPE
        SYNTAX Unsigned32
        MAX-ACCESS read-write
        STATUS current
        DESCRIPTION
            "This parameter specifies priority 2 of an IEEE 1588 packet sent over the GPS port."
        ::= { optixAtomGpsPortEntry 3 }

    -- 1.3.6.1.4.1.2011.2.25.4.50.52.1.26.1.4
    optixAtomGpsPortTimeYear OBJECT-TYPE
        SYNTAX Unsigned32
        MAX-ACCESS read-only
        STATUS current
        DESCRIPTION
            "This parameter specifies the year of the GPS port time."
        ::= { optixAtomGpsPortEntry 4 }

    -- 1.3.6.1.4.1.2011.2.25.4.50.52.1.26.1.5
    optixAtomGpsPortTimeMonth OBJECT-TYPE
        SYNTAX Unsigned32
        MAX-ACCESS read-only
        STATUS current
        DESCRIPTION
            "This parameter specifies the month of the GPS port time."
        ::= { optixAtomGpsPortEntry 5 }

    -- 1.3.6.1.4.1.2011.2.25.4.50.52.1.26.1.6
    optixAtomGpsPortTimeDay OBJECT-TYPE
        SYNTAX Unsigned32
        MAX-ACCESS read-only
        STATUS current
        DESCRIPTION
            "This parameter specifies the day of the GPS port time."
        ::= { optixAtomGpsPortEntry 6 }

    -- 1.3.6.1.4.1.2011.2.25.4.50.52.1.26.1.7
    optixAtomGpsPortTimeHour OBJECT-TYPE
        SYNTAX Unsigned32
        MAX-ACCESS read-only
        STATUS current
        DESCRIPTION
            "This parameter specifies the hour of the GPS port time."
        ::= { optixAtomGpsPortEntry 7 }

    -- 1.3.6.1.4.1.2011.2.25.4.50.52.1.26.1.8
    optixAtomGpsPortTimeMinute OBJECT-TYPE
        SYNTAX Unsigned32
        MAX-ACCESS read-only
        STATUS current
        DESCRIPTION
            "This parameter specifies the minute of the GPS port time."
        ::= { optixAtomGpsPortEntry 8 }

    -- 1.3.6.1.4.1.2011.2.25.4.50.52.1.26.1.9
    optixAtomGpsPortTimeSecond OBJECT-TYPE
        SYNTAX Unsigned32
        MAX-ACCESS read-only
        STATUS current
        DESCRIPTION
            "This parameter specifies the second of the GPS port time."
        ::= { optixAtomGpsPortEntry 9 }

    -- 1.3.6.1.4.1.2011.2.25.4.50.52.1.26.1.10
    optixAtomGpsPortTimeLockState OBJECT-TYPE
        SYNTAX INTEGER
        {
            unlock(0),
            lock(1)
        }
        MAX-ACCESS read-only
        STATUS current
        DESCRIPTION
            "This parameter specifies the time locking status of the GPS port."
        ::= { optixAtomGpsPortEntry 10 }

    -- 1.3.6.1.4.1.2011.2.25.4.50.52.1.26.1.11
    optixAtomGpsPortLliteNum OBJECT-TYPE
        SYNTAX Unsigned32
        MAX-ACCESS read-only
        STATUS current
        DESCRIPTION
            "This parameter specifies the number of satellites available for the GPS port."
        ::= { optixAtomGpsPortEntry 11 }

    -- 1.3.6.1.4.1.2011.2.25.4.50.52.1.26.1.12
    optixAtomGpsPortLliteId OBJECT-TYPE
        SYNTAX OCTET STRING (SIZE(0..128))
        MAX-ACCESS read-only
        STATUS current
        DESCRIPTION
            "This parameter specifies the satellite ID of the GPS port."
        ::= { optixAtomGpsPortEntry 12 }

    -- 1.3.6.1.4.1.2011.2.25.4.50.52.1.26.1.13
    optixAtomGpsPortLliteRatio OBJECT-TYPE
        SYNTAX OCTET STRING (SIZE(0..128))
        MAX-ACCESS read-only
        STATUS current
        DESCRIPTION
            "This parameter specifies the satellite SNR of the GPS port."
        ::= { optixAtomGpsPortEntry 13 }

    -- 1.3.6.1.4.1.2011.2.25.4.50.52.1.26.1.14
    optixAtomGpsPortSelfHealEn OBJECT-TYPE
        SYNTAX INTEGER
        {
            disable(0),
            enable(1)
        }
        MAX-ACCESS read-write
        STATUS current
        DESCRIPTION
            "This parameter specifies whether the self-healing of the GPS port is enabled."
        ::= { optixAtomGpsPortEntry 14 }

    -- 1.3.6.1.4.1.2011.2.25.4.50.52.1.26.1.15
    optixAtomGpsPortFreqLockState OBJECT-TYPE
        SYNTAX INTEGER
        {
            unlock(0),
            lock(1)
        }
        MAX-ACCESS read-only
        STATUS current
        DESCRIPTION
            "This parameter specifies the frequency locking status of the GPS port."
        ::= { optixAtomGpsPortEntry 15 }

    -- 1.3.6.1.4.1.2011.2.25.4.50.52.1.26.1.16
    optixAtomGpsPortReStart OBJECT-TYPE
        SYNTAX INTEGER
        {
            restart(0)
        }
        MAX-ACCESS read-write
        STATUS current
        DESCRIPTION
            "This parameter specifies the row status of the GPS port."
        ::= { optixAtomGpsPortEntry 16 }

    -- 1.3.6.1.4.1.2011.2.25.4.50.52.1.27
    optixVlanIfMemberTable OBJECT-TYPE
        SYNTAX SEQUENCE OF OptixVlanIfMemberEntry
        MAX-ACCESS not-accessible
        STATUS current
        DESCRIPTION
            "This table contains basic configuration information about VLAN-IF member ports."
        ::= { optixPktPortGroup 27 }

    -- 1.3.6.1.4.1.2011.2.25.4.50.52.1.27.1
    optixVlanIfMemberEntry OBJECT-TYPE
        SYNTAX OptixVlanIfMemberEntry
        MAX-ACCESS not-accessible
        STATUS current
        DESCRIPTION
            "The entry contains basic configuration information about VLAN-IF member ports."
        INDEX{ optixLogBoardId,optixLogSubCardId,optixVlanPortId,optixVlanIfMemberBid,optixVlanIfMemberSubId,optixVlanIfMemberPid }
        ::= { optixVlanIfMemberTable 1 }

    OptixVlanIfMemberEntry ::=
        SEQUENCE {
            optixVlanIfMemberBid
                Unsigned32,
            optixVlanIfMemberSubId
                Unsigned32,
            optixVlanIfMemberPid
                Unsigned32,
            optixVlanIfMemberRowStatus
                RowStatus
        }

    -- 1.3.6.1.4.1.2011.2.25.4.50.52.1.27.1.1
    optixVlanIfMemberBid OBJECT-TYPE
        SYNTAX Unsigned32
        MAX-ACCESS not-accessible
        STATUS current
        DESCRIPTION
            "This parameter specifies the slot ID of the board providing VLAN-IF member ports."
        ::= { optixVlanIfMemberEntry 1 }

    -- 1.3.6.1.4.1.2011.2.25.4.50.52.1.27.1.2
    optixVlanIfMemberSubId OBJECT-TYPE
        SYNTAX Unsigned32
        MAX-ACCESS not-accessible
        STATUS current
        DESCRIPTION
            "This parameter specifies the subboard ID of the board providing VLAN-IF member ports."
        ::= { optixVlanIfMemberEntry 2 }

    -- 1.3.6.1.4.1.2011.2.25.4.50.52.1.27.1.3
    optixVlanIfMemberPid OBJECT-TYPE
        SYNTAX Unsigned32
        MAX-ACCESS not-accessible
        STATUS current
        DESCRIPTION
            "This parameter specifies the ID of VLAN-IF member ports."
        ::= { optixVlanIfMemberEntry 3 }

    -- 1.3.6.1.4.1.2011.2.25.4.50.52.1.27.1.255
    optixVlanIfMemberRowStatus OBJECT-TYPE
        SYNTAX RowStatus
        MAX-ACCESS read-create
        STATUS current
        DESCRIPTION
            "This parameter specifies row status of VLAN-IF member ports."
        ::= { optixVlanIfMemberEntry 255 }

    -- 1.3.6.1.4.1.2011.2.25.4.50.52.1.28
    optixEthPortCaptureHeaderTable OBJECT-TYPE
        SYNTAX SEQUENCE OF OptixEthPortCaptureHeaderEntry
        MAX-ACCESS not-accessible
        STATUS current
        DESCRIPTION
            "This table describes basic information about captured packet headers."
        ::= { optixPktPortGroup 28 }

    -- 1.3.6.1.4.1.2011.2.25.4.50.52.1.28.1
    optixEthPortCaptureHeaderEntry OBJECT-TYPE
        SYNTAX OptixEthPortCaptureHeaderEntry
        MAX-ACCESS not-accessible
        STATUS current
        DESCRIPTION
            "This entry contains basic configuration information about captured packet headers."
        INDEX{ optixEthPortCaptureHeaderBId,optixEthPortCaptureHeaderSubId,optixEthPortCaptureHeaderPortId,optixEthPortCaptureHeaderDigType,optixEthPortCaptureHeaderHeadDir }
        ::= { optixEthPortCaptureHeaderTable 1 }

    OptixEthPortCaptureHeaderEntry ::=
        SEQUENCE {
            optixEthPortCaptureHeaderBId
                Unsigned32,
            optixEthPortCaptureHeaderSubId
                Unsigned32,
            optixEthPortCaptureHeaderPortId
                Unsigned32,
            optixEthPortCaptureHeaderDigType
                INTEGER,
            optixEthPortCaptureHeaderHeadDir
                INTEGER,
            optixEthPortCaptureHeaderType
                INTEGER,
            optixEthPortCaptureHeaderMode
                INTEGER,
            optixEthPortCaptureHeaderHeadNum
                Unsigned32,
            optixEthPortCaptureHeaderHeadLen
                Unsigned32,
            optixEthPortCaptureHeaderAgeTime
                Unsigned32,
            optixEthPortCaptureHeaderMask
                Unsigned32,
            optixEthPortCaptureHeaderRule
                OCTET STRING,
            optixEthPortCaphdrOffset
                Unsigned32,
            optixEthPortCaphdrMatchLen
                Unsigned32,
            optixEthPortCaphdrMatchRule
                OCTET STRING
        }

    -- 1.3.6.1.4.1.2011.2.25.4.50.52.1.28.1.1
    optixEthPortCaptureHeaderBId OBJECT-TYPE
        SYNTAX Unsigned32
        MAX-ACCESS not-accessible
        STATUS current
        DESCRIPTION
            "This parameter specifies the board ID of an Ethernet port."
        ::= { optixEthPortCaptureHeaderEntry 1 }

    -- 1.3.6.1.4.1.2011.2.25.4.50.52.1.28.1.2
    optixEthPortCaptureHeaderSubId OBJECT-TYPE
        SYNTAX Unsigned32
        MAX-ACCESS not-accessible
        STATUS current
        DESCRIPTION
            "This parameter specifies the subboard ID of an Ethernet port."
        ::= { optixEthPortCaptureHeaderEntry 2 }

    -- 1.3.6.1.4.1.2011.2.25.4.50.52.1.28.1.3
    optixEthPortCaptureHeaderPortId OBJECT-TYPE
        SYNTAX Unsigned32
        MAX-ACCESS not-accessible
        STATUS current
        DESCRIPTION
            "This parameter specifies the ID of an Ethernet port."
        ::= { optixEthPortCaptureHeaderEntry 3 }

    -- 1.3.6.1.4.1.2011.2.25.4.50.52.1.28.1.4
    optixEthPortCaptureHeaderDigType OBJECT-TYPE
        SYNTAX INTEGER
        {
            service(0),
            protocol(1),
            all(255)
        }
        MAX-ACCESS not-accessible
        STATUS current
        DESCRIPTION
            "This parameter indicates the type of captured packets.{service(0),protocol(1),all(255)}"
        ::= { optixEthPortCaptureHeaderEntry 4 }

    -- 1.3.6.1.4.1.2011.2.25.4.50.52.1.28.1.5
    optixEthPortCaptureHeaderHeadDir OBJECT-TYPE
        SYNTAX INTEGER
        {
            ingress(0),
            egress(1),
            all(255)
        }
        MAX-ACCESS not-accessible
        STATUS current
        DESCRIPTION
            "This parameter specifies the direction in which packet headers are captured.{ingress(0),egress(1),all(255)}"
        ::= { optixEthPortCaptureHeaderEntry 5 }

    -- 1.3.6.1.4.1.2011.2.25.4.50.52.1.28.1.6
    optixEthPortCaptureHeaderType OBJECT-TYPE
        SYNTAX INTEGER
        {
            l2captureheader(0),
            l3captureheader(1),
            l2procaptureheader(2),
            l2l3captureheader(3)
        }
        MAX-ACCESS read-only
        STATUS current
        DESCRIPTION
            "This parameter specifies the packet type of captured packets.{l2captureheader(0),l3captureheader(1),l2procaptureheader(2),l2l3captureheader(3)"
        ::= { optixEthPortCaptureHeaderEntry 6 }

    -- 1.3.6.1.4.1.2011.2.25.4.50.52.1.28.1.7
    optixEthPortCaptureHeaderMode OBJECT-TYPE
        SYNTAX INTEGER
        {
            once(0),
            continuance(1)
        }
        MAX-ACCESS read-only
        STATUS current
        DESCRIPTION
            "This parameter indicates the mode of captured packets.{once(0),continuance(1)}"
        ::= { optixEthPortCaptureHeaderEntry 7 }

    -- 1.3.6.1.4.1.2011.2.25.4.50.52.1.28.1.8
    optixEthPortCaptureHeaderHeadNum OBJECT-TYPE
        SYNTAX Unsigned32
        MAX-ACCESS read-only
        STATUS current
        DESCRIPTION
            "This parameter indicates the number of captured packets."
        ::= { optixEthPortCaptureHeaderEntry 8 }

    -- 1.3.6.1.4.1.2011.2.25.4.50.52.1.28.1.9
    optixEthPortCaptureHeaderHeadLen OBJECT-TYPE
        SYNTAX Unsigned32
        MAX-ACCESS read-only
        STATUS current
        DESCRIPTION
            "This parameter indicates the length of the packet header."
        ::= { optixEthPortCaptureHeaderEntry 9 }

    -- 1.3.6.1.4.1.2011.2.25.4.50.52.1.28.1.10
    optixEthPortCaptureHeaderAgeTime OBJECT-TYPE
        SYNTAX Unsigned32
        MAX-ACCESS read-only
        STATUS current
        DESCRIPTION
            "This parameter specifies the aging time of capturing packet headers."
        ::= { optixEthPortCaptureHeaderEntry 10 }

    -- 1.3.6.1.4.1.2011.2.25.4.50.52.1.28.1.11
    optixEthPortCaptureHeaderMask OBJECT-TYPE
        SYNTAX Unsigned32
        MAX-ACCESS read-only
        STATUS current
        DESCRIPTION
            "This parameter specifies a mask code of capturing packet headers."
        ::= { optixEthPortCaptureHeaderEntry 11 }

    -- 1.3.6.1.4.1.2011.2.25.4.50.52.1.28.1.12
    optixEthPortCaptureHeaderRule OBJECT-TYPE
        SYNTAX OCTET STRING
        MAX-ACCESS read-only
        STATUS current
        DESCRIPTION
            "This parameter indicates the rule of capturing packet headers."
        ::= { optixEthPortCaptureHeaderEntry 12 }

    -- 1.3.6.1.4.1.2011.2.25.4.50.52.1.28.1.13
    optixEthPortCaphdrOffset OBJECT-TYPE
        SYNTAX Unsigned32
        MAX-ACCESS read-only
        STATUS current
        DESCRIPTION
            "This parameter indicates the offset index of capturing packet headers."
        ::= { optixEthPortCaptureHeaderEntry 13 }

    -- 1.3.6.1.4.1.2011.2.25.4.50.52.1.28.1.14
    optixEthPortCaphdrMatchLen OBJECT-TYPE
        SYNTAX Unsigned32
        MAX-ACCESS read-only
        STATUS current
        DESCRIPTION
            "This parameter specifies the match length of capturing packet headers."
        ::= { optixEthPortCaptureHeaderEntry 14 }

    -- 1.3.6.1.4.1.2011.2.25.4.50.52.1.28.1.15
    optixEthPortCaphdrMatchRule OBJECT-TYPE
        SYNTAX OCTET STRING
        MAX-ACCESS read-only
        STATUS current
        DESCRIPTION
            "This parameter specifies the match rule of capturing packet headers."
        ::= { optixEthPortCaptureHeaderEntry 15 }

    -- 1.3.6.1.4.1.2011.2.25.4.50.52.1.29
    optixDelayWatchTable OBJECT-TYPE
        SYNTAX SEQUENCE OF OptixDelayWatchEntry
        MAX-ACCESS not-accessible
        STATUS current
        DESCRIPTION
            "This table describes the information about accurate expansion."
        ::= { optixPktPortGroup 29 }

    -- 1.3.6.1.4.1.2011.2.25.4.50.52.1.29.1
    optixDelayWatchEntry OBJECT-TYPE
        SYNTAX OptixDelayWatchEntry
        MAX-ACCESS not-accessible
        STATUS current
        DESCRIPTION
            "This entry contains the information about accurate expansion."
        INDEX{ optixLogBoardId,optixLogSubCardId,optixPortId,optixDelayWatchStartTime,optixDelayWatchEndTime,optixDelayWatchTimelist }
        ::= { optixDelayWatchTable 1 }

    OptixDelayWatchEntry ::=
        SEQUENCE {
            optixDelayWatchStartTime
                DateAndTime,
            optixDelayWatchEndTime
                DateAndTime,
            optixDelayWatchTimelist
                Unsigned32,
            optixDelayWatchrealStartTime
                DateAndTime,
            optixDelayWatchDataFlag
                Unsigned32,
            optixDelayWatchDelayMax
                Unsigned32,
            optixDelayWatchDelayAvg
                Unsigned32,
            optixDelayWatchDelayInfo1
                Unsigned32,
            optixDelayWatchDelayInfo2
                Unsigned32,
            optixDelayWatchDelayInfo3
                Unsigned32,
            optixDelayWatchDelayInfo4
                Unsigned32,
            optixDelayWatchDelayInfo5
                Unsigned32,
            optixDelayWatchDelayInfo6
                Unsigned32,
            optixDelayWatchDelayInfo7
                Unsigned32,
            optixDelayWatchDelayInfo8
                Unsigned32
        }

    -- 1.3.6.1.4.1.2011.2.25.4.50.52.1.29.1.1
    optixDelayWatchStartTime OBJECT-TYPE
        SYNTAX DateAndTime
        MAX-ACCESS not-accessible
        STATUS current
        DESCRIPTION
            "This parameter is used to query the start time of accurate expansion delay information."
        ::= { optixDelayWatchEntry 1 }

    -- 1.3.6.1.4.1.2011.2.25.4.50.52.1.29.1.2
    optixDelayWatchEndTime OBJECT-TYPE
        SYNTAX DateAndTime
        MAX-ACCESS not-accessible
        STATUS current
        DESCRIPTION
            "This parameter is used to query the end time of accurate expansion delay information."
        ::= { optixDelayWatchEntry 2 }

    -- 1.3.6.1.4.1.2011.2.25.4.50.52.1.29.1.3
    optixDelayWatchTimelist OBJECT-TYPE
        SYNTAX Unsigned32
        MAX-ACCESS not-accessible
        STATUS current
        DESCRIPTION
            "This parameter is used to query the number of accurate expansion delay information."
        ::= { optixDelayWatchEntry 3 }

    -- 1.3.6.1.4.1.2011.2.25.4.50.52.1.29.1.4
    optixDelayWatchrealStartTime OBJECT-TYPE
        SYNTAX DateAndTime
        MAX-ACCESS read-only
        STATUS current
        DESCRIPTION
            "This parameter is used to query the actual start time of the accurate expansion delay information."
        ::= { optixDelayWatchEntry 4 }

    -- 1.3.6.1.4.1.2011.2.25.4.50.52.1.29.1.5
    optixDelayWatchDataFlag OBJECT-TYPE
        SYNTAX Unsigned32
        MAX-ACCESS read-only
        STATUS current
        DESCRIPTION
            "This parameter is used to check for delay data in accurate expansion. 0-no delay data, 1-delay data"
        ::= { optixDelayWatchEntry 5 }

    -- 1.3.6.1.4.1.2011.2.25.4.50.52.1.29.1.6
    optixDelayWatchDelayMax OBJECT-TYPE
        SYNTAX Unsigned32
        MAX-ACCESS read-only
        STATUS current
        DESCRIPTION
            "This parameter is used to query the maximum delay of accurate expansion."
        ::= { optixDelayWatchEntry 6 }

    -- 1.3.6.1.4.1.2011.2.25.4.50.52.1.29.1.7
    optixDelayWatchDelayAvg OBJECT-TYPE
        SYNTAX Unsigned32
        MAX-ACCESS read-only
        STATUS current
        DESCRIPTION
            "This parameter is used to query the average delay of accurate expansion."
        ::= { optixDelayWatchEntry 7 }

    -- 1.3.6.1.4.1.2011.2.25.4.50.52.1.29.1.8
    optixDelayWatchDelayInfo1 OBJECT-TYPE
        SYNTAX Unsigned32
        MAX-ACCESS read-only
        STATUS current
        DESCRIPTION
            "This parameter is used to query the percentage of &lt; 1 ms delay distributions."
        ::= { optixDelayWatchEntry 8 }

    -- 1.3.6.1.4.1.2011.2.25.4.50.52.1.29.1.9
    optixDelayWatchDelayInfo2 OBJECT-TYPE
        SYNTAX Unsigned32
        MAX-ACCESS read-only
        STATUS current
        DESCRIPTION
            "This parameter is used to query the percentage of 1-2 ms delay distributions."
        ::= { optixDelayWatchEntry 9 }

    -- 1.3.6.1.4.1.2011.2.25.4.50.52.1.29.1.10
    optixDelayWatchDelayInfo3 OBJECT-TYPE
        SYNTAX Unsigned32
        MAX-ACCESS read-only
        STATUS current
        DESCRIPTION
            "This parameter is used to query the percentage of 2-4 ms delay distributions."
        ::= { optixDelayWatchEntry 10 }

    -- 1.3.6.1.4.1.2011.2.25.4.50.52.1.29.1.11
    optixDelayWatchDelayInfo4 OBJECT-TYPE
        SYNTAX Unsigned32
        MAX-ACCESS read-only
        STATUS current
        DESCRIPTION
            "This parameter is used to query the percentage of 4-6 ms delay distributions."
        ::= { optixDelayWatchEntry 11 }

    -- 1.3.6.1.4.1.2011.2.25.4.50.52.1.29.1.12
    optixDelayWatchDelayInfo5 OBJECT-TYPE
        SYNTAX Unsigned32
        MAX-ACCESS read-only
        STATUS current
        DESCRIPTION
            "This parameter is used to query the percentage of 6-10 ms delay distributions."
        ::= { optixDelayWatchEntry 12 }

    -- 1.3.6.1.4.1.2011.2.25.4.50.52.1.29.1.13
    optixDelayWatchDelayInfo6 OBJECT-TYPE
        SYNTAX Unsigned32
        MAX-ACCESS read-only
        STATUS current
        DESCRIPTION
            "This parameter is used to query the percentage of 10-15 ms delay distributions."
        ::= { optixDelayWatchEntry 13 }

    -- 1.3.6.1.4.1.2011.2.25.4.50.52.1.29.1.14
    optixDelayWatchDelayInfo7 OBJECT-TYPE
        SYNTAX Unsigned32
        MAX-ACCESS read-only
        STATUS current
        DESCRIPTION
            "This parameter is used to query the percentage of 15-20 ms delay distributions."
        ::= { optixDelayWatchEntry 14 }

    -- 1.3.6.1.4.1.2011.2.25.4.50.52.1.29.1.15
    optixDelayWatchDelayInfo8 OBJECT-TYPE
        SYNTAX Unsigned32
        MAX-ACCESS read-only
        STATUS current
        DESCRIPTION
            "This parameter is used to query the percentage of &gt; 20 ms delay distributions."
        ::= { optixDelayWatchEntry 15 }

END
