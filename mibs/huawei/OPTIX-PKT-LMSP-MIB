-- OPTIX-PKT-LMSP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-LMSP-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus,DateAndTime
            FROM SNMPv2-TC
        ;

    optixPktLmsp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies configuration information of LMSP"
        REVISION "201204200000Z"
        DESCRIPTION
            "The initial revision of this MIB module1."
        ::={ optixProvisionPtn 28 }

    -- 1.3.6.1.4.1.2011.2.25.4.50.28.1
    optixPktLmspGroup OBJECT IDENTIFIER ::= { optixPktLmsp 1 }

    -- 1.3.6.1.4.1.2011.2.25.4.50.28.1.1
    optixPktLmspgTable OBJECT-TYPE
        SYNTAX SEQUENCE OF OptixPktLmspgEntry
        MAX-ACCESS not-accessible
        STATUS current
        DESCRIPTION
            "This table describes the LMSP group configurations."
        ::= { optixPktLmspGroup 1 }

    -- 1.3.6.1.4.1.2011.2.25.4.50.28.1.1.1
    optixPktLmspgEntry OBJECT-TYPE
        SYNTAX OptixPktLmspgEntry
        MAX-ACCESS not-accessible
        STATUS current
        DESCRIPTION
            "This entry describes the LMSP group configurations."
        INDEX{ optixPktLmspgid }
        ::= { optixPktLmspgTable 1 }

    OptixPktLmspgEntry ::=
        SEQUENCE {
            optixPktLmspgid
                Unsigned32,
            optixPktLmspProtectType
                INTEGER,
            optixPktLmspWorkChnNum
                Unsigned32,
            optixPktLmspOPMode
                INTEGER,
            optixPktLmspActiveFlag
                INTEGER,
            optixPktLmspSDFlag
                INTEGER,
            optixPktLmspRvtMode
                INTEGER,
            optixPktLmspSWMode
                INTEGER,
            optixPktLmspProtocolType
                INTEGER,
            optixPktLmspHoldOffTime
                Unsigned32,
            optixPktLmspSfSdLevel
                INTEGER,
            optixPktLmspK2State
                INTEGER,
            optixPktLmspWtrTime
                Unsigned32,
            optixPktLmspActiveState
                INTEGER,
            optixPktLmspStartFlag
                INTEGER,
            optixPktEvent
                Unsigned32,
            optixPktLmspgRowStatus
                RowStatus
        }

    -- 1.3.6.1.4.1.2011.2.25.4.50.28.1.1.1.1
    optixPktLmspgid OBJECT-TYPE
        SYNTAX Unsigned32
        MAX-ACCESS not-accessible
        STATUS current
        DESCRIPTION
            "This object indicates the LMSP group ID."
        ::= { optixPktLmspgEntry 1 }

    -- 1.3.6.1.4.1.2011.2.25.4.50.28.1.1.1.2
    optixPktLmspProtectType OBJECT-TYPE
        SYNTAX INTEGER
        {
            snmp1j1(0),
            snmp1pn(1)
        }
        MAX-ACCESS read-create
        STATUS current
        DESCRIPTION
            "This object indicates the LMSP protection type. 0: SNMP 1+1, 1: SNMP 1:N"
        ::= { optixPktLmspgEntry 2 }

    -- 1.3.6.1.4.1.2011.2.25.4.50.28.1.1.1.3
    optixPktLmspWorkChnNum OBJECT-TYPE
        SYNTAX Unsigned32
        MAX-ACCESS read-create
        STATUS current
        DESCRIPTION
            "This object indicates the number of LMSP working channels. For 1+1 protection, the value is 1. For 1:N protection, the value is N (1 ~ 14)."
        ::= { optixPktLmspgEntry 3 }

    -- 1.3.6.1.4.1.2011.2.25.4.50.28.1.1.1.4
    optixPktLmspOPMode OBJECT-TYPE
        SYNTAX INTEGER
        {
            uniend(0),
            biend(1)
        }
        MAX-ACCESS read-create
        STATUS current
        DESCRIPTION
            "This object indicates the LMSP operation mode. 0: uniend, 1: biend"
        ::= { optixPktLmspgEntry 4 }

    -- 1.3.6.1.4.1.2011.2.25.4.50.28.1.1.1.5
    optixPktLmspActiveFlag OBJECT-TYPE
        SYNTAX INTEGER
        {
            adding(1),
            deleting(2),
            active(3)
        }
        MAX-ACCESS read-only
        STATUS current
        DESCRIPTION
            "This object indicates the LMSP activation flag. 1: adding, 2: deleting, 3: active"
        ::= { optixPktLmspgEntry 5 }

    -- 1.3.6.1.4.1.2011.2.25.4.50.28.1.1.1.6
    optixPktLmspSDFlag OBJECT-TYPE
        SYNTAX INTEGER
        {
            disable(0),
            enable(1)
        }
        MAX-ACCESS read-create
        STATUS current
        DESCRIPTION
            "This object indicates the enable status of the LMSP SD switching. 0: disable, 1: enable"
        ::= { optixPktLmspgEntry 6 }

    -- 1.3.6.1.4.1.2011.2.25.4.50.28.1.1.1.7
    optixPktLmspRvtMode OBJECT-TYPE
        SYNTAX INTEGER
        {
            norvt(0),
            rvt(1)
        }
        MAX-ACCESS read-create
        STATUS current
        DESCRIPTION
            "This object indicates the LMSPrevertion mode. 0: norvt, 1: rvt"
        ::= { optixPktLmspgEntry 7 }

    -- 1.3.6.1.4.1.2011.2.25.4.50.28.1.1.1.8
    optixPktLmspSWMode OBJECT-TYPE
        SYNTAX INTEGER
        {
            uniend(0),
            biend(1)
        }
        MAX-ACCESS read-create
        STATUS current
        DESCRIPTION
            "This object indicates the LMSPsingle-/dual-ended mode. 0: uniend, 1: biend"
        ::= { optixPktLmspgEntry 8 }

    -- 1.3.6.1.4.1.2011.2.25.4.50.28.1.1.1.9
    optixPktLmspProtocolType OBJECT-TYPE
        SYNTAX INTEGER
        {
            old(0),
            new(1),
            restruct(2)
        }
        MAX-ACCESS read-create
        STATUS current
        DESCRIPTION
            "This object indicates the LMSP protocol type. 0: old, 1: new, 2: restruct"
        ::= { optixPktLmspgEntry 9 }

    -- 1.3.6.1.4.1.2011.2.25.4.50.28.1.1.1.10
    optixPktLmspHoldOffTime OBJECT-TYPE
        SYNTAX Unsigned32
        MAX-ACCESS read-create
        STATUS current
        DESCRIPTION
            "This object indicates the LMSP switching delay time."
        ::= { optixPktLmspgEntry 10 }

    -- 1.3.6.1.4.1.2011.2.25.4.50.28.1.1.1.11
    optixPktLmspSfSdLevel OBJECT-TYPE
        SYNTAX INTEGER
        {
            kHigh(0),
            kLow(1)
        }
        MAX-ACCESS read-create
        STATUS current
        DESCRIPTION
            "This object indicates the LMSP SD/SF priority. 0: kHigh, 1: kLow"
        ::= { optixPktLmspgEntry 11 }

    -- 1.3.6.1.4.1.2011.2.25.4.50.28.1.1.1.12
    optixPktLmspK2State OBJECT-TYPE
        SYNTAX INTEGER
        {
            noindicate(0),
            indicate(1)
        }
        MAX-ACCESS read-create
        STATUS current
        DESCRIPTION
            "This object indicates the switching mode of the last three bits of the LMSP K2 byte. 0: noindicate, 1: indicate"
        ::= { optixPktLmspgEntry 12 }

    -- 1.3.6.1.4.1.2011.2.25.4.50.28.1.1.1.13
    optixPktLmspWtrTime OBJECT-TYPE
        SYNTAX Unsigned32
        MAX-ACCESS read-create
        STATUS current
        DESCRIPTION
            "This object indicates the WTR time of the LMSP group."
        ::= { optixPktLmspgEntry 13 }

    -- 1.3.6.1.4.1.2011.2.25.4.50.28.1.1.1.14
    optixPktLmspActiveState OBJECT-TYPE
        SYNTAX INTEGER
        {
            noactive(0),
            active(1)
        }
        MAX-ACCESS read-create
        STATUS current
        DESCRIPTION
            "This object indicates the LMSP activation status. 0: noactve, 1: active"
        ::= { optixPktLmspgEntry 14 }

    -- 1.3.6.1.4.1.2011.2.25.4.50.28.1.1.1.15
    optixPktLmspStartFlag OBJECT-TYPE
        SYNTAX INTEGER
        {
            protocolStop(0),
            protocolStart(1)
        }
        MAX-ACCESS read-create
        STATUS current
        DESCRIPTION
            "This object indicates the start flag of the LMSP group. 0: protocolStop, 1: protocolStart"
        ::= { optixPktLmspgEntry 15 }

    -- 1.3.6.1.4.1.2011.2.25.4.50.28.1.1.1.16
    optixPktEvent OBJECT-TYPE
        SYNTAX Unsigned32
        MAX-ACCESS read-create
        STATUS current
        DESCRIPTION
            "This object indicates the event of LMSP."
        ::= { optixPktLmspgEntry 16 }

    -- 1.3.6.1.4.1.2011.2.25.4.50.28.1.1.1.255
    optixPktLmspgRowStatus OBJECT-TYPE
        SYNTAX RowStatus
        MAX-ACCESS read-create
        STATUS current
        DESCRIPTION
            "This object indicates the row status of the LMSP group."
        ::= { optixPktLmspgEntry 255 }

    -- 1.3.6.1.4.1.2011.2.25.4.50.28.1.2
    optixPktLmspEventTable OBJECT-TYPE
        SYNTAX SEQUENCE OF OptixPktLmspEventEntry
        MAX-ACCESS not-accessible
        STATUS current
        DESCRIPTION
            "This table describes the configurations of the LMSP group event."
        ::= { optixPktLmspGroup 2 }

    -- 1.3.6.1.4.1.2011.2.25.4.50.28.1.2.1
    optixPktLmspEventEntry OBJECT-TYPE
        SYNTAX OptixPktLmspEventEntry
        MAX-ACCESS not-accessible
        STATUS current
        DESCRIPTION
            "This entry describes the configurations of the LMSP group event."
        INDEX{ optixPktLmspgid,optixPktLmspHisSwitchEventID }
        ::= { optixPktLmspEventTable 1 }

    OptixPktLmspEventEntry ::=
        SEQUENCE {
            optixPktLmspHisSwitchEventID
                Unsigned32,
            optixPktLmspHisSwitchEventValue
                INTEGER,
            optixPktLmspHisSwitchEventPara
                Unsigned32,
            optixPktLmspHisSwitchTime
                DateAndTime,
            optixPktLmspHisSwitchTimeStamp
                Unsigned32
        }

    -- 1.3.6.1.4.1.2011.2.25.4.50.28.1.2.1.1
    optixPktLmspHisSwitchEventID OBJECT-TYPE
        SYNTAX Unsigned32
        MAX-ACCESS not-accessible
        STATUS current
        DESCRIPTION
            "This object indicates the number of the historical LMSP switching events. Value range: 1 to 65535."
        ::= { optixPktLmspEventEntry 1 }

    -- 1.3.6.1.4.1.2011.2.25.4.50.28.1.2.1.2
    optixPktLmspHisSwitchEventValue OBJECT-TYPE
        SYNTAX INTEGER
        {
            kSends(1),
            kDir(2),
            getK(5),
            rstApsc(6),
            stateTrans(7),
            kReceived(8),
            sfClears(9),
            sfDetected(10),
            sdClears(11),
            sdDetected(12),
            t1Start(13),
            t1Stop(14),
            t2Start(15),
            t2Stop(16),
            tk12Start(17),
            tk12Stop(18),
            rstLpsc(19),
            t1Expire(20),
            t2Expire(21),
            osCommand(22),
            stopApsc(23),
            kpassOn(24),
            kpassDrop(25),
            xcExecute(26),
            kOnOff(27),
            otherEvent(28),
            tk12Expire(29),
            kOff(30),
            bdOffline(31),
            extcmdtimerStart(32),
            extcmdtimerStop(33),
            extcmdtimerExpire(34),
            modematchStart(35),
            modematchStop(36),
            modematchExpire(37),
            modemmStart(38),
            modemmStop(39),
            modemmExpire(40)
        }
        MAX-ACCESS read-only
        STATUS current
        DESCRIPTION
            "This object indicates the value of the historical LMSP switching event. 1: kSends, 2: kDir, 5: getK, 6: rstApsc, 7: stateTrans, 8: kReceived, 9: sfClears, 10: sfDetected, 11: sdClears, 12: sdDetected, 13: t1Start, 14: t1Stop, 15: t2Start, 16: t2Stop, 17: tk12Start, 18: tk12Stop, 19: rstLpsc, 20: t1Expire, 21: t2Expire, 22: osCommand, 23: stopApsc, 24: kpassOn, 25: kpassDrop, 26: xcExecute, 27: kOnOff, 28: otherEvent, 29: tk12Expire, 30: kOff, 31: bdOffline, 32: extcmdtimerStart, 33: extcmdtimerStop, 34: extcmdtimerExpire, 35: modematchStart, 36: modematchStop, 37: modematchExpire, 38: modemmStart, 39: modemmStop, 40: modemmExpire"
        ::= { optixPktLmspEventEntry 2 }

    -- 1.3.6.1.4.1.2011.2.25.4.50.28.1.2.1.3
    optixPktLmspHisSwitchEventPara OBJECT-TYPE
        SYNTAX Unsigned32
        MAX-ACCESS read-only
        STATUS current
        DESCRIPTION
            "This object indicates the parameter of the historical LMSP switching event."
        ::= { optixPktLmspEventEntry 3 }

    -- 1.3.6.1.4.1.2011.2.25.4.50.28.1.2.1.4
    optixPktLmspHisSwitchTime OBJECT-TYPE
        SYNTAX DateAndTime
        MAX-ACCESS read-only
        STATUS current
        DESCRIPTION
            "This object indicates the date of the historical switching event."
        ::= { optixPktLmspEventEntry 4 }

    -- 1.3.6.1.4.1.2011.2.25.4.50.28.1.2.1.5
    optixPktLmspHisSwitchTimeStamp OBJECT-TYPE
        SYNTAX Unsigned32
        MAX-ACCESS read-only
        STATUS current
        DESCRIPTION
            "This object indicates the time stamp of the historical LMSP switching event."
        ::= { optixPktLmspEventEntry 5 }

    -- 1.3.6.1.4.1.2011.2.25.4.50.28.1.3
    optixPktLmspuTable OBJECT-TYPE
        SYNTAX SEQUENCE OF OptixPktLmspuEntry
        MAX-ACCESS not-accessible
        STATUS current
        DESCRIPTION
            "This table describes the configurations of LMSPprotection units."
        ::= { optixPktLmspGroup 3 }

    -- 1.3.6.1.4.1.2011.2.25.4.50.28.1.3.1
    optixPktLmspuEntry OBJECT-TYPE
        SYNTAX OptixPktLmspuEntry
        MAX-ACCESS not-accessible
        STATUS current
        DESCRIPTION
            "This entry describes the configurations of LMSPprotection units."
        INDEX{ optixPktLmspgid,optixPktLmspuid }
        ::= { optixPktLmspuTable 1 }

    OptixPktLmspuEntry ::=
        SEQUENCE {
            optixPktLmspuid
                Unsigned32,
            optixPktLmspSwitchRequest
                INTEGER,
            optixPktLmspSwitchState
                INTEGER,
            optixPktLmspReqSite
                INTEGER,
            optixPktLmspExtSwitchCmd
                INTEGER,
            optixPktLmspuRowStatus
                RowStatus
        }

    -- 1.3.6.1.4.1.2011.2.25.4.50.28.1.3.1.1
    optixPktLmspuid OBJECT-TYPE
        SYNTAX Unsigned32
        MAX-ACCESS not-accessible
        STATUS current
        DESCRIPTION
            "This object indicates the LMSPprotection unitID. Value range: 1 to 255 (based on the number of linear MSs supported by the NE)."
        ::= { optixPktLmspuEntry 1 }

    -- 1.3.6.1.4.1.2011.2.25.4.50.28.1.3.1.2
    optixPktLmspSwitchRequest OBJECT-TYPE
        SYNTAX INTEGER
        {
            lpsLp(240),
            lpsFs(224),
            lpsSf(208),
            lpsSfLow(192),
            lpsSd(176),
            lpsSdLow(160),
            lpsMs(128),
            lpsWtr(96),
            lpsExer(64),
            lpsDnr(16),
            lpsNr(0)
        }
        MAX-ACCESS read-only
        STATUS current
        DESCRIPTION
            "This object indicates the LMSP switching request. 240: lpsLp, 224: lpsFs, 208: lpsSf, 192: lpsSfLow, 176: lpsSd, 160: lpsSdLow, 128: lpsMs, 96: lpsWtr, 64: lpsExer, 16: lpsDnr, 0: lpsNr"
        ::= { optixPktLmspuEntry 2 }

    -- 1.3.6.1.4.1.2011.2.25.4.50.28.1.3.1.3
    optixPktLmspSwitchState OBJECT-TYPE
        SYNTAX INTEGER
        {
            stop(0),
            starting(255),
            i(1),
            s(4)
        }
        MAX-ACCESS read-only
        STATUS current
        DESCRIPTION
            "This object indicates the LMSP switching status. 0: stop, 255: starting, 1: I, 4: s"
        ::= { optixPktLmspuEntry 3 }

    -- 1.3.6.1.4.1.2011.2.25.4.50.28.1.3.1.4
    optixPktLmspReqSite OBJECT-TYPE
        SYNTAX INTEGER
        {
            near(1),
            far(2)
        }
        MAX-ACCESS read-only
        STATUS current
        DESCRIPTION
            "This object indicates the LMSP remote/local end. 1: near, 2: far"
        ::= { optixPktLmspuEntry 4 }

    -- 1.3.6.1.4.1.2011.2.25.4.50.28.1.3.1.5
    optixPktLmspExtSwitchCmd OBJECT-TYPE
        SYNTAX INTEGER
        {
            lmsLock(15),
            lmsUnlock(31),
            lmsForce(14),
            lmsForceclr(30),
            lmsMan(8),
            lmsManclr(24),
            lmsExer(4),
            lmsExerclr(20),
            lmsClearall(16),
            lmsClearwtr(22),
            lmsLockwork(5),
            lmsUnlockwork(21),
            lmsInvalid(0)
        }
        MAX-ACCESS read-create
        STATUS current
        DESCRIPTION
            "This object indicates the LMSP external switching cmd. 15: lmsLock, 31: lmsUnlock, 14: lmsForce, 30: lmsForceclr, 8: lmsMan, 24: lmsManclr, 4: lmsExer, 20: lmsExerclr, 16: lmsClearall, 22: lmsClearwtr, 5: lmsLockwork, 21: lmsUnlockwork, 0: lmsInvalid"
        ::= { optixPktLmspuEntry 5 }

    -- 1.3.6.1.4.1.2011.2.25.4.50.28.1.3.1.255
    optixPktLmspuRowStatus OBJECT-TYPE
        SYNTAX RowStatus
        MAX-ACCESS read-create
        STATUS current
        DESCRIPTION
            "This object indicates the row status of the LMSP protection unit."
        ::= { optixPktLmspuEntry 255 }

    -- 1.3.6.1.4.1.2011.2.25.4.50.28.1.4
    optixPktLmspAu4Table OBJECT-TYPE
        SYNTAX SEQUENCE OF OptixPktLmspAu4Entry
        MAX-ACCESS not-accessible
        STATUS current
        DESCRIPTION
            "This table describes the LMSP group Au4 configurations."
        ::= { optixPktLmspGroup 4 }

    -- 1.3.6.1.4.1.2011.2.25.4.50.28.1.4.1
    optixPktLmspAu4Entry OBJECT-TYPE
        SYNTAX OptixPktLmspAu4Entry
        MAX-ACCESS not-accessible
        STATUS current
        DESCRIPTION
            "This entry describes the LMSP group Au4 configurations."
        INDEX{ optixPktLmspgid,optixPktLmspuid }
        ::= { optixPktLmspAu4Table 1 }

    OptixPktLmspAu4Entry ::=
        SEQUENCE {
            optixPktLmspBoardId
                Unsigned32,
            optixPktLmspSubId
                Unsigned32,
            optixPktLmspPortId
                Unsigned32,
            optixPktLmspPumap
                OCTET STRING,
            optixPktLmspAu4RowStatus
                RowStatus
        }

    -- 1.3.6.1.4.1.2011.2.25.4.50.28.1.4.1.1
    optixPktLmspBoardId OBJECT-TYPE
        SYNTAX Unsigned32
        MAX-ACCESS read-create
        STATUS current
        DESCRIPTION
            "This object indicates the slot ID of the LMSP protection unit mapping. Value range: 1 to 65535 (based on the number of boards supported by the NE)."
        ::= { optixPktLmspAu4Entry 1 }

    -- 1.3.6.1.4.1.2011.2.25.4.50.28.1.4.1.2
    optixPktLmspSubId OBJECT-TYPE
        SYNTAX Unsigned32
        MAX-ACCESS read-create
        STATUS current
        DESCRIPTION
            "This object indicates the subboard ID of the LMSP protection unit mapping. Value range: 1 to 255. If the NE does not support subboards, the value is 255."
        ::= { optixPktLmspAu4Entry 2 }

    -- 1.3.6.1.4.1.2011.2.25.4.50.28.1.4.1.3
    optixPktLmspPortId OBJECT-TYPE
        SYNTAX Unsigned32
        MAX-ACCESS read-create
        STATUS current
        DESCRIPTION
            "This object indicates the port number of the LMSP protection unit mapping. Value range: 1 to 65535 (based on the number of ports supported by the board)."
        ::= { optixPktLmspAu4Entry 3 }

    -- 1.3.6.1.4.1.2011.2.25.4.50.28.1.4.1.4
    optixPktLmspPumap OBJECT-TYPE
        SYNTAX OCTET STRING (SIZE(0..32))
        MAX-ACCESS read-create
        STATUS current
        DESCRIPTION
            "This object indicates the LMSP protection unit mapping."
        ::= { optixPktLmspAu4Entry 4 }

    -- 1.3.6.1.4.1.2011.2.25.4.50.28.1.4.1.255
    optixPktLmspAu4RowStatus OBJECT-TYPE
        SYNTAX RowStatus
        MAX-ACCESS read-create
        STATUS current
        DESCRIPTION
            "This object indicates the row status of the LMSP protection unit Au4."
        ::= { optixPktLmspAu4Entry 255 }

    -- 1.3.6.1.4.1.2011.2.25.4.50.28.2
    optixPktLmspNEGroup OBJECT IDENTIFIER ::= { optixPktLmsp 2 }

    -- 1.3.6.1.4.1.2011.2.25.4.50.28.2.1
    optixPktLmspVerfiy OBJECT-TYPE
        SYNTAX INTEGER
        {
            invalid(0),
            verify(1)
        }
        MAX-ACCESS read-write
        STATUS current
        DESCRIPTION
            "This object describes the verify pkt lmsp. 0: invalid, 1: verify"
        ::= { optixPktLmspNEGroup 1 }

END
