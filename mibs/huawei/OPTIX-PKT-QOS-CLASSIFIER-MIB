-- OPTIX-PKT-QOS-CLASSIFIER-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-QOS-CLASSIFIER-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        optixPolicyType,optixPolicyId
            FROM OPTIX-PKT-QOS-POLICY-MIB
        ;

    optixPktQosClassifier MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes QoS configurations on devices."
        REVISION "201204200000Z"
        DESCRIPTION
            "Initial draft."
        ::={ optixProvisionPtn 30 }

    -- 1.3.6.1.4.1.2011.2.25.4.50.30.1
    optixPktQosClassifierGroup OBJECT IDENTIFIER ::= { optixPktQosClassifier 1 }

    -- 1.3.6.1.4.1.2011.2.25.4.50.30.1.1
    optixClassifierTable OBJECT-TYPE
        SYNTAX SEQUENCE OF OptixClassifierEntry
        MAX-ACCESS not-accessible
        STATUS current
        DESCRIPTION
            "This table describes the basic configurations of the QoS flow classification."
        ::= { optixPktQosClassifierGroup 1 }

    -- 1.3.6.1.4.1.2011.2.25.4.50.30.1.1.1
    optixClassifierEntry OBJECT-TYPE
        SYNTAX OptixClassifierEntry
        MAX-ACCESS not-accessible
        STATUS current
        DESCRIPTION
            "This entry describes the basic configurations of the QoS flow classification."
        INDEX{ optixPolicyType,optixPolicyId,optixClassifierId,optixClassifierRuleId }
        ::= { optixClassifierTable 1 }

    OptixClassifierEntry ::=
        SEQUENCE {
            optixClassifierId
                Unsigned32,
            optixClassifierRuleId
                Unsigned32,
            optixClassifierMatchId
                Unsigned32,
            optixClassifierLogicType
                INTEGER,
            optixClassifierRule
                OCTET STRING,
            optixClassifierRowStatus
                RowStatus
        }

    -- 1.3.6.1.4.1.2011.2.25.4.50.30.1.1.1.1
    optixClassifierId OBJECT-TYPE
        SYNTAX Unsigned32
        MAX-ACCESS not-accessible
        STATUS current
        DESCRIPTION
            "This object indicates the flow classification ID of the QoS module. Value range for PORT: 0 to 512. Value range for Vuniingress: 0 to 1024 (for RTN 950A: 0 to 512)."
        ::= { optixClassifierEntry 1 }

    -- 1.3.6.1.4.1.2011.2.25.4.50.30.1.1.1.2
    optixClassifierRuleId OBJECT-TYPE
        SYNTAX Unsigned32
        MAX-ACCESS not-accessible
        STATUS current
        DESCRIPTION
            "This object indicates the flow classification rule ID of the QoS module. Value range for RTN equipment: 0 to 20."
        ::= { optixClassifierEntry 2 }

    -- 1.3.6.1.4.1.2011.2.25.4.50.30.1.1.1.3
    optixClassifierMatchId OBJECT-TYPE
        SYNTAX Unsigned32
        MAX-ACCESS read-create
        STATUS current
        DESCRIPTION
            "This object indicates the flow classification matching ID of the QoS module. Value range for RTN equipment: 0 to 20."
        ::= { optixClassifierEntry 3 }

    -- 1.3.6.1.4.1.2011.2.25.4.50.30.1.1.1.4
    optixClassifierLogicType OBJECT-TYPE
        SYNTAX INTEGER
        {
            and(1),
            or(2)
        }
        MAX-ACCESS read-create
        STATUS current
        DESCRIPTION
            "This object indicates the flow classification logic type of the QoS module. 1: and, 2: or"
        ::= { optixClassifierEntry 4 }

    -- 1.3.6.1.4.1.2011.2.25.4.50.30.1.1.1.5
    optixClassifierRule OBJECT-TYPE
        SYNTAX OCTET STRING (SIZE(0..64))
        MAX-ACCESS read-create
        STATUS current
        DESCRIPTION
            "This object indicates the flow classification rule of the QoS module."
        ::= { optixClassifierEntry 5 }

    -- 1.3.6.1.4.1.2011.2.25.4.50.30.1.1.1.255
    optixClassifierRowStatus OBJECT-TYPE
        SYNTAX RowStatus
        MAX-ACCESS read-create
        STATUS current
        DESCRIPTION
            "This object indiates the flow classification row statusof the QoS module."
        ::= { optixClassifierEntry 255 }

    -- 1.3.6.1.4.1.2011.2.25.4.50.30.1.2
    optixClassifierDetailTable OBJECT-TYPE
        SYNTAX SEQUENCE OF OptixClassifierDetailEntry
        MAX-ACCESS not-accessible
        STATUS current
        DESCRIPTION
            "This table describes the basic configurations of the QoS flow classification management."
        ::= { optixPktQosClassifierGroup 2 }

    -- 1.3.6.1.4.1.2011.2.25.4.50.30.1.2.1
    optixClassifierDetailEntry OBJECT-TYPE
        SYNTAX OptixClassifierDetailEntry
        MAX-ACCESS not-accessible
        STATUS current
        DESCRIPTION
            "This entry describes the basic configurations of the QoS flow classification management."
        INDEX{ optixPolicyType,optixPolicyId,optixClassifierId }
        ::= { optixClassifierDetailTable 1 }

    OptixClassifierDetailEntry ::=
        SEQUENCE {
            optixClassifierAcl
                INTEGER,
            optixClassifierCosType
                INTEGER,
            optixClassifierCir
                Unsigned32,
            optixClassifierCbs
                Unsigned32,
            optixClassifierPir
                Unsigned32,
            optixClassifierPbs
                Unsigned32,
            optixClassifierColorMode
                INTEGER,
            optixClassifierGreenAction
                INTEGER,
            optixClassifierGreenRemarkCos
                INTEGER,
            optixClassifierGreenRemarkColor
                INTEGER,
            optixClassifierYellowAction
                INTEGER,
            optixClassifierYellowRemarkCos
                INTEGER,
            optixClassifierYellowRemarkColor
                INTEGER,
            optixClassifierRedAction
                INTEGER,
            optixClassifierRedRemarkCos
                INTEGER,
            optixClassifierRedRemarkColor
                INTEGER,
            optixClassifierCarStatus
                INTEGER,
            optixClassifierDetailRowStatus
                RowStatus
        }

    -- 1.3.6.1.4.1.2011.2.25.4.50.30.1.2.1.1
    optixClassifierAcl OBJECT-TYPE
        SYNTAX INTEGER
        {
            permit(1),
            deny(2)
        }
        MAX-ACCESS read-create
        STATUS current
        DESCRIPTION
            "This object indicates the ACL action of the QoS module. 1: permit, 2: deny"
        ::= { optixClassifierDetailEntry 1 }

    -- 1.3.6.1.4.1.2011.2.25.4.50.30.1.2.1.2
    optixClassifierCosType OBJECT-TYPE
        SYNTAX INTEGER
        {
            cs7(1),
            cs6(2),
            ef(3),
            af4(4),
            af3(5),
            af2(6),
            af1(7),
            be(8),
            none(255)
        }
        MAX-ACCESS read-create
        STATUS current
        DESCRIPTION
            "This object indicates the CoS type of the QoS module. 1: cs7, 2: cs6, 3: ef, 4: af4, 5: af3, 6: af2, 7: af1, 8: be, 255: none"
        ::= { optixClassifierDetailEntry 2 }

    -- 1.3.6.1.4.1.2011.2.25.4.50.30.1.2.1.3
    optixClassifierCir OBJECT-TYPE
        SYNTAX Unsigned32
        MAX-ACCESS read-create
        STATUS current
        DESCRIPTION
            "This object indicates the CIR of the QoS module. Value range for RTN equipment: 0 to 1000000."
        ::= { optixClassifierDetailEntry 3 }

    -- 1.3.6.1.4.1.2011.2.25.4.50.30.1.2.1.4
    optixClassifierCbs OBJECT-TYPE
        SYNTAX Unsigned32
        MAX-ACCESS read-create
        STATUS current
        DESCRIPTION
            "This object indicates the CBS of the QoS module. Value range for RTN equipment: 0 to 4294967295."
        ::= { optixClassifierDetailEntry 4 }

    -- 1.3.6.1.4.1.2011.2.25.4.50.30.1.2.1.5
    optixClassifierPir OBJECT-TYPE
        SYNTAX Unsigned32
        MAX-ACCESS read-create
        STATUS current
        DESCRIPTION
            "This object indicates the PIR of the QoS module. Value range for RTN equipment: 0 to 1000000."
        ::= { optixClassifierDetailEntry 5 }

    -- 1.3.6.1.4.1.2011.2.25.4.50.30.1.2.1.6
    optixClassifierPbs OBJECT-TYPE
        SYNTAX Unsigned32
        MAX-ACCESS read-create
        STATUS current
        DESCRIPTION
            "This object indicates the PBS of the QoS module. Value range for RTN equipment: 0 to 4294967295."
        ::= { optixClassifierDetailEntry 6 }

    -- 1.3.6.1.4.1.2011.2.25.4.50.30.1.2.1.7
    optixClassifierColorMode OBJECT-TYPE
        SYNTAX INTEGER
        {
            blind(1),
            aware(2),
            none(255)
        }
        MAX-ACCESS read-only
        STATUS current
        DESCRIPTION
            "This object indicates the color modeof the QoS module.1: blind, 2: aware, 255: none"
        ::= { optixClassifierDetailEntry 7 }

    -- 1.3.6.1.4.1.2011.2.25.4.50.30.1.2.1.8
    optixClassifierGreenAction OBJECT-TYPE
        SYNTAX INTEGER
        {
            pass(1),
            discard(2),
            remark(3),
            none(255)
        }
        MAX-ACCESS read-create
        STATUS current
        DESCRIPTION
            "This object indicates the green packet action of the QoS module. 1: pass, 2: discard, 3: remark, 255: none"
        ::= { optixClassifierDetailEntry 8 }

    -- 1.3.6.1.4.1.2011.2.25.4.50.30.1.2.1.9
    optixClassifierGreenRemarkCos OBJECT-TYPE
        SYNTAX INTEGER
        {
            cs7(1),
            cs6(2),
            ef(3),
            af4(4),
            af3(5),
            af2(6),
            af1(7),
            be(8),
            all(0),
            none(255)
        }
        MAX-ACCESS read-create
        STATUS current
        DESCRIPTION
            "This object indicates the re-marking CoS of the green packets of the QoS module. 1: cs7, 2: cs6, 3: ef, 4: af4, 5: af3, 6: af2, 7: af1, 8: be, 255: none"
        ::= { optixClassifierDetailEntry 9 }

    -- 1.3.6.1.4.1.2011.2.25.4.50.30.1.2.1.10
    optixClassifierGreenRemarkColor OBJECT-TYPE
        SYNTAX INTEGER
        {
            red(1),
            yellow(2),
            green(3),
            none(255)
        }
        MAX-ACCESS read-create
        STATUS current
        DESCRIPTION
            "This object indicates the re-marked color of the green packets of the QoS module. 1: red, 2: yellow, 3: green, 255: none"
        ::= { optixClassifierDetailEntry 10 }

    -- 1.3.6.1.4.1.2011.2.25.4.50.30.1.2.1.11
    optixClassifierYellowAction OBJECT-TYPE
        SYNTAX INTEGER
        {
            pass(1),
            discard(2),
            remark(3),
            none(255)
        }
        MAX-ACCESS read-create
        STATUS current
        DESCRIPTION
            "This object indicates the yellow packet action of the QoS module. 1: pass, 2: discard, 3: remark, 255: none"
        ::= { optixClassifierDetailEntry 11 }

    -- 1.3.6.1.4.1.2011.2.25.4.50.30.1.2.1.12
    optixClassifierYellowRemarkCos OBJECT-TYPE
        SYNTAX INTEGER
        {
            cs7(1),
            cs6(2),
            ef(3),
            af4(4),
            af3(5),
            af2(6),
            af1(7),
            be(8),
            all(0),
            none(255)
        }
        MAX-ACCESS read-create
        STATUS current
        DESCRIPTION
            "This object indicates the re-marking CoS of the yellow packets of the QoS module.1: cs7, 2: cs6, 3: ef, 4: af4, 5: af3, 6: af2, 7: af1, 8: be, 255: none"
        ::= { optixClassifierDetailEntry 12 }

    -- 1.3.6.1.4.1.2011.2.25.4.50.30.1.2.1.13
    optixClassifierYellowRemarkColor OBJECT-TYPE
        SYNTAX INTEGER
        {
            red(1),
            yellow(2),
            green(3),
            none(255)
        }
        MAX-ACCESS read-create
        STATUS current
        DESCRIPTION
            "This object indicates the re-marked color of the yellow packets of the QoS module. 1: red, 2: yellow, 3: green, 255: none"
        ::= { optixClassifierDetailEntry 13 }

    -- 1.3.6.1.4.1.2011.2.25.4.50.30.1.2.1.14
    optixClassifierRedAction OBJECT-TYPE
        SYNTAX INTEGER
        {
            pass(1),
            discard(2),
            remark(3),
            none(255)
        }
        MAX-ACCESS read-create
        STATUS current
        DESCRIPTION
            "This object indicates the red packet action of the QoS module. 1: pass, 2: discard, 3: remark, 255: none"
        ::= { optixClassifierDetailEntry 14 }

    -- 1.3.6.1.4.1.2011.2.25.4.50.30.1.2.1.15
    optixClassifierRedRemarkCos OBJECT-TYPE
        SYNTAX INTEGER
        {
            cs7(1),
            cs6(2),
            ef(3),
            af4(4),
            af3(5),
            af2(6),
            af1(7),
            be(8),
            all(0),
            none(255)
        }
        MAX-ACCESS read-create
        STATUS current
        DESCRIPTION
            "This object indicates the re-marking CoS of the red packets of the QoS module.1: cs7, 2: cs6, 3: ef, 4: af4, 5: af3, 6: af2, 7: af1, 8: be, 255: none"
        ::= { optixClassifierDetailEntry 15 }

    -- 1.3.6.1.4.1.2011.2.25.4.50.30.1.2.1.16
    optixClassifierRedRemarkColor OBJECT-TYPE
        SYNTAX INTEGER
        {
            red(1),
            yellow(2),
            green(3),
            none(255)
        }
        MAX-ACCESS read-create
        STATUS current
        DESCRIPTION
            "This object indicates the re-marked color of the red packets of the QoS module. 1: red, 2: yellow, 3: green, 255: none"
        ::= { optixClassifierDetailEntry 16 }

    -- 1.3.6.1.4.1.2011.2.25.4.50.30.1.2.1.17
    optixClassifierCarStatus OBJECT-TYPE
        SYNTAX INTEGER
        {
            created(0),
            delete(1)
        }
        MAX-ACCESS read-create
        STATUS current
        DESCRIPTION
            "This object indicates the CAR Status of the QoS module. 0: created, 1: delete"
        ::= { optixClassifierDetailEntry 17 }

    -- 1.3.6.1.4.1.2011.2.25.4.50.30.1.2.1.255
    optixClassifierDetailRowStatus OBJECT-TYPE
        SYNTAX RowStatus
        MAX-ACCESS read-create
        STATUS current
        DESCRIPTION
            "This object indiates the flow classification row status of the QoS module."
        ::= { optixClassifierDetailEntry 255 }

    -- 1.3.6.1.4.1.2011.2.25.4.50.30.1.3
    optixClassifierShapingTable OBJECT-TYPE
        SYNTAX SEQUENCE OF OptixClassifierShapingEntry
        MAX-ACCESS not-accessible
        STATUS current
        DESCRIPTION
            "This table describes the basic QoS Policy Classifier Shaping schedualing configurations."
        ::= { optixPktQosClassifierGroup 3 }

    -- 1.3.6.1.4.1.2011.2.25.4.50.30.1.3.1
    optixClassifierShapingEntry OBJECT-TYPE
        SYNTAX OptixClassifierShapingEntry
        MAX-ACCESS not-accessible
        STATUS current
        DESCRIPTION
            "This entry describes the basic QoS Policy Classifier Shaping schedualing configurations."
        INDEX{ optixClassifierShapingType,optixClassifierShapingPolicyID,optixClassifierShapingClassifierID }
        ::= { optixClassifierShapingTable 1 }

    OptixClassifierShapingEntry ::=
        SEQUENCE {
            optixClassifierShapingType
                INTEGER,
            optixClassifierShapingPolicyID
                Unsigned32,
            optixClassifierShapingClassifierID
                Unsigned32,
            optixClassifierShapingCIR
                Unsigned32,
            optixClassifierShapingCBS
                Unsigned32,
            optixClassifierShapingPIR
                Unsigned32,
            optixClassifierShapingPBS
                Unsigned32,
            optixClassifierShapingRowStatus
                RowStatus
        }

    -- 1.3.6.1.4.1.2011.2.25.4.50.30.1.3.1.1
    optixClassifierShapingType OBJECT-TYPE
        SYNTAX INTEGER
        {
            port(1),
            vuniingress(2),
            vuniegress(3),
            pw(4),
            atm(5),
            qinq(6)
        }
        MAX-ACCESS not-accessible
        STATUS current
        DESCRIPTION
            "This object indicates the Qos Policy Classifier Shaping type of the QoS module. 1: port, 2: vuniingress, 3: vuniegress, 4: pw, 5: atm, 6: qinq"
        ::= { optixClassifierShapingEntry 1 }

    -- 1.3.6.1.4.1.2011.2.25.4.50.30.1.3.1.2
    optixClassifierShapingPolicyID OBJECT-TYPE
        SYNTAX Unsigned32
        MAX-ACCESS not-accessible
        STATUS current
        DESCRIPTION
            "This object indicates the Qos Policy Classifier ID of the QoS module. Value range for ATM: 0 to 1024. Value range for PORT: 0 to 256. Value range for VUNIINGRESS: 1 to 1024 (for RTN 950 and RTN 950A: 1 to 256)."
        ::= { optixClassifierShapingEntry 2 }

    -- 1.3.6.1.4.1.2011.2.25.4.50.30.1.3.1.3
    optixClassifierShapingClassifierID OBJECT-TYPE
        SYNTAX Unsigned32
        MAX-ACCESS not-accessible
        STATUS current
        DESCRIPTION
            "This object indicates the Qos Policy Shaping ID of the QoS module. Value range for PORT: 0 to 512. Value range for Vuniingress: 0 to 1024 (for RTN 950A: 0 to 512)."
        ::= { optixClassifierShapingEntry 3 }

    -- 1.3.6.1.4.1.2011.2.25.4.50.30.1.3.1.4
    optixClassifierShapingCIR OBJECT-TYPE
        SYNTAX Unsigned32
        MAX-ACCESS read-create
        STATUS current
        DESCRIPTION
            "This object indicates the Qos Shaping CIR of the QoS module. Value range for RTN equipment: 0 to 1000000."
        ::= { optixClassifierShapingEntry 4 }

    -- 1.3.6.1.4.1.2011.2.25.4.50.30.1.3.1.5
    optixClassifierShapingCBS OBJECT-TYPE
        SYNTAX Unsigned32
        MAX-ACCESS read-create
        STATUS current
        DESCRIPTION
            "This object indicates the Qos Shaping CBS of the QoS module. Value range for RTN equipment: 0 to 4294967295."
        ::= { optixClassifierShapingEntry 5 }

    -- 1.3.6.1.4.1.2011.2.25.4.50.30.1.3.1.6
    optixClassifierShapingPIR OBJECT-TYPE
        SYNTAX Unsigned32
        MAX-ACCESS read-create
        STATUS current
        DESCRIPTION
            "This object indicates the Qos Shaping PIR of the QoS module. Value range for RTN equipment: 0 to 1000000."
        ::= { optixClassifierShapingEntry 6 }

    -- 1.3.6.1.4.1.2011.2.25.4.50.30.1.3.1.7
    optixClassifierShapingPBS OBJECT-TYPE
        SYNTAX Unsigned32
        MAX-ACCESS read-create
        STATUS current
        DESCRIPTION
            "This object indicates the Qos Shaping PBS of the QoS module. Value range for RTN equipment: 0 to 4294967295."
        ::= { optixClassifierShapingEntry 7 }

    -- 1.3.6.1.4.1.2011.2.25.4.50.30.1.3.1.255
    optixClassifierShapingRowStatus OBJECT-TYPE
        SYNTAX RowStatus
        MAX-ACCESS read-create
        STATUS current
        DESCRIPTION
            "This object indicates the basic QoS Policy Classifier Shaping row status."
        ::= { optixClassifierShapingEntry 255 }

    -- 1.3.6.1.4.1.2011.2.25.4.50.30.2
    optixQosCarGroup OBJECT IDENTIFIER ::= { optixPktQosClassifier 2 }

    -- 1.3.6.1.4.1.2011.2.25.4.50.30.2.1
    optixQosCarLmtType OBJECT-TYPE
        SYNTAX INTEGER
        {
            l1(1),
            l2(2)
        }
        MAX-ACCESS read-write
        STATUS current
        DESCRIPTION
            "This parameter indicates the type of car limit."
        ::= { optixQosCarGroup 1 }

END
