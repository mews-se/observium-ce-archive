-- OPTIX-SDH-XC-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-XC-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        ;

    optixSdhXc MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes cross-connection configurations."
        REVISION "201204200000Z"
        DESCRIPTION
            "The initial revision of this MIB module1."
        ::={ optixProvisionSdh 49 }

    -- 1.3.6.1.4.1.2011.2.25.4.10.49.1
    optixSdhXcGroup OBJECT IDENTIFIER ::= { optixSdhXc 1 }

    -- 1.3.6.1.4.1.2011.2.25.4.10.49.1.1
    optixSdhXcTable OBJECT-TYPE
        SYNTAX SEQUENCE OF OptixSdhXcEntry
        MAX-ACCESS not-accessible
        STATUS current
        DESCRIPTION
            "This table describes cross-connection configurations."
        ::= { optixSdhXcGroup 1 }

    -- 1.3.6.1.4.1.2011.2.25.4.10.49.1.1.1
    optixSdhXcEntry OBJECT-TYPE
        SYNTAX OptixSdhXcEntry
        MAX-ACCESS not-accessible
        STATUS current
        DESCRIPTION
            "Thisentry describes cross-connection configurations."
        INDEX{ optixSdhXcSrcBid,optixSdhXcSinkBid,optixSdhXcId }
        ::= { optixSdhXcTable 1 }

    OptixSdhXcEntry ::=
        SEQUENCE {
            optixSdhXcSrcBid
                Unsigned32,
            optixSdhXcSinkBid
                Unsigned32,
            optixSdhXcId
                Unsigned32,
            optixSdhXcSrcSubid
                Unsigned32,
            optixSdhXcSrcPid
                Unsigned32,
            optixSdhXcSrcHP
                Unsigned32,
            optixSdhXcSrcLP
                Unsigned32,
            optixSdhXcSinkSubid
                Unsigned32,
            optixSdhXcSinkPid
                Unsigned32,
            optixSdhXcSinkHP
                Unsigned32,
            optixShdXcSinkLP
                Unsigned32,
            optixSdhXcLevel
                INTEGER,
            optixSdhXcState
                INTEGER,
            optixSdhXcRowStatus
                RowStatus
        }

    -- 1.3.6.1.4.1.2011.2.25.4.10.49.1.1.1.1
    optixSdhXcSrcBid OBJECT-TYPE
        SYNTAX Unsigned32
        MAX-ACCESS not-accessible
        STATUS current
        DESCRIPTION
            "This object indicates the source slot ID of the cross-connection. Value range: 1 to 20. The slots that house lower order cross-connect boards are excluded from the range."
        ::= { optixSdhXcEntry 1 }

    -- 1.3.6.1.4.1.2011.2.25.4.10.49.1.1.1.2
    optixSdhXcSinkBid OBJECT-TYPE
        SYNTAX Unsigned32
        MAX-ACCESS not-accessible
        STATUS current
        DESCRIPTION
            "This object indicates the sink slot ID of the cross-connection. Value range: 1 to 20. The slots that house lower order cross-connect boards are excluded from the range."
        ::= { optixSdhXcEntry 2 }

    -- 1.3.6.1.4.1.2011.2.25.4.10.49.1.1.1.3
    optixSdhXcId OBJECT-TYPE
        SYNTAX Unsigned32
        MAX-ACCESS not-accessible
        STATUS current
        DESCRIPTION
            "This object indicates the cross-connection ID. The IDs allocated by the NMS start from 1 and different value ranges apply to different devices. The value 0 represents that cross-connection IDs are allocated automatically by the system."
        ::= { optixSdhXcEntry 3 }

    -- 1.3.6.1.4.1.2011.2.25.4.10.49.1.1.1.4
    optixSdhXcSrcSubid OBJECT-TYPE
        SYNTAX Unsigned32
        MAX-ACCESS read-only
        STATUS current
        DESCRIPTION
            "This object indicates the source subboard ID of the cross-connection. This parameter takes a fixed value of 255."
        ::= { optixSdhXcEntry 4 }

    -- 1.3.6.1.4.1.2011.2.25.4.10.49.1.1.1.5
    optixSdhXcSrcPid OBJECT-TYPE
        SYNTAX Unsigned32
        MAX-ACCESS read-only
        STATUS current
        DESCRIPTION
            "This object indicates the source port number of the cross-connection.If the source is a line board, this parameter indicates a source optical port ID. The value range varies with boards. If the source is a tributary board, this parameter indicates a port ID on the tributary board. The value range varies with boards. For 10GV2, the value ranges from 1 to 16. The value depends on the board type. If the source is an Ethernet board, the value is 1."
        ::= { optixSdhXcEntry 5 }

    -- 1.3.6.1.4.1.2011.2.25.4.10.49.1.1.1.6
    optixSdhXcSrcHP OBJECT-TYPE
        SYNTAX Unsigned32
        MAX-ACCESS read-only
        STATUS current
        DESCRIPTION
            "This object indicates the source higher order path ID of the cross-connection. 10GV2: This parameter takes the value 1 if the source board is GE02. This parameter takes the value 0 if the source is a tributary board. This parameter indicates a VC-4 number if the source is an Ethernet board."
        ::= { optixSdhXcEntry 6 }

    -- 1.3.6.1.4.1.2011.2.25.4.10.49.1.1.1.7
    optixSdhXcSrcLP OBJECT-TYPE
        SYNTAX Unsigned32
        MAX-ACCESS read-only
        STATUS current
        DESCRIPTION
            "This object indicates the source lower order path ID of the cross-connection. For higher order services, this parameter is 0. For lower order services, this parameter indicates the sink lower order path number. This parameter takes the value 0 if the source is a tributary board. 10GV2: For VC-12 services, the value ranges from 1 to 63; for VC-3 services, the value ranges from 1 to 3. If the source is a 10M/100M Ethernet board, this parameter is the VC-3 number within a VC-4 and the value ranges from 1 to 3. If the source is a 1000M Ethernet board, this parameter takes the value 0."
        ::= { optixSdhXcEntry 7 }

    -- 1.3.6.1.4.1.2011.2.25.4.10.49.1.1.1.8
    optixSdhXcSinkSubid OBJECT-TYPE
        SYNTAX Unsigned32
        MAX-ACCESS read-only
        STATUS current
        DESCRIPTION
            "This object indicates the sink subboard ID of the cross-connection. This parameter takes a fixed value of 255."
        ::= { optixSdhXcEntry 8 }

    -- 1.3.6.1.4.1.2011.2.25.4.10.49.1.1.1.9
    optixSdhXcSinkPid OBJECT-TYPE
        SYNTAX Unsigned32
        MAX-ACCESS read-only
        STATUS current
        DESCRIPTION
            "This object indicates the sink port number of the cross-connection. If the sink is a line board, this parameter indicates a sink optical port ID. The value range varies with boards. If the sink is a tributary board, this parameter indicates a port ID on the tributary board. The value range varies with boards. For 10GV2, the value ranges from 1 to 16. The value depends on the board type. If the sink is an Ethernet board, the value is 1."
        ::= { optixSdhXcEntry 9 }

    -- 1.3.6.1.4.1.2011.2.25.4.10.49.1.1.1.10
    optixSdhXcSinkHP OBJECT-TYPE
        SYNTAX Unsigned32
        MAX-ACCESS read-only
        STATUS current
        DESCRIPTION
            "This object indicates the sink higher order path ID of the cross-connection. Sink AU-4 number (a VC-4 timeslot on an optical port): For concatenated services, this parameter takes the number of the first VC-4. 10GV2: This parameter takes the value 1 if the sink board is GE02. This parameter takes the value 0 if the sink is a tributary board. This parameter indicates a VC-4 number if the sink is an Ethernet board."
        ::= { optixSdhXcEntry 10 }

    -- 1.3.6.1.4.1.2011.2.25.4.10.49.1.1.1.11
    optixShdXcSinkLP OBJECT-TYPE
        SYNTAX Unsigned32
        MAX-ACCESS read-only
        STATUS current
        DESCRIPTION
            "This object indicates the sink lower order path ID of the cross-connection. For higher order services, this parameter is 0; for lower order services, this parameter indicates the sink lower order path number. For VC-12 services, the value ranges from 1 to 63; for VC-3 services, the value ranges from 1 to 3. This parameter takes the value 0 if the sink is a tributary board. If the sink is a 10M/100M Ethernet board, this parameter is the VC-3 number within a VC-4 and the value ranges from 1 to 3."
        ::= { optixSdhXcEntry 11 }

    -- 1.3.6.1.4.1.2011.2.25.4.10.49.1.1.1.12
    optixSdhXcLevel OBJECT-TYPE
        SYNTAX INTEGER
        {
            allLevel(0),
            vc12(6),
            vc3(7),
            vc4(1),
            au4V4c(2),
            au4V8c(3),
            au4V16c(4),
            au4V64c(5),
            au3(9)
        }
        MAX-ACCESS read-only
        STATUS current
        DESCRIPTION
            "This object indicates the cross-connection level. 0: allLevel, 6: vc12, 7: vc3, 1: vc4, 2: au4V4c, 3: au4V8c, 4: au4V16c, 5: au4V64c, 9: au3"
        ::= { optixSdhXcEntry 12 }

    -- 1.3.6.1.4.1.2011.2.25.4.10.49.1.1.1.13
    optixSdhXcState OBJECT-TYPE
        SYNTAX INTEGER
        {
            adding(1),
            deleting(2),
            active(3)
        }
        MAX-ACCESS read-only
        STATUS current
        DESCRIPTION
            "This object indicates the current status of the cross-connection. 1: adding, 2: deleting, 3: active"
        ::= { optixSdhXcEntry 13 }

    -- 1.3.6.1.4.1.2011.2.25.4.10.49.1.1.1.255
    optixSdhXcRowStatus OBJECT-TYPE
        SYNTAX RowStatus
        MAX-ACCESS read-only
        STATUS current
        DESCRIPTION
            "This object indicates the row status of the cross-connection."
        ::= { optixSdhXcEntry 255 }

    -- 1.3.6.1.4.1.2011.2.25.4.10.49.1.2
    optixSdhXcEXTTable OBJECT-TYPE
        SYNTAX SEQUENCE OF OptixSdhXcEXTEntry
        MAX-ACCESS not-accessible
        STATUS current
        DESCRIPTION
            "This table describes EXT cross-connection configurations."
        ::= { optixSdhXcGroup 2 }

    -- 1.3.6.1.4.1.2011.2.25.4.10.49.1.2.1
    optixSdhXcEXTEntry OBJECT-TYPE
        SYNTAX OptixSdhXcEXTEntry
        MAX-ACCESS not-accessible
        STATUS current
        DESCRIPTION
            "Thisentry describes V2 cross-connection configurations."
        INDEX{ optixSdhXcSrcBid,optixSdhXcSrcSubid,optixSdhXcSrcPid,optixSdhXcSrcHP,optixSdhXcSrcLP,optixSdhXcSinkBid,optixSdhXcSinkSubid,optixSdhXcSinkPid,optixSdhXcSinkHP,optixShdXcSinkLP,optixSdhXcLevel }
        ::= { optixSdhXcEXTTable 1 }

    OptixSdhXcEXTEntry ::=
        SEQUENCE {
            optixSdhXcEXTId
                Unsigned32,
            optixSdhXcEXTState
                INTEGER,
            optixSdhXcE1SrvPriority
                INTEGER,
            optixSdhXcEXTRowStatus
                RowStatus
        }

    -- 1.3.6.1.4.1.2011.2.25.4.10.49.1.2.1.1
    optixSdhXcEXTId OBJECT-TYPE
        SYNTAX Unsigned32
        MAX-ACCESS read-create
        STATUS current
        DESCRIPTION
            "This object indicates the V2 cross-connection ID."
        ::= { optixSdhXcEXTEntry 1 }

    -- 1.3.6.1.4.1.2011.2.25.4.10.49.1.2.1.2
    optixSdhXcEXTState OBJECT-TYPE
        SYNTAX INTEGER
        {
            adding(1),
            deleting(2),
            active(3)
        }
        MAX-ACCESS read-only
        STATUS current
        DESCRIPTION
            "This object indicates the current status of the V2 cross-connection. 1: adding, 2: deleting, 3: active"
        ::= { optixSdhXcEXTEntry 2 }

    -- 1.3.6.1.4.1.2011.2.25.4.10.49.1.2.1.3
    optixSdhXcE1SrvPriority OBJECT-TYPE
        SYNTAX INTEGER
        {
            level0(0),
            level1(1),
            levelNO(255)
        }
        MAX-ACCESS read-create
        STATUS current
        DESCRIPTION
            "This object indicates the service priority level of E1 port. 0: level0, 1: level1, 255: levelNO"
        ::= { optixSdhXcEXTEntry 3 }

    -- 1.3.6.1.4.1.2011.2.25.4.10.49.1.2.1.255
    optixSdhXcEXTRowStatus OBJECT-TYPE
        SYNTAX RowStatus
        MAX-ACCESS read-create
        STATUS current
        DESCRIPTION
            "This object indicates the row status of the V2 cross-connection."
        ::= { optixSdhXcEXTEntry 255 }

    -- 1.3.6.1.4.1.2011.2.25.4.10.49.1.5
    optixSdhSncpToXcTable OBJECT-TYPE
        SYNTAX SEQUENCE OF OptixSdhSncpToXcEntry
        MAX-ACCESS not-accessible
        STATUS current
        DESCRIPTION
            "This table implements conversion from SNCPs to cross-connections."
        ::= { optixSdhXcGroup 5 }

    -- 1.3.6.1.4.1.2011.2.25.4.10.49.1.5.1
    optixSdhSncpToXcEntry OBJECT-TYPE
        SYNTAX OptixSdhSncpToXcEntry
        MAX-ACCESS not-accessible
        STATUS current
        DESCRIPTION
            "This entry implements conversion from SNCPs to cross-connections."
        INDEX{ optixSdhSncpToXcPGIdExt,optixSdhSncpToXcPUIdExt,optixSdhXcEXTId }
        ::= { optixSdhSncpToXcTable 1 }

    OptixSdhSncpToXcEntry ::=
        SEQUENCE {
            optixSdhSncpToXcConvert
                INTEGER,
            optixSdhSncpToXcPGIdExt
                Unsigned32,
            optixSdhSncpToXcPUIdExt
                Unsigned32
        }

    -- 1.3.6.1.4.1.2011.2.25.4.10.49.1.5.1.1
    optixSdhSncpToXcConvert OBJECT-TYPE
        SYNTAX INTEGER
        {
            convert(0)
        }
        MAX-ACCESS read-write
        STATUS current
        DESCRIPTION
            "This object is used to implement conversion from SNCPs to cross-connections. No query result is available."
        ::= { optixSdhSncpToXcEntry 1 }

    -- 1.3.6.1.4.1.2011.2.25.4.10.49.1.5.1.2
    optixSdhSncpToXcPGIdExt OBJECT-TYPE
        SYNTAX Unsigned32
        MAX-ACCESS not-accessible
        STATUS current
        DESCRIPTION
            "This object indicates the SNCP group ID."
        ::= { optixSdhSncpToXcEntry 2 }

    -- 1.3.6.1.4.1.2011.2.25.4.10.49.1.5.1.3
    optixSdhSncpToXcPUIdExt OBJECT-TYPE
        SYNTAX Unsigned32
        MAX-ACCESS not-accessible
        STATUS current
        DESCRIPTION
            "This object indicates the SNCPprotection unitID. Value range: 1 to 2016."
        ::= { optixSdhSncpToXcEntry 3 }

END
