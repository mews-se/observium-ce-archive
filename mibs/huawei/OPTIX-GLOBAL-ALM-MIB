-- OPTIX-GLOBAL-ALM-MIB
-- MIB generated by ExcelToMIB tool 1.0
-- 
-- =================================================================
--  Copyright (C) 2012 by HUAWEI TECHNOLOGIES. All rights reserved
--  Description:
-- Description:This MIB describes the Alarm interface of Huawei macrowave transmit
--  Reference:
--  Version: V1.00
--  History:
--  <author>,<date>,<contents>
-- =================================================================
--
OPTIX-GLOBAL-ALM-MIB DEFINITIONS ::= BEGIN
    IMPORTS
        optixCommonGlobal
            FROM OPTIX-OID-MIB
        optixGlobalTrap,rptEvtNumber,rptAlmName,rptEvtNtfcnCde,rptEvtState,rptEvtStartTime,rptEvtSrvEff,rptEvtObjType,rptEvtPara,rptEvtEndTime
            FROM OPTIX-GLOBAL-TRAPS-MIB
        AlarmEventType,AlmDataNtfcnCdeType,AlmDataSrvEffType,ObjType
            FROM OPTIX-GLOBAL-TC-MIB
        OBJECT-GROUP,MODULE-COMPLIANCE
            FROM SNMPv2-CONF
        Unsigned32,OBJECT-TYPE,MODULE-IDENTITY
            FROM SNMPv2-SMI
        DateAndTime
            FROM SNMPv2-TC
        ;

    optixGlobalAlarm MODULE-IDENTITY
        LAST-UPDATED "1003300000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Alarm module"
	REVISION "1003300000Z"
        DESCRIPTION
            "The initial version"
        ::={ optixCommonGlobal 30 }

    -- 1.3.6.1.4.1.2011.2.25.3.40.30.10
    queryAlmData OBJECT IDENTIFIER ::= { optixGlobalAlarm 10 }

    -- 1.3.6.1.4.1.2011.2.25.3.40.30.10.10
    curAlmDataTable OBJECT-TYPE
        SYNTAX SEQUENCE OF CurAlmDataEntry
        MAX-ACCESS not-accessible
        STATUS current
        DESCRIPTION
            "Indicates the current alarms on the NE."
        ::= { queryAlmData 10 }

    -- 1.3.6.1.4.1.2011.2.25.3.40.30.10.10.1
    curAlmDataEntry OBJECT-TYPE
        SYNTAX CurAlmDataEntry
        MAX-ACCESS not-accessible
        STATUS current
        DESCRIPTION
            "Indicates the entry node in the current alarm table."
        INDEX{ curAlmNUM }
        ::= { curAlmDataTable 1 }

    CurAlmDataEntry ::=
        SEQUENCE {
            curAlmNUM
                INTEGER,
            curAlmEID
                AlarmEventType,
            curAlmSeverity
                AlmDataNtfcnCdeType,
            curAlmState
                INTEGER,
            curAlmStartTime
                DateAndTime,
            curAlmEndTime
                DateAndTime,
            curAlmSrvEff
                AlmDataSrvEffType,
            curAlmObjType
                ObjType,
            curAlmPara
                OCTET STRING
        }

    -- 1.3.6.1.4.1.2011.2.25.3.40.30.10.10.1.1
    curAlmNUM OBJECT-TYPE
        SYNTAX INTEGER
        MAX-ACCESS read-only
        STATUS current
        DESCRIPTION
            "Indicates the current alarm number."
        ::= { curAlmDataEntry 1 }

    -- 1.3.6.1.4.1.2011.2.25.3.40.30.10.10.1.2
    curAlmEID OBJECT-TYPE
        SYNTAX AlarmEventType
        MAX-ACCESS read-only
        STATUS current
        DESCRIPTION
            "Indicates the current alarm ID."
        ::= { curAlmDataEntry 2 }

    -- 1.3.6.1.4.1.2011.2.25.3.40.30.10.10.1.3
    curAlmSeverity OBJECT-TYPE
        SYNTAX AlmDataNtfcnCdeType
        MAX-ACCESS read-only
        STATUS current
        DESCRIPTION
            "Indicates the alarm severity, which can be critical (CR), major (MJ), and minor (MN)."
        ::= { curAlmDataEntry 3 }

    -- 1.3.6.1.4.1.2011.2.25.3.40.30.10.10.1.4
    curAlmState OBJECT-TYPE
        SYNTAX INTEGER
        {
            start(1),
            end(3)
        }
        MAX-ACCESS read-only
        STATUS current
        DESCRIPTION
            "Indicates the current alarm status."
        ::= { curAlmDataEntry 4 }

    -- 1.3.6.1.4.1.2011.2.25.3.40.30.10.10.1.5
    curAlmStartTime OBJECT-TYPE
        SYNTAX DateAndTime
        MAX-ACCESS read-only
        STATUS current
        DESCRIPTION
            "Indicates the start time of current alarm."
        ::= { curAlmDataEntry 5 }

    -- 1.3.6.1.4.1.2011.2.25.3.40.30.10.10.1.6
    curAlmEndTime OBJECT-TYPE
        SYNTAX DateAndTime
        MAX-ACCESS read-only
        STATUS current
        DESCRIPTION
            "Indicates the end time of current alarm."
        ::= { curAlmDataEntry 6 }

    -- 1.3.6.1.4.1.2011.2.25.3.40.30.10.10.1.7
    curAlmSrvEff OBJECT-TYPE
        SYNTAX AlmDataSrvEffType
        MAX-ACCESS read-only
        STATUS current
        DESCRIPTION
            "Indicates whether services are affected by current alarm."
        ::= { curAlmDataEntry 7 }

    -- 1.3.6.1.4.1.2011.2.25.3.40.30.10.10.1.8
    curAlmObjType OBJECT-TYPE
        SYNTAX ObjType
        MAX-ACCESS read-only
        STATUS current
        DESCRIPTION
            "Indicates current alarm object type."
        ::= { curAlmDataEntry 8 }

    -- 1.3.6.1.4.1.2011.2.25.3.40.30.10.10.1.9
    curAlmPara OBJECT-TYPE
        SYNTAX OCTET STRING (SIZE (0..128))
        MAX-ACCESS read-only
        STATUS current
        DESCRIPTION
            "Indicates current alarm parameter."
        ::= { curAlmDataEntry 9 }

    -- 1.3.6.1.4.1.2011.2.25.3.40.30.10.20
    hisAlmDataTable OBJECT-TYPE
        SYNTAX SEQUENCE OF HisAlmDataEntry
        MAX-ACCESS not-accessible
        STATUS current
        DESCRIPTION
            "Indicates the historical alarm table."
        ::= { queryAlmData 20 }

    -- 1.3.6.1.4.1.2011.2.25.3.40.30.10.20.1
    hisAlmDataEntry OBJECT-TYPE
        SYNTAX HisAlmDataEntry
        MAX-ACCESS not-accessible
        STATUS current
        DESCRIPTION
            "Indicates the entry node in the historical alarm table."
        INDEX{ hisAlmNUM }
        ::= { hisAlmDataTable 1 }

    HisAlmDataEntry ::=
        SEQUENCE {
            hisAlmNUM
                INTEGER,
            hisAlmEID
                AlarmEventType,
            hisAlmSeverity
                AlmDataNtfcnCdeType,
            hisAlmState
                INTEGER,
            hisAlmStartTime
                DateAndTime,
            hisAlmEndTime
                DateAndTime,
            hisAlmSrvEff
                AlmDataSrvEffType,
            hisAlmObjType
                ObjType,
            hisAlmPara
                OCTET STRING
        }

    -- 1.3.6.1.4.1.2011.2.25.3.40.30.10.20.1.1
    hisAlmNUM OBJECT-TYPE
        SYNTAX INTEGER
        MAX-ACCESS read-only
        STATUS current
        DESCRIPTION
            "Indicates the historical alarm number."
        ::= { hisAlmDataEntry 1 }

    -- 1.3.6.1.4.1.2011.2.25.3.40.30.10.20.1.2
    hisAlmEID OBJECT-TYPE
        SYNTAX AlarmEventType
        MAX-ACCESS read-only
        STATUS current
        DESCRIPTION
            "Indicates the historical alarm ID."
        ::= { hisAlmDataEntry 2 }

    -- 1.3.6.1.4.1.2011.2.25.3.40.30.10.20.1.3
    hisAlmSeverity OBJECT-TYPE
        SYNTAX AlmDataNtfcnCdeType
        MAX-ACCESS read-only
        STATUS current
        DESCRIPTION
            "Indicates the historical alarm severity, which can be critical (CR), major (MJ), and minor (MN)."
        ::= { hisAlmDataEntry 3 }

    -- 1.3.6.1.4.1.2011.2.25.3.40.30.10.20.1.4
    hisAlmState OBJECT-TYPE
        SYNTAX INTEGER
        {
            start(1),
            end(3)
        }
        MAX-ACCESS read-only
        STATUS current
        DESCRIPTION
            "Indicates the historical alarm status."
        ::= { hisAlmDataEntry 4 }

    -- 1.3.6.1.4.1.2011.2.25.3.40.30.10.20.1.5
    hisAlmStartTime OBJECT-TYPE
        SYNTAX DateAndTime
        MAX-ACCESS read-only
        STATUS current
        DESCRIPTION
            "Indicates the start time of a historical alarm."
        ::= { hisAlmDataEntry 5 }

    -- 1.3.6.1.4.1.2011.2.25.3.40.30.10.20.1.6
    hisAlmEndTime OBJECT-TYPE
        SYNTAX DateAndTime
        MAX-ACCESS read-only
        STATUS current
        DESCRIPTION
            "Indicates the end time of a historical alarm."
        ::= { hisAlmDataEntry 6 }

    -- 1.3.6.1.4.1.2011.2.25.3.40.30.10.20.1.7
    hisAlmSrvEff OBJECT-TYPE
        SYNTAX AlmDataSrvEffType
        MAX-ACCESS read-only
        STATUS current
        DESCRIPTION
            "Indicates whether the historical alarm affects services."
        ::= { hisAlmDataEntry 7 }

    -- 1.3.6.1.4.1.2011.2.25.3.40.30.10.20.1.8
    hisAlmObjType OBJECT-TYPE
        SYNTAX ObjType
        MAX-ACCESS read-only
        STATUS current
        DESCRIPTION
            "Indicates the historical alarm object type."
        ::= { hisAlmDataEntry 8 }

    -- 1.3.6.1.4.1.2011.2.25.3.40.30.10.20.1.9
    hisAlmPara OBJECT-TYPE
        SYNTAX OCTET STRING (SIZE (0..128))
        MAX-ACCESS read-only
        STATUS current
        DESCRIPTION
            "Indicates the historical alarm parameter."
        ::= { hisAlmDataEntry 9 }

END
