-- OPTIX-GLOBAL-PER-TIME-MIB
-- MIB generated by ExcelToMIB tool 1.0
-- 
-- =================================================================
--  Copyright (C) 2012 by HUAWEI TECHNOLOGIES. All rights reserved
--  Description:This MIB describes the Performance interface of Huawei microwave transmit
--  Reference:
--  Version: V1.00
--  History:
--  <author>,<date>,<contents>
-- =================================================================
--
OPTIX-GLOBAL-PER-TIME-MIB DEFINITIONS ::= BEGIN
    IMPORTS
        optixCommonGlobal
            FROM OPTIX-OID-MIB
        PerformanceEventType,ValidflagType
            FROM OPTIX-GLOBAL-TC-MIB
        OBJECT-GROUP,MODULE-COMPLIANCE
            FROM SNMPv2-CONF
        Integer32,Unsigned32,OBJECT-TYPE,MODULE-IDENTITY
            FROM SNMPv2-SMI
        DateAndTime,DisplayString
            FROM SNMPv2-TC
        ;

    optixGlobalPER MODULE-IDENTITY
        LAST-UPDATED "200805240500Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "SDH performance module"
        REVISION "200805240500Z"
        DESCRIPTION
            "The initial version"
        ::={ optixCommonGlobal 20 }

    -- 1.3.6.1.4.1.2011.2.25.3.40.20.10
    perMonitorTime OBJECT IDENTIFIER ::= { optixGlobalPER 10 }

    -- 1.3.6.1.4.1.2011.2.25.3.40.20.10.10
    per15mMonitorTime OBJECT IDENTIFIER ::= { perMonitorTime 10 }

    -- 1.3.6.1.4.1.2011.2.25.3.40.20.10.10.10
    per15mMonitorStartTime OBJECT-TYPE
        SYNTAX DateAndTime
        MAX-ACCESS read-write
        STATUS current
        DESCRIPTION
            "Indicates the start time and date of the 15-minute PM period. When the system is at this time, the 15-minute PM period monitoring starts. The start date and time of the 15-minute PM period cannot be set to be earlier than the current system date and time. When it is set to 1990-00-00 00:00:00, it indicates immediate start of the 15-minute PM period monitoring. A reset of the period will terminate the ongoing monitoring and start a new monitoring. When the 15-minute PM period expires, the start date and time of the 15-minute PM period will be reset to zero."
        ::= { per15mMonitorTime 10 }

    -- 1.3.6.1.4.1.2011.2.25.3.40.20.10.10.20
    per15mMonitorEndTime OBJECT-TYPE
        SYNTAX DateAndTime
        MAX-ACCESS read-write
        STATUS current
        DESCRIPTION
            "Indicates the end time and date of the 15-minute PM period. The end date and time of the 15-minute PM period must be set after the start date and time of the 15-minute PM period is set. And the end date and time of the 15-minute PM period must be later than the start date and time of the 15-minute PM period. When the end date and time of the 15-minute PM period is set to 1990-00-00 00:00:00, it indicates immediate end of the 15-minute PM period monitoring. When the 15-minute PM period expires, the end date and time of the 15-minute PM period will be reset to zero."
        ::= { per15mMonitorTime 20 }

    -- 1.3.6.1.4.1.2011.2.25.3.40.20.10.20
    per24hMonitorTime OBJECT IDENTIFIER ::= { perMonitorTime 20 }

    -- 1.3.6.1.4.1.2011.2.25.3.40.20.10.20.10
    per24hMonitorStartTime OBJECT-TYPE
        SYNTAX DateAndTime
        MAX-ACCESS read-write
        STATUS current
        DESCRIPTION
            "Indicates the start date and time of the 24-hour PM period. When the system is at this time, the 24-hour PM period monitoring starts. The start date and time of the 24-hour PM period cannot be set to be earlier than the current system date and time. When it is set to 1990-00-00 00:00:00, it indicates immediate start of the 24-hour PM period monitoring. A reset of the period will terminate the ongoing monitoring and start a new monitoring. When the 24-hour PM period expires, the start date and time of the 24-hour PM period will be reset to zero."
        ::= { per24hMonitorTime 10 }

    -- 1.3.6.1.4.1.2011.2.25.3.40.20.10.20.20
    per24hMonitorEndTime OBJECT-TYPE
        SYNTAX DateAndTime
        MAX-ACCESS read-write
        STATUS current
        DESCRIPTION
            "Indicates the end date and time of the 24-hour PM period. The end date and time of the 24-hour PM period must be set after the start date and time of the 24-hour PM period is set. And the end date and time of the 24-hour PM period must be later than the start date and time of the 24-hour PM period. When the end date and time of the 24-hour PM period is set to 1990-00-00 00:00:00, it indicates immediate end of the 24-hour PM period monitoring. When the 24-hour PM period expires, the end date and time of the 24-hour PM period will be reset to zero."
        ::= { per24hMonitorTime 20 }

END
