-- OPTIX-PKT-QOS-POLICY-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-QOS-POLICY-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        ;

    optixPktQosPolicy MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the QOS service configuration information of device"
        REVISION "201204200000Z"
        DESCRIPTION
            "The initial revision of this MIB module1."
        ::={ optixProvisionPtn 32 }

    -- 1.3.6.1.4.1.2011.2.25.4.50.32.1
    optixPktQosPolicyGroup OBJECT IDENTIFIER ::= { optixPktQosPolicy 1 }

    -- 1.3.6.1.4.1.2011.2.25.4.50.32.1.1
    optixWRRTable OBJECT-TYPE
        SYNTAX SEQUENCE OF OptixWRREntry
        MAX-ACCESS not-accessible
        STATUS current
        DESCRIPTION
            "This table describes the basic QoS WRR scheduling configurations."
        ::= { optixPktQosPolicyGroup 1 }

    -- 1.3.6.1.4.1.2011.2.25.4.50.32.1.1.1
    optixWRREntry OBJECT-TYPE
        SYNTAX OptixWRREntry
        MAX-ACCESS not-accessible
        STATUS current
        DESCRIPTION
            "This entry describes the basic QoS WRR scheduling configurations."
        INDEX{ optixWRRId }
        ::= { optixWRRTable 1 }

    OptixWRREntry ::=
        SEQUENCE {
            optixWRRId
                Unsigned32,
            optixWRRCs7Weight
                Unsigned32,
            optixWRRCs6Weight
                Unsigned32,
            optixWRREfWeight
                Unsigned32,
            optixWRRAf4Weight
                Unsigned32,
            optixWRRAf3Weight
                Unsigned32,
            optixWRRAf2Weight
                Unsigned32,
            optixWRRAf1Weight
                Unsigned32,
            optixWRRBeWeight
                Unsigned32,
            optixWRRInfo
                OCTET STRING,
            optixWRRRowStatus
                RowStatus
        }

    -- 1.3.6.1.4.1.2011.2.25.4.50.32.1.1.1.1
    optixWRRId OBJECT-TYPE
        SYNTAX Unsigned32
        MAX-ACCESS not-accessible
        STATUS current
        DESCRIPTION
            "This object indicates the WRR scheduling ID of the QoS module. Value range for RTN equipment: 0 to 128."
        ::= { optixWRREntry 1 }

    -- 1.3.6.1.4.1.2011.2.25.4.50.32.1.1.1.2
    optixWRRCs7Weight OBJECT-TYPE
        SYNTAX Unsigned32
        MAX-ACCESS read-create
        STATUS current
        DESCRIPTION
            "This object indicates the CS7 scheduling weight of the QoS module. Value range: 0 to 100."
        ::= { optixWRREntry 2 }

    -- 1.3.6.1.4.1.2011.2.25.4.50.32.1.1.1.3
    optixWRRCs6Weight OBJECT-TYPE
        SYNTAX Unsigned32
        MAX-ACCESS read-create
        STATUS current
        DESCRIPTION
            "This object indicates the CS6 scheduling weight of the QoS module. Value range: 0 to 100."
        ::= { optixWRREntry 3 }

    -- 1.3.6.1.4.1.2011.2.25.4.50.32.1.1.1.4
    optixWRREfWeight OBJECT-TYPE
        SYNTAX Unsigned32
        MAX-ACCESS read-create
        STATUS current
        DESCRIPTION
            "This object indicates the EF scheduling weight of the QoS module. Value range: 0 to 100."
        ::= { optixWRREntry 4 }

    -- 1.3.6.1.4.1.2011.2.25.4.50.32.1.1.1.5
    optixWRRAf4Weight OBJECT-TYPE
        SYNTAX Unsigned32
        MAX-ACCESS read-create
        STATUS current
        DESCRIPTION
            "This object indicates the AF4 scheduling weight of the QoS module. Value range: 0 to 100."
        ::= { optixWRREntry 5 }

    -- 1.3.6.1.4.1.2011.2.25.4.50.32.1.1.1.6
    optixWRRAf3Weight OBJECT-TYPE
        SYNTAX Unsigned32
        MAX-ACCESS read-create
        STATUS current
        DESCRIPTION
            "This object indicates the AF3 scheduling weight of the QoS module. Value range: 0 to 100."
        ::= { optixWRREntry 6 }

    -- 1.3.6.1.4.1.2011.2.25.4.50.32.1.1.1.7
    optixWRRAf2Weight OBJECT-TYPE
        SYNTAX Unsigned32
        MAX-ACCESS read-create
        STATUS current
        DESCRIPTION
            "This object indicates the AF2 scheduling weight of the QoS module. Value range: 0 to 100."
        ::= { optixWRREntry 7 }

    -- 1.3.6.1.4.1.2011.2.25.4.50.32.1.1.1.8
    optixWRRAf1Weight OBJECT-TYPE
        SYNTAX Unsigned32
        MAX-ACCESS read-create
        STATUS current
        DESCRIPTION
            "This object indicates the AF1 scheduling weight of the QoS module. Value range: 0 to 100."
        ::= { optixWRREntry 8 }

    -- 1.3.6.1.4.1.2011.2.25.4.50.32.1.1.1.9
    optixWRRBeWeight OBJECT-TYPE
        SYNTAX Unsigned32
        MAX-ACCESS read-create
        STATUS current
        DESCRIPTION
            "This object indicates the BF scheduling weight of the QoS module. Value range: 0 to 100."
        ::= { optixWRREntry 9 }

    -- 1.3.6.1.4.1.2011.2.25.4.50.32.1.1.1.10
    optixWRRInfo OBJECT-TYPE
        SYNTAX OCTET STRING (SIZE(0..64))
        MAX-ACCESS read-create
        STATUS current
        DESCRIPTION
            "This object indicates the WRR scheduling information of the QoS module."
        ::= { optixWRREntry 10 }

    -- 1.3.6.1.4.1.2011.2.25.4.50.32.1.1.1.255
    optixWRRRowStatus OBJECT-TYPE
        SYNTAX RowStatus
        MAX-ACCESS read-create
        STATUS current
        DESCRIPTION
            "This object indicates the WRR scheduling row status of the QoS module."
        ::= { optixWRREntry 255 }

    -- 1.3.6.1.4.1.2011.2.25.4.50.32.1.2
    optixPolicyTable OBJECT-TYPE
        SYNTAX SEQUENCE OF OptixPolicyEntry
        MAX-ACCESS not-accessible
        STATUS current
        DESCRIPTION
            "This table describes the basic QoS policy configurations."
        ::= { optixPktQosPolicyGroup 2 }

    -- 1.3.6.1.4.1.2011.2.25.4.50.32.1.2.1
    optixPolicyEntry OBJECT-TYPE
        SYNTAX OptixPolicyEntry
        MAX-ACCESS not-accessible
        STATUS current
        DESCRIPTION
            "This entry describes the basic QoS policy configurations."
        INDEX{ optixPolicyType,optixPolicyId }
        ::= { optixPolicyTable 1 }

    OptixPolicyEntry ::=
        SEQUENCE {
            optixPolicyType
                INTEGER,
            optixPolicyId
                Unsigned32,
            optixPolicyClassifierShareFlag
                INTEGER,
            optixPolicyWfqId
                Unsigned32,
            optixPolicyInfo
                OCTET STRING,
            optixPolicyIndex1
                Unsigned32,
            optixPolicyIndex2
                Unsigned32,
            optixPolicyIndex3
                Unsigned32,
            optixPolicyDirection
                INTEGER,
            optixPolicyCs7Weight
                INTEGER,
            optixPolicyCs6Weight
                INTEGER,
            optixPolicyEfWeight
                INTEGER,
            optixPolicyAf4Weight
                INTEGER,
            optixPolicyAf3Weight
                INTEGER,
            optixPolicyAf2Weight
                INTEGER,
            optixPolicyAf1Weight
                INTEGER,
            optixPolicyBeWeight
                INTEGER,
            optixPolicyRowStatus
                RowStatus
        }

    -- 1.3.6.1.4.1.2011.2.25.4.50.32.1.2.1.1
    optixPolicyType OBJECT-TYPE
        SYNTAX INTEGER
        {
            port(1),
            vuniingress(2),
            vuniegress(3),
            pw(4),
            atm(5),
            qinq(6)
        }
        MAX-ACCESS not-accessible
        STATUS current
        DESCRIPTION
            "This object indicates the QoS policy type of the QoS module. 1: port, 2: vuniingress, 3: vuniegress, 4: pw, 5: atm, 6: qinq"
        ::= { optixPolicyEntry 1 }

    -- 1.3.6.1.4.1.2011.2.25.4.50.32.1.2.1.2
    optixPolicyId OBJECT-TYPE
        SYNTAX Unsigned32
        MAX-ACCESS not-accessible
        STATUS current
        DESCRIPTION
            "This object indicates the QoS policyvalue of the QoS module. Value range for ATM: 0 to 1024. Value range for PORT: 0 to 256. Value range for VUNIINGRESS: 1 to 1024 (for RTN 950 and RTN 950A: 1 to 256)."
        ::= { optixPolicyEntry 2 }

    -- 1.3.6.1.4.1.2011.2.25.4.50.32.1.2.1.3
    optixPolicyClassifierShareFlag OBJECT-TYPE
        SYNTAX INTEGER
        {
            disable(1),
            enable(2),
            none(255)
        }
        MAX-ACCESS read-only
        STATUS current
        DESCRIPTION
            "This object indicates the flow classification instance flag. 1: disable, 2: enable, 255: none"
        ::= { optixPolicyEntry 3 }

    -- 1.3.6.1.4.1.2011.2.25.4.50.32.1.2.1.4
    optixPolicyWfqId OBJECT-TYPE
        SYNTAX Unsigned32
        MAX-ACCESS read-only
        STATUS current
        DESCRIPTION
            "This object indicates the WFQ scheduling ID of the QoS module."
        ::= { optixPolicyEntry 4 }

    -- 1.3.6.1.4.1.2011.2.25.4.50.32.1.2.1.5
    optixPolicyInfo OBJECT-TYPE
        SYNTAX OCTET STRING (SIZE(0..64))
        MAX-ACCESS read-only
        STATUS current
        DESCRIPTION
            "This object indicates the QoS policyinformation of the QoS module."
        ::= { optixPolicyEntry 5 }

    -- 1.3.6.1.4.1.2011.2.25.4.50.32.1.2.1.6
    optixPolicyIndex1 OBJECT-TYPE
        SYNTAX Unsigned32
        MAX-ACCESS read-only
        STATUS current
        DESCRIPTION
            "This object indicates the policy index 1 of the QoS module."
        ::= { optixPolicyEntry 6 }

    -- 1.3.6.1.4.1.2011.2.25.4.50.32.1.2.1.7
    optixPolicyIndex2 OBJECT-TYPE
        SYNTAX Unsigned32
        MAX-ACCESS read-only
        STATUS current
        DESCRIPTION
            "This object indicates the policy index 2 of the QoS module."
        ::= { optixPolicyEntry 7 }

    -- 1.3.6.1.4.1.2011.2.25.4.50.32.1.2.1.8
    optixPolicyIndex3 OBJECT-TYPE
        SYNTAX Unsigned32
        MAX-ACCESS read-only
        STATUS current
        DESCRIPTION
            "This object indicates the policy index 3 of the QoS module."
        ::= { optixPolicyEntry 8 }

    -- 1.3.6.1.4.1.2011.2.25.4.50.32.1.2.1.9
    optixPolicyDirection OBJECT-TYPE
        SYNTAX INTEGER
        {
            ingress(1),
            egress(2),
            none(255),
            all(0)
        }
        MAX-ACCESS read-only
        STATUS current
        DESCRIPTION
            "This object indicates the policy direction of the QoS module.1: ingress, 2: egress, 255: none, 0: all"
        ::= { optixPolicyEntry 9 }

    -- 1.3.6.1.4.1.2011.2.25.4.50.32.1.2.1.10
    optixPolicyCs7Weight OBJECT-TYPE
        SYNTAX INTEGER
        {
            sp(1),
            wrr(2),
            wfq(3),
            drr(4),
            none(255)
        }
        MAX-ACCESS read-only
        STATUS current
        DESCRIPTION
            "This object indicates the CS7 scheduling weight of the QoS module. 1: sp, 2: wrr, 3: wfq, 4: drr, 255: none"
        ::= { optixPolicyEntry 10 }

    -- 1.3.6.1.4.1.2011.2.25.4.50.32.1.2.1.11
    optixPolicyCs6Weight OBJECT-TYPE
        SYNTAX INTEGER
        {
            sp(1),
            wrr(2),
            wfq(3),
            drr(4),
            none(255)
        }
        MAX-ACCESS read-only
        STATUS current
        DESCRIPTION
            "This object indicates the CS6 scheduling weight of the QoS module. 1: sp, 2: wrr, 3: wfq, 4: drr, 255: none"
        ::= { optixPolicyEntry 11 }

    -- 1.3.6.1.4.1.2011.2.25.4.50.32.1.2.1.12
    optixPolicyEfWeight OBJECT-TYPE
        SYNTAX INTEGER
        {
            sp(1),
            wrr(2),
            wfq(3),
            drr(4),
            none(255)
        }
        MAX-ACCESS read-only
        STATUS current
        DESCRIPTION
            "This object indicates the EF scheduling weight of the QoS module. 1: sp, 2: wrr, 3: wfq, 4: drr, 255: none"
        ::= { optixPolicyEntry 12 }

    -- 1.3.6.1.4.1.2011.2.25.4.50.32.1.2.1.13
    optixPolicyAf4Weight OBJECT-TYPE
        SYNTAX INTEGER
        {
            sp(1),
            wrr(2),
            wfq(3),
            drr(4),
            none(255)
        }
        MAX-ACCESS read-only
        STATUS current
        DESCRIPTION
            "This object indicates the AF4 scheduling weight of the QoS module. 1: sp, 2: wrr, 3: wfq, 4: drr, 255: none"
        ::= { optixPolicyEntry 13 }

    -- 1.3.6.1.4.1.2011.2.25.4.50.32.1.2.1.14
    optixPolicyAf3Weight OBJECT-TYPE
        SYNTAX INTEGER
        {
            sp(1),
            wrr(2),
            wfq(3),
            drr(4),
            none(255)
        }
        MAX-ACCESS read-only
        STATUS current
        DESCRIPTION
            "This object indicates the AF3 scheduling weight of the QoS module. 1: sp, 2: wrr, 3: wfq, 4: drr, 255: none"
        ::= { optixPolicyEntry 14 }

    -- 1.3.6.1.4.1.2011.2.25.4.50.32.1.2.1.15
    optixPolicyAf2Weight OBJECT-TYPE
        SYNTAX INTEGER
        {
            sp(1),
            wrr(2),
            wfq(3),
            drr(4),
            none(255)
        }
        MAX-ACCESS read-only
        STATUS current
        DESCRIPTION
            "This object indicates the AF2 scheduling weight of the QoS module. 1: sp, 2: wrr, 3: wfq, 4: drr, 255: none"
        ::= { optixPolicyEntry 15 }

    -- 1.3.6.1.4.1.2011.2.25.4.50.32.1.2.1.16
    optixPolicyAf1Weight OBJECT-TYPE
        SYNTAX INTEGER
        {
            sp(1),
            wrr(2),
            wfq(3),
            drr(4),
            none(255)
        }
        MAX-ACCESS read-only
        STATUS current
        DESCRIPTION
            "This object indicates the AF1 scheduling weight of the QoS module. 1: sp, 2: wrr, 3: wfq, 4: drr, 255: none"
        ::= { optixPolicyEntry 16 }

    -- 1.3.6.1.4.1.2011.2.25.4.50.32.1.2.1.17
    optixPolicyBeWeight OBJECT-TYPE
        SYNTAX INTEGER
        {
            sp(1),
            wrr(2),
            wfq(3),
            drr(4),
            none(255)
        }
        MAX-ACCESS read-only
        STATUS current
        DESCRIPTION
            "This object indicates the BE scheduling weight of the QoS module. 1: sp, 2: wrr, 3: wfq, 4: drr, 255: none"
        ::= { optixPolicyEntry 17 }

    -- 1.3.6.1.4.1.2011.2.25.4.50.32.1.2.1.255
    optixPolicyRowStatus OBJECT-TYPE
        SYNTAX RowStatus
        MAX-ACCESS read-only
        STATUS current
        DESCRIPTION
            "This object indicates the QoS row status of the QoS module."
        ::= { optixPolicyEntry 255 }

    -- 1.3.6.1.4.1.2011.2.25.4.50.32.1.3
    optixPolicyQueueTable OBJECT-TYPE
        SYNTAX SEQUENCE OF OptixPolicyQueueEntry
        MAX-ACCESS not-accessible
        STATUS current
        DESCRIPTION
            "This table describes the basic flow classification configurations of the QoS policy ."
        ::= { optixPktQosPolicyGroup 3 }

    -- 1.3.6.1.4.1.2011.2.25.4.50.32.1.3.1
    optixPolicyQueueEntry OBJECT-TYPE
        SYNTAX OptixPolicyQueueEntry
        MAX-ACCESS not-accessible
        STATUS current
        DESCRIPTION
            "This entry describes the basic flow classification configurations of the QoS policy ."
        INDEX{ optixPolicyType,optixPolicyId,optixPolicyQueueType }
        ::= { optixPolicyQueueTable 1 }

    OptixPolicyQueueEntry ::=
        SEQUENCE {
            optixPolicyQueueType
                INTEGER,
            optixPolicyQueueCir
                Unsigned32,
            optixPolicyQueueCbs
                Unsigned32,
            optixPolicyQueuePir
                Unsigned32,
            optixPolicyQueuePbs
                Unsigned32,
            optixPolicyQueueTaildrop
                Unsigned32,
            optixPolicyQueueWredId
                Unsigned32,
            optixPolicyQueueRowStatus
                RowStatus
        }

    -- 1.3.6.1.4.1.2011.2.25.4.50.32.1.3.1.1
    optixPolicyQueueType OBJECT-TYPE
        SYNTAX INTEGER
        {
            cs7(1),
            cs6(2),
            ef(3),
            af4(4),
            af3(5),
            af2(6),
            af1(7),
            be(8),
            all(0),
            none(255)
        }
        MAX-ACCESS not-accessible
        STATUS current
        DESCRIPTION
            "This object indicates the policy queue type of the QoS module."
        ::= { optixPolicyQueueEntry 1 }

    -- 1.3.6.1.4.1.2011.2.25.4.50.32.1.3.1.2
    optixPolicyQueueCir OBJECT-TYPE
        SYNTAX Unsigned32
        MAX-ACCESS read-create
        STATUS current
        DESCRIPTION
            "This object indicates the policy queue CIR of the QoS module. Value range: MIN_ETH_CIR to MAX_ETH_CIR (unit: Kbit/s) For CS7, CS6, and EF, the value must be PIR. The bandwidth granularity (step length) is determined by each board and is set to a value closest to a specified value."
        ::= { optixPolicyQueueEntry 2 }

    -- 1.3.6.1.4.1.2011.2.25.4.50.32.1.3.1.3
    optixPolicyQueueCbs OBJECT-TYPE
        SYNTAX Unsigned32
        MAX-ACCESS read-create
        STATUS current
        DESCRIPTION
            "This object indicates the policy queue CBS of the QoS module. Value range: MIN_ETH_CBS to MAX_ETH_CBS (unit: byte)."
        ::= { optixPolicyQueueEntry 3 }

    -- 1.3.6.1.4.1.2011.2.25.4.50.32.1.3.1.4
    optixPolicyQueuePir OBJECT-TYPE
        SYNTAX Unsigned32
        MAX-ACCESS read-create
        STATUS current
        DESCRIPTION
            "This object indicates the policy queue PIR of the QoS module. Value range: MIN_ETH_CIR to MAX_ETH_CIR (unit: Kbit/s) For CS7, CS6, and EF, the value must be PIR. The bandwidth granularity (step length) is determined by each board and is set to a value closest to a specified value."
        ::= { optixPolicyQueueEntry 4 }

    -- 1.3.6.1.4.1.2011.2.25.4.50.32.1.3.1.5
    optixPolicyQueuePbs OBJECT-TYPE
        SYNTAX Unsigned32
        MAX-ACCESS read-create
        STATUS current
        DESCRIPTION
            "This object indicates the policy queue PBS of the QoS module. Value range: MIN_ETH_PBS to MAX_ETH_PBS (unit: byte)."
        ::= { optixPolicyQueueEntry 5 }

    -- 1.3.6.1.4.1.2011.2.25.4.50.32.1.3.1.6
    optixPolicyQueueTaildrop OBJECT-TYPE
        SYNTAX Unsigned32
        MAX-ACCESS read-create
        STATUS current
        DESCRIPTION
            "This object indicates the thresholdof droppingtail policies of the QoS module. Value range: 0 to 4095. The default value is 65535."
        ::= { optixPolicyQueueEntry 6 }

    -- 1.3.6.1.4.1.2011.2.25.4.50.32.1.3.1.7
    optixPolicyQueueWredId OBJECT-TYPE
        SYNTAX Unsigned32
        MAX-ACCESS read-create
        STATUS current
        DESCRIPTION
            "This object indicates the WRED ID of the QoS module. Value range for port: 0 to 8. Value range for service: 0 to 127."
        ::= { optixPolicyQueueEntry 7 }

    -- 1.3.6.1.4.1.2011.2.25.4.50.32.1.3.1.255
    optixPolicyQueueRowStatus OBJECT-TYPE
        SYNTAX RowStatus
        MAX-ACCESS read-create
        STATUS current
        DESCRIPTION
            "This object indicates the QoS queue row status of the QoS module."
        ::= { optixPolicyQueueEntry 255 }

    -- 1.3.6.1.4.1.2011.2.25.4.50.32.1.4
    optixAtmPolicyTable OBJECT-TYPE
        SYNTAX SEQUENCE OF OptixAtmPolicyEntry
        MAX-ACCESS not-accessible
        STATUS current
        DESCRIPTION
            "This table describes the basicATM policy configurations."
        ::= { optixPktQosPolicyGroup 4 }

    -- 1.3.6.1.4.1.2011.2.25.4.50.32.1.4.1
    optixAtmPolicyEntry OBJECT-TYPE
        SYNTAX OptixAtmPolicyEntry
        MAX-ACCESS not-accessible
        STATUS current
        DESCRIPTION
            "Thisentry describes the basic ATM policy configurations."
        INDEX{ optixPolicyType,optixPolicyId }
        ::= { optixAtmPolicyTable 1 }

    OptixAtmPolicyEntry ::=
        SEQUENCE {
            optixAtmPolicyCategory
                INTEGER,
            optixAtmPolicyTrafficType
                INTEGER,
            optixAtmPolicyPara1
                Unsigned32,
            optixAtmPolicyPara2
                Unsigned32,
            optixAtmPolicyPara3
                Unsigned32,
            optixAtmPolicyPara4
                Unsigned32,
            optixAtmPolicyFrameDiscardFlag
                INTEGER,
            optixAtmPolicyUPCNPCFlag
                INTEGER,
            optixAtmPolicyRowStatus
                RowStatus
        }

    -- 1.3.6.1.4.1.2011.2.25.4.50.32.1.4.1.1
    optixAtmPolicyCategory OBJECT-TYPE
        SYNTAX INTEGER
        {
            ubr(1),
            cbr(2),
            rtvbr(3),
            nrtvbr(4),
            ubrplus(5),
            portTrans(6),
            all(0)
        }
        MAX-ACCESS read-create
        STATUS current
        DESCRIPTION
            "This object indicates the ATM policy category. 1: ubr, 2: cbr, 3: rtvbr, 4: nrtvbr, 5: ubrplus, 6: portTrans, 0: all"
        ::= { optixAtmPolicyEntry 1 }

    -- 1.3.6.1.4.1.2011.2.25.4.50.32.1.4.1.2
    optixAtmPolicyTrafficType OBJECT-TYPE
        SYNTAX INTEGER
        {
            nodscr(1),
            noclpnoscr(2),
            clpnotagnoscr(3),
            clptagnoscr(4),
            noclpscr(5),
            clpnotagscr(6),
            clptagscr(7),
            clpnotagmcr(8),
            clptrnspnoscr(9),
            clptrnspscr(10),
            noclptagnoscr(11),
            noclpnoscrcdvt(12),
            noclpscrcdvt(13),
            clpnotagscrcdvt(14),
            clptagscrcdvt(15),
            atmnotrafficdescriptormcr(16),
            atmnoclpmcr(17),
            atmnoclpmcrcdvt(18)
        }
        MAX-ACCESS read-create
        STATUS current
        DESCRIPTION
            "This object indicates the ATM QoS traffic type. 1: nodscr, 2: noclpnoscr, 3: clpnotagnoscr, 4: clptagnoscr, 5: noclpscr, 6: clpnotagscr, 7: clptagscr, 8: clpnotagmcr, 9: clptrnspnoscr, 10: clptrnspscr, 11: noclptagnoscr, 12: noclpnoscrcdvt, 13: noclpscrcdvt, 14: clpnotagscrcdvt, 15: clptagscrcdvt, 16: atmnotrafficdescriptormcr, 17: atmnoclpmcr, 18: atmnoclpmcrcdvt"
        ::= { optixAtmPolicyEntry 2 }

    -- 1.3.6.1.4.1.2011.2.25.4.50.32.1.4.1.3
    optixAtmPolicyPara1 OBJECT-TYPE
        SYNTAX Unsigned32
        MAX-ACCESS read-create
        STATUS current
        DESCRIPTION
            "This object indicates the first ATM QoS parameter."
        ::= { optixAtmPolicyEntry 3 }

    -- 1.3.6.1.4.1.2011.2.25.4.50.32.1.4.1.4
    optixAtmPolicyPara2 OBJECT-TYPE
        SYNTAX Unsigned32
        MAX-ACCESS read-create
        STATUS current
        DESCRIPTION
            "This object indicates the second ATM QoS parameter."
        ::= { optixAtmPolicyEntry 4 }

    -- 1.3.6.1.4.1.2011.2.25.4.50.32.1.4.1.5
    optixAtmPolicyPara3 OBJECT-TYPE
        SYNTAX Unsigned32
        MAX-ACCESS read-create
        STATUS current
        DESCRIPTION
            "This object indicates the third ATM QoS parameter."
        ::= { optixAtmPolicyEntry 5 }

    -- 1.3.6.1.4.1.2011.2.25.4.50.32.1.4.1.6
    optixAtmPolicyPara4 OBJECT-TYPE
        SYNTAX Unsigned32
        MAX-ACCESS read-create
        STATUS current
        DESCRIPTION
            "This object indicates the fourth ATM QoS parameter."
        ::= { optixAtmPolicyEntry 6 }

    -- 1.3.6.1.4.1.2011.2.25.4.50.32.1.4.1.7
    optixAtmPolicyFrameDiscardFlag OBJECT-TYPE
        SYNTAX INTEGER
        {
            disable(0),
            enable(1)
        }
        MAX-ACCESS read-create
        STATUS current
        DESCRIPTION
            "This object indicates enable status of dropping ATM QoS frames. 0: disable, 1: enable"
        ::= { optixAtmPolicyEntry 7 }

    -- 1.3.6.1.4.1.2011.2.25.4.50.32.1.4.1.8
    optixAtmPolicyUPCNPCFlag OBJECT-TYPE
        SYNTAX INTEGER
        {
            disable(0),
            enable(1)
        }
        MAX-ACCESS read-create
        STATUS current
        DESCRIPTION
            "This object indicates enable status ofATM QoS UPC/NPC. 0: disable, 1: enable"
        ::= { optixAtmPolicyEntry 8 }

    -- 1.3.6.1.4.1.2011.2.25.4.50.32.1.4.1.255
    optixAtmPolicyRowStatus OBJECT-TYPE
        SYNTAX RowStatus
        MAX-ACCESS read-create
        STATUS current
        DESCRIPTION
            "This object indicates the ATM QoS row status."
        ::= { optixAtmPolicyEntry 255 }

    -- 1.3.6.1.4.1.2011.2.25.4.50.32.1.5
    optixVUNIGroupTable OBJECT-TYPE
        SYNTAX SEQUENCE OF OptixVUNIGroupEntry
        MAX-ACCESS not-accessible
        STATUS current
        DESCRIPTION
            "This table describes the VUNI Group of the QoS module."
        ::= { optixPktQosPolicyGroup 5 }

    -- 1.3.6.1.4.1.2011.2.25.4.50.32.1.5.1
    optixVUNIGroupEntry OBJECT-TYPE
        SYNTAX OptixVUNIGroupEntry
        MAX-ACCESS not-accessible
        STATUS current
        DESCRIPTION
            "This entry describes  the VUNI Group of the QoS module."
        INDEX{ optixVUNIGroupId }
        ::= { optixVUNIGroupTable 1 }

    OptixVUNIGroupEntry ::=
        SEQUENCE {
            optixVUNIGroupId
                Unsigned32,
            optixVUNIGroupType
                INTEGER,
            optixVUNIGroupMembNum
                Unsigned32,
            optixVUNIGroupSrvId
                Unsigned32,
            optixVUNIGroupVuniID
                Unsigned32,
            optixVUNIGroupCir
                Unsigned32,
            optixVUNIGroupCbs
                Unsigned32,
            optixVUNIGroupPir
                Unsigned32,
            optixVUNIGroupPbs
                Unsigned32,
            optixVUNIGroupStartCir
                Unsigned32,
            optixVUNIGroupStartPir
                Unsigned32,
            optixVUNIGroupState
                INTEGER,
            optixVUNIGroupRowStatus
                RowStatus
        }

    -- 1.3.6.1.4.1.2011.2.25.4.50.32.1.5.1.1
    optixVUNIGroupId OBJECT-TYPE
        SYNTAX Unsigned32
        MAX-ACCESS not-accessible
        STATUS current
        DESCRIPTION
            "This object indicates the VUNI Group ID of the QoS module. Value range: RTN 950: 0 to 128. RTN 905 1C: 0 to 1000. RTN 905: 0 to 1000. RTN 910: 0 to 1000. RTN 950A: 0 to 64. RTN980: 0 to 1000."
        ::= { optixVUNIGroupEntry 1 }

    -- 1.3.6.1.4.1.2011.2.25.4.50.32.1.5.1.2
    optixVUNIGroupType OBJECT-TYPE
        SYNTAX INTEGER
        {
            ingress(1),
            egress(2),
            none(255),
            all(0)
        }
        MAX-ACCESS read-create
        STATUS current
        DESCRIPTION
            "This object indicates the type of the VUNI Group ID of the QoS module. 1: ingress, 2: egress, 255: none, 0: all"
        ::= { optixVUNIGroupEntry 2 }

    -- 1.3.6.1.4.1.2011.2.25.4.50.32.1.5.1.3
    optixVUNIGroupMembNum OBJECT-TYPE
        SYNTAX Unsigned32
        MAX-ACCESS read-create
        STATUS current
        DESCRIPTION
            "This object indicates the number of the VUNI membersof the QoS module. Value range: RTN 950: 0 to 2000. RTN 905 1C: 0 to 2000. RTN 905: 0 to 2000. RTN 910: 0 to 2000. RTN 950A: 0 to 2000. RTN980: 0 to 2000."
        ::= { optixVUNIGroupEntry 3 }

    -- 1.3.6.1.4.1.2011.2.25.4.50.32.1.5.1.4
    optixVUNIGroupSrvId OBJECT-TYPE
        SYNTAX Unsigned32
        MAX-ACCESS read-create
        STATUS current
        DESCRIPTION
            "This object indicates the operation ID of the VUNI Group of the QoS module."
        ::= { optixVUNIGroupEntry 4 }

    -- 1.3.6.1.4.1.2011.2.25.4.50.32.1.5.1.5
    optixVUNIGroupVuniID OBJECT-TYPE
        SYNTAX Unsigned32
        MAX-ACCESS read-create
        STATUS current
        DESCRIPTION
            "This object indicates the VUNI ID of the VUNI Group of the QoS module."
        ::= { optixVUNIGroupEntry 5 }

    -- 1.3.6.1.4.1.2011.2.25.4.50.32.1.5.1.6
    optixVUNIGroupCir OBJECT-TYPE
        SYNTAX Unsigned32
        MAX-ACCESS read-create
        STATUS current
        DESCRIPTION
            "This object indicates the CIR of the VUNI Group of the QoS module. Value range in the egress direction: RTN 950: 128 to 10000000. RTN 905 1C: 66000 to 10000000. RTN 905: 66000 to 10000000. RTN 910: 66000 to 10000000. RTN 950A: 128 to 10000000. RTN980: 66000 to 10000000 (unit: Kbit/s) Value range in the ingress direction: RTN 950: 128 to 10000000. RTN 905 1C: 66000 to 10000000. RTN 905: 66000 to 10000000. RTN 910: 66000 to 10000000. RTN 950A: 128 to 10000000. RTN 980: 66000 to 10000000 (unit: Kbit/s)"
        ::= { optixVUNIGroupEntry 6 }

    -- 1.3.6.1.4.1.2011.2.25.4.50.32.1.5.1.7
    optixVUNIGroupCbs OBJECT-TYPE
        SYNTAX Unsigned32
        MAX-ACCESS read-create
        STATUS current
        DESCRIPTION
            "This object indicates the CBS of the VUNI Group of the QoS module. Value range in the egress direction: RTN 950: 64 to 512000. RTN 905 1C: 4294967295. RTN 905: 4294967295. RTN 910: 4294967295. RTN 950A: 0 to 4294967295. RTN980: 4294967295. Value range in the ingress direction: RTN 950: 64 to 512000. RTN 905 1C: 4294967295. RTN 905: 4294967295. RTN 910: 4294967295. RTN 950A: 0 to 4294967295. RTN980: 4294967295 (unit: byte) If no bandwidth is configured, the value is 0xFFFFFFFF."
        ::= { optixVUNIGroupEntry 7 }

    -- 1.3.6.1.4.1.2011.2.25.4.50.32.1.5.1.8
    optixVUNIGroupPir OBJECT-TYPE
        SYNTAX Unsigned32
        MAX-ACCESS read-create
        STATUS current
        DESCRIPTION
            "This object indicates the PIR of the VUNI Group of the QoS module. Value range in the egress direction: RTN 950: 128 to 10000000. RTN 905 1C: 66000 to 10000000. RTN 905: 66000 to 10000000. RTN 910: 66000 to 10000000. RTN 950A: 128 to 10000000. RTN980: 66000 to 10000000 (unit: Kbit/s) Value range in the ingress direction: RTN 950: 128 to 10000000. RTN 905 1C: 66000 to 10000000. RTN 905: 66000 to 10000000. RTN 910: 66000 to 10000000. RTN 950A: 128 to 10000000. RTN 980: 66000 to 10000000 (unit: Kbit/s)"
        ::= { optixVUNIGroupEntry 8 }

    -- 1.3.6.1.4.1.2011.2.25.4.50.32.1.5.1.9
    optixVUNIGroupPbs OBJECT-TYPE
        SYNTAX Unsigned32
        MAX-ACCESS read-create
        STATUS current
        DESCRIPTION
            "This object indicates the PBS of the VUNI Group of the QoS module. Value range in the egress direction: RTN 950: 64 to 512000. RTN 905 1C: 64 to 512000. RTN 905: 64 to 512000. RTN 910: 64 to 512000. RTN 950A: 10 to 4294967295. RTN980: 64 to 512000 (unit: Kbit/s) Value range in the ingress direction: RTN 950: 64 to 512000. RTN 905 1C: 64 to 512000. RTN 905: 64 to 512000. RTN 910: 64 to 512000. RTN 950A: 10 to 4294967295. RTN980: 64 to 512000 (unit: Kbit/s)"
        ::= { optixVUNIGroupEntry 9 }

    -- 1.3.6.1.4.1.2011.2.25.4.50.32.1.5.1.10
    optixVUNIGroupStartCir OBJECT-TYPE
        SYNTAX Unsigned32
        MAX-ACCESS read-only
        STATUS current
        DESCRIPTION
            "This object indicates the starting CIR of the VUNI Group of the QoS module. Value range in the egress direction: RTN 950: 128 to 10000000. RTN 905 1C: 66000 to 10000000. RTN 905: 66000 to 10000000. RTN 910: 66000 to 10000000. RTN 950A: 128 to 10000000. RTN980: 66000 to 10000000 (unit: Kbit/s) Value range in the ingress direction: RTN 950: 128 to 10000000. RTN 905 1C: 66000 to 10000000. RTN 905: 66000 to 10000000. RTN 910: 66000 to 10000000. RTN 950A: 128 to 10000000. RTN 980: 66000 to 10000000 (unit: Kbit/s)"
        ::= { optixVUNIGroupEntry 10 }

    -- 1.3.6.1.4.1.2011.2.25.4.50.32.1.5.1.11
    optixVUNIGroupStartPir OBJECT-TYPE
        SYNTAX Unsigned32
        MAX-ACCESS read-only
        STATUS current
        DESCRIPTION
            "This object indicates the starting CBS of the VUNI Group t of the QoS module. Value range in the egress direction: RTN 950: 128 to 10000000. RTN 905 1C: 66000 to 10000000. RTN 905: 66000 to 10000000. RTN 910: 66000 to 10000000. RTN 950A: 128 to 10000000. RTN980: 66000 to 10000000 (unit: Kbit/s) Value range in the ingress direction: RTN 950: 128 to 10000000. RTN 905 1C: 66000 to 10000000. RTN 905: 66000 to 10000000. RTN 910: 66000 to 10000000. RTN 950A: 128 to 10000000. RTN 980: 66000 to 10000000 (unit: Kbit/s)"
        ::= { optixVUNIGroupEntry 11 }

    -- 1.3.6.1.4.1.2011.2.25.4.50.32.1.5.1.12
    optixVUNIGroupState OBJECT-TYPE
        SYNTAX INTEGER
        {
            created(1),
            notcreate(0)
        }
        MAX-ACCESS read-create
        STATUS current
        DESCRIPTION
            "This object indicates the real state of the VUNI Group of the QoS module. 1: created, 0: notcreate"
        ::= { optixVUNIGroupEntry 12 }

    -- 1.3.6.1.4.1.2011.2.25.4.50.32.1.5.1.255
    optixVUNIGroupRowStatus OBJECT-TYPE
        SYNTAX RowStatus
        MAX-ACCESS read-create
        STATUS current
        DESCRIPTION
            "This object indicates the row status of the VUNI Group of the QoS module."
        ::= { optixVUNIGroupEntry 255 }

    -- 1.3.6.1.4.1.2011.2.25.4.50.32.1.6
    optixVUNIGroupMembTable OBJECT-TYPE
        SYNTAX SEQUENCE OF OptixVUNIGroupMembEntry
        MAX-ACCESS not-accessible
        STATUS current
        DESCRIPTION
            "This table describes the Member of the VUNI Group."
        ::= { optixPktQosPolicyGroup 6 }

    -- 1.3.6.1.4.1.2011.2.25.4.50.32.1.6.1
    optixVUNIGroupMembEntry OBJECT-TYPE
        SYNTAX OptixVUNIGroupMembEntry
        MAX-ACCESS not-accessible
        STATUS current
        DESCRIPTION
            "This entry describes the Member of the VUNI Group."
        INDEX{ optixVUNIGroupId,optixVUNIGroupSrvId,optixVUNIGroupVuniID }
        ::= { optixVUNIGroupMembTable 1 }

    OptixVUNIGroupMembEntry ::=
        SEQUENCE {
            optixVUNIRowStatus
                RowStatus
        }

    -- 1.3.6.1.4.1.2011.2.25.4.50.32.1.6.1.255
    optixVUNIRowStatus OBJECT-TYPE
        SYNTAX RowStatus
        MAX-ACCESS read-create
        STATUS current
        DESCRIPTION
            "This object indicates the rowstatusthe Member of the VUNI Group."
        ::= { optixVUNIGroupMembEntry 255 }

    -- 1.3.6.1.4.1.2011.2.25.4.50.32.1.7
    optixEXTPolicyTable OBJECT-TYPE
        SYNTAX SEQUENCE OF OptixEXTPolicyEntry
        MAX-ACCESS not-accessible
        STATUS current
        DESCRIPTION
            "This table describes the basic QoS policy configurations."
        ::= { optixPktQosPolicyGroup 7 }

    -- 1.3.6.1.4.1.2011.2.25.4.50.32.1.7.1
    optixEXTPolicyEntry OBJECT-TYPE
        SYNTAX OptixEXTPolicyEntry
        MAX-ACCESS not-accessible
        STATUS current
        DESCRIPTION
            "This entry describes the basic QoS policy configurations."
        INDEX{ optixEXTPolicyType,optixEXTPolicyId }
        ::= { optixEXTPolicyTable 1 }

    OptixEXTPolicyEntry ::=
        SEQUENCE {
            optixEXTPolicyType
                INTEGER,
            optixEXTPolicyId
                Unsigned32,
            optixEXTPolicyClassifierShareFlag
                INTEGER,
            optixEXTPolicyWfqId
                Unsigned32,
            optixEXTPolicyInfo
                OCTET STRING,
            optixEXTPolicyDirection
                INTEGER,
            optixEXTPolicyCs7Weight
                INTEGER,
            optixEXTPolicyCs6Weight
                INTEGER,
            optixEXTPolicyEfWeight
                INTEGER,
            optixEXTPolicyAf4Weight
                INTEGER,
            optixEXTPolicyAf3Weight
                INTEGER,
            optixEXTPolicyAf2Weight
                INTEGER,
            optixEXTPolicyAf1Weight
                INTEGER,
            optixEXTPolicyBeWeight
                INTEGER,
            optixEXTPolicyWrrId
                Unsigned32,
            optixEXTPolicyRowStatus
                RowStatus
        }

    -- 1.3.6.1.4.1.2011.2.25.4.50.32.1.7.1.1
    optixEXTPolicyType OBJECT-TYPE
        SYNTAX INTEGER
        {
            port(1),
            vuniingress(2),
            vuniegress(3),
            pw(4),
            atm(5),
            qinq(6)
        }
        MAX-ACCESS not-accessible
        STATUS current
        DESCRIPTION
            "This object indicates the QoS policy type of the QoS module. 1: port, 2: vuniingress, 3: vuniegress, 4: pw, 5: atm, 6: qinq"
        ::= { optixEXTPolicyEntry 1 }

    -- 1.3.6.1.4.1.2011.2.25.4.50.32.1.7.1.2
    optixEXTPolicyId OBJECT-TYPE
        SYNTAX Unsigned32
        MAX-ACCESS not-accessible
        STATUS current
        DESCRIPTION
            "This object indicates the QoS policy value of the QoS module."
        ::= { optixEXTPolicyEntry 2 }

    -- 1.3.6.1.4.1.2011.2.25.4.50.32.1.7.1.3
    optixEXTPolicyClassifierShareFlag OBJECT-TYPE
        SYNTAX INTEGER
        {
            disable(1),
            enable(2),
            none(255)
        }
        MAX-ACCESS read-only
        STATUS current
        DESCRIPTION
            "This object indicates the flow classification instance flag. 1: disable, 2: enable, 255: none"
        ::= { optixEXTPolicyEntry 3 }

    -- 1.3.6.1.4.1.2011.2.25.4.50.32.1.7.1.4
    optixEXTPolicyWfqId OBJECT-TYPE
        SYNTAX Unsigned32
        MAX-ACCESS read-only
        STATUS current
        DESCRIPTION
            "This object indicates the WFQ scheduling ID of the QoS module. Value range: 0 to 36."
        ::= { optixEXTPolicyEntry 4 }

    -- 1.3.6.1.4.1.2011.2.25.4.50.32.1.7.1.5
    optixEXTPolicyInfo OBJECT-TYPE
        SYNTAX OCTET STRING (SIZE(0..64))
        MAX-ACCESS read-create
        STATUS current
        DESCRIPTION
            "This object indicates the QoS policyinformation of the QoS module."
        ::= { optixEXTPolicyEntry 5 }

    -- 1.3.6.1.4.1.2011.2.25.4.50.32.1.7.1.6
    optixEXTPolicyDirection OBJECT-TYPE
        SYNTAX INTEGER
        {
            ingress(1),
            egress(2),
            none(255),
            all(0)
        }
        MAX-ACCESS read-only
        STATUS current
        DESCRIPTION
            "This object indicates the policy direction of the QoS module."
        ::= { optixEXTPolicyEntry 6 }

    -- 1.3.6.1.4.1.2011.2.25.4.50.32.1.7.1.7
    optixEXTPolicyCs7Weight OBJECT-TYPE
        SYNTAX INTEGER
        {
            sp(1),
            wrr(2),
            wfq(3),
            drr(4),
            none(255)
        }
        MAX-ACCESS read-create
        STATUS current
        DESCRIPTION
            "This object indicates the CS7 scheduling weight of the QoS module. 1: sp, 2: wrr, 3: wfq, 4: drr, 255: none"
        ::= { optixEXTPolicyEntry 7 }

    -- 1.3.6.1.4.1.2011.2.25.4.50.32.1.7.1.8
    optixEXTPolicyCs6Weight OBJECT-TYPE
        SYNTAX INTEGER
        {
            sp(1),
            wrr(2),
            wfq(3),
            drr(4),
            none(255)
        }
        MAX-ACCESS read-create
        STATUS current
        DESCRIPTION
            "This object indicates the CS6 scheduling weight of the QoS module. 1: sp, 2: wrr, 3: wfq, 4: drr, 255: none"
        ::= { optixEXTPolicyEntry 8 }

    -- 1.3.6.1.4.1.2011.2.25.4.50.32.1.7.1.9
    optixEXTPolicyEfWeight OBJECT-TYPE
        SYNTAX INTEGER
        {
            sp(1),
            wrr(2),
            wfq(3),
            drr(4),
            none(255)
        }
        MAX-ACCESS read-create
        STATUS current
        DESCRIPTION
            "This object indicates theEF scheduling weight of the QoS module. 1: sp, 2: wrr, 3: wfq, 4: drr, 255: none"
        ::= { optixEXTPolicyEntry 9 }

    -- 1.3.6.1.4.1.2011.2.25.4.50.32.1.7.1.10
    optixEXTPolicyAf4Weight OBJECT-TYPE
        SYNTAX INTEGER
        {
            sp(1),
            wrr(2),
            wfq(3),
            drr(4),
            none(255)
        }
        MAX-ACCESS read-create
        STATUS current
        DESCRIPTION
            "This object indicates theAF4 scheduling weight of the QoS module. 1: sp, 2: wrr, 3: wfq, 4: drr, 255: none"
        ::= { optixEXTPolicyEntry 10 }

    -- 1.3.6.1.4.1.2011.2.25.4.50.32.1.7.1.11
    optixEXTPolicyAf3Weight OBJECT-TYPE
        SYNTAX INTEGER
        {
            sp(1),
            wrr(2),
            wfq(3),
            drr(4),
            none(255)
        }
        MAX-ACCESS read-create
        STATUS current
        DESCRIPTION
            "This object indicates the AF3 scheduling weight of the QoS module. 1: sp, 2: wrr, 3: wfq, 4: drr, 255: none"
        ::= { optixEXTPolicyEntry 11 }

    -- 1.3.6.1.4.1.2011.2.25.4.50.32.1.7.1.12
    optixEXTPolicyAf2Weight OBJECT-TYPE
        SYNTAX INTEGER
        {
            sp(1),
            wrr(2),
            wfq(3),
            drr(4),
            none(255)
        }
        MAX-ACCESS read-create
        STATUS current
        DESCRIPTION
            "This object indicates the AF2 scheduling weight of the QoS module. 1: sp, 2: wrr, 3: wfq, 4: drr, 255: none"
        ::= { optixEXTPolicyEntry 12 }

    -- 1.3.6.1.4.1.2011.2.25.4.50.32.1.7.1.13
    optixEXTPolicyAf1Weight OBJECT-TYPE
        SYNTAX INTEGER
        {
            sp(1),
            wrr(2),
            wfq(3),
            drr(4),
            none(255)
        }
        MAX-ACCESS read-create
        STATUS current
        DESCRIPTION
            "This object indicates the AF1 scheduling weight of the QoS module. 1: sp, 2: wrr, 3: wfq, 4: drr, 255: none"
        ::= { optixEXTPolicyEntry 13 }

    -- 1.3.6.1.4.1.2011.2.25.4.50.32.1.7.1.14
    optixEXTPolicyBeWeight OBJECT-TYPE
        SYNTAX INTEGER
        {
            sp(1),
            wrr(2),
            wfq(3),
            drr(4),
            none(255)
        }
        MAX-ACCESS read-create
        STATUS current
        DESCRIPTION
            "This object indicates the BE scheduling weight of the QoS module. 1: sp, 2: wrr, 3: wfq, 4: drr, 255: none"
        ::= { optixEXTPolicyEntry 14 }

    -- 1.3.6.1.4.1.2011.2.25.4.50.32.1.7.1.15
    optixEXTPolicyWrrId OBJECT-TYPE
        SYNTAX Unsigned32
        MAX-ACCESS read-create
        STATUS current
        DESCRIPTION
            "This object indicates the WRR scheduling ID of the QoS module. Value range for port: 0 to 8. Value range for service: 0 to 127."
        ::= { optixEXTPolicyEntry 15 }

    -- 1.3.6.1.4.1.2011.2.25.4.50.32.1.7.1.255
    optixEXTPolicyRowStatus OBJECT-TYPE
        SYNTAX RowStatus
        MAX-ACCESS read-create
        STATUS current
        DESCRIPTION
            "This object indicates theQoS row status of the QoS module."
        ::= { optixEXTPolicyEntry 255 }

END
