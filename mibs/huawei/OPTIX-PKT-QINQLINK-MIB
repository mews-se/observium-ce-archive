-- OPTIX-PKT-QINQLINK-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-QINQLINK-MIB DEFINITIONS ::= BEGIN
    IMPORTS
        optixProvisionPtn
            FROM OPTIX-OID-MIB
        OBJECT-GROUP,MODULE-COMPLIANCE
            FROM SNMPv2-CONF
        OBJECT-TYPE,MODULE-IDENTITY,Unsigned32
            FROM SNMPv2-SMI
        RowStatus
            FROM SNMPv2-TC
        ;

    optixQinqLink MODULE-IDENTITY
        LAST-UPDATED "201211151353Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "this mib describes configuration of QINQ link"
        REVISION "201211151353Z"
        DESCRIPTION
            "The initial revision of this MIB module."
        ::={ optixProvisionPtn 12 }

    -- 1.3.6.1.4.1.2011.2.25.4.50.12.1
    optixQinqLinkGroup OBJECT IDENTIFIER ::= { optixQinqLink 1 }

    -- 1.3.6.1.4.1.2011.2.25.4.50.12.1.1
    optixQinqLinkTable OBJECT-TYPE
        SYNTAX SEQUENCE OF OptixQinqLinkEntry
        MAX-ACCESS not-accessible
        STATUS current
        DESCRIPTION
            "this table describes the information of the QINQ link."
        ::= { optixQinqLinkGroup 1 }

    -- 1.3.6.1.4.1.2011.2.25.4.50.12.1.1.1
    optixQinqLinkEntry OBJECT-TYPE
        SYNTAX OptixQinqLinkEntry
        MAX-ACCESS not-accessible
        STATUS current
        DESCRIPTION
            "this entry describes the information of the QINQ link."
        INDEX{ optixQinqLinkIndex }
        ::= { optixQinqLinkTable 1 }

    OptixQinqLinkEntry ::=
        SEQUENCE {
            optixQinqLinkIndex
                Unsigned32,
            optixQinqLinkBoardId
                Unsigned32,
            optixQinqLinkSubBdId
                Unsigned32,
            optixQinqLinkPortId
                Unsigned32,
            optixQinqLinkVlanId
                Unsigned32,
            optixQinqLinkRowStatus
                RowStatus
        }

    -- 1.3.6.1.4.1.2011.2.25.4.50.12.1.1.1.1
    optixQinqLinkIndex OBJECT-TYPE
        SYNTAX Unsigned32
        MAX-ACCESS not-accessible
        STATUS current
        DESCRIPTION
            "this parameter describes the index of the QINQ link. Value range for RTN 950: 0 to 128. RTN 905 1C: 0 to 1024. RTN 905: 0 to 1024. RTN 910: 0 to 1024. RTN 950A: 0 to 128. RTN 980: 0 to 1024"
        ::= { optixQinqLinkEntry 1 }

    -- 1.3.6.1.4.1.2011.2.25.4.50.12.1.1.1.2
    optixQinqLinkBoardId OBJECT-TYPE
        SYNTAX Unsigned32
        MAX-ACCESS read-create
        STATUS current
        DESCRIPTION
            "this parameter describes the board ID."
        ::= { optixQinqLinkEntry 2 }

    -- 1.3.6.1.4.1.2011.2.25.4.50.12.1.1.1.3
    optixQinqLinkSubBdId OBJECT-TYPE
        SYNTAX Unsigned32
        MAX-ACCESS read-create
        STATUS current
        DESCRIPTION
            "this parameter describes the subboard ID."
        ::= { optixQinqLinkEntry 3 }

    -- 1.3.6.1.4.1.2011.2.25.4.50.12.1.1.1.4
    optixQinqLinkPortId OBJECT-TYPE
        SYNTAX Unsigned32
        MAX-ACCESS read-create
        STATUS current
        DESCRIPTION
            "this parameter describes the port ID."
        ::= { optixQinqLinkEntry 4 }

    -- 1.3.6.1.4.1.2011.2.25.4.50.12.1.1.1.5
    optixQinqLinkVlanId OBJECT-TYPE
        SYNTAX Unsigned32
        MAX-ACCESS read-create
        STATUS current
        DESCRIPTION
            "this parameter describes the VLAN ID. Value range: 0 to 4095."
        ::= { optixQinqLinkEntry 5 }

    -- 1.3.6.1.4.1.2011.2.25.4.50.12.1.1.1.255
    optixQinqLinkRowStatus OBJECT-TYPE
        SYNTAX RowStatus
        MAX-ACCESS read-create
        STATUS current
        DESCRIPTION
            "this parameter describes the row status of the QINQ link."
        ::= { optixQinqLinkEntry 255 }

    -- 1.3.6.1.4.1.2011.2.25.4.50.12.1.2
    optixQinqQosInfoTable OBJECT-TYPE
        SYNTAX SEQUENCE OF OptixQinqQosInfoEntry
        MAX-ACCESS not-accessible
        STATUS current
        DESCRIPTION
            "this table describes the information of the QINQ Qos information."
        ::= { optixQinqLinkGroup 2 }

    -- 1.3.6.1.4.1.2011.2.25.4.50.12.1.2.1
    optixQinqQosInfoEntry OBJECT-TYPE
        SYNTAX OptixQinqQosInfoEntry
        MAX-ACCESS not-accessible
        STATUS current
        DESCRIPTION
            "This entry describes the QINQ QoS information of devices."
        INDEX{ optixQinqLinkIndex,optixQinqQosPointDir }
        ::= { optixQinqQosInfoTable 1 }

    OptixQinqQosInfoEntry ::=
        SEQUENCE {
            optixQinqQosPointDir
                INTEGER,
            optixQinqQosConfigCIR
                Unsigned32,
            optixQinqQosCBS
                Unsigned32,
            optixQinqQosConfigPIR
                Unsigned32,
            optixQinqQosPBS
                Unsigned32,
            optixQinqQosPolicyID
                Unsigned32,
            optixQinqQosActualCIR
                Unsigned32,
            optixQinqQosActualPIR
                Unsigned32,
            optixQinqQosInfoRowStatus
                RowStatus
        }

    -- 1.3.6.1.4.1.2011.2.25.4.50.12.1.2.1.1
    optixQinqQosPointDir OBJECT-TYPE
        SYNTAX INTEGER
        {
            all(0),
            ingress(1),
            egress(2),
            none(255)
        }
        MAX-ACCESS not-accessible
        STATUS current
        DESCRIPTION
            "this parameter describes the direction of the QINQ Oos information. 0: all, 1: ingress, 2: egress, 255: none"
        ::= { optixQinqQosInfoEntry 1 }

    -- 1.3.6.1.4.1.2011.2.25.4.50.12.1.2.1.2
    optixQinqQosConfigCIR OBJECT-TYPE
        SYNTAX Unsigned32
        MAX-ACCESS read-create
        STATUS current
        DESCRIPTION
            "This parameter describes CIR. Value range in the egress direction: RTN 950: 64 to 1000000. RTN 905 1C: 0 to 1000000. RTN 905: 0 to 1000000. RTN 910: 0 to 1000000. RTN 950A: 64 to 1000000. RTN980: 0 to 1000000 (unit: Kbit/s) Value range in the ingress direction: RTN 950: 64 to 1000000. RTN 905 1C: 0 to 1000000. RTN 905: 0 to 1000000. RTN 910: 0 to 1000000. RTN 950A: 64 to 1000000. RTN 980: 0 to 1000000 (unit: Kbit/s)"
        ::= { optixQinqQosInfoEntry 2 }

    -- 1.3.6.1.4.1.2011.2.25.4.50.12.1.2.1.3
    optixQinqQosCBS OBJECT-TYPE
        SYNTAX Unsigned32
        MAX-ACCESS read-create
        STATUS current
        DESCRIPTION
            "This parameter describes CBS. Value range in the egress direction: RTN 950: 64 to 1000000. RTN 905 1C: 64 to 4294967295. RTN 905: 0 to 1000000. RTN 910: 0 to 1000000. RTN 950A: 0 to 4294967295. RTN980: 64 to 1000000 (unit: Kbit/s) Value range in the ingress direction: RTN 950: 64 to 1000000. RTN 905 1C: 64 to 4294967295. RTN 905: 0 to 1000000. RTN 910: 0 to 1000000. RTN 950A: 0 to 4294967295. RTN 980: 64 to 1000000 (unit: Kbit/s)"
        ::= { optixQinqQosInfoEntry 3 }

    -- 1.3.6.1.4.1.2011.2.25.4.50.12.1.2.1.4
    optixQinqQosConfigPIR OBJECT-TYPE
        SYNTAX Unsigned32
        MAX-ACCESS read-create
        STATUS current
        DESCRIPTION
            "This parameter describes PIR. Value range in the egress direction: RTN 950: 64 to 1000000. RTN 905 1C: 0 to 1000000. RTN 905: 0 to 1000000. RTN 910: 0 to 1000000. RTN 950A: 64 to 1000000. RTN980: 0 to 1000000 (unit: Kbit/s) Value range in the ingress direction: RTN 950: 64 to 1000000. RTN 905 1C: 0 to 1000000. RTN 905: 0 to 1000000. RTN 910: 0 to 1000000. RTN 950A: 64 to 1000000. RTN 980: 0 to 1000000 (unit: Kbit/s)"
        ::= { optixQinqQosInfoEntry 4 }

    -- 1.3.6.1.4.1.2011.2.25.4.50.12.1.2.1.5
    optixQinqQosPBS OBJECT-TYPE
        SYNTAX Unsigned32
        MAX-ACCESS read-create
        STATUS current
        DESCRIPTION
            "This parameter describes PBS. Value range in the egress direction: RTN 950: 64 to 1000000. RTN 905 1C: 64 to 4294967295. RTN 905: 0 to 1000000. RTN 910: 0 to 1000000. RTN 950A: 0 to 4294967295. RTN980: 64 to 1000000 (unit: Kbit/s) Value range in the ingress direction: RTN 950: 64 to 1000000. RTN 905 1C: 64 to 4294967295. RTN 905: 0 to 1000000. RTN 910: 0 to 1000000. RTN 950A: 0 to 4294967295. RTN 980: 64 to 1000000 (unit: Kbit/s)"
        ::= { optixQinqQosInfoEntry 5 }

    -- 1.3.6.1.4.1.2011.2.25.4.50.12.1.2.1.6
    optixQinqQosPolicyID OBJECT-TYPE
        SYNTAX Unsigned32
        MAX-ACCESS read-create
        STATUS current
        DESCRIPTION
            "This parameter describes the policy ID. Value range for ATM: 0 to 1024. Value range for PORT: 0 to 256. Value range for VUNIINGRESS: 1 to 1024 (for RTN 950 and RTN 950A: 1 to 256)."
        ::= { optixQinqQosInfoEntry 6 }

    -- 1.3.6.1.4.1.2011.2.25.4.50.12.1.2.1.7
    optixQinqQosActualCIR OBJECT-TYPE
        SYNTAX Unsigned32
        MAX-ACCESS read-only
        STATUS current
        DESCRIPTION
            "This parameter describes the actual CIR. Value range in the egress direction: RTN 950: 64 to 1000000. RTN 905 1C: 64 to 4294967295. RTN 905: 0 to 1000000. RTN 910: 0 to 1000000. RTN 950A: 0 to 4294967295. RTN980: 64 to 1000000 (unit: Kbit/s) Value range in the ingress direction: RTN 950: 64 to 1000000. RTN 905 1C: 64 to 4294967295. RTN 905: 0 to 1000000. RTN 910: 0 to 1000000. RTN 950A: 0 to 4294967295. RTN 980: 64 to 1000000 (unit: Kbit/s)"
        ::= { optixQinqQosInfoEntry 7 }

    -- 1.3.6.1.4.1.2011.2.25.4.50.12.1.2.1.8
    optixQinqQosActualPIR OBJECT-TYPE
        SYNTAX Unsigned32
        MAX-ACCESS read-only
        STATUS current
        DESCRIPTION
            "This parameter describes the actual PIR. Value range in the egress direction: RTN 950: 64 to 1000000. RTN 905 1C: 64 to 4294967295. RTN 905: 0 to 1000000. RTN 910: 0 to 1000000. RTN 950A: 0 to 4294967295. RTN980: 64 to 1000000 (unit: Kbit/s) Value range in the ingress direction: RTN 950: 64 to 1000000. RTN 905 1C: 64 to 4294967295. RTN 905: 0 to 1000000. RTN 910: 0 to 1000000. RTN 950A: 0 to 4294967295. RTN 980: 64 to 1000000 (unit: Kbit/s)"
        ::= { optixQinqQosInfoEntry 8 }

    -- 1.3.6.1.4.1.2011.2.25.4.50.12.1.2.1.255
    optixQinqQosInfoRowStatus OBJECT-TYPE
        SYNTAX RowStatus
        MAX-ACCESS read-create
        STATUS current
        DESCRIPTION
            "this parameter describes the row status of the QINQ link."
        ::= { optixQinqQosInfoEntry 255 }

END
