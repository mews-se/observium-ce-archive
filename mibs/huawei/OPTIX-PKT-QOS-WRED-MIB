-- OPTIX-PKT-QOS-WRED-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-QOS-WRED-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        ;

    optixPktQosWred MODULE-IDENTITY
        LAST-UPDATED "201212041112Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the QOS service configuration information of device"
        REVISION "201212041112Z"
        DESCRIPTION
            "The initial revision of this MIB module1."
        ::={ optixProvisionPtn 14 }

    -- 1.3.6.1.4.1.2011.2.25.4.50.14.1
    optixPktQosWredGroup OBJECT IDENTIFIER ::= { optixPktQosWred 1 }

    -- 1.3.6.1.4.1.2011.2.25.4.50.14.1.1
    optixWredTable OBJECT-TYPE
        SYNTAX SEQUENCE OF OptixWredEntry
        MAX-ACCESS not-accessible
        STATUS current
        DESCRIPTION
            "This table describes the basic QoS Wred scheduling configurations."
        ::= { optixPktQosWredGroup 1 }

    -- 1.3.6.1.4.1.2011.2.25.4.50.14.1.1.1
    optixWredEntry OBJECT-TYPE
        SYNTAX OptixWredEntry
        MAX-ACCESS not-accessible
        STATUS current
        DESCRIPTION
            "This entry describes the basic QoS Wred scheduling configurations."
        INDEX{ optixWredType,optixWredId }
        ::= { optixWredTable 1 }

    OptixWredEntry ::=
        SEQUENCE {
            optixWredType
                INTEGER,
            optixWredId
                Unsigned32,
            optixWredGreenlowlimit
                Unsigned32,
            optixWredGreenhighlimit
                Unsigned32,
            optixWredGreenProbability
                Unsigned32,
            optixWredYellowlowlimit
                Unsigned32,
            optixWredYellowhighlimit
                Unsigned32,
            optixWredYellowProbability
                Unsigned32,
            optixWredRedlowlimit
                Unsigned32,
            optixWredRedhighlimit
                Unsigned32,
            optixWredRedProbability
                Unsigned32,
            optixWredinfo
                OCTET STRING,
            optixWredTHMode
                INTEGER,
            optixWredQueueLength
                Unsigned32,
            optixWredRowStatus
                RowStatus
        }

    -- 1.3.6.1.4.1.2011.2.25.4.50.14.1.1.1.1
    optixWredType OBJECT-TYPE
        SYNTAX INTEGER
        {
            port(1),
            service(2)
        }
        MAX-ACCESS not-accessible
        STATUS current
        DESCRIPTION
            "This object indicates the Wred scheduling Type of the QoS module. 1: port, 2: service"
        ::= { optixWredEntry 1 }

    -- 1.3.6.1.4.1.2011.2.25.4.50.14.1.1.1.2
    optixWredId OBJECT-TYPE
        SYNTAX Unsigned32
        MAX-ACCESS not-accessible
        STATUS current
        DESCRIPTION
            "This object indicates the Wred scheduling ID of the QoS module. Value range for port: RTN 950: 1 to 8. RTN 905 1C: 1 to 7. RTN 905: 1 to 7. RTN 910: 1 to 8. RTN 950A: 1 to 64. RTN980: 1 to 8. Value range for service: RTN 950: 1 to 8. RTN 905 1C: 1 to 36. RTN 905: 1 to 36. RTN 910: 1 to 8. RTN 950A: 1 to 64. RTN980: 1 to 8."
        ::= { optixWredEntry 2 }

    -- 1.3.6.1.4.1.2011.2.25.4.50.14.1.1.1.3
    optixWredGreenlowlimit OBJECT-TYPE
        SYNTAX Unsigned32
        MAX-ACCESS read-create
        STATUS current
        DESCRIPTION
            "This object indicates the Wred scheduling Green low limit of the QoS module. Value range for port: 0 to 480. Value range for servcie: 0 to 4095. Unit: 256 bytes"
        ::= { optixWredEntry 3 }

    -- 1.3.6.1.4.1.2011.2.25.4.50.14.1.1.1.4
    optixWredGreenhighlimit OBJECT-TYPE
        SYNTAX Unsigned32
        MAX-ACCESS read-create
        STATUS current
        DESCRIPTION
            "This object indicates the Wred scheduling Green high limit of the QoS module. Value range for port: 0 to 480. Value range for servcie: 0 to 4095. Unit: 256 bytes"
        ::= { optixWredEntry 4 }

    -- 1.3.6.1.4.1.2011.2.25.4.50.14.1.1.1.5
    optixWredGreenProbability OBJECT-TYPE
        SYNTAX Unsigned32
        MAX-ACCESS read-create
        STATUS current
        DESCRIPTION
            "This object indicates the Wred scheduling Green Probability of the QoS module. Value range for RTN equipment: 1 to 100 (unit: %)."
        ::= { optixWredEntry 5 }

    -- 1.3.6.1.4.1.2011.2.25.4.50.14.1.1.1.6
    optixWredYellowlowlimit OBJECT-TYPE
        SYNTAX Unsigned32
        MAX-ACCESS read-create
        STATUS current
        DESCRIPTION
            "This object indicates the Wred scheduling Yellow low limit of the QoS module. Value range for port: 0 to 480. Value range for servcie: 0 to 4095. Unit: 256 bytes"
        ::= { optixWredEntry 6 }

    -- 1.3.6.1.4.1.2011.2.25.4.50.14.1.1.1.7
    optixWredYellowhighlimit OBJECT-TYPE
        SYNTAX Unsigned32
        MAX-ACCESS read-create
        STATUS current
        DESCRIPTION
            "This object indicates the Wred scheduling Yellow high limit of the QoS module. Value range for port: 0 to 480. Value range for servcie: 0 to 4095. Unit: 256 bytes"
        ::= { optixWredEntry 7 }

    -- 1.3.6.1.4.1.2011.2.25.4.50.14.1.1.1.8
    optixWredYellowProbability OBJECT-TYPE
        SYNTAX Unsigned32
        MAX-ACCESS read-create
        STATUS current
        DESCRIPTION
            "This object indicates the Wred scheduling Yellow Probability of the QoS module."
        ::= { optixWredEntry 8 }

    -- 1.3.6.1.4.1.2011.2.25.4.50.14.1.1.1.9
    optixWredRedlowlimit OBJECT-TYPE
        SYNTAX Unsigned32
        MAX-ACCESS read-create
        STATUS current
        DESCRIPTION
            "This object indicates the Wred scheduling Red low limit of the QoS module. Value range for port: 0 to 480. Value range for servcie: 0 to 4095. Unit: 256 bytes"
        ::= { optixWredEntry 9 }

    -- 1.3.6.1.4.1.2011.2.25.4.50.14.1.1.1.10
    optixWredRedhighlimit OBJECT-TYPE
        SYNTAX Unsigned32
        MAX-ACCESS read-create
        STATUS current
        DESCRIPTION
            "This object indicates the Wred scheduling Red high limit of the QoS module. Value range for port: 0 to 480. Value range for servcie: 0 to 4095. Unit: 256 bytes"
        ::= { optixWredEntry 10 }

    -- 1.3.6.1.4.1.2011.2.25.4.50.14.1.1.1.11
    optixWredRedProbability OBJECT-TYPE
        SYNTAX Unsigned32
        MAX-ACCESS read-create
        STATUS current
        DESCRIPTION
            "This object indicates the Wred scheduling Red Probability of the QoS module. Value range for RTN equipment: 1 to 100 (unit: %)."
        ::= { optixWredEntry 11 }

    -- 1.3.6.1.4.1.2011.2.25.4.50.14.1.1.1.12
    optixWredinfo OBJECT-TYPE
        SYNTAX OCTET STRING (SIZE(0..64))
        MAX-ACCESS read-create
        STATUS current
        DESCRIPTION
            "This object indicates the Wred scheduling information of the QoS module."
        ::= { optixWredEntry 12 }

    -- 1.3.6.1.4.1.2011.2.25.4.50.14.1.1.1.13
    optixWredTHMode OBJECT-TYPE
        SYNTAX INTEGER
        {
            value(1),
            percent(2)
        }
        MAX-ACCESS read-create
        STATUS current
        DESCRIPTION
            "This parameter is used to describe the WRED threshold mode of the QoS module. 1: value; 2: percentage"
        ::= { optixWredEntry 13 }

    -- 1.3.6.1.4.1.2011.2.25.4.50.14.1.1.1.14
    optixWredQueueLength OBJECT-TYPE
        SYNTAX Unsigned32
        MAX-ACCESS read-create
        STATUS current
        DESCRIPTION
            "This parameter is used to describe the WRED queue length of the QoS module. Value range: 0-4294967295"
        ::= { optixWredEntry 14 }

    -- 1.3.6.1.4.1.2011.2.25.4.50.14.1.1.1.255
    optixWredRowStatus OBJECT-TYPE
        SYNTAX RowStatus
        MAX-ACCESS read-create
        STATUS current
        DESCRIPTION
            "This object indicates the Wred row status."
        ::= { optixWredEntry 255 }

END
