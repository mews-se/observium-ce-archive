-- OPTIX-GLOBAL-PER-SDH-RTN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-PER-SDH-RTN-MIB DEFINITIONS ::= BEGIN
    IMPORTS
        PerformanceEventType,ValidflagType
            FROM OPTIX-GLOBAL-TC-MIB
        optixCommon,rtn
            FROM OPTIX-OID-MIB
        OBJECT-GROUP,MODULE-COMPLIANCE
            FROM SNMPv2-CONF
        Unsigned32,OBJECT-TYPE,MODULE-IDENTITY
            FROM SNMPv2-SMI
        DateAndTime
            FROM SNMPv2-TC
        ;

    rtnPerformance MODULE-IDENTITY
        LAST-UPDATED "201208210935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Description."
        REVISION "201208210935Z"
        DESCRIPTION
            "The initial revision of this MIB module."
        ::={ rtn 10 }

    -- 1.3.6.1.4.1.2011.2.25.3.70.10.7
    tunnel OBJECT IDENTIFIER ::= { rtnPerformance 7 }

    -- 1.3.6.1.4.1.2011.2.25.3.70.10.7.60
    tunnelPer15mCurTable OBJECT-TYPE
        SYNTAX SEQUENCE OF TunnelPer15mCurEntry
        MAX-ACCESS not-accessible
        STATUS current
        DESCRIPTION
            "tunnelPer15mCur."
        ::= { tunnel 60 }

    -- 1.3.6.1.4.1.2011.2.25.3.70.10.7.60.1
    tunnelPer15mCurEntry OBJECT-TYPE
        SYNTAX TunnelPer15mCurEntry
        MAX-ACCESS not-accessible
        STATUS current
        DESCRIPTION
            "tunnelPer15mCur."
        INDEX{ tunnelPer15mCurEid,tunnelPer15mCurPara }
        ::= { tunnelPer15mCurTable 1 }

    TunnelPer15mCurEntry ::=
        SEQUENCE {
            tunnelPer15mCurEid
                PerformanceEventType,
            tunnelPer15mCurMonValue
                OCTET STRING,
            tunnelPer15mCurVldty
                ValidflagType,
            tunnelPer15mCurDatetime
                DateAndTime,
            tunnelPer15mCurParaLen
                Unsigned32,
            tunnelPer15mCurPara
                OCTET STRING
        }

    -- 1.3.6.1.4.1.2011.2.25.3.70.10.7.60.1.1
    tunnelPer15mCurEid OBJECT-TYPE
        SYNTAX PerformanceEventType
        MAX-ACCESS read-only
        STATUS current
        DESCRIPTION
            "tunnelPer15mCur"
        ::= { tunnelPer15mCurEntry 1 }

    -- 1.3.6.1.4.1.2011.2.25.3.70.10.7.60.1.2
    tunnelPer15mCurMonValue OBJECT-TYPE
        SYNTAX OCTET STRING
        MAX-ACCESS read-only
        STATUS current
        DESCRIPTION
            "perMonValue."
        ::= { tunnelPer15mCurEntry 2 }

    -- 1.3.6.1.4.1.2011.2.25.3.70.10.7.60.1.3
    tunnelPer15mCurVldty OBJECT-TYPE
        SYNTAX ValidflagType
        MAX-ACCESS read-only
        STATUS current
        DESCRIPTION
            "perVldty."
        ::= { tunnelPer15mCurEntry 3 }

    -- 1.3.6.1.4.1.2011.2.25.3.70.10.7.60.1.4
    tunnelPer15mCurDatetime OBJECT-TYPE
        SYNTAX DateAndTime
        MAX-ACCESS read-only
        STATUS current
        DESCRIPTION
            "perDateTime."
        ::= { tunnelPer15mCurEntry 4 }

    -- 1.3.6.1.4.1.2011.2.25.3.70.10.7.60.1.5
    tunnelPer15mCurParaLen OBJECT-TYPE
        SYNTAX Unsigned32
        MAX-ACCESS read-only
        STATUS current
        DESCRIPTION
            "perParaLen."
        ::= { tunnelPer15mCurEntry 5 }

    -- 1.3.6.1.4.1.2011.2.25.3.70.10.7.60.1.6
    tunnelPer15mCurPara OBJECT-TYPE
        SYNTAX OCTET STRING
        MAX-ACCESS read-only
        STATUS current
        DESCRIPTION
            "perPara."
        ::= { tunnelPer15mCurEntry 6 }

    -- 1.3.6.1.4.1.2011.2.25.3.70.10.7.70
    tunnelPer15mHisTable OBJECT-TYPE
        SYNTAX SEQUENCE OF TunnelPer15mHisEntry
        MAX-ACCESS not-accessible
        STATUS current
        DESCRIPTION
            "tunnelPer15mHis."
        ::= { tunnel 70 }

    -- 1.3.6.1.4.1.2011.2.25.3.70.10.7.70.1
    tunnelPer15mHisEntry OBJECT-TYPE
        SYNTAX TunnelPer15mHisEntry
        MAX-ACCESS not-accessible
        STATUS current
        DESCRIPTION
            "tunnelPer15mHis."
        INDEX{ tunnelPer15mHisEid,tunnelPer15mHisParaLen,tunnelPer15mHisPara,tunnelPer15mHisStartTime,tunnelPer15mHisEndTime }
        ::= { tunnelPer15mHisTable 1 }

    TunnelPer15mHisEntry ::=
        SEQUENCE {
            tunnelPer15mHisEid
                PerformanceEventType,
            tunnelPer15mHisParaLen
                Unsigned32,
            tunnelPer15mHisPara
                OCTET STRING,
            tunnelPer15mHisMonValue
                OCTET STRING,
            tunnelPer15mHisStartTime
                DateAndTime,
            tunnelPer15mHisEndTime
                DateAndTime,
            tunnelPer15mHisVldty
                ValidflagType
        }

    -- 1.3.6.1.4.1.2011.2.25.3.70.10.7.70.1.1
    tunnelPer15mHisEid OBJECT-TYPE
        SYNTAX PerformanceEventType
        MAX-ACCESS read-only
        STATUS current
        DESCRIPTION
            "perEid."
        ::= { tunnelPer15mHisEntry 1 }

    -- 1.3.6.1.4.1.2011.2.25.3.70.10.7.70.1.2
    tunnelPer15mHisParaLen OBJECT-TYPE
        SYNTAX Unsigned32
        MAX-ACCESS read-only
        STATUS current
        DESCRIPTION
            "perParaLen."
        ::= { tunnelPer15mHisEntry 2 }

    -- 1.3.6.1.4.1.2011.2.25.3.70.10.7.70.1.3
    tunnelPer15mHisPara OBJECT-TYPE
        SYNTAX OCTET STRING
        MAX-ACCESS read-only
        STATUS current
        DESCRIPTION
            "perPara."
        ::= { tunnelPer15mHisEntry 3 }

    -- 1.3.6.1.4.1.2011.2.25.3.70.10.7.70.1.4
    tunnelPer15mHisMonValue OBJECT-TYPE
        SYNTAX OCTET STRING
        MAX-ACCESS read-only
        STATUS current
        DESCRIPTION
            "perMonValue."
        ::= { tunnelPer15mHisEntry 4 }

    -- 1.3.6.1.4.1.2011.2.25.3.70.10.7.70.1.5
    tunnelPer15mHisStartTime OBJECT-TYPE
        SYNTAX DateAndTime
        MAX-ACCESS read-only
        STATUS current
        DESCRIPTION
            "perDateTimeStart."
        ::= { tunnelPer15mHisEntry 5 }

    -- 1.3.6.1.4.1.2011.2.25.3.70.10.7.70.1.6
    tunnelPer15mHisEndTime OBJECT-TYPE
        SYNTAX DateAndTime
        MAX-ACCESS read-only
        STATUS current
        DESCRIPTION
            "perDateTimeEnd."
        ::= { tunnelPer15mHisEntry 6 }

    -- 1.3.6.1.4.1.2011.2.25.3.70.10.7.70.1.7
    tunnelPer15mHisVldty OBJECT-TYPE
        SYNTAX ValidflagType
        MAX-ACCESS read-only
        STATUS current
        DESCRIPTION
            "perVldty."
        ::= { tunnelPer15mHisEntry 7 }

    -- 1.3.6.1.4.1.2011.2.25.3.70.10.7.80
    tunnelPer24hCurTable OBJECT-TYPE
        SYNTAX SEQUENCE OF TunnelPer24hCurEntry
        MAX-ACCESS not-accessible
        STATUS current
        DESCRIPTION
            "tunnelPer24hCur."
        ::= { tunnel 80 }

    -- 1.3.6.1.4.1.2011.2.25.3.70.10.7.80.1
    tunnelPer24hCurEntry OBJECT-TYPE
        SYNTAX TunnelPer24hCurEntry
        MAX-ACCESS not-accessible
        STATUS current
        DESCRIPTION
            "tunnelPer24hCur"
        INDEX{ tunnelPer24hCurEid,tunnelPer24hCurPara }
        ::= { tunnelPer24hCurTable 1 }

    TunnelPer24hCurEntry ::=
        SEQUENCE {
            tunnelPer24hCurEid
                PerformanceEventType,
            tunnelPer24hCurMonValue
                OCTET STRING,
            tunnelPer24hCurVldty
                ValidflagType,
            tunnelPer24hCurDatetime
                DateAndTime,
            tunnelPer24hCurParaLen
                Unsigned32,
            tunnelPer24hCurPara
                OCTET STRING
        }

    -- 1.3.6.1.4.1.2011.2.25.3.70.10.7.80.1.1
    tunnelPer24hCurEid OBJECT-TYPE
        SYNTAX PerformanceEventType
        MAX-ACCESS read-only
        STATUS current
        DESCRIPTION
            "perEid."
        ::= { tunnelPer24hCurEntry 1 }

    -- 1.3.6.1.4.1.2011.2.25.3.70.10.7.80.1.2
    tunnelPer24hCurMonValue OBJECT-TYPE
        SYNTAX OCTET STRING
        MAX-ACCESS read-only
        STATUS current
        DESCRIPTION
            "perMonValue."
        ::= { tunnelPer24hCurEntry 2 }

    -- 1.3.6.1.4.1.2011.2.25.3.70.10.7.80.1.3
    tunnelPer24hCurVldty OBJECT-TYPE
        SYNTAX ValidflagType
        MAX-ACCESS read-only
        STATUS current
        DESCRIPTION
            "perVldty."
        ::= { tunnelPer24hCurEntry 3 }

    -- 1.3.6.1.4.1.2011.2.25.3.70.10.7.80.1.4
    tunnelPer24hCurDatetime OBJECT-TYPE
        SYNTAX DateAndTime
        MAX-ACCESS read-only
        STATUS current
        DESCRIPTION
            "perDateTime."
        ::= { tunnelPer24hCurEntry 4 }

    -- 1.3.6.1.4.1.2011.2.25.3.70.10.7.80.1.5
    tunnelPer24hCurParaLen OBJECT-TYPE
        SYNTAX Unsigned32
        MAX-ACCESS read-only
        STATUS current
        DESCRIPTION
            "perParaLen."
        ::= { tunnelPer24hCurEntry 5 }

    -- 1.3.6.1.4.1.2011.2.25.3.70.10.7.80.1.6
    tunnelPer24hCurPara OBJECT-TYPE
        SYNTAX OCTET STRING
        MAX-ACCESS read-only
        STATUS current
        DESCRIPTION
            "perPara."
        ::= { tunnelPer24hCurEntry 6 }

    -- 1.3.6.1.4.1.2011.2.25.3.70.10.7.90
    tunnelPer24hHisTable OBJECT-TYPE
        SYNTAX SEQUENCE OF TunnelPer24hHisEntry
        MAX-ACCESS not-accessible
        STATUS current
        DESCRIPTION
            "tunnelPer24hHis."
        ::= { tunnel 90 }

    -- 1.3.6.1.4.1.2011.2.25.3.70.10.7.90.1
    tunnelPer24hHisEntry OBJECT-TYPE
        SYNTAX TunnelPer24hHisEntry
        MAX-ACCESS not-accessible
        STATUS current
        DESCRIPTION
            "tunnelPer24hHis."
        INDEX{ tunnelPer24hHisEid,tunnelPer24hHisParaLen,tunnelPer24hHisPara,tunnelPer24hHisStartTime,tunnelPer24hHisEndTime }
        ::= { tunnelPer24hHisTable 1 }

    TunnelPer24hHisEntry ::=
        SEQUENCE {
            tunnelPer24hHisEid
                PerformanceEventType,
            tunnelPer24hHisParaLen
                Unsigned32,
            tunnelPer24hHisPara
                OCTET STRING,
            tunnelPer24hHisMonValue
                OCTET STRING,
            tunnelPer24hHisStartTime
                DateAndTime,
            tunnelPer24hHisEndTime
                DateAndTime,
            tunnelPer24hHisVldty
                ValidflagType
        }

    -- 1.3.6.1.4.1.2011.2.25.3.70.10.7.90.1.1
    tunnelPer24hHisEid OBJECT-TYPE
        SYNTAX PerformanceEventType
        MAX-ACCESS read-only
        STATUS current
        DESCRIPTION
            "perEid."
        ::= { tunnelPer24hHisEntry 1 }

    -- 1.3.6.1.4.1.2011.2.25.3.70.10.7.90.1.2
    tunnelPer24hHisParaLen OBJECT-TYPE
        SYNTAX Unsigned32
        MAX-ACCESS read-only
        STATUS current
        DESCRIPTION
            "perParaLen."
        ::= { tunnelPer24hHisEntry 2 }

    -- 1.3.6.1.4.1.2011.2.25.3.70.10.7.90.1.3
    tunnelPer24hHisPara OBJECT-TYPE
        SYNTAX OCTET STRING
        MAX-ACCESS read-only
        STATUS current
        DESCRIPTION
            "perPara."
        ::= { tunnelPer24hHisEntry 3 }

    -- 1.3.6.1.4.1.2011.2.25.3.70.10.7.90.1.4
    tunnelPer24hHisMonValue OBJECT-TYPE
        SYNTAX OCTET STRING
        MAX-ACCESS read-only
        STATUS current
        DESCRIPTION
            "perMonValue."
        ::= { tunnelPer24hHisEntry 4 }

    -- 1.3.6.1.4.1.2011.2.25.3.70.10.7.90.1.5
    tunnelPer24hHisStartTime OBJECT-TYPE
        SYNTAX DateAndTime
        MAX-ACCESS read-only
        STATUS current
        DESCRIPTION
            "perDateTimeStart."
        ::= { tunnelPer24hHisEntry 5 }

    -- 1.3.6.1.4.1.2011.2.25.3.70.10.7.90.1.6
    tunnelPer24hHisEndTime OBJECT-TYPE
        SYNTAX DateAndTime
        MAX-ACCESS read-only
        STATUS current
        DESCRIPTION
            "perDateTimeEnd."
        ::= { tunnelPer24hHisEntry 6 }

    -- 1.3.6.1.4.1.2011.2.25.3.70.10.7.90.1.7
    tunnelPer24hHisVldty OBJECT-TYPE
        SYNTAX ValidflagType
        MAX-ACCESS read-only
        STATUS current
        DESCRIPTION
            "perVldty."
        ::= { tunnelPer24hHisEntry 7 }

    -- 1.3.6.1.4.1.2011.2.25.3.70.10.10
    board OBJECT IDENTIFIER ::= { rtnPerformance 10 }

    -- 1.3.6.1.4.1.2011.2.25.3.70.10.10.60
    boardPer15mCurTable OBJECT-TYPE
        SYNTAX SEQUENCE OF BoardPer15mCurEntry
        MAX-ACCESS not-accessible
        STATUS current
        DESCRIPTION
            "boardPer15mCur."
        ::= { board 60 }

    -- 1.3.6.1.4.1.2011.2.25.3.70.10.10.60.1
    boardPer15mCurEntry OBJECT-TYPE
        SYNTAX BoardPer15mCurEntry
        MAX-ACCESS not-accessible
        STATUS current
        DESCRIPTION
            "boardPer15mCur."
        INDEX{ boardPer15mCurEid,boardPer15mCurPara }
        ::= { boardPer15mCurTable 1 }

    BoardPer15mCurEntry ::=
        SEQUENCE {
            boardPer15mCurEid
                PerformanceEventType,
            boardPer15mCurMonValue
                OCTET STRING,
            boardPer15mCurVldty
                ValidflagType,
            boardPer15mCurDatetime
                DateAndTime,
            boardPer15mCurParaLen
                Unsigned32,
            boardPer15mCurPara
                OCTET STRING
        }

    -- 1.3.6.1.4.1.2011.2.25.3.70.10.10.60.1.1
    boardPer15mCurEid OBJECT-TYPE
        SYNTAX PerformanceEventType
        MAX-ACCESS read-only
        STATUS current
        DESCRIPTION
            "perEid."
        ::= { boardPer15mCurEntry 1 }

    -- 1.3.6.1.4.1.2011.2.25.3.70.10.10.60.1.2
    boardPer15mCurMonValue OBJECT-TYPE
        SYNTAX OCTET STRING
        MAX-ACCESS read-only
        STATUS current
        DESCRIPTION
            "perMonValue."
        ::= { boardPer15mCurEntry 2 }

    -- 1.3.6.1.4.1.2011.2.25.3.70.10.10.60.1.3
    boardPer15mCurVldty OBJECT-TYPE
        SYNTAX ValidflagType
        MAX-ACCESS read-only
        STATUS current
        DESCRIPTION
            "perVldty."
        ::= { boardPer15mCurEntry 3 }

    -- 1.3.6.1.4.1.2011.2.25.3.70.10.10.60.1.4
    boardPer15mCurDatetime OBJECT-TYPE
        SYNTAX DateAndTime
        MAX-ACCESS read-only
        STATUS current
        DESCRIPTION
            "perDateTime."
        ::= { boardPer15mCurEntry 4 }

    -- 1.3.6.1.4.1.2011.2.25.3.70.10.10.60.1.5
    boardPer15mCurParaLen OBJECT-TYPE
        SYNTAX Unsigned32
        MAX-ACCESS read-only
        STATUS current
        DESCRIPTION
            "perParaLen."
        ::= { boardPer15mCurEntry 5 }

    -- 1.3.6.1.4.1.2011.2.25.3.70.10.10.60.1.6
    boardPer15mCurPara OBJECT-TYPE
        SYNTAX OCTET STRING
        MAX-ACCESS read-only
        STATUS current
        DESCRIPTION
            "perPara."
        ::= { boardPer15mCurEntry 6 }

    -- 1.3.6.1.4.1.2011.2.25.3.70.10.10.70
    boardPer15mHisTable OBJECT-TYPE
        SYNTAX SEQUENCE OF BoardPer15mHisEntry
        MAX-ACCESS not-accessible
        STATUS current
        DESCRIPTION
            "boardPer15mHis."
        ::= { board 70 }

    -- 1.3.6.1.4.1.2011.2.25.3.70.10.10.70.1
    boardPer15mHisEntry OBJECT-TYPE
        SYNTAX BoardPer15mHisEntry
        MAX-ACCESS not-accessible
        STATUS current
        DESCRIPTION
            "boardPer15mHis."
        INDEX{ boardPer15mHisEid,boardPer15mHisParaLen,boardPer15mHisPara,boardPer15mHisStartTime,boardPer15mHisEndTime }
        ::= { boardPer15mHisTable 1 }

    BoardPer15mHisEntry ::=
        SEQUENCE {
            boardPer15mHisEid
                PerformanceEventType,
            boardPer15mHisParaLen
                Unsigned32,
            boardPer15mHisPara
                OCTET STRING,
            boardPer15mHisMonValue
                OCTET STRING,
            boardPer15mHisStartTime
                DateAndTime,
            boardPer15mHisEndTime
                DateAndTime,
            boardPer15mHisVldty
                ValidflagType
        }

    -- 1.3.6.1.4.1.2011.2.25.3.70.10.10.70.1.1
    boardPer15mHisEid OBJECT-TYPE
        SYNTAX PerformanceEventType
        MAX-ACCESS read-only
        STATUS current
        DESCRIPTION
            "perEid."
        ::= { boardPer15mHisEntry 1 }

    -- 1.3.6.1.4.1.2011.2.25.3.70.10.10.70.1.2
    boardPer15mHisParaLen OBJECT-TYPE
        SYNTAX Unsigned32
        MAX-ACCESS read-only
        STATUS current
        DESCRIPTION
            "perParaLen."
        ::= { boardPer15mHisEntry 2 }

    -- 1.3.6.1.4.1.2011.2.25.3.70.10.10.70.1.3
    boardPer15mHisPara OBJECT-TYPE
        SYNTAX OCTET STRING
        MAX-ACCESS read-only
        STATUS current
        DESCRIPTION
            "perPara."
        ::= { boardPer15mHisEntry 3 }

    -- 1.3.6.1.4.1.2011.2.25.3.70.10.10.70.1.4
    boardPer15mHisMonValue OBJECT-TYPE
        SYNTAX OCTET STRING
        MAX-ACCESS read-only
        STATUS current
        DESCRIPTION
            "perMonValue."
        ::= { boardPer15mHisEntry 4 }

    -- 1.3.6.1.4.1.2011.2.25.3.70.10.10.70.1.5
    boardPer15mHisStartTime OBJECT-TYPE
        SYNTAX DateAndTime
        MAX-ACCESS read-only
        STATUS current
        DESCRIPTION
            "perDateTimeStart."
        ::= { boardPer15mHisEntry 5 }

    -- 1.3.6.1.4.1.2011.2.25.3.70.10.10.70.1.6
    boardPer15mHisEndTime OBJECT-TYPE
        SYNTAX DateAndTime
        MAX-ACCESS read-only
        STATUS current
        DESCRIPTION
            "perDateTimeEnd."
        ::= { boardPer15mHisEntry 6 }

    -- 1.3.6.1.4.1.2011.2.25.3.70.10.10.70.1.7
    boardPer15mHisVldty OBJECT-TYPE
        SYNTAX ValidflagType
        MAX-ACCESS read-only
        STATUS current
        DESCRIPTION
            "perVldty."
        ::= { boardPer15mHisEntry 7 }

    -- 1.3.6.1.4.1.2011.2.25.3.70.10.10.80
    boardPer24hCurTable OBJECT-TYPE
        SYNTAX SEQUENCE OF BoardPer24hCurEntry
        MAX-ACCESS not-accessible
        STATUS current
        DESCRIPTION
            "boardPer24hCur."
        ::= { board 80 }

    -- 1.3.6.1.4.1.2011.2.25.3.70.10.10.80.1
    boardPer24hCurEntry OBJECT-TYPE
        SYNTAX BoardPer24hCurEntry
        MAX-ACCESS not-accessible
        STATUS current
        DESCRIPTION
            "boardPer24hCur."
        INDEX{ boardPer24hCurEid,boardPer24hCurPara }
        ::= { boardPer24hCurTable 1 }

    BoardPer24hCurEntry ::=
        SEQUENCE {
            boardPer24hCurEid
                PerformanceEventType,
            boardPer24hCurMonValue
                OCTET STRING,
            boardPer24hCurVldty
                ValidflagType,
            boardPer24hCurDatetime
                DateAndTime,
            boardPer24hCurParaLen
                Unsigned32,
            boardPer24hCurPara
                OCTET STRING
        }

    -- 1.3.6.1.4.1.2011.2.25.3.70.10.10.80.1.1
    boardPer24hCurEid OBJECT-TYPE
        SYNTAX PerformanceEventType
        MAX-ACCESS read-only
        STATUS current
        DESCRIPTION
            "perEid."
        ::= { boardPer24hCurEntry 1 }

    -- 1.3.6.1.4.1.2011.2.25.3.70.10.10.80.1.2
    boardPer24hCurMonValue OBJECT-TYPE
        SYNTAX OCTET STRING
        MAX-ACCESS read-only
        STATUS current
        DESCRIPTION
            "perMonValue."
        ::= { boardPer24hCurEntry 2 }

    -- 1.3.6.1.4.1.2011.2.25.3.70.10.10.80.1.3
    boardPer24hCurVldty OBJECT-TYPE
        SYNTAX ValidflagType
        MAX-ACCESS read-only
        STATUS current
        DESCRIPTION
            "perVldty."
        ::= { boardPer24hCurEntry 3 }

    -- 1.3.6.1.4.1.2011.2.25.3.70.10.10.80.1.4
    boardPer24hCurDatetime OBJECT-TYPE
        SYNTAX DateAndTime
        MAX-ACCESS read-only
        STATUS current
        DESCRIPTION
            "perDateTime."
        ::= { boardPer24hCurEntry 4 }

    -- 1.3.6.1.4.1.2011.2.25.3.70.10.10.80.1.5
    boardPer24hCurParaLen OBJECT-TYPE
        SYNTAX Unsigned32
        MAX-ACCESS read-only
        STATUS current
        DESCRIPTION
            "perParaLen."
        ::= { boardPer24hCurEntry 5 }

    -- 1.3.6.1.4.1.2011.2.25.3.70.10.10.80.1.6
    boardPer24hCurPara OBJECT-TYPE
        SYNTAX OCTET STRING
        MAX-ACCESS read-only
        STATUS current
        DESCRIPTION
            "perPara."
        ::= { boardPer24hCurEntry 6 }

    -- 1.3.6.1.4.1.2011.2.25.3.70.10.10.90
    boardPer24hHisTable OBJECT-TYPE
        SYNTAX SEQUENCE OF BoardPer24hHisEntry
        MAX-ACCESS not-accessible
        STATUS current
        DESCRIPTION
            "boardPer24hHis."
        ::= { board 90 }

    -- 1.3.6.1.4.1.2011.2.25.3.70.10.10.90.1
    boardPer24hHisEntry OBJECT-TYPE
        SYNTAX BoardPer24hHisEntry
        MAX-ACCESS not-accessible
        STATUS current
        DESCRIPTION
            "boardPer24hHis."
        INDEX{ boardPer24hHisEid,boardPer24hHisParaLen,boardPer24hHisPara,boardPer24hHisStartTime,boardPer24hHisEndTime }
        ::= { boardPer24hHisTable 1 }

    BoardPer24hHisEntry ::=
        SEQUENCE {
            boardPer24hHisEid
                PerformanceEventType,
            boardPer24hHisParaLen
                Unsigned32,
            boardPer24hHisPara
                OCTET STRING,
            boardPer24hHisMonValue
                OCTET STRING,
            boardPer24hHisStartTime
                DateAndTime,
            boardPer24hHisEndTime
                DateAndTime,
            boardPer24hHisVldty
                ValidflagType
        }

    -- 1.3.6.1.4.1.2011.2.25.3.70.10.10.90.1.1
    boardPer24hHisEid OBJECT-TYPE
        SYNTAX PerformanceEventType
        MAX-ACCESS read-only
        STATUS current
        DESCRIPTION
            "perEid."
        ::= { boardPer24hHisEntry 1 }

    -- 1.3.6.1.4.1.2011.2.25.3.70.10.10.90.1.2
    boardPer24hHisParaLen OBJECT-TYPE
        SYNTAX Unsigned32
        MAX-ACCESS read-only
        STATUS current
        DESCRIPTION
            "perParaLen."
        ::= { boardPer24hHisEntry 2 }

    -- 1.3.6.1.4.1.2011.2.25.3.70.10.10.90.1.3
    boardPer24hHisPara OBJECT-TYPE
        SYNTAX OCTET STRING
        MAX-ACCESS read-only
        STATUS current
        DESCRIPTION
            "perPara."
        ::= { boardPer24hHisEntry 3 }

    -- 1.3.6.1.4.1.2011.2.25.3.70.10.10.90.1.4
    boardPer24hHisMonValue OBJECT-TYPE
        SYNTAX OCTET STRING
        MAX-ACCESS read-only
        STATUS current
        DESCRIPTION
            "perMonValue."
        ::= { boardPer24hHisEntry 4 }

    -- 1.3.6.1.4.1.2011.2.25.3.70.10.10.90.1.5
    boardPer24hHisStartTime OBJECT-TYPE
        SYNTAX DateAndTime
        MAX-ACCESS read-only
        STATUS current
        DESCRIPTION
            "perDateTimeStart."
        ::= { boardPer24hHisEntry 5 }

    -- 1.3.6.1.4.1.2011.2.25.3.70.10.10.90.1.6
    boardPer24hHisEndTime OBJECT-TYPE
        SYNTAX DateAndTime
        MAX-ACCESS read-only
        STATUS current
        DESCRIPTION
            "perDateTimeEnd."
        ::= { boardPer24hHisEntry 6 }

    -- 1.3.6.1.4.1.2011.2.25.3.70.10.10.90.1.7
    boardPer24hHisVldty OBJECT-TYPE
        SYNTAX ValidflagType
        MAX-ACCESS read-only
        STATUS current
        DESCRIPTION
            "perVldty."
        ::= { boardPer24hHisEntry 7 }

    -- 1.3.6.1.4.1.2011.2.25.3.70.10.20
    ifboard OBJECT IDENTIFIER ::= { rtnPerformance 20 }

    -- 1.3.6.1.4.1.2011.2.25.3.70.10.20.60
    ifboardPer15mCurTable OBJECT-TYPE
        SYNTAX SEQUENCE OF IfboardPer15mCurEntry
        MAX-ACCESS not-accessible
        STATUS current
        DESCRIPTION
            "ifboardPer15mCur."
        ::= { ifboard 60 }

    -- 1.3.6.1.4.1.2011.2.25.3.70.10.20.60.1
    ifboardPer15mCurEntry OBJECT-TYPE
        SYNTAX IfboardPer15mCurEntry
        MAX-ACCESS not-accessible
        STATUS current
        DESCRIPTION
            "ifboardPer15mCur."
        INDEX{ ifboardPer15mCurEid,ifboardPer15mCurPara }
        ::= { ifboardPer15mCurTable 1 }

    IfboardPer15mCurEntry ::=
        SEQUENCE {
            ifboardPer15mCurEid
                PerformanceEventType,
            ifboardPer15mCurMonValue
                OCTET STRING,
            ifboardPer15mCurVldty
                ValidflagType,
            ifboardPer15mCurDatetime
                DateAndTime,
            ifboardPer15mCurParaLen
                Unsigned32,
            ifboardPer15mCurPara
                OCTET STRING
        }

    -- 1.3.6.1.4.1.2011.2.25.3.70.10.20.60.1.1
    ifboardPer15mCurEid OBJECT-TYPE
        SYNTAX PerformanceEventType
        MAX-ACCESS read-only
        STATUS current
        DESCRIPTION
            "perEid."
        ::= { ifboardPer15mCurEntry 1 }

    -- 1.3.6.1.4.1.2011.2.25.3.70.10.20.60.1.2
    ifboardPer15mCurMonValue OBJECT-TYPE
        SYNTAX OCTET STRING
        MAX-ACCESS read-only
        STATUS current
        DESCRIPTION
            "perMonValue."
        ::= { ifboardPer15mCurEntry 2 }

    -- 1.3.6.1.4.1.2011.2.25.3.70.10.20.60.1.3
    ifboardPer15mCurVldty OBJECT-TYPE
        SYNTAX ValidflagType
        MAX-ACCESS read-only
        STATUS current
        DESCRIPTION
            "perVldty."
        ::= { ifboardPer15mCurEntry 3 }

    -- 1.3.6.1.4.1.2011.2.25.3.70.10.20.60.1.4
    ifboardPer15mCurDatetime OBJECT-TYPE
        SYNTAX DateAndTime
        MAX-ACCESS read-only
        STATUS current
        DESCRIPTION
            "perDateTime."
        ::= { ifboardPer15mCurEntry 4 }

    -- 1.3.6.1.4.1.2011.2.25.3.70.10.20.60.1.5
    ifboardPer15mCurParaLen OBJECT-TYPE
        SYNTAX Unsigned32
        MAX-ACCESS read-only
        STATUS current
        DESCRIPTION
            "perParaLen."
        ::= { ifboardPer15mCurEntry 5 }

    -- 1.3.6.1.4.1.2011.2.25.3.70.10.20.60.1.6
    ifboardPer15mCurPara OBJECT-TYPE
        SYNTAX OCTET STRING
        MAX-ACCESS read-only
        STATUS current
        DESCRIPTION
            "perPara."
        ::= { ifboardPer15mCurEntry 6 }

    -- 1.3.6.1.4.1.2011.2.25.3.70.10.20.70
    ifboardPer15mHisTable OBJECT-TYPE
        SYNTAX SEQUENCE OF IfboardPer15mHisEntry
        MAX-ACCESS not-accessible
        STATUS current
        DESCRIPTION
            "ifboardPer15mHis."
        ::= { ifboard 70 }

    -- 1.3.6.1.4.1.2011.2.25.3.70.10.20.70.1
    ifboardPer15mHisEntry OBJECT-TYPE
        SYNTAX IfboardPer15mHisEntry
        MAX-ACCESS not-accessible
        STATUS current
        DESCRIPTION
            "ifboardPer15mHis."
        INDEX{ ifboardPer15mHisEid,ifboardPer15mHisParaLen,ifboardPer15mHisPara,ifboardPer15mHisStartTime,ifboardPer15mHisEndTime }
        ::= { ifboardPer15mHisTable 1 }

    IfboardPer15mHisEntry ::=
        SEQUENCE {
            ifboardPer15mHisEid
                PerformanceEventType,
            ifboardPer15mHisParaLen
                Unsigned32,
            ifboardPer15mHisPara
                OCTET STRING,
            ifboardPer15mHisMonValue
                OCTET STRING,
            ifboardPer15mHisStartTime
                DateAndTime,
            ifboardPer15mHisEndTime
                DateAndTime,
            ifboardPer15mHisVldty
                ValidflagType
        }

    -- 1.3.6.1.4.1.2011.2.25.3.70.10.20.70.1.1
    ifboardPer15mHisEid OBJECT-TYPE
        SYNTAX PerformanceEventType
        MAX-ACCESS read-only
        STATUS current
        DESCRIPTION
            "perEid."
        ::= { ifboardPer15mHisEntry 1 }

    -- 1.3.6.1.4.1.2011.2.25.3.70.10.20.70.1.2
    ifboardPer15mHisParaLen OBJECT-TYPE
        SYNTAX Unsigned32
        MAX-ACCESS read-only
        STATUS current
        DESCRIPTION
            "perParaLen."
        ::= { ifboardPer15mHisEntry 2 }

    -- 1.3.6.1.4.1.2011.2.25.3.70.10.20.70.1.3
    ifboardPer15mHisPara OBJECT-TYPE
        SYNTAX OCTET STRING
        MAX-ACCESS read-only
        STATUS current
        DESCRIPTION
            "perPara."
        ::= { ifboardPer15mHisEntry 3 }

    -- 1.3.6.1.4.1.2011.2.25.3.70.10.20.70.1.4
    ifboardPer15mHisMonValue OBJECT-TYPE
        SYNTAX OCTET STRING
        MAX-ACCESS read-only
        STATUS current
        DESCRIPTION
            "perMonValue."
        ::= { ifboardPer15mHisEntry 4 }

    -- 1.3.6.1.4.1.2011.2.25.3.70.10.20.70.1.5
    ifboardPer15mHisStartTime OBJECT-TYPE
        SYNTAX DateAndTime
        MAX-ACCESS read-only
        STATUS current
        DESCRIPTION
            "perDateTimeStart."
        ::= { ifboardPer15mHisEntry 5 }

    -- 1.3.6.1.4.1.2011.2.25.3.70.10.20.70.1.6
    ifboardPer15mHisEndTime OBJECT-TYPE
        SYNTAX DateAndTime
        MAX-ACCESS read-only
        STATUS current
        DESCRIPTION
            "perDateTimeEnd."
        ::= { ifboardPer15mHisEntry 6 }

    -- 1.3.6.1.4.1.2011.2.25.3.70.10.20.70.1.7
    ifboardPer15mHisVldty OBJECT-TYPE
        SYNTAX ValidflagType
        MAX-ACCESS read-only
        STATUS current
        DESCRIPTION
            "perVldty."
        ::= { ifboardPer15mHisEntry 7 }

    -- 1.3.6.1.4.1.2011.2.25.3.70.10.20.80
    ifboardPer24hCurTable OBJECT-TYPE
        SYNTAX SEQUENCE OF IfboardPer24hCurEntry
        MAX-ACCESS not-accessible
        STATUS current
        DESCRIPTION
            "ifboardPer24hCur."
        ::= { ifboard 80 }

    -- 1.3.6.1.4.1.2011.2.25.3.70.10.20.80.1
    ifboardPer24hCurEntry OBJECT-TYPE
        SYNTAX IfboardPer24hCurEntry
        MAX-ACCESS not-accessible
        STATUS current
        DESCRIPTION
            "ifboardPer24hCur."
        INDEX{ ifboardPer24hCurEid,ifboardPer24hCurPara }
        ::= { ifboardPer24hCurTable 1 }

    IfboardPer24hCurEntry ::=
        SEQUENCE {
            ifboardPer24hCurEid
                PerformanceEventType,
            ifboardPer24hCurMonValue
                OCTET STRING,
            ifboardPer24hCurVldty
                ValidflagType,
            ifboardPer24hCurDatetime
                DateAndTime,
            ifboardPer24hCurParaLen
                Unsigned32,
            ifboardPer24hCurPara
                OCTET STRING
        }

    -- 1.3.6.1.4.1.2011.2.25.3.70.10.20.80.1.1
    ifboardPer24hCurEid OBJECT-TYPE
        SYNTAX PerformanceEventType
        MAX-ACCESS read-only
        STATUS current
        DESCRIPTION
            "perEid."
        ::= { ifboardPer24hCurEntry 1 }

    -- 1.3.6.1.4.1.2011.2.25.3.70.10.20.80.1.2
    ifboardPer24hCurMonValue OBJECT-TYPE
        SYNTAX OCTET STRING
        MAX-ACCESS read-only
        STATUS current
        DESCRIPTION
            "perMonValue."
        ::= { ifboardPer24hCurEntry 2 }

    -- 1.3.6.1.4.1.2011.2.25.3.70.10.20.80.1.3
    ifboardPer24hCurVldty OBJECT-TYPE
        SYNTAX ValidflagType
        MAX-ACCESS read-only
        STATUS current
        DESCRIPTION
            "perVldty."
        ::= { ifboardPer24hCurEntry 3 }

    -- 1.3.6.1.4.1.2011.2.25.3.70.10.20.80.1.4
    ifboardPer24hCurDatetime OBJECT-TYPE
        SYNTAX DateAndTime
        MAX-ACCESS read-only
        STATUS current
        DESCRIPTION
            "perDateTime."
        ::= { ifboardPer24hCurEntry 4 }

    -- 1.3.6.1.4.1.2011.2.25.3.70.10.20.80.1.5
    ifboardPer24hCurParaLen OBJECT-TYPE
        SYNTAX Unsigned32
        MAX-ACCESS read-only
        STATUS current
        DESCRIPTION
            "perParaLen."
        ::= { ifboardPer24hCurEntry 5 }

    -- 1.3.6.1.4.1.2011.2.25.3.70.10.20.80.1.6
    ifboardPer24hCurPara OBJECT-TYPE
        SYNTAX OCTET STRING
        MAX-ACCESS read-only
        STATUS current
        DESCRIPTION
            "perPara."
        ::= { ifboardPer24hCurEntry 6 }

    -- 1.3.6.1.4.1.2011.2.25.3.70.10.20.90
    ifboardPer24hHisTable OBJECT-TYPE
        SYNTAX SEQUENCE OF IfboardPer24hHisEntry
        MAX-ACCESS not-accessible
        STATUS current
        DESCRIPTION
            "ifboardPer24hHis."
        ::= { ifboard 90 }

    -- 1.3.6.1.4.1.2011.2.25.3.70.10.20.90.1
    ifboardPer24hHisEntry OBJECT-TYPE
        SYNTAX IfboardPer24hHisEntry
        MAX-ACCESS not-accessible
        STATUS current
        DESCRIPTION
            "ifboardPer24hHis."
        INDEX{ ifboardPer24hHisEid,ifboardPer24hHisParaLen,ifboardPer24hHisPara,ifboardPer24hHisStartTime,ifboardPer24hHisEndTime }
        ::= { ifboardPer24hHisTable 1 }

    IfboardPer24hHisEntry ::=
        SEQUENCE {
            ifboardPer24hHisEid
                PerformanceEventType,
            ifboardPer24hHisParaLen
                Unsigned32,
            ifboardPer24hHisPara
                OCTET STRING,
            ifboardPer24hHisMonValue
                OCTET STRING,
            ifboardPer24hHisStartTime
                DateAndTime,
            ifboardPer24hHisEndTime
                DateAndTime,
            ifboardPer24hHisVldty
                ValidflagType
        }

    -- 1.3.6.1.4.1.2011.2.25.3.70.10.20.90.1.1
    ifboardPer24hHisEid OBJECT-TYPE
        SYNTAX PerformanceEventType
        MAX-ACCESS read-only
        STATUS current
        DESCRIPTION
            "perEid."
        ::= { ifboardPer24hHisEntry 1 }

    -- 1.3.6.1.4.1.2011.2.25.3.70.10.20.90.1.2
    ifboardPer24hHisParaLen OBJECT-TYPE
        SYNTAX Unsigned32
        MAX-ACCESS read-only
        STATUS current
        DESCRIPTION
            "perParaLen."
        ::= { ifboardPer24hHisEntry 2 }

    -- 1.3.6.1.4.1.2011.2.25.3.70.10.20.90.1.3
    ifboardPer24hHisPara OBJECT-TYPE
        SYNTAX OCTET STRING
        MAX-ACCESS read-only
        STATUS current
        DESCRIPTION
            "perPara."
        ::= { ifboardPer24hHisEntry 3 }

    -- 1.3.6.1.4.1.2011.2.25.3.70.10.20.90.1.4
    ifboardPer24hHisMonValue OBJECT-TYPE
        SYNTAX OCTET STRING
        MAX-ACCESS read-only
        STATUS current
        DESCRIPTION
            "perMonValue."
        ::= { ifboardPer24hHisEntry 4 }

    -- 1.3.6.1.4.1.2011.2.25.3.70.10.20.90.1.5
    ifboardPer24hHisStartTime OBJECT-TYPE
        SYNTAX DateAndTime
        MAX-ACCESS read-only
        STATUS current
        DESCRIPTION
            "perDateTimeStart."
        ::= { ifboardPer24hHisEntry 5 }

    -- 1.3.6.1.4.1.2011.2.25.3.70.10.20.90.1.6
    ifboardPer24hHisEndTime OBJECT-TYPE
        SYNTAX DateAndTime
        MAX-ACCESS read-only
        STATUS current
        DESCRIPTION
            "perDateTimeEnd."
        ::= { ifboardPer24hHisEntry 6 }

    -- 1.3.6.1.4.1.2011.2.25.3.70.10.20.90.1.7
    ifboardPer24hHisVldty OBJECT-TYPE
        SYNTAX ValidflagType
        MAX-ACCESS read-only
        STATUS current
        DESCRIPTION
            "perVldty."
        ::= { ifboardPer24hHisEntry 7 }

    -- 1.3.6.1.4.1.2011.2.25.3.70.10.30
    oduboard OBJECT IDENTIFIER ::= { rtnPerformance 30 }

    -- 1.3.6.1.4.1.2011.2.25.3.70.10.30.60
    oduboardPer15mCurTable OBJECT-TYPE
        SYNTAX SEQUENCE OF OduboardPer15mCurEntry
        MAX-ACCESS not-accessible
        STATUS current
        DESCRIPTION
            "oduboardPer15mCur."
        ::= { oduboard 60 }

    -- 1.3.6.1.4.1.2011.2.25.3.70.10.30.60.1
    oduboardPer15mCurEntry OBJECT-TYPE
        SYNTAX OduboardPer15mCurEntry
        MAX-ACCESS not-accessible
        STATUS current
        DESCRIPTION
            "oduboardPer15mCur."
        INDEX{ oduboardPer15mCurEid,oduboardPer15mCurPara }
        ::= { oduboardPer15mCurTable 1 }

    OduboardPer15mCurEntry ::=
        SEQUENCE {
            oduboardPer15mCurEid
                PerformanceEventType,
            oduboardPer15mCurMonValue
                OCTET STRING,
            oduboardPer15mCurVldty
                ValidflagType,
            oduboardPer15mCurDatetime
                DateAndTime,
            oduboardPer15mCurParaLen
                Unsigned32,
            oduboardPer15mCurPara
                OCTET STRING
        }

    -- 1.3.6.1.4.1.2011.2.25.3.70.10.30.60.1.1
    oduboardPer15mCurEid OBJECT-TYPE
        SYNTAX PerformanceEventType
        MAX-ACCESS read-only
        STATUS current
        DESCRIPTION
            "perEid."
        ::= { oduboardPer15mCurEntry 1 }

    -- 1.3.6.1.4.1.2011.2.25.3.70.10.30.60.1.2
    oduboardPer15mCurMonValue OBJECT-TYPE
        SYNTAX OCTET STRING
        MAX-ACCESS read-only
        STATUS current
        DESCRIPTION
            "perMonValue."
        ::= { oduboardPer15mCurEntry 2 }

    -- 1.3.6.1.4.1.2011.2.25.3.70.10.30.60.1.3
    oduboardPer15mCurVldty OBJECT-TYPE
        SYNTAX ValidflagType
        MAX-ACCESS read-only
        STATUS current
        DESCRIPTION
            "perVldty."
        ::= { oduboardPer15mCurEntry 3 }

    -- 1.3.6.1.4.1.2011.2.25.3.70.10.30.60.1.4
    oduboardPer15mCurDatetime OBJECT-TYPE
        SYNTAX DateAndTime
        MAX-ACCESS read-only
        STATUS current
        DESCRIPTION
            "perDateTime."
        ::= { oduboardPer15mCurEntry 4 }

    -- 1.3.6.1.4.1.2011.2.25.3.70.10.30.60.1.5
    oduboardPer15mCurParaLen OBJECT-TYPE
        SYNTAX Unsigned32
        MAX-ACCESS read-only
        STATUS current
        DESCRIPTION
            "perParaLen."
        ::= { oduboardPer15mCurEntry 5 }

    -- 1.3.6.1.4.1.2011.2.25.3.70.10.30.60.1.6
    oduboardPer15mCurPara OBJECT-TYPE
        SYNTAX OCTET STRING
        MAX-ACCESS read-only
        STATUS current
        DESCRIPTION
            "perPara."
        ::= { oduboardPer15mCurEntry 6 }

    -- 1.3.6.1.4.1.2011.2.25.3.70.10.30.70
    oduboardPer15mHisTable OBJECT-TYPE
        SYNTAX SEQUENCE OF OduboardPer15mHisEntry
        MAX-ACCESS not-accessible
        STATUS current
        DESCRIPTION
            "oduboardPer15mHis."
        ::= { oduboard 70 }

    -- 1.3.6.1.4.1.2011.2.25.3.70.10.30.70.1
    oduboardPer15mHisEntry OBJECT-TYPE
        SYNTAX OduboardPer15mHisEntry
        MAX-ACCESS not-accessible
        STATUS current
        DESCRIPTION
            "oduboardPer15mHis."
        INDEX{ oduboardPer15mHisEid,oduboardPer15mHisParaLen,oduboardPer15mHisPara,oduboardPer15mHisStartTime,oduboardPer15mHisEndTime }
        ::= { oduboardPer15mHisTable 1 }

    OduboardPer15mHisEntry ::=
        SEQUENCE {
            oduboardPer15mHisEid
                PerformanceEventType,
            oduboardPer15mHisParaLen
                Unsigned32,
            oduboardPer15mHisPara
                OCTET STRING,
            oduboardPer15mHisMonValue
                OCTET STRING,
            oduboardPer15mHisStartTime
                DateAndTime,
            oduboardPer15mHisEndTime
                DateAndTime,
            oduboardPer15mHisVldty
                ValidflagType
        }

    -- 1.3.6.1.4.1.2011.2.25.3.70.10.30.70.1.1
    oduboardPer15mHisEid OBJECT-TYPE
        SYNTAX PerformanceEventType
        MAX-ACCESS read-only
        STATUS current
        DESCRIPTION
            "perEid."
        ::= { oduboardPer15mHisEntry 1 }

    -- 1.3.6.1.4.1.2011.2.25.3.70.10.30.70.1.2
    oduboardPer15mHisParaLen OBJECT-TYPE
        SYNTAX Unsigned32
        MAX-ACCESS read-only
        STATUS current
        DESCRIPTION
            "perParaLen."
        ::= { oduboardPer15mHisEntry 2 }

    -- 1.3.6.1.4.1.2011.2.25.3.70.10.30.70.1.3
    oduboardPer15mHisPara OBJECT-TYPE
        SYNTAX OCTET STRING
        MAX-ACCESS read-only
        STATUS current
        DESCRIPTION
            "perPara."
        ::= { oduboardPer15mHisEntry 3 }

    -- 1.3.6.1.4.1.2011.2.25.3.70.10.30.70.1.4
    oduboardPer15mHisMonValue OBJECT-TYPE
        SYNTAX OCTET STRING
        MAX-ACCESS read-only
        STATUS current
        DESCRIPTION
            "perMonValue."
        ::= { oduboardPer15mHisEntry 4 }

    -- 1.3.6.1.4.1.2011.2.25.3.70.10.30.70.1.5
    oduboardPer15mHisStartTime OBJECT-TYPE
        SYNTAX DateAndTime
        MAX-ACCESS read-only
        STATUS current
        DESCRIPTION
            "perDateTimeStart."
        ::= { oduboardPer15mHisEntry 5 }

    -- 1.3.6.1.4.1.2011.2.25.3.70.10.30.70.1.6
    oduboardPer15mHisEndTime OBJECT-TYPE
        SYNTAX DateAndTime
        MAX-ACCESS read-only
        STATUS current
        DESCRIPTION
            "perDateTimeEnd."
        ::= { oduboardPer15mHisEntry 6 }

    -- 1.3.6.1.4.1.2011.2.25.3.70.10.30.70.1.7
    oduboardPer15mHisVldty OBJECT-TYPE
        SYNTAX ValidflagType
        MAX-ACCESS read-only
        STATUS current
        DESCRIPTION
            "perVldty."
        ::= { oduboardPer15mHisEntry 7 }

    -- 1.3.6.1.4.1.2011.2.25.3.70.10.30.80
    oduboardPer24hCurTable OBJECT-TYPE
        SYNTAX SEQUENCE OF OduboardPer24hCurEntry
        MAX-ACCESS not-accessible
        STATUS current
        DESCRIPTION
            "oduboardPer24hCur."
        ::= { oduboard 80 }

    -- 1.3.6.1.4.1.2011.2.25.3.70.10.30.80.1
    oduboardPer24hCurEntry OBJECT-TYPE
        SYNTAX OduboardPer24hCurEntry
        MAX-ACCESS not-accessible
        STATUS current
        DESCRIPTION
            "oduboardPer24hCur."
        INDEX{ oduboardPer24hCurEid,oduboardPer24hCurPara }
        ::= { oduboardPer24hCurTable 1 }

    OduboardPer24hCurEntry ::=
        SEQUENCE {
            oduboardPer24hCurEid
                PerformanceEventType,
            oduboardPer24hCurMonValue
                OCTET STRING,
            oduboardPer24hCurVldty
                ValidflagType,
            oduboardPer24hCurDatetime
                DateAndTime,
            oduboardPer24hCurParaLen
                Unsigned32,
            oduboardPer24hCurPara
                OCTET STRING
        }

    -- 1.3.6.1.4.1.2011.2.25.3.70.10.30.80.1.1
    oduboardPer24hCurEid OBJECT-TYPE
        SYNTAX PerformanceEventType
        MAX-ACCESS read-only
        STATUS current
        DESCRIPTION
            "perEid."
        ::= { oduboardPer24hCurEntry 1 }

    -- 1.3.6.1.4.1.2011.2.25.3.70.10.30.80.1.2
    oduboardPer24hCurMonValue OBJECT-TYPE
        SYNTAX OCTET STRING
        MAX-ACCESS read-only
        STATUS current
        DESCRIPTION
            "perMonValue."
        ::= { oduboardPer24hCurEntry 2 }

    -- 1.3.6.1.4.1.2011.2.25.3.70.10.30.80.1.3
    oduboardPer24hCurVldty OBJECT-TYPE
        SYNTAX ValidflagType
        MAX-ACCESS read-only
        STATUS current
        DESCRIPTION
            "perVldty."
        ::= { oduboardPer24hCurEntry 3 }

    -- 1.3.6.1.4.1.2011.2.25.3.70.10.30.80.1.4
    oduboardPer24hCurDatetime OBJECT-TYPE
        SYNTAX DateAndTime
        MAX-ACCESS read-only
        STATUS current
        DESCRIPTION
            "perDateTime."
        ::= { oduboardPer24hCurEntry 4 }

    -- 1.3.6.1.4.1.2011.2.25.3.70.10.30.80.1.5
    oduboardPer24hCurParaLen OBJECT-TYPE
        SYNTAX Unsigned32
        MAX-ACCESS read-only
        STATUS current
        DESCRIPTION
            "perParaLen."
        ::= { oduboardPer24hCurEntry 5 }

    -- 1.3.6.1.4.1.2011.2.25.3.70.10.30.80.1.6
    oduboardPer24hCurPara OBJECT-TYPE
        SYNTAX OCTET STRING
        MAX-ACCESS read-only
        STATUS current
        DESCRIPTION
            "perPara."
        ::= { oduboardPer24hCurEntry 6 }

    -- 1.3.6.1.4.1.2011.2.25.3.70.10.30.90
    oduboardPer24hHisTable OBJECT-TYPE
        SYNTAX SEQUENCE OF OduboardPer24hHisEntry
        MAX-ACCESS not-accessible
        STATUS current
        DESCRIPTION
            "oduboardPer24hHis."
        ::= { oduboard 90 }

    -- 1.3.6.1.4.1.2011.2.25.3.70.10.30.90.1
    oduboardPer24hHisEntry OBJECT-TYPE
        SYNTAX OduboardPer24hHisEntry
        MAX-ACCESS not-accessible
        STATUS current
        DESCRIPTION
            "oduboardPer24hHis."
        INDEX{ oduboardPer24hHisEid,oduboardPer24hHisParaLen,oduboardPer24hHisPara,oduboardPer24hHisStartTime,oduboardPer24hHisEndTime }
        ::= { oduboardPer24hHisTable 1 }

    OduboardPer24hHisEntry ::=
        SEQUENCE {
            oduboardPer24hHisEid
                PerformanceEventType,
            oduboardPer24hHisParaLen
                Unsigned32,
            oduboardPer24hHisPara
                OCTET STRING,
            oduboardPer24hHisMonValue
                OCTET STRING,
            oduboardPer24hHisStartTime
                DateAndTime,
            oduboardPer24hHisEndTime
                DateAndTime,
            oduboardPer24hHisVldty
                ValidflagType
        }

    -- 1.3.6.1.4.1.2011.2.25.3.70.10.30.90.1.1
    oduboardPer24hHisEid OBJECT-TYPE
        SYNTAX PerformanceEventType
        MAX-ACCESS read-only
        STATUS current
        DESCRIPTION
            "perEid."
        ::= { oduboardPer24hHisEntry 1 }

    -- 1.3.6.1.4.1.2011.2.25.3.70.10.30.90.1.2
    oduboardPer24hHisParaLen OBJECT-TYPE
        SYNTAX Unsigned32
        MAX-ACCESS read-only
        STATUS current
        DESCRIPTION
            "perParaLen."
        ::= { oduboardPer24hHisEntry 2 }

    -- 1.3.6.1.4.1.2011.2.25.3.70.10.30.90.1.3
    oduboardPer24hHisPara OBJECT-TYPE
        SYNTAX OCTET STRING
        MAX-ACCESS read-only
        STATUS current
        DESCRIPTION
            "perPara."
        ::= { oduboardPer24hHisEntry 3 }

    -- 1.3.6.1.4.1.2011.2.25.3.70.10.30.90.1.4
    oduboardPer24hHisMonValue OBJECT-TYPE
        SYNTAX OCTET STRING
        MAX-ACCESS read-only
        STATUS current
        DESCRIPTION
            "perMonValue."
        ::= { oduboardPer24hHisEntry 4 }

    -- 1.3.6.1.4.1.2011.2.25.3.70.10.30.90.1.5
    oduboardPer24hHisStartTime OBJECT-TYPE
        SYNTAX DateAndTime
        MAX-ACCESS read-only
        STATUS current
        DESCRIPTION
            "perDateTimeStart."
        ::= { oduboardPer24hHisEntry 5 }

    -- 1.3.6.1.4.1.2011.2.25.3.70.10.30.90.1.6
    oduboardPer24hHisEndTime OBJECT-TYPE
        SYNTAX DateAndTime
        MAX-ACCESS read-only
        STATUS current
        DESCRIPTION
            "perDateTimeEnd."
        ::= { oduboardPer24hHisEntry 6 }

    -- 1.3.6.1.4.1.2011.2.25.3.70.10.30.90.1.7
    oduboardPer24hHisVldty OBJECT-TYPE
        SYNTAX ValidflagType
        MAX-ACCESS read-only
        STATUS current
        DESCRIPTION
            "perVldty."
        ::= { oduboardPer24hHisEntry 7 }

    -- 1.3.6.1.4.1.2011.2.25.3.70.10.40
    laser OBJECT IDENTIFIER ::= { rtnPerformance 40 }

    -- 1.3.6.1.4.1.2011.2.25.3.70.10.40.60
    laserPer15mCurTable OBJECT-TYPE
        SYNTAX SEQUENCE OF LaserPer15mCurEntry
        MAX-ACCESS not-accessible
        STATUS current
        DESCRIPTION
            "laserPer15mCur."
        ::= { laser 60 }

    -- 1.3.6.1.4.1.2011.2.25.3.70.10.40.60.1
    laserPer15mCurEntry OBJECT-TYPE
        SYNTAX LaserPer15mCurEntry
        MAX-ACCESS not-accessible
        STATUS current
        DESCRIPTION
            "laserPer15mCur."
        INDEX{ laserPer15mCurEid,laserPer15mCurPara }
        ::= { laserPer15mCurTable 1 }

    LaserPer15mCurEntry ::=
        SEQUENCE {
            laserPer15mCurEid
                PerformanceEventType,
            laserPer15mCurMonValue
                OCTET STRING,
            laserPer15mCurVldty
                ValidflagType,
            laserPer15mCurDatetime
                DateAndTime,
            laserPer15mCurParaLen
                Unsigned32,
            laserPer15mCurPara
                OCTET STRING
        }

    -- 1.3.6.1.4.1.2011.2.25.3.70.10.40.60.1.1
    laserPer15mCurEid OBJECT-TYPE
        SYNTAX PerformanceEventType
        MAX-ACCESS read-only
        STATUS current
        DESCRIPTION
            "perEid."
        ::= { laserPer15mCurEntry 1 }

    -- 1.3.6.1.4.1.2011.2.25.3.70.10.40.60.1.2
    laserPer15mCurMonValue OBJECT-TYPE
        SYNTAX OCTET STRING
        MAX-ACCESS read-only
        STATUS current
        DESCRIPTION
            "perMonValue."
        ::= { laserPer15mCurEntry 2 }

    -- 1.3.6.1.4.1.2011.2.25.3.70.10.40.60.1.3
    laserPer15mCurVldty OBJECT-TYPE
        SYNTAX ValidflagType
        MAX-ACCESS read-only
        STATUS current
        DESCRIPTION
            "perVldty."
        ::= { laserPer15mCurEntry 3 }

    -- 1.3.6.1.4.1.2011.2.25.3.70.10.40.60.1.4
    laserPer15mCurDatetime OBJECT-TYPE
        SYNTAX DateAndTime
        MAX-ACCESS read-only
        STATUS current
        DESCRIPTION
            "perDateTime."
        ::= { laserPer15mCurEntry 4 }

    -- 1.3.6.1.4.1.2011.2.25.3.70.10.40.60.1.5
    laserPer15mCurParaLen OBJECT-TYPE
        SYNTAX Unsigned32
        MAX-ACCESS read-only
        STATUS current
        DESCRIPTION
            "perParaLen."
        ::= { laserPer15mCurEntry 5 }

    -- 1.3.6.1.4.1.2011.2.25.3.70.10.40.60.1.6
    laserPer15mCurPara OBJECT-TYPE
        SYNTAX OCTET STRING
        MAX-ACCESS read-only
        STATUS current
        DESCRIPTION
            "perPara."
        ::= { laserPer15mCurEntry 6 }

    -- 1.3.6.1.4.1.2011.2.25.3.70.10.40.70
    laserPer15mHisTable OBJECT-TYPE
        SYNTAX SEQUENCE OF LaserPer15mHisEntry
        MAX-ACCESS not-accessible
        STATUS current
        DESCRIPTION
            "laserPer15mHis."
        ::= { laser 70 }

    -- 1.3.6.1.4.1.2011.2.25.3.70.10.40.70.1
    laserPer15mHisEntry OBJECT-TYPE
        SYNTAX LaserPer15mHisEntry
        MAX-ACCESS not-accessible
        STATUS current
        DESCRIPTION
            "laserPer15mHis."
        INDEX{ laserPer15mHisEid,laserPer15mHisParaLen,laserPer15mHisPara,laserPer15mHisStartTime,laserPer15mHisEndTime }
        ::= { laserPer15mHisTable 1 }

    LaserPer15mHisEntry ::=
        SEQUENCE {
            laserPer15mHisEid
                PerformanceEventType,
            laserPer15mHisParaLen
                Unsigned32,
            laserPer15mHisPara
                OCTET STRING,
            laserPer15mHisMonValue
                OCTET STRING,
            laserPer15mHisStartTime
                DateAndTime,
            laserPer15mHisEndTime
                DateAndTime,
            laserPer15mHisVldty
                ValidflagType
        }

    -- 1.3.6.1.4.1.2011.2.25.3.70.10.40.70.1.1
    laserPer15mHisEid OBJECT-TYPE
        SYNTAX PerformanceEventType
        MAX-ACCESS read-only
        STATUS current
        DESCRIPTION
            "perEid."
        ::= { laserPer15mHisEntry 1 }

    -- 1.3.6.1.4.1.2011.2.25.3.70.10.40.70.1.2
    laserPer15mHisParaLen OBJECT-TYPE
        SYNTAX Unsigned32
        MAX-ACCESS read-only
        STATUS current
        DESCRIPTION
            "perParaLen."
        ::= { laserPer15mHisEntry 2 }

    -- 1.3.6.1.4.1.2011.2.25.3.70.10.40.70.1.3
    laserPer15mHisPara OBJECT-TYPE
        SYNTAX OCTET STRING
        MAX-ACCESS read-only
        STATUS current
        DESCRIPTION
            "perPara."
        ::= { laserPer15mHisEntry 3 }

    -- 1.3.6.1.4.1.2011.2.25.3.70.10.40.70.1.4
    laserPer15mHisMonValue OBJECT-TYPE
        SYNTAX OCTET STRING
        MAX-ACCESS read-only
        STATUS current
        DESCRIPTION
            "perMonValue."
        ::= { laserPer15mHisEntry 4 }

    -- 1.3.6.1.4.1.2011.2.25.3.70.10.40.70.1.5
    laserPer15mHisStartTime OBJECT-TYPE
        SYNTAX DateAndTime
        MAX-ACCESS read-only
        STATUS current
        DESCRIPTION
            "perDateTimeStart."
        ::= { laserPer15mHisEntry 5 }

    -- 1.3.6.1.4.1.2011.2.25.3.70.10.40.70.1.6
    laserPer15mHisEndTime OBJECT-TYPE
        SYNTAX DateAndTime
        MAX-ACCESS read-only
        STATUS current
        DESCRIPTION
            "perDateTimeEnd."
        ::= { laserPer15mHisEntry 6 }

    -- 1.3.6.1.4.1.2011.2.25.3.70.10.40.70.1.7
    laserPer15mHisVldty OBJECT-TYPE
        SYNTAX ValidflagType
        MAX-ACCESS read-only
        STATUS current
        DESCRIPTION
            "perVldty."
        ::= { laserPer15mHisEntry 7 }

    -- 1.3.6.1.4.1.2011.2.25.3.70.10.40.80
    laserPer24hCurTable OBJECT-TYPE
        SYNTAX SEQUENCE OF LaserPer24hCurEntry
        MAX-ACCESS not-accessible
        STATUS current
        DESCRIPTION
            "laserPer24hCur."
        ::= { laser 80 }

    -- 1.3.6.1.4.1.2011.2.25.3.70.10.40.80.1
    laserPer24hCurEntry OBJECT-TYPE
        SYNTAX LaserPer24hCurEntry
        MAX-ACCESS not-accessible
        STATUS current
        DESCRIPTION
            "laserPer24hCur."
        INDEX{ laserPer24hCurEid,laserPer24hCurPara }
        ::= { laserPer24hCurTable 1 }

    LaserPer24hCurEntry ::=
        SEQUENCE {
            laserPer24hCurEid
                PerformanceEventType,
            laserPer24hCurMonValue
                OCTET STRING,
            laserPer24hCurVldty
                ValidflagType,
            laserPer24hCurDatetime
                DateAndTime,
            laserPer24hCurParaLen
                Unsigned32,
            laserPer24hCurPara
                OCTET STRING
        }

    -- 1.3.6.1.4.1.2011.2.25.3.70.10.40.80.1.1
    laserPer24hCurEid OBJECT-TYPE
        SYNTAX PerformanceEventType
        MAX-ACCESS read-only
        STATUS current
        DESCRIPTION
            "perEid."
        ::= { laserPer24hCurEntry 1 }

    -- 1.3.6.1.4.1.2011.2.25.3.70.10.40.80.1.2
    laserPer24hCurMonValue OBJECT-TYPE
        SYNTAX OCTET STRING
        MAX-ACCESS read-only
        STATUS current
        DESCRIPTION
            "perMonValue."
        ::= { laserPer24hCurEntry 2 }

    -- 1.3.6.1.4.1.2011.2.25.3.70.10.40.80.1.3
    laserPer24hCurVldty OBJECT-TYPE
        SYNTAX ValidflagType
        MAX-ACCESS read-only
        STATUS current
        DESCRIPTION
            "perVldty."
        ::= { laserPer24hCurEntry 3 }

    -- 1.3.6.1.4.1.2011.2.25.3.70.10.40.80.1.4
    laserPer24hCurDatetime OBJECT-TYPE
        SYNTAX DateAndTime
        MAX-ACCESS read-only
        STATUS current
        DESCRIPTION
            "perDateTime."
        ::= { laserPer24hCurEntry 4 }

    -- 1.3.6.1.4.1.2011.2.25.3.70.10.40.80.1.5
    laserPer24hCurParaLen OBJECT-TYPE
        SYNTAX Unsigned32
        MAX-ACCESS read-only
        STATUS current
        DESCRIPTION
            "perParaLen."
        ::= { laserPer24hCurEntry 5 }

    -- 1.3.6.1.4.1.2011.2.25.3.70.10.40.80.1.6
    laserPer24hCurPara OBJECT-TYPE
        SYNTAX OCTET STRING
        MAX-ACCESS read-only
        STATUS current
        DESCRIPTION
            "perPara."
        ::= { laserPer24hCurEntry 6 }

    -- 1.3.6.1.4.1.2011.2.25.3.70.10.40.90
    laserPer24hHisTable OBJECT-TYPE
        SYNTAX SEQUENCE OF LaserPer24hHisEntry
        MAX-ACCESS not-accessible
        STATUS current
        DESCRIPTION
            "laserPer24hHis."
        ::= { laser 90 }

    -- 1.3.6.1.4.1.2011.2.25.3.70.10.40.90.1
    laserPer24hHisEntry OBJECT-TYPE
        SYNTAX LaserPer24hHisEntry
        MAX-ACCESS not-accessible
        STATUS current
        DESCRIPTION
            "laserPer24hHis."
        INDEX{ laserPer24hHisEid,laserPer24hHisParaLen,laserPer24hHisPara,laserPer24hHisStartTime,laserPer24hHisEndTime }
        ::= { laserPer24hHisTable 1 }

    LaserPer24hHisEntry ::=
        SEQUENCE {
            laserPer24hHisEid
                PerformanceEventType,
            laserPer24hHisParaLen
                Unsigned32,
            laserPer24hHisPara
                OCTET STRING,
            laserPer24hHisMonValue
                OCTET STRING,
            laserPer24hHisStartTime
                DateAndTime,
            laserPer24hHisEndTime
                DateAndTime,
            laserPer24hHisVldty
                ValidflagType
        }

    -- 1.3.6.1.4.1.2011.2.25.3.70.10.40.90.1.1
    laserPer24hHisEid OBJECT-TYPE
        SYNTAX PerformanceEventType
        MAX-ACCESS read-only
        STATUS current
        DESCRIPTION
            "perEid."
        ::= { laserPer24hHisEntry 1 }

    -- 1.3.6.1.4.1.2011.2.25.3.70.10.40.90.1.2
    laserPer24hHisParaLen OBJECT-TYPE
        SYNTAX Unsigned32
        MAX-ACCESS read-only
        STATUS current
        DESCRIPTION
            "perParaLen."
        ::= { laserPer24hHisEntry 2 }

    -- 1.3.6.1.4.1.2011.2.25.3.70.10.40.90.1.3
    laserPer24hHisPara OBJECT-TYPE
        SYNTAX OCTET STRING
        MAX-ACCESS read-only
        STATUS current
        DESCRIPTION
            "perPara."
        ::= { laserPer24hHisEntry 3 }

    -- 1.3.6.1.4.1.2011.2.25.3.70.10.40.90.1.4
    laserPer24hHisMonValue OBJECT-TYPE
        SYNTAX OCTET STRING
        MAX-ACCESS read-only
        STATUS current
        DESCRIPTION
            "perMonValue."
        ::= { laserPer24hHisEntry 4 }

    -- 1.3.6.1.4.1.2011.2.25.3.70.10.40.90.1.5
    laserPer24hHisStartTime OBJECT-TYPE
        SYNTAX DateAndTime
        MAX-ACCESS read-only
        STATUS current
        DESCRIPTION
            "perDateTimeStart."
        ::= { laserPer24hHisEntry 5 }

    -- 1.3.6.1.4.1.2011.2.25.3.70.10.40.90.1.6
    laserPer24hHisEndTime OBJECT-TYPE
        SYNTAX DateAndTime
        MAX-ACCESS read-only
        STATUS current
        DESCRIPTION
            "perDateTimeEnd."
        ::= { laserPer24hHisEntry 6 }

    -- 1.3.6.1.4.1.2011.2.25.3.70.10.40.90.1.7
    laserPer24hHisVldty OBJECT-TYPE
        SYNTAX ValidflagType
        MAX-ACCESS read-only
        STATUS current
        DESCRIPTION
            "perVldty."
        ::= { laserPer24hHisEntry 7 }

    -- 1.3.6.1.4.1.2011.2.25.3.70.10.42
    pwofatm OBJECT IDENTIFIER ::= { rtnPerformance 42 }

    -- 1.3.6.1.4.1.2011.2.25.3.70.10.42.60
    pwofatmPer15mCurTable OBJECT-TYPE
        SYNTAX SEQUENCE OF PwofatmPer15mCurEntry
        MAX-ACCESS not-accessible
        STATUS current
        DESCRIPTION
            "pwofatmPer15mCur."
        ::= { pwofatm 60 }

    -- 1.3.6.1.4.1.2011.2.25.3.70.10.42.60.1
    pwofatmPer15mCurEntry OBJECT-TYPE
        SYNTAX PwofatmPer15mCurEntry
        MAX-ACCESS not-accessible
        STATUS current
        DESCRIPTION
            "pwofatmPer15mCur."
        INDEX{ pwofatmPer15mCurEid,pwofatmPer15mCurPara }
        ::= { pwofatmPer15mCurTable 1 }

    PwofatmPer15mCurEntry ::=
        SEQUENCE {
            pwofatmPer15mCurEid
                PerformanceEventType,
            pwofatmPer15mCurMonValue
                OCTET STRING,
            pwofatmPer15mCurVldty
                ValidflagType,
            pwofatmPer15mCurDatetime
                DateAndTime,
            pwofatmPer15mCurParaLen
                Unsigned32,
            pwofatmPer15mCurPara
                OCTET STRING
        }

    -- 1.3.6.1.4.1.2011.2.25.3.70.10.42.60.1.1
    pwofatmPer15mCurEid OBJECT-TYPE
        SYNTAX PerformanceEventType
        MAX-ACCESS read-only
        STATUS current
        DESCRIPTION
            "perEid."
        ::= { pwofatmPer15mCurEntry 1 }

    -- 1.3.6.1.4.1.2011.2.25.3.70.10.42.60.1.2
    pwofatmPer15mCurMonValue OBJECT-TYPE
        SYNTAX OCTET STRING
        MAX-ACCESS read-only
        STATUS current
        DESCRIPTION
            "perMonValue."
        ::= { pwofatmPer15mCurEntry 2 }

    -- 1.3.6.1.4.1.2011.2.25.3.70.10.42.60.1.3
    pwofatmPer15mCurVldty OBJECT-TYPE
        SYNTAX ValidflagType
        MAX-ACCESS read-only
        STATUS current
        DESCRIPTION
            "perVldty."
        ::= { pwofatmPer15mCurEntry 3 }

    -- 1.3.6.1.4.1.2011.2.25.3.70.10.42.60.1.4
    pwofatmPer15mCurDatetime OBJECT-TYPE
        SYNTAX DateAndTime
        MAX-ACCESS read-only
        STATUS current
        DESCRIPTION
            "perDateTime."
        ::= { pwofatmPer15mCurEntry 4 }

    -- 1.3.6.1.4.1.2011.2.25.3.70.10.42.60.1.5
    pwofatmPer15mCurParaLen OBJECT-TYPE
        SYNTAX Unsigned32
        MAX-ACCESS read-only
        STATUS current
        DESCRIPTION
            "perParaLen."
        ::= { pwofatmPer15mCurEntry 5 }

    -- 1.3.6.1.4.1.2011.2.25.3.70.10.42.60.1.6
    pwofatmPer15mCurPara OBJECT-TYPE
        SYNTAX OCTET STRING
        MAX-ACCESS read-only
        STATUS current
        DESCRIPTION
            "perPara."
        ::= { pwofatmPer15mCurEntry 6 }

    -- 1.3.6.1.4.1.2011.2.25.3.70.10.42.70
    pwofatmPer15mHisTable OBJECT-TYPE
        SYNTAX SEQUENCE OF PwofatmPer15mHisEntry
        MAX-ACCESS not-accessible
        STATUS current
        DESCRIPTION
            "pwofatmPer15mHis."
        ::= { pwofatm 70 }

    -- 1.3.6.1.4.1.2011.2.25.3.70.10.42.70.1
    pwofatmPer15mHisEntry OBJECT-TYPE
        SYNTAX PwofatmPer15mHisEntry
        MAX-ACCESS not-accessible
        STATUS current
        DESCRIPTION
            "pwofatmPer15mHis."
        INDEX{ pwofatmPer15mHisEid,pwofatmPer15mHisParaLen,pwofatmPer15mHisPara,pwofatmPer15mHisStartTime,pwofatmPer15mHisEndTime }
        ::= { pwofatmPer15mHisTable 1 }

    PwofatmPer15mHisEntry ::=
        SEQUENCE {
            pwofatmPer15mHisEid
                PerformanceEventType,
            pwofatmPer15mHisParaLen
                Unsigned32,
            pwofatmPer15mHisPara
                OCTET STRING,
            pwofatmPer15mHisMonValue
                OCTET STRING,
            pwofatmPer15mHisStartTime
                DateAndTime,
            pwofatmPer15mHisEndTime
                DateAndTime,
            pwofatmPer15mHisVldty
                ValidflagType
        }

    -- 1.3.6.1.4.1.2011.2.25.3.70.10.42.70.1.1
    pwofatmPer15mHisEid OBJECT-TYPE
        SYNTAX PerformanceEventType
        MAX-ACCESS read-only
        STATUS current
        DESCRIPTION
            "perEid."
        ::= { pwofatmPer15mHisEntry 1 }

    -- 1.3.6.1.4.1.2011.2.25.3.70.10.42.70.1.2
    pwofatmPer15mHisParaLen OBJECT-TYPE
        SYNTAX Unsigned32
        MAX-ACCESS read-only
        STATUS current
        DESCRIPTION
            "perParaLen."
        ::= { pwofatmPer15mHisEntry 2 }

    -- 1.3.6.1.4.1.2011.2.25.3.70.10.42.70.1.3
    pwofatmPer15mHisPara OBJECT-TYPE
        SYNTAX OCTET STRING
        MAX-ACCESS read-only
        STATUS current
        DESCRIPTION
            "perPara."
        ::= { pwofatmPer15mHisEntry 3 }

    -- 1.3.6.1.4.1.2011.2.25.3.70.10.42.70.1.4
    pwofatmPer15mHisMonValue OBJECT-TYPE
        SYNTAX OCTET STRING
        MAX-ACCESS read-only
        STATUS current
        DESCRIPTION
            "perMonValue."
        ::= { pwofatmPer15mHisEntry 4 }

    -- 1.3.6.1.4.1.2011.2.25.3.70.10.42.70.1.5
    pwofatmPer15mHisStartTime OBJECT-TYPE
        SYNTAX DateAndTime
        MAX-ACCESS read-only
        STATUS current
        DESCRIPTION
            "perDateTimeStart."
        ::= { pwofatmPer15mHisEntry 5 }

    -- 1.3.6.1.4.1.2011.2.25.3.70.10.42.70.1.6
    pwofatmPer15mHisEndTime OBJECT-TYPE
        SYNTAX DateAndTime
        MAX-ACCESS read-only
        STATUS current
        DESCRIPTION
            "perDateTimeEnd."
        ::= { pwofatmPer15mHisEntry 6 }

    -- 1.3.6.1.4.1.2011.2.25.3.70.10.42.70.1.7
    pwofatmPer15mHisVldty OBJECT-TYPE
        SYNTAX ValidflagType
        MAX-ACCESS read-only
        STATUS current
        DESCRIPTION
            "perVldty."
        ::= { pwofatmPer15mHisEntry 7 }

    -- 1.3.6.1.4.1.2011.2.25.3.70.10.42.80
    pwofatmPer24hCurTable OBJECT-TYPE
        SYNTAX SEQUENCE OF PwofatmPer24hCurEntry
        MAX-ACCESS not-accessible
        STATUS current
        DESCRIPTION
            "pwofatmPer24hCur."
        ::= { pwofatm 80 }

    -- 1.3.6.1.4.1.2011.2.25.3.70.10.42.80.1
    pwofatmPer24hCurEntry OBJECT-TYPE
        SYNTAX PwofatmPer24hCurEntry
        MAX-ACCESS not-accessible
        STATUS current
        DESCRIPTION
            "pwofatmPer24hCur."
        INDEX{ pwofatmPer24hCurEid,pwofatmPer24hCurPara }
        ::= { pwofatmPer24hCurTable 1 }

    PwofatmPer24hCurEntry ::=
        SEQUENCE {
            pwofatmPer24hCurEid
                PerformanceEventType,
            pwofatmPer24hCurMonValue
                OCTET STRING,
            pwofatmPer24hCurVldty
                ValidflagType,
            pwofatmPer24hCurDatetime
                DateAndTime,
            pwofatmPer24hCurParaLen
                Unsigned32,
            pwofatmPer24hCurPara
                OCTET STRING
        }

    -- 1.3.6.1.4.1.2011.2.25.3.70.10.42.80.1.1
    pwofatmPer24hCurEid OBJECT-TYPE
        SYNTAX PerformanceEventType
        MAX-ACCESS read-only
        STATUS current
        DESCRIPTION
            "perEid."
        ::= { pwofatmPer24hCurEntry 1 }

    -- 1.3.6.1.4.1.2011.2.25.3.70.10.42.80.1.2
    pwofatmPer24hCurMonValue OBJECT-TYPE
        SYNTAX OCTET STRING
        MAX-ACCESS read-only
        STATUS current
        DESCRIPTION
            "perMonValue."
        ::= { pwofatmPer24hCurEntry 2 }

    -- 1.3.6.1.4.1.2011.2.25.3.70.10.42.80.1.3
    pwofatmPer24hCurVldty OBJECT-TYPE
        SYNTAX ValidflagType
        MAX-ACCESS read-only
        STATUS current
        DESCRIPTION
            "perVldty."
        ::= { pwofatmPer24hCurEntry 3 }

    -- 1.3.6.1.4.1.2011.2.25.3.70.10.42.80.1.4
    pwofatmPer24hCurDatetime OBJECT-TYPE
        SYNTAX DateAndTime
        MAX-ACCESS read-only
        STATUS current
        DESCRIPTION
            "perDateTime."
        ::= { pwofatmPer24hCurEntry 4 }

    -- 1.3.6.1.4.1.2011.2.25.3.70.10.42.80.1.5
    pwofatmPer24hCurParaLen OBJECT-TYPE
        SYNTAX Unsigned32
        MAX-ACCESS read-only
        STATUS current
        DESCRIPTION
            "perParaLen."
        ::= { pwofatmPer24hCurEntry 5 }

    -- 1.3.6.1.4.1.2011.2.25.3.70.10.42.80.1.6
    pwofatmPer24hCurPara OBJECT-TYPE
        SYNTAX OCTET STRING
        MAX-ACCESS read-only
        STATUS current
        DESCRIPTION
            "perPara."
        ::= { pwofatmPer24hCurEntry 6 }

    -- 1.3.6.1.4.1.2011.2.25.3.70.10.42.90
    pwofatmPer24hHisTable OBJECT-TYPE
        SYNTAX SEQUENCE OF PwofatmPer24hHisEntry
        MAX-ACCESS not-accessible
        STATUS current
        DESCRIPTION
            "pwofatmPer24hHis."
        ::= { pwofatm 90 }

    -- 1.3.6.1.4.1.2011.2.25.3.70.10.42.90.1
    pwofatmPer24hHisEntry OBJECT-TYPE
        SYNTAX PwofatmPer24hHisEntry
        MAX-ACCESS not-accessible
        STATUS current
        DESCRIPTION
            "pwofatmPer24hHis."
        INDEX{ pwofatmPer24hHisEid,pwofatmPer24hHisParaLen,pwofatmPer24hHisPara,pwofatmPer24hHisStartTime,pwofatmPer24hHisEndTime }
        ::= { pwofatmPer24hHisTable 1 }

    PwofatmPer24hHisEntry ::=
        SEQUENCE {
            pwofatmPer24hHisEid
                PerformanceEventType,
            pwofatmPer24hHisParaLen
                Unsigned32,
            pwofatmPer24hHisPara
                OCTET STRING,
            pwofatmPer24hHisMonValue
                OCTET STRING,
            pwofatmPer24hHisStartTime
                DateAndTime,
            pwofatmPer24hHisEndTime
                DateAndTime,
            pwofatmPer24hHisVldty
                ValidflagType
        }

    -- 1.3.6.1.4.1.2011.2.25.3.70.10.42.90.1.1
    pwofatmPer24hHisEid OBJECT-TYPE
        SYNTAX PerformanceEventType
        MAX-ACCESS read-only
        STATUS current
        DESCRIPTION
            "perEid."
        ::= { pwofatmPer24hHisEntry 1 }

    -- 1.3.6.1.4.1.2011.2.25.3.70.10.42.90.1.2
    pwofatmPer24hHisParaLen OBJECT-TYPE
        SYNTAX Unsigned32
        MAX-ACCESS read-only
        STATUS current
        DESCRIPTION
            "perParaLen."
        ::= { pwofatmPer24hHisEntry 2 }

    -- 1.3.6.1.4.1.2011.2.25.3.70.10.42.90.1.3
    pwofatmPer24hHisPara OBJECT-TYPE
        SYNTAX OCTET STRING
        MAX-ACCESS read-only
        STATUS current
        DESCRIPTION
            "perPara."
        ::= { pwofatmPer24hHisEntry 3 }

    -- 1.3.6.1.4.1.2011.2.25.3.70.10.42.90.1.4
    pwofatmPer24hHisMonValue OBJECT-TYPE
        SYNTAX OCTET STRING
        MAX-ACCESS read-only
        STATUS current
        DESCRIPTION
            "perMonValue."
        ::= { pwofatmPer24hHisEntry 4 }

    -- 1.3.6.1.4.1.2011.2.25.3.70.10.42.90.1.5
    pwofatmPer24hHisStartTime OBJECT-TYPE
        SYNTAX DateAndTime
        MAX-ACCESS read-only
        STATUS current
        DESCRIPTION
            "perDateTimeStart."
        ::= { pwofatmPer24hHisEntry 5 }

    -- 1.3.6.1.4.1.2011.2.25.3.70.10.42.90.1.6
    pwofatmPer24hHisEndTime OBJECT-TYPE
        SYNTAX DateAndTime
        MAX-ACCESS read-only
        STATUS current
        DESCRIPTION
            "perDateTimeEnd."
        ::= { pwofatmPer24hHisEntry 6 }

    -- 1.3.6.1.4.1.2011.2.25.3.70.10.42.90.1.7
    pwofatmPer24hHisVldty OBJECT-TYPE
        SYNTAX ValidflagType
        MAX-ACCESS read-only
        STATUS current
        DESCRIPTION
            "perVldty."
        ::= { pwofatmPer24hHisEntry 7 }

    -- 1.3.6.1.4.1.2011.2.25.3.70.10.43
    pwofces OBJECT IDENTIFIER ::= { rtnPerformance 43 }

    -- 1.3.6.1.4.1.2011.2.25.3.70.10.43.60
    pwofcesPer15mCurTable OBJECT-TYPE
        SYNTAX SEQUENCE OF PwofcesPer15mCurEntry
        MAX-ACCESS not-accessible
        STATUS current
        DESCRIPTION
            "pwofcesPer15mCur."
        ::= { pwofces 60 }

    -- 1.3.6.1.4.1.2011.2.25.3.70.10.43.60.1
    pwofcesPer15mCurEntry OBJECT-TYPE
        SYNTAX PwofcesPer15mCurEntry
        MAX-ACCESS not-accessible
        STATUS current
        DESCRIPTION
            "pwofcesPer15mCur."
        INDEX{ pwofcesPer15mCurEid,pwofcesPer15mCurPara }
        ::= { pwofcesPer15mCurTable 1 }

    PwofcesPer15mCurEntry ::=
        SEQUENCE {
            pwofcesPer15mCurEid
                PerformanceEventType,
            pwofcesPer15mCurMonValue
                OCTET STRING,
            pwofcesPer15mCurVldty
                ValidflagType,
            pwofcesPer15mCurDatetime
                DateAndTime,
            pwofcesPer15mCurParaLen
                Unsigned32,
            pwofcesPer15mCurPara
                OCTET STRING
        }

    -- 1.3.6.1.4.1.2011.2.25.3.70.10.43.60.1.1
    pwofcesPer15mCurEid OBJECT-TYPE
        SYNTAX PerformanceEventType
        MAX-ACCESS read-only
        STATUS current
        DESCRIPTION
            "perEid."
        ::= { pwofcesPer15mCurEntry 1 }

    -- 1.3.6.1.4.1.2011.2.25.3.70.10.43.60.1.2
    pwofcesPer15mCurMonValue OBJECT-TYPE
        SYNTAX OCTET STRING
        MAX-ACCESS read-only
        STATUS current
        DESCRIPTION
            "perMonValue."
        ::= { pwofcesPer15mCurEntry 2 }

    -- 1.3.6.1.4.1.2011.2.25.3.70.10.43.60.1.3
    pwofcesPer15mCurVldty OBJECT-TYPE
        SYNTAX ValidflagType
        MAX-ACCESS read-only
        STATUS current
        DESCRIPTION
            "perVldty."
        ::= { pwofcesPer15mCurEntry 3 }

    -- 1.3.6.1.4.1.2011.2.25.3.70.10.43.60.1.4
    pwofcesPer15mCurDatetime OBJECT-TYPE
        SYNTAX DateAndTime
        MAX-ACCESS read-only
        STATUS current
        DESCRIPTION
            "perDateTime."
        ::= { pwofcesPer15mCurEntry 4 }

    -- 1.3.6.1.4.1.2011.2.25.3.70.10.43.60.1.5
    pwofcesPer15mCurParaLen OBJECT-TYPE
        SYNTAX Unsigned32
        MAX-ACCESS read-only
        STATUS current
        DESCRIPTION
            "perParaLen."
        ::= { pwofcesPer15mCurEntry 5 }

    -- 1.3.6.1.4.1.2011.2.25.3.70.10.43.60.1.6
    pwofcesPer15mCurPara OBJECT-TYPE
        SYNTAX OCTET STRING
        MAX-ACCESS read-only
        STATUS current
        DESCRIPTION
            "perPara."
        ::= { pwofcesPer15mCurEntry 6 }

    -- 1.3.6.1.4.1.2011.2.25.3.70.10.43.70
    pwofcesPer15mHisTable OBJECT-TYPE
        SYNTAX SEQUENCE OF PwofcesPer15mHisEntry
        MAX-ACCESS not-accessible
        STATUS current
        DESCRIPTION
            "pwofcesPer15mHis."
        ::= { pwofces 70 }

    -- 1.3.6.1.4.1.2011.2.25.3.70.10.43.70.1
    pwofcesPer15mHisEntry OBJECT-TYPE
        SYNTAX PwofcesPer15mHisEntry
        MAX-ACCESS not-accessible
        STATUS current
        DESCRIPTION
            "pwofcesPer15mHis."
        INDEX{ pwofcesPer15mHisEid,pwofcesPer15mHisParaLen,pwofcesPer15mHisPara,pwofcesPer15mHisStartTime,pwofcesPer15mHisEndTime }
        ::= { pwofcesPer15mHisTable 1 }

    PwofcesPer15mHisEntry ::=
        SEQUENCE {
            pwofcesPer15mHisEid
                PerformanceEventType,
            pwofcesPer15mHisParaLen
                Unsigned32,
            pwofcesPer15mHisPara
                OCTET STRING,
            pwofcesPer15mHisMonValue
                OCTET STRING,
            pwofcesPer15mHisStartTime
                DateAndTime,
            pwofcesPer15mHisEndTime
                DateAndTime,
            pwofcesPer15mHisVldty
                ValidflagType
        }

    -- 1.3.6.1.4.1.2011.2.25.3.70.10.43.70.1.1
    pwofcesPer15mHisEid OBJECT-TYPE
        SYNTAX PerformanceEventType
        MAX-ACCESS read-only
        STATUS current
        DESCRIPTION
            "perEid."
        ::= { pwofcesPer15mHisEntry 1 }

    -- 1.3.6.1.4.1.2011.2.25.3.70.10.43.70.1.2
    pwofcesPer15mHisParaLen OBJECT-TYPE
        SYNTAX Unsigned32
        MAX-ACCESS read-only
        STATUS current
        DESCRIPTION
            "perParaLen."
        ::= { pwofcesPer15mHisEntry 2 }

    -- 1.3.6.1.4.1.2011.2.25.3.70.10.43.70.1.3
    pwofcesPer15mHisPara OBJECT-TYPE
        SYNTAX OCTET STRING
        MAX-ACCESS read-only
        STATUS current
        DESCRIPTION
            "perPara."
        ::= { pwofcesPer15mHisEntry 3 }

    -- 1.3.6.1.4.1.2011.2.25.3.70.10.43.70.1.4
    pwofcesPer15mHisMonValue OBJECT-TYPE
        SYNTAX OCTET STRING
        MAX-ACCESS read-only
        STATUS current
        DESCRIPTION
            "perMonValue."
        ::= { pwofcesPer15mHisEntry 4 }

    -- 1.3.6.1.4.1.2011.2.25.3.70.10.43.70.1.5
    pwofcesPer15mHisStartTime OBJECT-TYPE
        SYNTAX DateAndTime
        MAX-ACCESS read-only
        STATUS current
        DESCRIPTION
            "perDateTimeStart."
        ::= { pwofcesPer15mHisEntry 5 }

    -- 1.3.6.1.4.1.2011.2.25.3.70.10.43.70.1.6
    pwofcesPer15mHisEndTime OBJECT-TYPE
        SYNTAX DateAndTime
        MAX-ACCESS read-only
        STATUS current
        DESCRIPTION
            "perDateTimeEnd."
        ::= { pwofcesPer15mHisEntry 6 }

    -- 1.3.6.1.4.1.2011.2.25.3.70.10.43.70.1.7
    pwofcesPer15mHisVldty OBJECT-TYPE
        SYNTAX ValidflagType
        MAX-ACCESS read-only
        STATUS current
        DESCRIPTION
            "perVldty."
        ::= { pwofcesPer15mHisEntry 7 }

    -- 1.3.6.1.4.1.2011.2.25.3.70.10.43.80
    pwofcesPer24hCurTable OBJECT-TYPE
        SYNTAX SEQUENCE OF PwofcesPer24hCurEntry
        MAX-ACCESS not-accessible
        STATUS current
        DESCRIPTION
            "pwofcesPer24hCur."
        ::= { pwofces 80 }

    -- 1.3.6.1.4.1.2011.2.25.3.70.10.43.80.1
    pwofcesPer24hCurEntry OBJECT-TYPE
        SYNTAX PwofcesPer24hCurEntry
        MAX-ACCESS not-accessible
        STATUS current
        DESCRIPTION
            "pwofcesPer24hCur."
        INDEX{ pwofcesPer24hCurEid,pwofcesPer24hCurPara }
        ::= { pwofcesPer24hCurTable 1 }

    PwofcesPer24hCurEntry ::=
        SEQUENCE {
            pwofcesPer24hCurEid
                PerformanceEventType,
            pwofcesPer24hCurMonValue
                OCTET STRING,
            pwofcesPer24hCurVldty
                ValidflagType,
            pwofcesPer24hCurDatetime
                DateAndTime,
            pwofcesPer24hCurParaLen
                Unsigned32,
            pwofcesPer24hCurPara
                OCTET STRING
        }

    -- 1.3.6.1.4.1.2011.2.25.3.70.10.43.80.1.1
    pwofcesPer24hCurEid OBJECT-TYPE
        SYNTAX PerformanceEventType
        MAX-ACCESS read-only
        STATUS current
        DESCRIPTION
            "perEid."
        ::= { pwofcesPer24hCurEntry 1 }

    -- 1.3.6.1.4.1.2011.2.25.3.70.10.43.80.1.2
    pwofcesPer24hCurMonValue OBJECT-TYPE
        SYNTAX OCTET STRING
        MAX-ACCESS read-only
        STATUS current
        DESCRIPTION
            "perMonValue."
        ::= { pwofcesPer24hCurEntry 2 }

    -- 1.3.6.1.4.1.2011.2.25.3.70.10.43.80.1.3
    pwofcesPer24hCurVldty OBJECT-TYPE
        SYNTAX ValidflagType
        MAX-ACCESS read-only
        STATUS current
        DESCRIPTION
            "perVldty."
        ::= { pwofcesPer24hCurEntry 3 }

    -- 1.3.6.1.4.1.2011.2.25.3.70.10.43.80.1.4
    pwofcesPer24hCurDatetime OBJECT-TYPE
        SYNTAX DateAndTime
        MAX-ACCESS read-only
        STATUS current
        DESCRIPTION
            "perDateTime."
        ::= { pwofcesPer24hCurEntry 4 }

    -- 1.3.6.1.4.1.2011.2.25.3.70.10.43.80.1.5
    pwofcesPer24hCurParaLen OBJECT-TYPE
        SYNTAX Unsigned32
        MAX-ACCESS read-only
        STATUS current
        DESCRIPTION
            "perParaLen."
        ::= { pwofcesPer24hCurEntry 5 }

    -- 1.3.6.1.4.1.2011.2.25.3.70.10.43.80.1.6
    pwofcesPer24hCurPara OBJECT-TYPE
        SYNTAX OCTET STRING
        MAX-ACCESS read-only
        STATUS current
        DESCRIPTION
            "perPara."
        ::= { pwofcesPer24hCurEntry 6 }

    -- 1.3.6.1.4.1.2011.2.25.3.70.10.43.90
    pwofcesPer24hHisTable OBJECT-TYPE
        SYNTAX SEQUENCE OF PwofcesPer24hHisEntry
        MAX-ACCESS not-accessible
        STATUS current
        DESCRIPTION
            "pwofcesPer24hHis."
        ::= { pwofces 90 }

    -- 1.3.6.1.4.1.2011.2.25.3.70.10.43.90.1
    pwofcesPer24hHisEntry OBJECT-TYPE
        SYNTAX PwofcesPer24hHisEntry
        MAX-ACCESS not-accessible
        STATUS current
        DESCRIPTION
            "pwofcesPer24hHis."
        INDEX{ pwofcesPer24hHisEid,pwofcesPer24hHisParaLen,pwofcesPer24hHisPara,pwofcesPer24hHisStartTime,pwofcesPer24hHisEndTime }
        ::= { pwofcesPer24hHisTable 1 }

    PwofcesPer24hHisEntry ::=
        SEQUENCE {
            pwofcesPer24hHisEid
                PerformanceEventType,
            pwofcesPer24hHisParaLen
                Unsigned32,
            pwofcesPer24hHisPara
                OCTET STRING,
            pwofcesPer24hHisMonValue
                OCTET STRING,
            pwofcesPer24hHisStartTime
                DateAndTime,
            pwofcesPer24hHisEndTime
                DateAndTime,
            pwofcesPer24hHisVldty
                ValidflagType
        }

    -- 1.3.6.1.4.1.2011.2.25.3.70.10.43.90.1.1
    pwofcesPer24hHisEid OBJECT-TYPE
        SYNTAX PerformanceEventType
        MAX-ACCESS read-only
        STATUS current
        DESCRIPTION
            "perEid."
        ::= { pwofcesPer24hHisEntry 1 }

    -- 1.3.6.1.4.1.2011.2.25.3.70.10.43.90.1.2
    pwofcesPer24hHisParaLen OBJECT-TYPE
        SYNTAX Unsigned32
        MAX-ACCESS read-only
        STATUS current
        DESCRIPTION
            "perParaLen."
        ::= { pwofcesPer24hHisEntry 2 }

    -- 1.3.6.1.4.1.2011.2.25.3.70.10.43.90.1.3
    pwofcesPer24hHisPara OBJECT-TYPE
        SYNTAX OCTET STRING
        MAX-ACCESS read-only
        STATUS current
        DESCRIPTION
            "perPara."
        ::= { pwofcesPer24hHisEntry 3 }

    -- 1.3.6.1.4.1.2011.2.25.3.70.10.43.90.1.4
    pwofcesPer24hHisMonValue OBJECT-TYPE
        SYNTAX OCTET STRING
        MAX-ACCESS read-only
        STATUS current
        DESCRIPTION
            "perMonValue."
        ::= { pwofcesPer24hHisEntry 4 }

    -- 1.3.6.1.4.1.2011.2.25.3.70.10.43.90.1.5
    pwofcesPer24hHisStartTime OBJECT-TYPE
        SYNTAX DateAndTime
        MAX-ACCESS read-only
        STATUS current
        DESCRIPTION
            "perDateTimeStart."
        ::= { pwofcesPer24hHisEntry 5 }

    -- 1.3.6.1.4.1.2011.2.25.3.70.10.43.90.1.6
    pwofcesPer24hHisEndTime OBJECT-TYPE
        SYNTAX DateAndTime
        MAX-ACCESS read-only
        STATUS current
        DESCRIPTION
            "perDateTimeEnd."
        ::= { pwofcesPer24hHisEntry 6 }

    -- 1.3.6.1.4.1.2011.2.25.3.70.10.43.90.1.7
    pwofcesPer24hHisVldty OBJECT-TYPE
        SYNTAX ValidflagType
        MAX-ACCESS read-only
        STATUS current
        DESCRIPTION
            "perVldty."
        ::= { pwofcesPer24hHisEntry 7 }

    -- 1.3.6.1.4.1.2011.2.25.3.70.10.44
    pwofl2vpn OBJECT IDENTIFIER ::= { rtnPerformance 44 }

    -- 1.3.6.1.4.1.2011.2.25.3.70.10.44.60
    pwofl2vpnPer15mCurTable OBJECT-TYPE
        SYNTAX SEQUENCE OF Pwofl2vpnPer15mCurEntry
        MAX-ACCESS not-accessible
        STATUS current
        DESCRIPTION
            "pwofl2vpnPer15mCur."
        ::= { pwofl2vpn 60 }

    -- 1.3.6.1.4.1.2011.2.25.3.70.10.44.60.1
    pwofl2vpnPer15mCurEntry OBJECT-TYPE
        SYNTAX Pwofl2vpnPer15mCurEntry
        MAX-ACCESS not-accessible
        STATUS current
        DESCRIPTION
            "pwofl2vpnPer15mCur."
        INDEX{ pwofl2vpnPer15mCurEid,pwofl2vpnPer15mCurPara }
        ::= { pwofl2vpnPer15mCurTable 1 }

    Pwofl2vpnPer15mCurEntry ::=
        SEQUENCE {
            pwofl2vpnPer15mCurEid
                PerformanceEventType,
            pwofl2vpnPer15mCurMonValue
                OCTET STRING,
            pwofl2vpnPer15mCurVldty
                ValidflagType,
            pwofl2vpnPer15mCurDatetime
                DateAndTime,
            pwofl2vpnPer15mCurParaLen
                Unsigned32,
            pwofl2vpnPer15mCurPara
                OCTET STRING
        }

    -- 1.3.6.1.4.1.2011.2.25.3.70.10.44.60.1.1
    pwofl2vpnPer15mCurEid OBJECT-TYPE
        SYNTAX PerformanceEventType
        MAX-ACCESS read-only
        STATUS current
        DESCRIPTION
            "perEid."
        ::= { pwofl2vpnPer15mCurEntry 1 }

    -- 1.3.6.1.4.1.2011.2.25.3.70.10.44.60.1.2
    pwofl2vpnPer15mCurMonValue OBJECT-TYPE
        SYNTAX OCTET STRING
        MAX-ACCESS read-only
        STATUS current
        DESCRIPTION
            "perMonValue."
        ::= { pwofl2vpnPer15mCurEntry 2 }

    -- 1.3.6.1.4.1.2011.2.25.3.70.10.44.60.1.3
    pwofl2vpnPer15mCurVldty OBJECT-TYPE
        SYNTAX ValidflagType
        MAX-ACCESS read-only
        STATUS current
        DESCRIPTION
            "perVldty."
        ::= { pwofl2vpnPer15mCurEntry 3 }

    -- 1.3.6.1.4.1.2011.2.25.3.70.10.44.60.1.4
    pwofl2vpnPer15mCurDatetime OBJECT-TYPE
        SYNTAX DateAndTime
        MAX-ACCESS read-only
        STATUS current
        DESCRIPTION
            "perDateTime."
        ::= { pwofl2vpnPer15mCurEntry 4 }

    -- 1.3.6.1.4.1.2011.2.25.3.70.10.44.60.1.5
    pwofl2vpnPer15mCurParaLen OBJECT-TYPE
        SYNTAX Unsigned32
        MAX-ACCESS read-only
        STATUS current
        DESCRIPTION
            "perParaLen."
        ::= { pwofl2vpnPer15mCurEntry 5 }

    -- 1.3.6.1.4.1.2011.2.25.3.70.10.44.60.1.6
    pwofl2vpnPer15mCurPara OBJECT-TYPE
        SYNTAX OCTET STRING
        MAX-ACCESS read-only
        STATUS current
        DESCRIPTION
            "perPara."
        ::= { pwofl2vpnPer15mCurEntry 6 }

    -- 1.3.6.1.4.1.2011.2.25.3.70.10.44.70
    pwofl2vpnPer15mHisTable OBJECT-TYPE
        SYNTAX SEQUENCE OF Pwofl2vpnPer15mHisEntry
        MAX-ACCESS not-accessible
        STATUS current
        DESCRIPTION
            "pwofl2vpnPer15mHis."
        ::= { pwofl2vpn 70 }

    -- 1.3.6.1.4.1.2011.2.25.3.70.10.44.70.1
    pwofl2vpnPer15mHisEntry OBJECT-TYPE
        SYNTAX Pwofl2vpnPer15mHisEntry
        MAX-ACCESS not-accessible
        STATUS current
        DESCRIPTION
            "pwofl2vpnPer15mHis."
        INDEX{ pwofl2vpnPer15mHisEid,pwofl2vpnPer15mHisParaLen,pwofl2vpnPer15mHisPara,pwofl2vpnPer15mHisStartTime,pwofl2vpnPer15mHisEndTime }
        ::= { pwofl2vpnPer15mHisTable 1 }

    Pwofl2vpnPer15mHisEntry ::=
        SEQUENCE {
            pwofl2vpnPer15mHisEid
                PerformanceEventType,
            pwofl2vpnPer15mHisParaLen
                Unsigned32,
            pwofl2vpnPer15mHisPara
                OCTET STRING,
            pwofl2vpnPer15mHisMonValue
                OCTET STRING,
            pwofl2vpnPer15mHisStartTime
                DateAndTime,
            pwofl2vpnPer15mHisEndTime
                DateAndTime,
            pwofl2vpnPer15mHisVldty
                ValidflagType
        }

    -- 1.3.6.1.4.1.2011.2.25.3.70.10.44.70.1.1
    pwofl2vpnPer15mHisEid OBJECT-TYPE
        SYNTAX PerformanceEventType
        MAX-ACCESS read-only
        STATUS current
        DESCRIPTION
            "perEid."
        ::= { pwofl2vpnPer15mHisEntry 1 }

    -- 1.3.6.1.4.1.2011.2.25.3.70.10.44.70.1.2
    pwofl2vpnPer15mHisParaLen OBJECT-TYPE
        SYNTAX Unsigned32
        MAX-ACCESS read-only
        STATUS current
        DESCRIPTION
            "perParaLen."
        ::= { pwofl2vpnPer15mHisEntry 2 }

    -- 1.3.6.1.4.1.2011.2.25.3.70.10.44.70.1.3
    pwofl2vpnPer15mHisPara OBJECT-TYPE
        SYNTAX OCTET STRING
        MAX-ACCESS read-only
        STATUS current
        DESCRIPTION
            "perPara."
        ::= { pwofl2vpnPer15mHisEntry 3 }

    -- 1.3.6.1.4.1.2011.2.25.3.70.10.44.70.1.4
    pwofl2vpnPer15mHisMonValue OBJECT-TYPE
        SYNTAX OCTET STRING
        MAX-ACCESS read-only
        STATUS current
        DESCRIPTION
            "perMonValue."
        ::= { pwofl2vpnPer15mHisEntry 4 }

    -- 1.3.6.1.4.1.2011.2.25.3.70.10.44.70.1.5
    pwofl2vpnPer15mHisStartTime OBJECT-TYPE
        SYNTAX DateAndTime
        MAX-ACCESS read-only
        STATUS current
        DESCRIPTION
            "perDateTimeStart."
        ::= { pwofl2vpnPer15mHisEntry 5 }

    -- 1.3.6.1.4.1.2011.2.25.3.70.10.44.70.1.6
    pwofl2vpnPer15mHisEndTime OBJECT-TYPE
        SYNTAX DateAndTime
        MAX-ACCESS read-only
        STATUS current
        DESCRIPTION
            "perDateTimeEnd."
        ::= { pwofl2vpnPer15mHisEntry 6 }

    -- 1.3.6.1.4.1.2011.2.25.3.70.10.44.70.1.7
    pwofl2vpnPer15mHisVldty OBJECT-TYPE
        SYNTAX ValidflagType
        MAX-ACCESS read-only
        STATUS current
        DESCRIPTION
            "perVldty."
        ::= { pwofl2vpnPer15mHisEntry 7 }

    -- 1.3.6.1.4.1.2011.2.25.3.70.10.44.80
    pwofl2vpnPer24hCurTable OBJECT-TYPE
        SYNTAX SEQUENCE OF Pwofl2vpnPer24hCurEntry
        MAX-ACCESS not-accessible
        STATUS current
        DESCRIPTION
            "pwofl2vpnPer24hCur."
        ::= { pwofl2vpn 80 }

    -- 1.3.6.1.4.1.2011.2.25.3.70.10.44.80.1
    pwofl2vpnPer24hCurEntry OBJECT-TYPE
        SYNTAX Pwofl2vpnPer24hCurEntry
        MAX-ACCESS not-accessible
        STATUS current
        DESCRIPTION
            "pwofl2vpnPer24hCur."
        INDEX{ pwofl2vpnPer24hCurEid,pwofl2vpnPer24hCurPara }
        ::= { pwofl2vpnPer24hCurTable 1 }

    Pwofl2vpnPer24hCurEntry ::=
        SEQUENCE {
            pwofl2vpnPer24hCurEid
                PerformanceEventType,
            pwofl2vpnPer24hCurMonValue
                OCTET STRING,
            pwofl2vpnPer24hCurVldty
                ValidflagType,
            pwofl2vpnPer24hCurDatetime
                DateAndTime,
            pwofl2vpnPer24hCurParaLen
                Unsigned32,
            pwofl2vpnPer24hCurPara
                OCTET STRING
        }

    -- 1.3.6.1.4.1.2011.2.25.3.70.10.44.80.1.1
    pwofl2vpnPer24hCurEid OBJECT-TYPE
        SYNTAX PerformanceEventType
        MAX-ACCESS read-only
        STATUS current
        DESCRIPTION
            "perEid."
        ::= { pwofl2vpnPer24hCurEntry 1 }

    -- 1.3.6.1.4.1.2011.2.25.3.70.10.44.80.1.2
    pwofl2vpnPer24hCurMonValue OBJECT-TYPE
        SYNTAX OCTET STRING
        MAX-ACCESS read-only
        STATUS current
        DESCRIPTION
            "perMonValue."
        ::= { pwofl2vpnPer24hCurEntry 2 }

    -- 1.3.6.1.4.1.2011.2.25.3.70.10.44.80.1.3
    pwofl2vpnPer24hCurVldty OBJECT-TYPE
        SYNTAX ValidflagType
        MAX-ACCESS read-only
        STATUS current
        DESCRIPTION
            "perVldty."
        ::= { pwofl2vpnPer24hCurEntry 3 }

    -- 1.3.6.1.4.1.2011.2.25.3.70.10.44.80.1.4
    pwofl2vpnPer24hCurDatetime OBJECT-TYPE
        SYNTAX DateAndTime
        MAX-ACCESS read-only
        STATUS current
        DESCRIPTION
            "perDateTime."
        ::= { pwofl2vpnPer24hCurEntry 4 }

    -- 1.3.6.1.4.1.2011.2.25.3.70.10.44.80.1.5
    pwofl2vpnPer24hCurParaLen OBJECT-TYPE
        SYNTAX Unsigned32
        MAX-ACCESS read-only
        STATUS current
        DESCRIPTION
            "perParaLen."
        ::= { pwofl2vpnPer24hCurEntry 5 }

    -- 1.3.6.1.4.1.2011.2.25.3.70.10.44.80.1.6
    pwofl2vpnPer24hCurPara OBJECT-TYPE
        SYNTAX OCTET STRING
        MAX-ACCESS read-only
        STATUS current
        DESCRIPTION
            "perPara."
        ::= { pwofl2vpnPer24hCurEntry 6 }

    -- 1.3.6.1.4.1.2011.2.25.3.70.10.44.90
    pwofl2vpnPer24hHisTable OBJECT-TYPE
        SYNTAX SEQUENCE OF Pwofl2vpnPer24hHisEntry
        MAX-ACCESS not-accessible
        STATUS current
        DESCRIPTION
            "pwofl2vpnPer24hHis."
        ::= { pwofl2vpn 90 }

    -- 1.3.6.1.4.1.2011.2.25.3.70.10.44.90.1
    pwofl2vpnPer24hHisEntry OBJECT-TYPE
        SYNTAX Pwofl2vpnPer24hHisEntry
        MAX-ACCESS not-accessible
        STATUS current
        DESCRIPTION
            "pwofl2vpnPer24hHis."
        INDEX{ pwofl2vpnPer24hHisEid,pwofl2vpnPer24hHisParaLen,pwofl2vpnPer24hHisPara,pwofl2vpnPer24hHisStartTime,pwofl2vpnPer24hHisEndTime }
        ::= { pwofl2vpnPer24hHisTable 1 }

    Pwofl2vpnPer24hHisEntry ::=
        SEQUENCE {
            pwofl2vpnPer24hHisEid
                PerformanceEventType,
            pwofl2vpnPer24hHisParaLen
                Unsigned32,
            pwofl2vpnPer24hHisPara
                OCTET STRING,
            pwofl2vpnPer24hHisMonValue
                OCTET STRING,
            pwofl2vpnPer24hHisStartTime
                DateAndTime,
            pwofl2vpnPer24hHisEndTime
                DateAndTime,
            pwofl2vpnPer24hHisVldty
                ValidflagType
        }

    -- 1.3.6.1.4.1.2011.2.25.3.70.10.44.90.1.1
    pwofl2vpnPer24hHisEid OBJECT-TYPE
        SYNTAX PerformanceEventType
        MAX-ACCESS read-only
        STATUS current
        DESCRIPTION
            "perEid."
        ::= { pwofl2vpnPer24hHisEntry 1 }

    -- 1.3.6.1.4.1.2011.2.25.3.70.10.44.90.1.2
    pwofl2vpnPer24hHisParaLen OBJECT-TYPE
        SYNTAX Unsigned32
        MAX-ACCESS read-only
        STATUS current
        DESCRIPTION
            "perParaLen."
        ::= { pwofl2vpnPer24hHisEntry 2 }

    -- 1.3.6.1.4.1.2011.2.25.3.70.10.44.90.1.3
    pwofl2vpnPer24hHisPara OBJECT-TYPE
        SYNTAX OCTET STRING
        MAX-ACCESS read-only
        STATUS current
        DESCRIPTION
            "perPara."
        ::= { pwofl2vpnPer24hHisEntry 3 }

    -- 1.3.6.1.4.1.2011.2.25.3.70.10.44.90.1.4
    pwofl2vpnPer24hHisMonValue OBJECT-TYPE
        SYNTAX OCTET STRING
        MAX-ACCESS read-only
        STATUS current
        DESCRIPTION
            "perMonValue."
        ::= { pwofl2vpnPer24hHisEntry 4 }

    -- 1.3.6.1.4.1.2011.2.25.3.70.10.44.90.1.5
    pwofl2vpnPer24hHisStartTime OBJECT-TYPE
        SYNTAX DateAndTime
        MAX-ACCESS read-only
        STATUS current
        DESCRIPTION
            "perDateTimeStart."
        ::= { pwofl2vpnPer24hHisEntry 5 }

    -- 1.3.6.1.4.1.2011.2.25.3.70.10.44.90.1.6
    pwofl2vpnPer24hHisEndTime OBJECT-TYPE
        SYNTAX DateAndTime
        MAX-ACCESS read-only
        STATUS current
        DESCRIPTION
            "perDateTimeEnd."
        ::= { pwofl2vpnPer24hHisEntry 6 }

    -- 1.3.6.1.4.1.2011.2.25.3.70.10.44.90.1.7
    pwofl2vpnPer24hHisVldty OBJECT-TYPE
        SYNTAX ValidflagType
        MAX-ACCESS read-only
        STATUS current
        DESCRIPTION
            "perVldty."
        ::= { pwofl2vpnPer24hHisEntry 7 }

    -- 1.3.6.1.4.1.2011.2.25.3.70.10.50
    wpidLaser OBJECT IDENTIFIER ::= { rtnPerformance 50 }

    -- 1.3.6.1.4.1.2011.2.25.3.70.10.50.60
    wpidLaserPer15mCurTable OBJECT-TYPE
        SYNTAX SEQUENCE OF WpidLaserPer15mCurEntry
        MAX-ACCESS not-accessible
        STATUS current
        DESCRIPTION
            "wpidLaserPer15mCur."
        ::= { wpidLaser 60 }

    -- 1.3.6.1.4.1.2011.2.25.3.70.10.50.60.1
    wpidLaserPer15mCurEntry OBJECT-TYPE
        SYNTAX WpidLaserPer15mCurEntry
        MAX-ACCESS not-accessible
        STATUS current
        DESCRIPTION
            "wpidLaserPer15mCur."
        INDEX{ wpidLaserPer15mCurEid,wpidLaserPer15mCurPara }
        ::= { wpidLaserPer15mCurTable 1 }

    WpidLaserPer15mCurEntry ::=
        SEQUENCE {
            wpidLaserPer15mCurEid
                PerformanceEventType,
            wpidLaserPer15mCurMonValue
                OCTET STRING,
            wpidLaserPer15mCurVldty
                ValidflagType,
            wpidLaserPer15mCurDatetime
                DateAndTime,
            wpidLaserPer15mCurParaLen
                Unsigned32,
            wpidLaserPer15mCurPara
                OCTET STRING
        }

    -- 1.3.6.1.4.1.2011.2.25.3.70.10.50.60.1.1
    wpidLaserPer15mCurEid OBJECT-TYPE
        SYNTAX PerformanceEventType
        MAX-ACCESS read-only
        STATUS current
        DESCRIPTION
            "perEid."
        ::= { wpidLaserPer15mCurEntry 1 }

    -- 1.3.6.1.4.1.2011.2.25.3.70.10.50.60.1.2
    wpidLaserPer15mCurMonValue OBJECT-TYPE
        SYNTAX OCTET STRING
        MAX-ACCESS read-only
        STATUS current
        DESCRIPTION
            "perMonValue."
        ::= { wpidLaserPer15mCurEntry 2 }

    -- 1.3.6.1.4.1.2011.2.25.3.70.10.50.60.1.3
    wpidLaserPer15mCurVldty OBJECT-TYPE
        SYNTAX ValidflagType
        MAX-ACCESS read-only
        STATUS current
        DESCRIPTION
            "perVldty."
        ::= { wpidLaserPer15mCurEntry 3 }

    -- 1.3.6.1.4.1.2011.2.25.3.70.10.50.60.1.4
    wpidLaserPer15mCurDatetime OBJECT-TYPE
        SYNTAX DateAndTime
        MAX-ACCESS read-only
        STATUS current
        DESCRIPTION
            "perDateTime."
        ::= { wpidLaserPer15mCurEntry 4 }

    -- 1.3.6.1.4.1.2011.2.25.3.70.10.50.60.1.5
    wpidLaserPer15mCurParaLen OBJECT-TYPE
        SYNTAX Unsigned32
        MAX-ACCESS read-only
        STATUS current
        DESCRIPTION
            "perParaLen."
        ::= { wpidLaserPer15mCurEntry 5 }

    -- 1.3.6.1.4.1.2011.2.25.3.70.10.50.60.1.6
    wpidLaserPer15mCurPara OBJECT-TYPE
        SYNTAX OCTET STRING
        MAX-ACCESS read-only
        STATUS current
        DESCRIPTION
            "perPara."
        ::= { wpidLaserPer15mCurEntry 6 }

    -- 1.3.6.1.4.1.2011.2.25.3.70.10.50.70
    wpidLaserPer15mHisTable OBJECT-TYPE
        SYNTAX SEQUENCE OF WpidLaserPer15mHisEntry
        MAX-ACCESS not-accessible
        STATUS current
        DESCRIPTION
            "wpidLaserPer15mHis."
        ::= { wpidLaser 70 }

    -- 1.3.6.1.4.1.2011.2.25.3.70.10.50.70.1
    wpidLaserPer15mHisEntry OBJECT-TYPE
        SYNTAX WpidLaserPer15mHisEntry
        MAX-ACCESS not-accessible
        STATUS current
        DESCRIPTION
            "wpidLaserPer15mHis."
        INDEX{ wpidLaserPer15mHisEid,wpidLaserPer15mHisParaLen,wpidLaserPer15mHisPara,wpidLaserPer15mHisStartTime,wpidLaserPer15mHisEndTime }
        ::= { wpidLaserPer15mHisTable 1 }

    WpidLaserPer15mHisEntry ::=
        SEQUENCE {
            wpidLaserPer15mHisEid
                PerformanceEventType,
            wpidLaserPer15mHisParaLen
                Unsigned32,
            wpidLaserPer15mHisPara
                OCTET STRING,
            wpidLaserPer15mHisMonValue
                OCTET STRING,
            wpidLaserPer15mHisStartTime
                DateAndTime,
            wpidLaserPer15mHisEndTime
                DateAndTime,
            wpidLaserPer15mHisVldty
                ValidflagType
        }

    -- 1.3.6.1.4.1.2011.2.25.3.70.10.50.70.1.1
    wpidLaserPer15mHisEid OBJECT-TYPE
        SYNTAX PerformanceEventType
        MAX-ACCESS read-only
        STATUS current
        DESCRIPTION
            "perEid."
        ::= { wpidLaserPer15mHisEntry 1 }

    -- 1.3.6.1.4.1.2011.2.25.3.70.10.50.70.1.2
    wpidLaserPer15mHisParaLen OBJECT-TYPE
        SYNTAX Unsigned32
        MAX-ACCESS read-only
        STATUS current
        DESCRIPTION
            "perParaLen."
        ::= { wpidLaserPer15mHisEntry 2 }

    -- 1.3.6.1.4.1.2011.2.25.3.70.10.50.70.1.3
    wpidLaserPer15mHisPara OBJECT-TYPE
        SYNTAX OCTET STRING
        MAX-ACCESS read-only
        STATUS current
        DESCRIPTION
            "perPara."
        ::= { wpidLaserPer15mHisEntry 3 }

    -- 1.3.6.1.4.1.2011.2.25.3.70.10.50.70.1.4
    wpidLaserPer15mHisMonValue OBJECT-TYPE
        SYNTAX OCTET STRING
        MAX-ACCESS read-only
        STATUS current
        DESCRIPTION
            "perMonValue."
        ::= { wpidLaserPer15mHisEntry 4 }

    -- 1.3.6.1.4.1.2011.2.25.3.70.10.50.70.1.5
    wpidLaserPer15mHisStartTime OBJECT-TYPE
        SYNTAX DateAndTime
        MAX-ACCESS read-only
        STATUS current
        DESCRIPTION
            "perDateTimeStart."
        ::= { wpidLaserPer15mHisEntry 5 }

    -- 1.3.6.1.4.1.2011.2.25.3.70.10.50.70.1.6
    wpidLaserPer15mHisEndTime OBJECT-TYPE
        SYNTAX DateAndTime
        MAX-ACCESS read-only
        STATUS current
        DESCRIPTION
            "perDateTimeEnd."
        ::= { wpidLaserPer15mHisEntry 6 }

    -- 1.3.6.1.4.1.2011.2.25.3.70.10.50.70.1.7
    wpidLaserPer15mHisVldty OBJECT-TYPE
        SYNTAX ValidflagType
        MAX-ACCESS read-only
        STATUS current
        DESCRIPTION
            "perVldty."
        ::= { wpidLaserPer15mHisEntry 7 }

    -- 1.3.6.1.4.1.2011.2.25.3.70.10.50.80
    wpidLaserPer24hCurTable OBJECT-TYPE
        SYNTAX SEQUENCE OF WpidLaserPer24hCurEntry
        MAX-ACCESS not-accessible
        STATUS current
        DESCRIPTION
            "wpidLaserPer24hCur."
        ::= { wpidLaser 80 }

    -- 1.3.6.1.4.1.2011.2.25.3.70.10.50.80.1
    wpidLaserPer24hCurEntry OBJECT-TYPE
        SYNTAX WpidLaserPer24hCurEntry
        MAX-ACCESS not-accessible
        STATUS current
        DESCRIPTION
            "wpidLaserPer24hCur."
        INDEX{ wpidLaserPer24hCurEid,wpidLaserPer24hCurPara }
        ::= { wpidLaserPer24hCurTable 1 }

    WpidLaserPer24hCurEntry ::=
        SEQUENCE {
            wpidLaserPer24hCurEid
                PerformanceEventType,
            wpidLaserPer24hCurMonValue
                OCTET STRING,
            wpidLaserPer24hCurVldty
                ValidflagType,
            wpidLaserPer24hCurDatetime
                DateAndTime,
            wpidLaserPer24hCurParaLen
                Unsigned32,
            wpidLaserPer24hCurPara
                OCTET STRING
        }

    -- 1.3.6.1.4.1.2011.2.25.3.70.10.50.80.1.1
    wpidLaserPer24hCurEid OBJECT-TYPE
        SYNTAX PerformanceEventType
        MAX-ACCESS read-only
        STATUS current
        DESCRIPTION
            "perEid."
        ::= { wpidLaserPer24hCurEntry 1 }

    -- 1.3.6.1.4.1.2011.2.25.3.70.10.50.80.1.2
    wpidLaserPer24hCurMonValue OBJECT-TYPE
        SYNTAX OCTET STRING
        MAX-ACCESS read-only
        STATUS current
        DESCRIPTION
            "perMonValue."
        ::= { wpidLaserPer24hCurEntry 2 }

    -- 1.3.6.1.4.1.2011.2.25.3.70.10.50.80.1.3
    wpidLaserPer24hCurVldty OBJECT-TYPE
        SYNTAX ValidflagType
        MAX-ACCESS read-only
        STATUS current
        DESCRIPTION
            "perVldty."
        ::= { wpidLaserPer24hCurEntry 3 }

    -- 1.3.6.1.4.1.2011.2.25.3.70.10.50.80.1.4
    wpidLaserPer24hCurDatetime OBJECT-TYPE
        SYNTAX DateAndTime
        MAX-ACCESS read-only
        STATUS current
        DESCRIPTION
            "perDateTime."
        ::= { wpidLaserPer24hCurEntry 4 }

    -- 1.3.6.1.4.1.2011.2.25.3.70.10.50.80.1.5
    wpidLaserPer24hCurParaLen OBJECT-TYPE
        SYNTAX Unsigned32
        MAX-ACCESS read-only
        STATUS current
        DESCRIPTION
            "perParaLen."
        ::= { wpidLaserPer24hCurEntry 5 }

    -- 1.3.6.1.4.1.2011.2.25.3.70.10.50.80.1.6
    wpidLaserPer24hCurPara OBJECT-TYPE
        SYNTAX OCTET STRING
        MAX-ACCESS read-only
        STATUS current
        DESCRIPTION
            "perPara."
        ::= { wpidLaserPer24hCurEntry 6 }

    -- 1.3.6.1.4.1.2011.2.25.3.70.10.50.90
    wpidLaserPer24hHisTable OBJECT-TYPE
        SYNTAX SEQUENCE OF WpidLaserPer24hHisEntry
        MAX-ACCESS not-accessible
        STATUS current
        DESCRIPTION
            "wpidLaserPer24hHis."
        ::= { wpidLaser 90 }

    -- 1.3.6.1.4.1.2011.2.25.3.70.10.50.90.1
    wpidLaserPer24hHisEntry OBJECT-TYPE
        SYNTAX WpidLaserPer24hHisEntry
        MAX-ACCESS not-accessible
        STATUS current
        DESCRIPTION
            "wpidLaserPer24hHis."
        INDEX{ wpidLaserPer24hHisEid,wpidLaserPer24hHisParaLen,wpidLaserPer24hHisPara,wpidLaserPer24hHisStartTime,wpidLaserPer24hHisEndTime }
        ::= { wpidLaserPer24hHisTable 1 }

    WpidLaserPer24hHisEntry ::=
        SEQUENCE {
            wpidLaserPer24hHisEid
                PerformanceEventType,
            wpidLaserPer24hHisParaLen
                Unsigned32,
            wpidLaserPer24hHisPara
                OCTET STRING,
            wpidLaserPer24hHisMonValue
                OCTET STRING,
            wpidLaserPer24hHisStartTime
                DateAndTime,
            wpidLaserPer24hHisEndTime
                DateAndTime,
            wpidLaserPer24hHisVldty
                ValidflagType
        }

    -- 1.3.6.1.4.1.2011.2.25.3.70.10.50.90.1.1
    wpidLaserPer24hHisEid OBJECT-TYPE
        SYNTAX PerformanceEventType
        MAX-ACCESS read-only
        STATUS current
        DESCRIPTION
            "perEid."
        ::= { wpidLaserPer24hHisEntry 1 }

    -- 1.3.6.1.4.1.2011.2.25.3.70.10.50.90.1.2
    wpidLaserPer24hHisParaLen OBJECT-TYPE
        SYNTAX Unsigned32
        MAX-ACCESS read-only
        STATUS current
        DESCRIPTION
            "perParaLen."
        ::= { wpidLaserPer24hHisEntry 2 }

    -- 1.3.6.1.4.1.2011.2.25.3.70.10.50.90.1.3
    wpidLaserPer24hHisPara OBJECT-TYPE
        SYNTAX OCTET STRING
        MAX-ACCESS read-only
        STATUS current
        DESCRIPTION
            "perPara."
        ::= { wpidLaserPer24hHisEntry 3 }

    -- 1.3.6.1.4.1.2011.2.25.3.70.10.50.90.1.4
    wpidLaserPer24hHisMonValue OBJECT-TYPE
        SYNTAX OCTET STRING
        MAX-ACCESS read-only
        STATUS current
        DESCRIPTION
            "perMonValue."
        ::= { wpidLaserPer24hHisEntry 4 }

    -- 1.3.6.1.4.1.2011.2.25.3.70.10.50.90.1.5
    wpidLaserPer24hHisStartTime OBJECT-TYPE
        SYNTAX DateAndTime
        MAX-ACCESS read-only
        STATUS current
        DESCRIPTION
            "perDateTimeStart."
        ::= { wpidLaserPer24hHisEntry 5 }

    -- 1.3.6.1.4.1.2011.2.25.3.70.10.50.90.1.6
    wpidLaserPer24hHisEndTime OBJECT-TYPE
        SYNTAX DateAndTime
        MAX-ACCESS read-only
        STATUS current
        DESCRIPTION
            "perDateTimeEnd."
        ::= { wpidLaserPer24hHisEntry 6 }

    -- 1.3.6.1.4.1.2011.2.25.3.70.10.50.90.1.7
    wpidLaserPer24hHisVldty OBJECT-TYPE
        SYNTAX ValidflagType
        MAX-ACCESS read-only
        STATUS current
        DESCRIPTION
            "perVldty."
        ::= { wpidLaserPer24hHisEntry 7 }
					
    -- 1.3.6.1.4.1.2011.2.25.3.70.10.56
    synSource OBJECT IDENTIFIER ::= { rtnPerformance 56 }

    -- 1.3.6.1.4.1.2011.2.25.3.70.10.56.60
    synSourcePer15mCurTable OBJECT-TYPE
        SYNTAX SEQUENCE OF SynSourcePer15mCurEntry
        MAX-ACCESS not-accessible
        STATUS current
        DESCRIPTION
            "synSourcePer15mCur."
        ::= { synSource 60 }

    -- 1.3.6.1.4.1.2011.2.25.3.70.10.56.60.1
    synSourcePer15mCurEntry OBJECT-TYPE
        SYNTAX SynSourcePer15mCurEntry
        MAX-ACCESS not-accessible
        STATUS current
        DESCRIPTION
            "synSourcePer15mCur."
        INDEX{ synSourcePer15mCurEid,synSourcePer15mCurPara }
        ::= { synSourcePer15mCurTable 1 }

    SynSourcePer15mCurEntry ::=
        SEQUENCE {
            synSourcePer15mCurEid
                Unsigned32,
            synSourcePer15mCurMonValue
                OCTET STRING,
            synSourcePer15mCurVldty
                ValidflagType,
            synSourcePer15mCurDatetime
                DateAndTime,
            synSourcePer15mCurParaLen
                Unsigned32,
            synSourcePer15mCurPara
                OCTET STRING
        }

    -- 1.3.6.1.4.1.2011.2.25.3.70.10.56.60.1.1
    synSourcePer15mCurEid OBJECT-TYPE
        SYNTAX Unsigned32
	{
	    maxclkda(16094),
	    minclkda(16095),
	    avgclkda(16096)
	}
	MAX-ACCESS read-only
        STATUS current
        DESCRIPTION
            "perEid."
        ::= { synSourcePer15mCurEntry 1 }

    -- 1.3.6.1.4.1.2011.2.25.3.70.10.56.60.1.2
    synSourcePer15mCurMonValue OBJECT-TYPE
        SYNTAX OCTET STRING
        MAX-ACCESS read-only
        STATUS current
        DESCRIPTION
            "perMonValue."
        ::= { synSourcePer15mCurEntry 2 }

    -- 1.3.6.1.4.1.2011.2.25.3.70.10.56.60.1.3
    synSourcePer15mCurVldty OBJECT-TYPE
        SYNTAX ValidflagType
        MAX-ACCESS read-only
        STATUS current
        DESCRIPTION
            "perVldty."
        ::= { synSourcePer15mCurEntry 3 }

    -- 1.3.6.1.4.1.2011.2.25.3.70.10.56.60.1.4
    synSourcePer15mCurDatetime OBJECT-TYPE
        SYNTAX DateAndTime
        MAX-ACCESS read-only
        STATUS current
        DESCRIPTION
            "perDateTime."
        ::= { synSourcePer15mCurEntry 4 }

    -- 1.3.6.1.4.1.2011.2.25.3.70.10.56.60.1.5
    synSourcePer15mCurParaLen OBJECT-TYPE
        SYNTAX Unsigned32
        MAX-ACCESS read-only
        STATUS current
        DESCRIPTION
            "perParaLen."
        ::= { synSourcePer15mCurEntry 5 }

    -- 1.3.6.1.4.1.2011.2.25.3.70.10.56.60.1.6
    synSourcePer15mCurPara OBJECT-TYPE
        SYNTAX OCTET STRING
        MAX-ACCESS read-only
        STATUS current
        DESCRIPTION
            "perPara."
        ::= { synSourcePer15mCurEntry 6 }

    -- 1.3.6.1.4.1.2011.2.25.3.70.10.56.70
    synSourcePer15mHisTable OBJECT-TYPE
        SYNTAX SEQUENCE OF SynSourcePer15mHisEntry
        MAX-ACCESS not-accessible
        STATUS current
        DESCRIPTION
            "synSourcePer15mHis."
        ::= { synSource 70 }

    -- 1.3.6.1.4.1.2011.2.25.3.70.10.56.70.1
    synSourcePer15mHisEntry OBJECT-TYPE
        SYNTAX SynSourcePer15mHisEntry
        MAX-ACCESS not-accessible
        STATUS current
        DESCRIPTION
            "synSourcePer15mHis."
        INDEX{ synSourcePer15mHisEid,synSourcePer15mHisParaLen,synSourcePer15mHisPara,synSourcePer15mHisStartTime,synSourcePer15mHisEndTime }
        ::= { synSourcePer15mHisTable 1 }

    SynSourcePer15mHisEntry ::=
        SEQUENCE {
            synSourcePer15mHisEid
                Unsigned32,
            synSourcePer15mHisParaLen
                Unsigned32,
            synSourcePer15mHisPara
                OCTET STRING,
            synSourcePer15mHisMonValue
                OCTET STRING,
            synSourcePer15mHisStartTime
                DateAndTime,
            synSourcePer15mHisEndTime
                DateAndTime,
            synSourcePer15mHisVldty
                ValidflagType
        }

    -- 1.3.6.1.4.1.2011.2.25.3.70.10.56.70.1.1
    synSourcePer15mHisEid OBJECT-TYPE
        SYNTAX Unsigned32
	{
	    maxclkda(16094),
	    minclkda(16095),
	    avgclkda(16096)
	}
        MAX-ACCESS read-only
        STATUS current
        DESCRIPTION
            "perEid."
        ::= { synSourcePer15mHisEntry 1 }

    -- 1.3.6.1.4.1.2011.2.25.3.70.10.56.70.1.2
    synSourcePer15mHisParaLen OBJECT-TYPE
        SYNTAX Unsigned32
        MAX-ACCESS read-only
        STATUS current
        DESCRIPTION
            "perParaLen."
        ::= { synSourcePer15mHisEntry 2 }

    -- 1.3.6.1.4.1.2011.2.25.3.70.10.56.70.1.3
    synSourcePer15mHisPara OBJECT-TYPE
        SYNTAX OCTET STRING
        MAX-ACCESS read-only
        STATUS current
        DESCRIPTION
            "perPara."
        ::= { synSourcePer15mHisEntry 3 }

    -- 1.3.6.1.4.1.2011.2.25.3.70.10.56.70.1.4
    synSourcePer15mHisMonValue OBJECT-TYPE
        SYNTAX OCTET STRING
        MAX-ACCESS read-only
        STATUS current
        DESCRIPTION
            "perMonValue."
        ::= { synSourcePer15mHisEntry 4 }

    -- 1.3.6.1.4.1.2011.2.25.3.70.10.56.70.1.5
    synSourcePer15mHisStartTime OBJECT-TYPE
        SYNTAX DateAndTime
        MAX-ACCESS read-only
        STATUS current
        DESCRIPTION
            "perDateTimeStart."
        ::= { synSourcePer15mHisEntry 5 }

    -- 1.3.6.1.4.1.2011.2.25.3.70.10.56.70.1.6
    synSourcePer15mHisEndTime OBJECT-TYPE
        SYNTAX DateAndTime
        MAX-ACCESS read-only
        STATUS current
        DESCRIPTION
            "perDateTimeEnd."
        ::= { synSourcePer15mHisEntry 6 }

    -- 1.3.6.1.4.1.2011.2.25.3.70.10.56.70.1.7
    synSourcePer15mHisVldty OBJECT-TYPE
        SYNTAX ValidflagType
        MAX-ACCESS read-only
        STATUS current
        DESCRIPTION
            "perVldty."
        ::= { synSourcePer15mHisEntry 7 }

    -- 1.3.6.1.4.1.2011.2.25.3.70.10.56.80
    synSourcePer24hCurTable OBJECT-TYPE
        SYNTAX SEQUENCE OF SynSourcePer24hCurEntry
        MAX-ACCESS not-accessible
        STATUS current
        DESCRIPTION
            "synSourcePer24hCur."
        ::= { synSource 80 }

    -- 1.3.6.1.4.1.2011.2.25.3.70.10.56.80.1
    synSourcePer24hCurEntry OBJECT-TYPE
        SYNTAX SynSourcePer24hCurEntry
        MAX-ACCESS not-accessible
        STATUS current
        DESCRIPTION
            "synSourcePer24hCur."
        INDEX{ synSourcePer24hCurEid,synSourcePer24hCurPara }
        ::= { synSourcePer24hCurTable 1 }

    SynSourcePer24hCurEntry ::=
        SEQUENCE {
            synSourcePer24hCurEid
                Unsigned32,
            synSourcePer24hCurMonValue
                OCTET STRING,
            synSourcePer24hCurVldty
                ValidflagType,
            synSourcePer24hCurDatetime
                DateAndTime,
            synSourcePer24hCurParaLen
                Unsigned32,
            synSourcePer24hCurPara
                OCTET STRING
        }

    -- 1.3.6.1.4.1.2011.2.25.3.70.10.56.80.1.1
    synSourcePer24hCurEid OBJECT-TYPE
        SYNTAX Unsigned32
	{
	    maxclkda(16094),
	    minclkda(16095),
	    avgclkda(16096)
	}
        MAX-ACCESS read-only
        STATUS current
        DESCRIPTION
            "perEid."
        ::= { synSourcePer24hCurEntry 1 }

    -- 1.3.6.1.4.1.2011.2.25.3.70.10.56.80.1.2
    synSourcePer24hCurMonValue OBJECT-TYPE
        SYNTAX OCTET STRING
        MAX-ACCESS read-only
        STATUS current
        DESCRIPTION
            "perMonValue."
        ::= { synSourcePer24hCurEntry 2 }

    -- 1.3.6.1.4.1.2011.2.25.3.70.10.56.80.1.3
    synSourcePer24hCurVldty OBJECT-TYPE
        SYNTAX ValidflagType
        MAX-ACCESS read-only
        STATUS current
        DESCRIPTION
            "perVldty."
        ::= { synSourcePer24hCurEntry 3 }

    -- 1.3.6.1.4.1.2011.2.25.3.70.10.56.80.1.4
    synSourcePer24hCurDatetime OBJECT-TYPE
        SYNTAX DateAndTime
        MAX-ACCESS read-only
        STATUS current
        DESCRIPTION
            "perDateTime."
        ::= { synSourcePer24hCurEntry 4 }

    -- 1.3.6.1.4.1.2011.2.25.3.70.10.56.80.1.5
    synSourcePer24hCurParaLen OBJECT-TYPE
        SYNTAX Unsigned32
        MAX-ACCESS read-only
        STATUS current
        DESCRIPTION
            "perParaLen."
        ::= { synSourcePer24hCurEntry 5 }

    -- 1.3.6.1.4.1.2011.2.25.3.70.10.56.80.1.6
    synSourcePer24hCurPara OBJECT-TYPE
        SYNTAX OCTET STRING
        MAX-ACCESS read-only
        STATUS current
        DESCRIPTION
            "perPara."
        ::= { synSourcePer24hCurEntry 6 }

    -- 1.3.6.1.4.1.2011.2.25.3.70.10.56.90
    synSourcePer24hHisTable OBJECT-TYPE
        SYNTAX SEQUENCE OF SynSourcePer24hHisEntry
        MAX-ACCESS not-accessible
        STATUS current
        DESCRIPTION
            "synSourcePer24hHis."
        ::= { synSource 90 }

    -- 1.3.6.1.4.1.2011.2.25.3.70.10.56.90.1
    synSourcePer24hHisEntry OBJECT-TYPE
        SYNTAX SynSourcePer24hHisEntry
        MAX-ACCESS not-accessible
        STATUS current
        DESCRIPTION
            "synSourcePer24hHis."
        INDEX{ synSourcePer24hHisEid,synSourcePer24hHisParaLen,synSourcePer24hHisPara,synSourcePer24hHisStartTime,synSourcePer24hHisEndTime }
        ::= { synSourcePer24hHisTable 1 }

    SynSourcePer24hHisEntry ::=
        SEQUENCE {
            synSourcePer24hHisEid
                Unsigned32,
            synSourcePer24hHisParaLen
                Unsigned32,
            synSourcePer24hHisPara
                OCTET STRING,
            synSourcePer24hHisMonValue
                OCTET STRING,
            synSourcePer24hHisStartTime
                DateAndTime,
            synSourcePer24hHisEndTime
                DateAndTime,
            synSourcePer24hHisVldty
                ValidflagType
        }

    -- 1.3.6.1.4.1.2011.2.25.3.70.10.56.90.1.1
    synSourcePer24hHisEid OBJECT-TYPE
        SYNTAX Unsigned32
	{
	    maxclkda(16094),
	    minclkda(16095),
	    avgclkda(16096)
	}
        MAX-ACCESS read-only
        STATUS current
        DESCRIPTION
            "perEid."
        ::= { synSourcePer24hHisEntry 1 }

    -- 1.3.6.1.4.1.2011.2.25.3.70.10.56.90.1.2
    synSourcePer24hHisParaLen OBJECT-TYPE
        SYNTAX Unsigned32
        MAX-ACCESS read-only
        STATUS current
        DESCRIPTION
            "perParaLen."
        ::= { synSourcePer24hHisEntry 2 }

    -- 1.3.6.1.4.1.2011.2.25.3.70.10.56.90.1.3
    synSourcePer24hHisPara OBJECT-TYPE
        SYNTAX OCTET STRING
        MAX-ACCESS read-only
        STATUS current
        DESCRIPTION
            "perPara."
        ::= { synSourcePer24hHisEntry 3 }

    -- 1.3.6.1.4.1.2011.2.25.3.70.10.56.90.1.4
    synSourcePer24hHisMonValue OBJECT-TYPE
        SYNTAX OCTET STRING
        MAX-ACCESS read-only
        STATUS current
        DESCRIPTION
            "perMonValue."
        ::= { synSourcePer24hHisEntry 4 }

    -- 1.3.6.1.4.1.2011.2.25.3.70.10.56.90.1.5
    synSourcePer24hHisStartTime OBJECT-TYPE
        SYNTAX DateAndTime
        MAX-ACCESS read-only
        STATUS current
        DESCRIPTION
            "perDateTimeStart."
        ::= { synSourcePer24hHisEntry 5 }

    -- 1.3.6.1.4.1.2011.2.25.3.70.10.56.90.1.6
    synSourcePer24hHisEndTime OBJECT-TYPE
        SYNTAX DateAndTime
        MAX-ACCESS read-only
        STATUS current
        DESCRIPTION
            "perDateTimeEnd."
        ::= { synSourcePer24hHisEntry 6 }

    -- 1.3.6.1.4.1.2011.2.25.3.70.10.56.90.1.7
    synSourcePer24hHisVldty OBJECT-TYPE
        SYNTAX ValidflagType
        MAX-ACCESS read-only
        STATUS current
        DESCRIPTION
            "perVldty."
        ::= { synSourcePer24hHisEntry 7 }

    -- 1.3.6.1.4.1.2011.2.25.3.70.10.60
    port OBJECT IDENTIFIER ::= { rtnPerformance 60 }

    -- 1.3.6.1.4.1.2011.2.25.3.70.10.60.60
    portPer15mCurTable OBJECT-TYPE
        SYNTAX SEQUENCE OF PortPer15mCurEntry
        MAX-ACCESS not-accessible
        STATUS current
        DESCRIPTION
            "portPer15mCur."
        ::= { port 60 }

    -- 1.3.6.1.4.1.2011.2.25.3.70.10.60.60.1
    portPer15mCurEntry OBJECT-TYPE
        SYNTAX PortPer15mCurEntry
        MAX-ACCESS not-accessible
        STATUS current
        DESCRIPTION
            "portPer15mCur."
        INDEX{ portPer15mCurEid,portPer15mCurPara }
        ::= { portPer15mCurTable 1 }

    PortPer15mCurEntry ::=
        SEQUENCE {
            portPer15mCurEid
                PerformanceEventType,
            portPer15mCurMonValue
                OCTET STRING,
            portPer15mCurVldty
                ValidflagType,
            portPer15mCurDatetime
                DateAndTime,
            portPer15mCurParaLen
                Unsigned32,
            portPer15mCurPara
                OCTET STRING
        }

    -- 1.3.6.1.4.1.2011.2.25.3.70.10.60.60.1.1
    portPer15mCurEid OBJECT-TYPE
        SYNTAX PerformanceEventType
        MAX-ACCESS read-only
        STATUS current
        DESCRIPTION
            "perEid."
        ::= { portPer15mCurEntry 1 }

    -- 1.3.6.1.4.1.2011.2.25.3.70.10.60.60.1.2
    portPer15mCurMonValue OBJECT-TYPE
        SYNTAX OCTET STRING
        MAX-ACCESS read-only
        STATUS current
        DESCRIPTION
            "perMonValue."
        ::= { portPer15mCurEntry 2 }

    -- 1.3.6.1.4.1.2011.2.25.3.70.10.60.60.1.3
    portPer15mCurVldty OBJECT-TYPE
        SYNTAX ValidflagType
        MAX-ACCESS read-only
        STATUS current
        DESCRIPTION
            "perVldty."
        ::= { portPer15mCurEntry 3 }

    -- 1.3.6.1.4.1.2011.2.25.3.70.10.60.60.1.4
    portPer15mCurDatetime OBJECT-TYPE
        SYNTAX DateAndTime
        MAX-ACCESS read-only
        STATUS current
        DESCRIPTION
            "perDateTime."
        ::= { portPer15mCurEntry 4 }

    -- 1.3.6.1.4.1.2011.2.25.3.70.10.60.60.1.5
    portPer15mCurParaLen OBJECT-TYPE
        SYNTAX Unsigned32
        MAX-ACCESS read-only
        STATUS current
        DESCRIPTION
            "perParaLen."
        ::= { portPer15mCurEntry 5 }

    -- 1.3.6.1.4.1.2011.2.25.3.70.10.60.60.1.6
    portPer15mCurPara OBJECT-TYPE
        SYNTAX OCTET STRING
        MAX-ACCESS read-only
        STATUS current
        DESCRIPTION
            "perPara."
        ::= { portPer15mCurEntry 6 }

    -- 1.3.6.1.4.1.2011.2.25.3.70.10.60.70
    portPer15mHisTable OBJECT-TYPE
        SYNTAX SEQUENCE OF PortPer15mHisEntry
        MAX-ACCESS not-accessible
        STATUS current
        DESCRIPTION
            "portPer15mHis."
        ::= { port 70 }

    -- 1.3.6.1.4.1.2011.2.25.3.70.10.60.70.1
    portPer15mHisEntry OBJECT-TYPE
        SYNTAX PortPer15mHisEntry
        MAX-ACCESS not-accessible
        STATUS current
        DESCRIPTION
            "portPer15mHis."
        INDEX{ portPer15mHisEid,portPer15mHisParaLen,portPer15mHisPara,portPer15mHisStartTime,portPer15mHisEndTime }
        ::= { portPer15mHisTable 1 }

    PortPer15mHisEntry ::=
        SEQUENCE {
            portPer15mHisEid
                PerformanceEventType,
            portPer15mHisParaLen
                Unsigned32,
            portPer15mHisPara
                OCTET STRING,
            portPer15mHisMonValue
                OCTET STRING,
            portPer15mHisStartTime
                DateAndTime,
            portPer15mHisEndTime
                DateAndTime,
            portPer15mHisVldty
                ValidflagType
        }

    -- 1.3.6.1.4.1.2011.2.25.3.70.10.60.70.1.1
    portPer15mHisEid OBJECT-TYPE
        SYNTAX PerformanceEventType
        MAX-ACCESS read-only
        STATUS current
        DESCRIPTION
            "perEid."
        ::= { portPer15mHisEntry 1 }

    -- 1.3.6.1.4.1.2011.2.25.3.70.10.60.70.1.2
    portPer15mHisParaLen OBJECT-TYPE
        SYNTAX Unsigned32
        MAX-ACCESS read-only
        STATUS current
        DESCRIPTION
            "perParaLen."
        ::= { portPer15mHisEntry 2 }

    -- 1.3.6.1.4.1.2011.2.25.3.70.10.60.70.1.3
    portPer15mHisPara OBJECT-TYPE
        SYNTAX OCTET STRING
        MAX-ACCESS read-only
        STATUS current
        DESCRIPTION
            "perPara."
        ::= { portPer15mHisEntry 3 }

    -- 1.3.6.1.4.1.2011.2.25.3.70.10.60.70.1.4
    portPer15mHisMonValue OBJECT-TYPE
        SYNTAX OCTET STRING
        MAX-ACCESS read-only
        STATUS current
        DESCRIPTION
            "perMonValue."
        ::= { portPer15mHisEntry 4 }

    -- 1.3.6.1.4.1.2011.2.25.3.70.10.60.70.1.5
    portPer15mHisStartTime OBJECT-TYPE
        SYNTAX DateAndTime
        MAX-ACCESS read-only
        STATUS current
        DESCRIPTION
            "perDateTimeStart."
        ::= { portPer15mHisEntry 5 }

    -- 1.3.6.1.4.1.2011.2.25.3.70.10.60.70.1.6
    portPer15mHisEndTime OBJECT-TYPE
        SYNTAX DateAndTime
        MAX-ACCESS read-only
        STATUS current
        DESCRIPTION
            "perDateTimeEnd."
        ::= { portPer15mHisEntry 6 }

    -- 1.3.6.1.4.1.2011.2.25.3.70.10.60.70.1.7
    portPer15mHisVldty OBJECT-TYPE
        SYNTAX ValidflagType
        MAX-ACCESS read-only
        STATUS current
        DESCRIPTION
            "perVldty."
        ::= { portPer15mHisEntry 7 }

    -- 1.3.6.1.4.1.2011.2.25.3.70.10.60.80
    portPer24hCurTable OBJECT-TYPE
        SYNTAX SEQUENCE OF PortPer24hCurEntry
        MAX-ACCESS not-accessible
        STATUS current
        DESCRIPTION
            "portPer24hCur."
        ::= { port 80 }

    -- 1.3.6.1.4.1.2011.2.25.3.70.10.60.80.1
    portPer24hCurEntry OBJECT-TYPE
        SYNTAX PortPer24hCurEntry
        MAX-ACCESS not-accessible
        STATUS current
        DESCRIPTION
            "portPer24hCur."
        INDEX{ portPer24hCurEid,portPer24hCurPara }
        ::= { portPer24hCurTable 1 }

    PortPer24hCurEntry ::=
        SEQUENCE {
            portPer24hCurEid
                PerformanceEventType,
            portPer24hCurMonValue
                OCTET STRING,
            portPer24hCurVldty
                ValidflagType,
            portPer24hCurDatetime
                DateAndTime,
            portPer24hCurParaLen
                Unsigned32,
            portPer24hCurPara
                OCTET STRING
        }

    -- 1.3.6.1.4.1.2011.2.25.3.70.10.60.80.1.1
    portPer24hCurEid OBJECT-TYPE
        SYNTAX PerformanceEventType
        MAX-ACCESS read-only
        STATUS current
        DESCRIPTION
            "perEid."
        ::= { portPer24hCurEntry 1 }

    -- 1.3.6.1.4.1.2011.2.25.3.70.10.60.80.1.2
    portPer24hCurMonValue OBJECT-TYPE
        SYNTAX OCTET STRING
        MAX-ACCESS read-only
        STATUS current
        DESCRIPTION
            "perMonValue."
        ::= { portPer24hCurEntry 2 }

    -- 1.3.6.1.4.1.2011.2.25.3.70.10.60.80.1.3
    portPer24hCurVldty OBJECT-TYPE
        SYNTAX ValidflagType
        MAX-ACCESS read-only
        STATUS current
        DESCRIPTION
            "perVldty."
        ::= { portPer24hCurEntry 3 }

    -- 1.3.6.1.4.1.2011.2.25.3.70.10.60.80.1.4
    portPer24hCurDatetime OBJECT-TYPE
        SYNTAX DateAndTime
        MAX-ACCESS read-only
        STATUS current
        DESCRIPTION
            "perDateTime."
        ::= { portPer24hCurEntry 4 }

    -- 1.3.6.1.4.1.2011.2.25.3.70.10.60.80.1.5
    portPer24hCurParaLen OBJECT-TYPE
        SYNTAX Unsigned32
        MAX-ACCESS read-only
        STATUS current
        DESCRIPTION
            "perParaLen."
        ::= { portPer24hCurEntry 5 }

    -- 1.3.6.1.4.1.2011.2.25.3.70.10.60.80.1.6
    portPer24hCurPara OBJECT-TYPE
        SYNTAX OCTET STRING
        MAX-ACCESS read-only
        STATUS current
        DESCRIPTION
            "perPara."
        ::= { portPer24hCurEntry 6 }

    -- 1.3.6.1.4.1.2011.2.25.3.70.10.60.90
    portPer24hHisTable OBJECT-TYPE
        SYNTAX SEQUENCE OF PortPer24hHisEntry
        MAX-ACCESS not-accessible
        STATUS current
        DESCRIPTION
            "portPer24hHis."
        ::= { port 90 }

    -- 1.3.6.1.4.1.2011.2.25.3.70.10.60.90.1
    portPer24hHisEntry OBJECT-TYPE
        SYNTAX PortPer24hHisEntry
        MAX-ACCESS not-accessible
        STATUS current
        DESCRIPTION
            "portPer24hHis."
        INDEX{ portPer24hHisEid,portPer24hHisParaLen,portPer24hHisPara,portPer24hHisStartTime,portPer24hHisEndTime }
        ::= { portPer24hHisTable 1 }

    PortPer24hHisEntry ::=
        SEQUENCE {
            portPer24hHisEid
                PerformanceEventType,
            portPer24hHisParaLen
                Unsigned32,
            portPer24hHisPara
                OCTET STRING,
            portPer24hHisMonValue
                OCTET STRING,
            portPer24hHisStartTime
                DateAndTime,
            portPer24hHisEndTime
                DateAndTime,
            portPer24hHisVldty
                ValidflagType
        }

    -- 1.3.6.1.4.1.2011.2.25.3.70.10.60.90.1.1
    portPer24hHisEid OBJECT-TYPE
        SYNTAX PerformanceEventType
        MAX-ACCESS read-only
        STATUS current
        DESCRIPTION
            "perEid."
        ::= { portPer24hHisEntry 1 }

    -- 1.3.6.1.4.1.2011.2.25.3.70.10.60.90.1.2
    portPer24hHisParaLen OBJECT-TYPE
        SYNTAX Unsigned32
        MAX-ACCESS read-only
        STATUS current
        DESCRIPTION
            "perParaLen."
        ::= { portPer24hHisEntry 2 }

    -- 1.3.6.1.4.1.2011.2.25.3.70.10.60.90.1.3
    portPer24hHisPara OBJECT-TYPE
        SYNTAX OCTET STRING
        MAX-ACCESS read-only
        STATUS current
        DESCRIPTION
            "perPara."
        ::= { portPer24hHisEntry 3 }

    -- 1.3.6.1.4.1.2011.2.25.3.70.10.60.90.1.4
    portPer24hHisMonValue OBJECT-TYPE
        SYNTAX OCTET STRING
        MAX-ACCESS read-only
        STATUS current
        DESCRIPTION
            "perMonValue."
        ::= { portPer24hHisEntry 4 }

    -- 1.3.6.1.4.1.2011.2.25.3.70.10.60.90.1.5
    portPer24hHisStartTime OBJECT-TYPE
        SYNTAX DateAndTime
        MAX-ACCESS read-only
        STATUS current
        DESCRIPTION
            "perDateTimeStart."
        ::= { portPer24hHisEntry 5 }

    -- 1.3.6.1.4.1.2011.2.25.3.70.10.60.90.1.6
    portPer24hHisEndTime OBJECT-TYPE
        SYNTAX DateAndTime
        MAX-ACCESS read-only
        STATUS current
        DESCRIPTION
            "perDateTimeEnd."
        ::= { portPer24hHisEntry 6 }

    -- 1.3.6.1.4.1.2011.2.25.3.70.10.60.90.1.7
    portPer24hHisVldty OBJECT-TYPE
        SYNTAX ValidflagType
        MAX-ACCESS read-only
        STATUS current
        DESCRIPTION
            "perVldty."
        ::= { portPer24hHisEntry 7 }

    -- 1.3.6.1.4.1.2011.2.25.3.70.10.70
    ifport OBJECT IDENTIFIER ::= { rtnPerformance 70 }

    -- 1.3.6.1.4.1.2011.2.25.3.70.10.70.60
    ifportPer15mCurTable OBJECT-TYPE
        SYNTAX SEQUENCE OF IfportPer15mCurEntry
        MAX-ACCESS not-accessible
        STATUS current
        DESCRIPTION
            "ifportPer15mCur."
        ::= { ifport 60 }

    -- 1.3.6.1.4.1.2011.2.25.3.70.10.70.60.1
    ifportPer15mCurEntry OBJECT-TYPE
        SYNTAX IfportPer15mCurEntry
        MAX-ACCESS not-accessible
        STATUS current
        DESCRIPTION
            "ifportPer15mCur."
        INDEX{ ifportPer15mCurEid,ifportPer15mCurPara }
        ::= { ifportPer15mCurTable 1 }

    IfportPer15mCurEntry ::=
        SEQUENCE {
            ifportPer15mCurEid
                PerformanceEventType,
            ifportPer15mCurMonValue
                OCTET STRING,
            ifportPer15mCurVldty
                ValidflagType,
            ifportPer15mCurDatetime
                DateAndTime,
            ifportPer15mCurParaLen
                Unsigned32,
            ifportPer15mCurPara
                OCTET STRING
        }

    -- 1.3.6.1.4.1.2011.2.25.3.70.10.70.60.1.1
    ifportPer15mCurEid OBJECT-TYPE
        SYNTAX PerformanceEventType
        MAX-ACCESS read-only
        STATUS current
        DESCRIPTION
            "perEid."
        ::= { ifportPer15mCurEntry 1 }

    -- 1.3.6.1.4.1.2011.2.25.3.70.10.70.60.1.2
    ifportPer15mCurMonValue OBJECT-TYPE
        SYNTAX OCTET STRING
        MAX-ACCESS read-only
        STATUS current
        DESCRIPTION
            "perMonValue."
        ::= { ifportPer15mCurEntry 2 }

    -- 1.3.6.1.4.1.2011.2.25.3.70.10.70.60.1.3
    ifportPer15mCurVldty OBJECT-TYPE
        SYNTAX ValidflagType
        MAX-ACCESS read-only
        STATUS current
        DESCRIPTION
            "perVldty."
        ::= { ifportPer15mCurEntry 3 }

    -- 1.3.6.1.4.1.2011.2.25.3.70.10.70.60.1.4
    ifportPer15mCurDatetime OBJECT-TYPE
        SYNTAX DateAndTime
        MAX-ACCESS read-only
        STATUS current
        DESCRIPTION
            "perDateTime."
        ::= { ifportPer15mCurEntry 4 }

    -- 1.3.6.1.4.1.2011.2.25.3.70.10.70.60.1.5
    ifportPer15mCurParaLen OBJECT-TYPE
        SYNTAX Unsigned32
        MAX-ACCESS read-only
        STATUS current
        DESCRIPTION
            "perParaLen."
        ::= { ifportPer15mCurEntry 5 }

    -- 1.3.6.1.4.1.2011.2.25.3.70.10.70.60.1.6
    ifportPer15mCurPara OBJECT-TYPE
        SYNTAX OCTET STRING
        MAX-ACCESS read-only
        STATUS current
        DESCRIPTION
            "perPara."
        ::= { ifportPer15mCurEntry 6 }

    -- 1.3.6.1.4.1.2011.2.25.3.70.10.70.70
    ifportPer15mHisTable OBJECT-TYPE
        SYNTAX SEQUENCE OF IfportPer15mHisEntry
        MAX-ACCESS not-accessible
        STATUS current
        DESCRIPTION
            "ifportPer15mHis."
        ::= { ifport 70 }

    -- 1.3.6.1.4.1.2011.2.25.3.70.10.70.70.1
    ifportPer15mHisEntry OBJECT-TYPE
        SYNTAX IfportPer15mHisEntry
        MAX-ACCESS not-accessible
        STATUS current
        DESCRIPTION
            "ifportPer15mHis."
        INDEX{ ifportPer15mHisEid,ifportPer15mHisParaLen,ifportPer15mHisPara,ifportPer15mHisStartTime,ifportPer15mHisEndTime }
        ::= { ifportPer15mHisTable 1 }

    IfportPer15mHisEntry ::=
        SEQUENCE {
            ifportPer15mHisEid
                PerformanceEventType,
            ifportPer15mHisParaLen
                Unsigned32,
            ifportPer15mHisPara
                OCTET STRING,
            ifportPer15mHisMonValue
                OCTET STRING,
            ifportPer15mHisStartTime
                DateAndTime,
            ifportPer15mHisEndTime
                DateAndTime,
            ifportPer15mHisVldty
                ValidflagType
        }

    -- 1.3.6.1.4.1.2011.2.25.3.70.10.70.70.1.1
    ifportPer15mHisEid OBJECT-TYPE
        SYNTAX PerformanceEventType
        MAX-ACCESS read-only
        STATUS current
        DESCRIPTION
            "perEid."
        ::= { ifportPer15mHisEntry 1 }

    -- 1.3.6.1.4.1.2011.2.25.3.70.10.70.70.1.2
    ifportPer15mHisParaLen OBJECT-TYPE
        SYNTAX Unsigned32
        MAX-ACCESS read-only
        STATUS current
        DESCRIPTION
            "perParaLen."
        ::= { ifportPer15mHisEntry 2 }

    -- 1.3.6.1.4.1.2011.2.25.3.70.10.70.70.1.3
    ifportPer15mHisPara OBJECT-TYPE
        SYNTAX OCTET STRING
        MAX-ACCESS read-only
        STATUS current
        DESCRIPTION
            "perPara."
        ::= { ifportPer15mHisEntry 3 }

    -- 1.3.6.1.4.1.2011.2.25.3.70.10.70.70.1.4
    ifportPer15mHisMonValue OBJECT-TYPE
        SYNTAX OCTET STRING
        MAX-ACCESS read-only
        STATUS current
        DESCRIPTION
            "perMonValue."
        ::= { ifportPer15mHisEntry 4 }

    -- 1.3.6.1.4.1.2011.2.25.3.70.10.70.70.1.5
    ifportPer15mHisStartTime OBJECT-TYPE
        SYNTAX DateAndTime
        MAX-ACCESS read-only
        STATUS current
        DESCRIPTION
            "perDateTimeStart."
        ::= { ifportPer15mHisEntry 5 }

    -- 1.3.6.1.4.1.2011.2.25.3.70.10.70.70.1.6
    ifportPer15mHisEndTime OBJECT-TYPE
        SYNTAX DateAndTime
        MAX-ACCESS read-only
        STATUS current
        DESCRIPTION
            "perDateTimeEnd."
        ::= { ifportPer15mHisEntry 6 }

    -- 1.3.6.1.4.1.2011.2.25.3.70.10.70.70.1.7
    ifportPer15mHisVldty OBJECT-TYPE
        SYNTAX ValidflagType
        MAX-ACCESS read-only
        STATUS current
        DESCRIPTION
            "perVldty."
        ::= { ifportPer15mHisEntry 7 }

    -- 1.3.6.1.4.1.2011.2.25.3.70.10.70.80
    ifportPer24hCurTable OBJECT-TYPE
        SYNTAX SEQUENCE OF IfportPer24hCurEntry
        MAX-ACCESS not-accessible
        STATUS current
        DESCRIPTION
            "ifportPer24hCur."
        ::= { ifport 80 }

    -- 1.3.6.1.4.1.2011.2.25.3.70.10.70.80.1
    ifportPer24hCurEntry OBJECT-TYPE
        SYNTAX IfportPer24hCurEntry
        MAX-ACCESS not-accessible
        STATUS current
        DESCRIPTION
            "ifportPer24hCur."
        INDEX{ ifportPer24hCurEid,ifportPer24hCurPara }
        ::= { ifportPer24hCurTable 1 }

    IfportPer24hCurEntry ::=
        SEQUENCE {
            ifportPer24hCurEid
                PerformanceEventType,
            ifportPer24hCurMonValue
                OCTET STRING,
            ifportPer24hCurVldty
                ValidflagType,
            ifportPer24hCurDatetime
                DateAndTime,
            ifportPer24hCurParaLen
                Unsigned32,
            ifportPer24hCurPara
                OCTET STRING
        }

    -- 1.3.6.1.4.1.2011.2.25.3.70.10.70.80.1.1
    ifportPer24hCurEid OBJECT-TYPE
        SYNTAX PerformanceEventType
        MAX-ACCESS read-only
        STATUS current
        DESCRIPTION
            "perEid."
        ::= { ifportPer24hCurEntry 1 }

    -- 1.3.6.1.4.1.2011.2.25.3.70.10.70.80.1.2
    ifportPer24hCurMonValue OBJECT-TYPE
        SYNTAX OCTET STRING
        MAX-ACCESS read-only
        STATUS current
        DESCRIPTION
            "perMonValue."
        ::= { ifportPer24hCurEntry 2 }

    -- 1.3.6.1.4.1.2011.2.25.3.70.10.70.80.1.3
    ifportPer24hCurVldty OBJECT-TYPE
        SYNTAX ValidflagType
        MAX-ACCESS read-only
        STATUS current
        DESCRIPTION
            "perVldty."
        ::= { ifportPer24hCurEntry 3 }

    -- 1.3.6.1.4.1.2011.2.25.3.70.10.70.80.1.4
    ifportPer24hCurDatetime OBJECT-TYPE
        SYNTAX DateAndTime
        MAX-ACCESS read-only
        STATUS current
        DESCRIPTION
            "perDateTime."
        ::= { ifportPer24hCurEntry 4 }

    -- 1.3.6.1.4.1.2011.2.25.3.70.10.70.80.1.5
    ifportPer24hCurParaLen OBJECT-TYPE
        SYNTAX Unsigned32
        MAX-ACCESS read-only
        STATUS current
        DESCRIPTION
            "perParaLen."
        ::= { ifportPer24hCurEntry 5 }

    -- 1.3.6.1.4.1.2011.2.25.3.70.10.70.80.1.6
    ifportPer24hCurPara OBJECT-TYPE
        SYNTAX OCTET STRING
        MAX-ACCESS read-only
        STATUS current
        DESCRIPTION
            "perPara."
        ::= { ifportPer24hCurEntry 6 }

    -- 1.3.6.1.4.1.2011.2.25.3.70.10.70.90
    ifportPer24hHisTable OBJECT-TYPE
        SYNTAX SEQUENCE OF IfportPer24hHisEntry
        MAX-ACCESS not-accessible
        STATUS current
        DESCRIPTION
            "ifportPer24hHis."
        ::= { ifport 90 }

    -- 1.3.6.1.4.1.2011.2.25.3.70.10.70.90.1
    ifportPer24hHisEntry OBJECT-TYPE
        SYNTAX IfportPer24hHisEntry
        MAX-ACCESS not-accessible
        STATUS current
        DESCRIPTION
            "ifportPer24hHis."
        INDEX{ ifportPer24hHisEid,ifportPer24hHisParaLen,ifportPer24hHisPara,ifportPer24hHisStartTime,ifportPer24hHisEndTime }
        ::= { ifportPer24hHisTable 1 }

    IfportPer24hHisEntry ::=
        SEQUENCE {
            ifportPer24hHisEid
                PerformanceEventType,
            ifportPer24hHisParaLen
                Unsigned32,
            ifportPer24hHisPara
                OCTET STRING,
            ifportPer24hHisMonValue
                OCTET STRING,
            ifportPer24hHisStartTime
                DateAndTime,
            ifportPer24hHisEndTime
                DateAndTime,
            ifportPer24hHisVldty
                ValidflagType
        }

    -- 1.3.6.1.4.1.2011.2.25.3.70.10.70.90.1.1
    ifportPer24hHisEid OBJECT-TYPE
        SYNTAX PerformanceEventType
        MAX-ACCESS read-only
        STATUS current
        DESCRIPTION
            "perEid."
        ::= { ifportPer24hHisEntry 1 }

    -- 1.3.6.1.4.1.2011.2.25.3.70.10.70.90.1.2
    ifportPer24hHisParaLen OBJECT-TYPE
        SYNTAX Unsigned32
        MAX-ACCESS read-only
        STATUS current
        DESCRIPTION
            "perParaLen."
        ::= { ifportPer24hHisEntry 2 }

    -- 1.3.6.1.4.1.2011.2.25.3.70.10.70.90.1.3
    ifportPer24hHisPara OBJECT-TYPE
        SYNTAX OCTET STRING
        MAX-ACCESS read-only
        STATUS current
        DESCRIPTION
            "perPara."
        ::= { ifportPer24hHisEntry 3 }

    -- 1.3.6.1.4.1.2011.2.25.3.70.10.70.90.1.4
    ifportPer24hHisMonValue OBJECT-TYPE
        SYNTAX OCTET STRING
        MAX-ACCESS read-only
        STATUS current
        DESCRIPTION
            "perMonValue."
        ::= { ifportPer24hHisEntry 4 }

    -- 1.3.6.1.4.1.2011.2.25.3.70.10.70.90.1.5
    ifportPer24hHisStartTime OBJECT-TYPE
        SYNTAX DateAndTime
        MAX-ACCESS read-only
        STATUS current
        DESCRIPTION
            "perDateTimeStart."
        ::= { ifportPer24hHisEntry 5 }

    -- 1.3.6.1.4.1.2011.2.25.3.70.10.70.90.1.6
    ifportPer24hHisEndTime OBJECT-TYPE
        SYNTAX DateAndTime
        MAX-ACCESS read-only
        STATUS current
        DESCRIPTION
            "perDateTimeEnd."
        ::= { ifportPer24hHisEntry 6 }

    -- 1.3.6.1.4.1.2011.2.25.3.70.10.70.90.1.7
    ifportPer24hHisVldty OBJECT-TYPE
        SYNTAX ValidflagType
        MAX-ACCESS read-only
        STATUS current
        DESCRIPTION
            "perVldty."
        ::= { ifportPer24hHisEntry 7 }

    -- 1.3.6.1.4.1.2011.2.25.3.70.10.80
    oduport OBJECT IDENTIFIER ::= { rtnPerformance 80 }

    -- 1.3.6.1.4.1.2011.2.25.3.70.10.80.60
    oduportPer15mCurTable OBJECT-TYPE
        SYNTAX SEQUENCE OF OduportPer15mCurEntry
        MAX-ACCESS not-accessible
        STATUS current
        DESCRIPTION
            "oduportPer15mCur."
        ::= { oduport 60 }

    -- 1.3.6.1.4.1.2011.2.25.3.70.10.80.60.1
    oduportPer15mCurEntry OBJECT-TYPE
        SYNTAX OduportPer15mCurEntry
        MAX-ACCESS not-accessible
        STATUS current
        DESCRIPTION
            "oduportPer15mCur."
        INDEX{ oduportPer15mCurEid,oduportPer15mCurPara }
        ::= { oduportPer15mCurTable 1 }

    OduportPer15mCurEntry ::=
        SEQUENCE {
            oduportPer15mCurEid
                PerformanceEventType,
            oduportPer15mCurMonValue
                OCTET STRING,
            oduportPer15mCurVldty
                ValidflagType,
            oduportPer15mCurDatetime
                DateAndTime,
            oduportPer15mCurParaLen
                Unsigned32,
            oduportPer15mCurPara
                OCTET STRING
        }

    -- 1.3.6.1.4.1.2011.2.25.3.70.10.80.60.1.1
    oduportPer15mCurEid OBJECT-TYPE
        SYNTAX PerformanceEventType
        MAX-ACCESS read-only
        STATUS current
        DESCRIPTION
            "perEid."
        ::= { oduportPer15mCurEntry 1 }

    -- 1.3.6.1.4.1.2011.2.25.3.70.10.80.60.1.2
    oduportPer15mCurMonValue OBJECT-TYPE
        SYNTAX OCTET STRING
        MAX-ACCESS read-only
        STATUS current
        DESCRIPTION
            "perMonValue."
        ::= { oduportPer15mCurEntry 2 }

    -- 1.3.6.1.4.1.2011.2.25.3.70.10.80.60.1.3
    oduportPer15mCurVldty OBJECT-TYPE
        SYNTAX ValidflagType
        MAX-ACCESS read-only
        STATUS current
        DESCRIPTION
            "perVldty."
        ::= { oduportPer15mCurEntry 3 }

    -- 1.3.6.1.4.1.2011.2.25.3.70.10.80.60.1.4
    oduportPer15mCurDatetime OBJECT-TYPE
        SYNTAX DateAndTime
        MAX-ACCESS read-only
        STATUS current
        DESCRIPTION
            "perDateTime."
        ::= { oduportPer15mCurEntry 4 }

    -- 1.3.6.1.4.1.2011.2.25.3.70.10.80.60.1.5
    oduportPer15mCurParaLen OBJECT-TYPE
        SYNTAX Unsigned32
        MAX-ACCESS read-only
        STATUS current
        DESCRIPTION
            "perParaLen."
        ::= { oduportPer15mCurEntry 5 }

    -- 1.3.6.1.4.1.2011.2.25.3.70.10.80.60.1.6
    oduportPer15mCurPara OBJECT-TYPE
        SYNTAX OCTET STRING
        MAX-ACCESS read-only
        STATUS current
        DESCRIPTION
            "perPara."
        ::= { oduportPer15mCurEntry 6 }

    -- 1.3.6.1.4.1.2011.2.25.3.70.10.80.70
    oduportPer15mHisTable OBJECT-TYPE
        SYNTAX SEQUENCE OF OduportPer15mHisEntry
        MAX-ACCESS not-accessible
        STATUS current
        DESCRIPTION
            "oduportPer15mHis."
        ::= { oduport 70 }

    -- 1.3.6.1.4.1.2011.2.25.3.70.10.80.70.1
    oduportPer15mHisEntry OBJECT-TYPE
        SYNTAX OduportPer15mHisEntry
        MAX-ACCESS not-accessible
        STATUS current
        DESCRIPTION
            "oduportPer15mHis."
        INDEX{ oduportPer15mHisEid,oduportPer15mHisParaLen,oduportPer15mHisPara,oduportPer15mHisStartTime,oduportPer15mHisEndTime }
        ::= { oduportPer15mHisTable 1 }

    OduportPer15mHisEntry ::=
        SEQUENCE {
            oduportPer15mHisEid
                PerformanceEventType,
            oduportPer15mHisParaLen
                Unsigned32,
            oduportPer15mHisPara
                OCTET STRING,
            oduportPer15mHisMonValue
                OCTET STRING,
            oduportPer15mHisStartTime
                DateAndTime,
            oduportPer15mHisEndTime
                DateAndTime,
            oduportPer15mHisVldty
                ValidflagType
        }

    -- 1.3.6.1.4.1.2011.2.25.3.70.10.80.70.1.1
    oduportPer15mHisEid OBJECT-TYPE
        SYNTAX PerformanceEventType
        MAX-ACCESS read-only
        STATUS current
        DESCRIPTION
            "perEid."
        ::= { oduportPer15mHisEntry 1 }

    -- 1.3.6.1.4.1.2011.2.25.3.70.10.80.70.1.2
    oduportPer15mHisParaLen OBJECT-TYPE
        SYNTAX Unsigned32
        MAX-ACCESS read-only
        STATUS current
        DESCRIPTION
            "perParaLen."
        ::= { oduportPer15mHisEntry 2 }

    -- 1.3.6.1.4.1.2011.2.25.3.70.10.80.70.1.3
    oduportPer15mHisPara OBJECT-TYPE
        SYNTAX OCTET STRING
        MAX-ACCESS read-only
        STATUS current
        DESCRIPTION
            "perPara."
        ::= { oduportPer15mHisEntry 3 }

    -- 1.3.6.1.4.1.2011.2.25.3.70.10.80.70.1.4
    oduportPer15mHisMonValue OBJECT-TYPE
        SYNTAX OCTET STRING
        MAX-ACCESS read-only
        STATUS current
        DESCRIPTION
            "perMonValue."
        ::= { oduportPer15mHisEntry 4 }

    -- 1.3.6.1.4.1.2011.2.25.3.70.10.80.70.1.5
    oduportPer15mHisStartTime OBJECT-TYPE
        SYNTAX DateAndTime
        MAX-ACCESS read-only
        STATUS current
        DESCRIPTION
            "perDateTimeStart."
        ::= { oduportPer15mHisEntry 5 }

    -- 1.3.6.1.4.1.2011.2.25.3.70.10.80.70.1.6
    oduportPer15mHisEndTime OBJECT-TYPE
        SYNTAX DateAndTime
        MAX-ACCESS read-only
        STATUS current
        DESCRIPTION
            "perDateTimeEnd."
        ::= { oduportPer15mHisEntry 6 }

    -- 1.3.6.1.4.1.2011.2.25.3.70.10.80.70.1.7
    oduportPer15mHisVldty OBJECT-TYPE
        SYNTAX ValidflagType
        MAX-ACCESS read-only
        STATUS current
        DESCRIPTION
            "perVldty."
        ::= { oduportPer15mHisEntry 7 }

    -- 1.3.6.1.4.1.2011.2.25.3.70.10.80.80
    oduportPer24hCurTable OBJECT-TYPE
        SYNTAX SEQUENCE OF OduportPer24hCurEntry
        MAX-ACCESS not-accessible
        STATUS current
        DESCRIPTION
            "oduportPer24hCur."
        ::= { oduport 80 }

    -- 1.3.6.1.4.1.2011.2.25.3.70.10.80.80.1
    oduportPer24hCurEntry OBJECT-TYPE
        SYNTAX OduportPer24hCurEntry
        MAX-ACCESS not-accessible
        STATUS current
        DESCRIPTION
            "oduportPer24hCur."
        INDEX{ oduportPer24hCurEid,oduportPer24hCurPara }
        ::= { oduportPer24hCurTable 1 }

    OduportPer24hCurEntry ::=
        SEQUENCE {
            oduportPer24hCurEid
                PerformanceEventType,
            oduportPer24hCurMonValue
                OCTET STRING,
            oduportPer24hCurVldty
                ValidflagType,
            oduportPer24hCurDatetime
                DateAndTime,
            oduportPer24hCurParaLen
                Unsigned32,
            oduportPer24hCurPara
                OCTET STRING
        }

    -- 1.3.6.1.4.1.2011.2.25.3.70.10.80.80.1.1
    oduportPer24hCurEid OBJECT-TYPE
        SYNTAX PerformanceEventType
        MAX-ACCESS read-only
        STATUS current
        DESCRIPTION
            "perEid."
        ::= { oduportPer24hCurEntry 1 }

    -- 1.3.6.1.4.1.2011.2.25.3.70.10.80.80.1.2
    oduportPer24hCurMonValue OBJECT-TYPE
        SYNTAX OCTET STRING
        MAX-ACCESS read-only
        STATUS current
        DESCRIPTION
            "perMonValue."
        ::= { oduportPer24hCurEntry 2 }

    -- 1.3.6.1.4.1.2011.2.25.3.70.10.80.80.1.3
    oduportPer24hCurVldty OBJECT-TYPE
        SYNTAX ValidflagType
        MAX-ACCESS read-only
        STATUS current
        DESCRIPTION
            "perVldty."
        ::= { oduportPer24hCurEntry 3 }

    -- 1.3.6.1.4.1.2011.2.25.3.70.10.80.80.1.4
    oduportPer24hCurDatetime OBJECT-TYPE
        SYNTAX DateAndTime
        MAX-ACCESS read-only
        STATUS current
        DESCRIPTION
            "perDateTime."
        ::= { oduportPer24hCurEntry 4 }

    -- 1.3.6.1.4.1.2011.2.25.3.70.10.80.80.1.5
    oduportPer24hCurParaLen OBJECT-TYPE
        SYNTAX Unsigned32
        MAX-ACCESS read-only
        STATUS current
        DESCRIPTION
            "perParaLen."
        ::= { oduportPer24hCurEntry 5 }

    -- 1.3.6.1.4.1.2011.2.25.3.70.10.80.80.1.6
    oduportPer24hCurPara OBJECT-TYPE
        SYNTAX OCTET STRING
        MAX-ACCESS read-only
        STATUS current
        DESCRIPTION
            "perPara."
        ::= { oduportPer24hCurEntry 6 }

    -- 1.3.6.1.4.1.2011.2.25.3.70.10.80.90
    oduportPer24hHisTable OBJECT-TYPE
        SYNTAX SEQUENCE OF OduportPer24hHisEntry
        MAX-ACCESS not-accessible
        STATUS current
        DESCRIPTION
            "oduportPer24hHis."
        ::= { oduport 90 }

    -- 1.3.6.1.4.1.2011.2.25.3.70.10.80.90.1
    oduportPer24hHisEntry OBJECT-TYPE
        SYNTAX OduportPer24hHisEntry
        MAX-ACCESS not-accessible
        STATUS current
        DESCRIPTION
            "oduportPer24hHis."
        INDEX{ oduportPer24hHisEid,oduportPer24hHisParaLen,oduportPer24hHisPara,oduportPer24hHisStartTime,oduportPer24hHisEndTime }
        ::= { oduportPer24hHisTable 1 }

    OduportPer24hHisEntry ::=
        SEQUENCE {
            oduportPer24hHisEid
                PerformanceEventType,
            oduportPer24hHisParaLen
                Unsigned32,
            oduportPer24hHisPara
                OCTET STRING,
            oduportPer24hHisMonValue
                OCTET STRING,
            oduportPer24hHisStartTime
                DateAndTime,
            oduportPer24hHisEndTime
                DateAndTime,
            oduportPer24hHisVldty
                ValidflagType
        }

    -- 1.3.6.1.4.1.2011.2.25.3.70.10.80.90.1.1
    oduportPer24hHisEid OBJECT-TYPE
        SYNTAX PerformanceEventType
        MAX-ACCESS read-only
        STATUS current
        DESCRIPTION
            "perEid."
        ::= { oduportPer24hHisEntry 1 }

    -- 1.3.6.1.4.1.2011.2.25.3.70.10.80.90.1.2
    oduportPer24hHisParaLen OBJECT-TYPE
        SYNTAX Unsigned32
        MAX-ACCESS read-only
        STATUS current
        DESCRIPTION
            "perParaLen."
        ::= { oduportPer24hHisEntry 2 }

    -- 1.3.6.1.4.1.2011.2.25.3.70.10.80.90.1.3
    oduportPer24hHisPara OBJECT-TYPE
        SYNTAX OCTET STRING
        MAX-ACCESS read-only
        STATUS current
        DESCRIPTION
            "perPara."
        ::= { oduportPer24hHisEntry 3 }

    -- 1.3.6.1.4.1.2011.2.25.3.70.10.80.90.1.4
    oduportPer24hHisMonValue OBJECT-TYPE
        SYNTAX OCTET STRING
        MAX-ACCESS read-only
        STATUS current
        DESCRIPTION
            "perMonValue."
        ::= { oduportPer24hHisEntry 4 }

    -- 1.3.6.1.4.1.2011.2.25.3.70.10.80.90.1.5
    oduportPer24hHisStartTime OBJECT-TYPE
        SYNTAX DateAndTime
        MAX-ACCESS read-only
        STATUS current
        DESCRIPTION
            "perDateTimeStart."
        ::= { oduportPer24hHisEntry 5 }

    -- 1.3.6.1.4.1.2011.2.25.3.70.10.80.90.1.6
    oduportPer24hHisEndTime OBJECT-TYPE
        SYNTAX DateAndTime
        MAX-ACCESS read-only
        STATUS current
        DESCRIPTION
            "perDateTimeEnd."
        ::= { oduportPer24hHisEntry 6 }

    -- 1.3.6.1.4.1.2011.2.25.3.70.10.80.90.1.7
    oduportPer24hHisVldty OBJECT-TYPE
        SYNTAX ValidflagType
        MAX-ACCESS read-only
        STATUS current
        DESCRIPTION
            "perVldty."
        ::= { oduportPer24hHisEntry 7 }

    -- 1.3.6.1.4.1.2011.2.25.3.70.10.90
    sdhport OBJECT IDENTIFIER ::= { rtnPerformance 90 }

    -- 1.3.6.1.4.1.2011.2.25.3.70.10.90.60
    sdhportPer15mCurTable OBJECT-TYPE
        SYNTAX SEQUENCE OF SdhportPer15mCurEntry
        MAX-ACCESS not-accessible
        STATUS current
        DESCRIPTION
            "sdhportPer15mCur."
        ::= { sdhport 60 }

    -- 1.3.6.1.4.1.2011.2.25.3.70.10.90.60.1
    sdhportPer15mCurEntry OBJECT-TYPE
        SYNTAX SdhportPer15mCurEntry
        MAX-ACCESS not-accessible
        STATUS current
        DESCRIPTION
            "sdhportPer15mCur."
        INDEX{ sdhportPer15mCurEid,sdhportPer15mCurPara }
        ::= { sdhportPer15mCurTable 1 }

    SdhportPer15mCurEntry ::=
        SEQUENCE {
            sdhportPer15mCurEid
                PerformanceEventType,
            sdhportPer15mCurMonValue
                OCTET STRING,
            sdhportPer15mCurVldty
                ValidflagType,
            sdhportPer15mCurDatetime
                DateAndTime,
            sdhportPer15mCurParaLen
                Unsigned32,
            sdhportPer15mCurPara
                OCTET STRING
        }

    -- 1.3.6.1.4.1.2011.2.25.3.70.10.90.60.1.1
    sdhportPer15mCurEid OBJECT-TYPE
        SYNTAX PerformanceEventType
        MAX-ACCESS read-only
        STATUS current
        DESCRIPTION
            "perEid."
        ::= { sdhportPer15mCurEntry 1 }

    -- 1.3.6.1.4.1.2011.2.25.3.70.10.90.60.1.2
    sdhportPer15mCurMonValue OBJECT-TYPE
        SYNTAX OCTET STRING
        MAX-ACCESS read-only
        STATUS current
        DESCRIPTION
            "perMonValue."
        ::= { sdhportPer15mCurEntry 2 }

    -- 1.3.6.1.4.1.2011.2.25.3.70.10.90.60.1.3
    sdhportPer15mCurVldty OBJECT-TYPE
        SYNTAX ValidflagType
        MAX-ACCESS read-only
        STATUS current
        DESCRIPTION
            "perVldty."
        ::= { sdhportPer15mCurEntry 3 }

    -- 1.3.6.1.4.1.2011.2.25.3.70.10.90.60.1.4
    sdhportPer15mCurDatetime OBJECT-TYPE
        SYNTAX DateAndTime
        MAX-ACCESS read-only
        STATUS current
        DESCRIPTION
            "perDateTime."
        ::= { sdhportPer15mCurEntry 4 }

    -- 1.3.6.1.4.1.2011.2.25.3.70.10.90.60.1.5
    sdhportPer15mCurParaLen OBJECT-TYPE
        SYNTAX Unsigned32
        MAX-ACCESS read-only
        STATUS current
        DESCRIPTION
            "perParaLen."
        ::= { sdhportPer15mCurEntry 5 }

    -- 1.3.6.1.4.1.2011.2.25.3.70.10.90.60.1.6
    sdhportPer15mCurPara OBJECT-TYPE
        SYNTAX OCTET STRING
        MAX-ACCESS read-only
        STATUS current
        DESCRIPTION
            "perPara."
        ::= { sdhportPer15mCurEntry 6 }

    -- 1.3.6.1.4.1.2011.2.25.3.70.10.90.70
    sdhportPer15mHisTable OBJECT-TYPE
        SYNTAX SEQUENCE OF SdhportPer15mHisEntry
        MAX-ACCESS not-accessible
        STATUS current
        DESCRIPTION
            "sdhportPer15mHis."
        ::= { sdhport 70 }

    -- 1.3.6.1.4.1.2011.2.25.3.70.10.90.70.1
    sdhportPer15mHisEntry OBJECT-TYPE
        SYNTAX SdhportPer15mHisEntry
        MAX-ACCESS not-accessible
        STATUS current
        DESCRIPTION
            "sdhportPer15mHis."
        INDEX{ sdhportPer15mHisEid,sdhportPer15mHisParaLen,sdhportPer15mHisPara,sdhportPer15mHisStartTime,sdhportPer15mHisEndTime }
        ::= { sdhportPer15mHisTable 1 }

    SdhportPer15mHisEntry ::=
        SEQUENCE {
            sdhportPer15mHisEid
                PerformanceEventType,
            sdhportPer15mHisParaLen
                Unsigned32,
            sdhportPer15mHisPara
                OCTET STRING,
            sdhportPer15mHisMonValue
                OCTET STRING,
            sdhportPer15mHisStartTime
                DateAndTime,
            sdhportPer15mHisEndTime
                DateAndTime,
            sdhportPer15mHisVldty
                ValidflagType
        }

    -- 1.3.6.1.4.1.2011.2.25.3.70.10.90.70.1.1
    sdhportPer15mHisEid OBJECT-TYPE
        SYNTAX PerformanceEventType
        MAX-ACCESS read-only
        STATUS current
        DESCRIPTION
            "perEid."
        ::= { sdhportPer15mHisEntry 1 }

    -- 1.3.6.1.4.1.2011.2.25.3.70.10.90.70.1.2
    sdhportPer15mHisParaLen OBJECT-TYPE
        SYNTAX Unsigned32
        MAX-ACCESS read-only
        STATUS current
        DESCRIPTION
            "perParaLen."
        ::= { sdhportPer15mHisEntry 2 }

    -- 1.3.6.1.4.1.2011.2.25.3.70.10.90.70.1.3
    sdhportPer15mHisPara OBJECT-TYPE
        SYNTAX OCTET STRING
        MAX-ACCESS read-only
        STATUS current
        DESCRIPTION
            "perPara."
        ::= { sdhportPer15mHisEntry 3 }

    -- 1.3.6.1.4.1.2011.2.25.3.70.10.90.70.1.4
    sdhportPer15mHisMonValue OBJECT-TYPE
        SYNTAX OCTET STRING
        MAX-ACCESS read-only
        STATUS current
        DESCRIPTION
            "perMonValue."
        ::= { sdhportPer15mHisEntry 4 }

    -- 1.3.6.1.4.1.2011.2.25.3.70.10.90.70.1.5
    sdhportPer15mHisStartTime OBJECT-TYPE
        SYNTAX DateAndTime
        MAX-ACCESS read-only
        STATUS current
        DESCRIPTION
            "perDateTimeStart."
        ::= { sdhportPer15mHisEntry 5 }

    -- 1.3.6.1.4.1.2011.2.25.3.70.10.90.70.1.6
    sdhportPer15mHisEndTime OBJECT-TYPE
        SYNTAX DateAndTime
        MAX-ACCESS read-only
        STATUS current
        DESCRIPTION
            "perDateTimeEnd."
        ::= { sdhportPer15mHisEntry 6 }

    -- 1.3.6.1.4.1.2011.2.25.3.70.10.90.70.1.7
    sdhportPer15mHisVldty OBJECT-TYPE
        SYNTAX ValidflagType
        MAX-ACCESS read-only
        STATUS current
        DESCRIPTION
            "perVldty."
        ::= { sdhportPer15mHisEntry 7 }

    -- 1.3.6.1.4.1.2011.2.25.3.70.10.90.80
    sdhportPer24hCurTable OBJECT-TYPE
        SYNTAX SEQUENCE OF SdhportPer24hCurEntry
        MAX-ACCESS not-accessible
        STATUS current
        DESCRIPTION
            "sdhportPer24hCur."
        ::= { sdhport 80 }

    -- 1.3.6.1.4.1.2011.2.25.3.70.10.90.80.1
    sdhportPer24hCurEntry OBJECT-TYPE
        SYNTAX SdhportPer24hCurEntry
        MAX-ACCESS not-accessible
        STATUS current
        DESCRIPTION
            "sdhportPer24hCur."
        INDEX{ sdhportPer24hCurEid,sdhportPer24hCurPara }
        ::= { sdhportPer24hCurTable 1 }

    SdhportPer24hCurEntry ::=
        SEQUENCE {
            sdhportPer24hCurEid
                PerformanceEventType,
            sdhportPer24hCurMonValue
                OCTET STRING,
            sdhportPer24hCurVldty
                ValidflagType,
            sdhportPer24hCurDatetime
                DateAndTime,
            sdhportPer24hCurParaLen
                Unsigned32,
            sdhportPer24hCurPara
                OCTET STRING
        }

    -- 1.3.6.1.4.1.2011.2.25.3.70.10.90.80.1.1
    sdhportPer24hCurEid OBJECT-TYPE
        SYNTAX PerformanceEventType
        MAX-ACCESS read-only
        STATUS current
        DESCRIPTION
            "perEid."
        ::= { sdhportPer24hCurEntry 1 }

    -- 1.3.6.1.4.1.2011.2.25.3.70.10.90.80.1.2
    sdhportPer24hCurMonValue OBJECT-TYPE
        SYNTAX OCTET STRING
        MAX-ACCESS read-only
        STATUS current
        DESCRIPTION
            "perMonValue."
        ::= { sdhportPer24hCurEntry 2 }

    -- 1.3.6.1.4.1.2011.2.25.3.70.10.90.80.1.3
    sdhportPer24hCurVldty OBJECT-TYPE
        SYNTAX ValidflagType
        MAX-ACCESS read-only
        STATUS current
        DESCRIPTION
            "perVldty."
        ::= { sdhportPer24hCurEntry 3 }

    -- 1.3.6.1.4.1.2011.2.25.3.70.10.90.80.1.4
    sdhportPer24hCurDatetime OBJECT-TYPE
        SYNTAX DateAndTime
        MAX-ACCESS read-only
        STATUS current
        DESCRIPTION
            "perDateTime."
        ::= { sdhportPer24hCurEntry 4 }

    -- 1.3.6.1.4.1.2011.2.25.3.70.10.90.80.1.5
    sdhportPer24hCurParaLen OBJECT-TYPE
        SYNTAX Unsigned32
        MAX-ACCESS read-only
        STATUS current
        DESCRIPTION
            "perParaLen."
        ::= { sdhportPer24hCurEntry 5 }

    -- 1.3.6.1.4.1.2011.2.25.3.70.10.90.80.1.6
    sdhportPer24hCurPara OBJECT-TYPE
        SYNTAX OCTET STRING
        MAX-ACCESS read-only
        STATUS current
        DESCRIPTION
            "perPara."
        ::= { sdhportPer24hCurEntry 6 }

    -- 1.3.6.1.4.1.2011.2.25.3.70.10.90.90
    sdhportPer24hHisTable OBJECT-TYPE
        SYNTAX SEQUENCE OF SdhportPer24hHisEntry
        MAX-ACCESS not-accessible
        STATUS current
        DESCRIPTION
            "sdhportPer24hHis."
        ::= { sdhport 90 }

    -- 1.3.6.1.4.1.2011.2.25.3.70.10.90.90.1
    sdhportPer24hHisEntry OBJECT-TYPE
        SYNTAX SdhportPer24hHisEntry
        MAX-ACCESS not-accessible
        STATUS current
        DESCRIPTION
            "sdhportPer24hHis."
        INDEX{ sdhportPer24hHisEid,sdhportPer24hHisParaLen,sdhportPer24hHisPara,sdhportPer24hHisStartTime,sdhportPer24hHisEndTime }
        ::= { sdhportPer24hHisTable 1 }

    SdhportPer24hHisEntry ::=
        SEQUENCE {
            sdhportPer24hHisEid
                PerformanceEventType,
            sdhportPer24hHisParaLen
                Unsigned32,
            sdhportPer24hHisPara
                OCTET STRING,
            sdhportPer24hHisMonValue
                OCTET STRING,
            sdhportPer24hHisStartTime
                DateAndTime,
            sdhportPer24hHisEndTime
                DateAndTime,
            sdhportPer24hHisVldty
                ValidflagType
        }

    -- 1.3.6.1.4.1.2011.2.25.3.70.10.90.90.1.1
    sdhportPer24hHisEid OBJECT-TYPE
        SYNTAX PerformanceEventType
        MAX-ACCESS read-only
        STATUS current
        DESCRIPTION
            "perEid."
        ::= { sdhportPer24hHisEntry 1 }

    -- 1.3.6.1.4.1.2011.2.25.3.70.10.90.90.1.2
    sdhportPer24hHisParaLen OBJECT-TYPE
        SYNTAX Unsigned32
        MAX-ACCESS read-only
        STATUS current
        DESCRIPTION
            "perParaLen."
        ::= { sdhportPer24hHisEntry 2 }

    -- 1.3.6.1.4.1.2011.2.25.3.70.10.90.90.1.3
    sdhportPer24hHisPara OBJECT-TYPE
        SYNTAX OCTET STRING
        MAX-ACCESS read-only
        STATUS current
        DESCRIPTION
            "perPara."
        ::= { sdhportPer24hHisEntry 3 }

    -- 1.3.6.1.4.1.2011.2.25.3.70.10.90.90.1.4
    sdhportPer24hHisMonValue OBJECT-TYPE
        SYNTAX OCTET STRING
        MAX-ACCESS read-only
        STATUS current
        DESCRIPTION
            "perMonValue."
        ::= { sdhportPer24hHisEntry 4 }

    -- 1.3.6.1.4.1.2011.2.25.3.70.10.90.90.1.5
    sdhportPer24hHisStartTime OBJECT-TYPE
        SYNTAX DateAndTime
        MAX-ACCESS read-only
        STATUS current
        DESCRIPTION
            "perDateTimeStart."
        ::= { sdhportPer24hHisEntry 5 }

    -- 1.3.6.1.4.1.2011.2.25.3.70.10.90.90.1.6
    sdhportPer24hHisEndTime OBJECT-TYPE
        SYNTAX DateAndTime
        MAX-ACCESS read-only
        STATUS current
        DESCRIPTION
            "perDateTimeEnd."
        ::= { sdhportPer24hHisEntry 6 }

    -- 1.3.6.1.4.1.2011.2.25.3.70.10.90.90.1.7
    sdhportPer24hHisVldty OBJECT-TYPE
        SYNTAX ValidflagType
        MAX-ACCESS read-only
        STATUS current
        DESCRIPTION
            "perVldty."
        ::= { sdhportPer24hHisEntry 7 }

    -- 1.3.6.1.4.1.2011.2.25.3.70.10.91
    e1port OBJECT IDENTIFIER ::= { rtnPerformance 91 }

    -- 1.3.6.1.4.1.2011.2.25.3.70.10.91.60
    e1portPer15mCurTable OBJECT-TYPE
        SYNTAX SEQUENCE OF E1portPer15mCurEntry
        MAX-ACCESS not-accessible
        STATUS current
        DESCRIPTION
            "e1portPer15mCur."
        ::= { e1port 60 }

    -- 1.3.6.1.4.1.2011.2.25.3.70.10.91.60.1
    e1portPer15mCurEntry OBJECT-TYPE
        SYNTAX E1portPer15mCurEntry
        MAX-ACCESS not-accessible
        STATUS current
        DESCRIPTION
            "e1portPer15mCur."
        INDEX{ e1portPer15mCurEid,e1portPer15mCurPara }
        ::= { e1portPer15mCurTable 1 }

    E1portPer15mCurEntry ::=
        SEQUENCE {
            e1portPer15mCurEid
                PerformanceEventType,
            e1portPer15mCurMonValue
                OCTET STRING,
            e1portPer15mCurVldty
                ValidflagType,
            e1portPer15mCurDatetime
                DateAndTime,
            e1portPer15mCurParaLen
                Unsigned32,
            e1portPer15mCurPara
                OCTET STRING
        }

    -- 1.3.6.1.4.1.2011.2.25.3.70.10.91.60.1.1
    e1portPer15mCurEid OBJECT-TYPE
        SYNTAX PerformanceEventType
        MAX-ACCESS read-only
        STATUS current
        DESCRIPTION
            "perEid."
        ::= { e1portPer15mCurEntry 1 }

    -- 1.3.6.1.4.1.2011.2.25.3.70.10.91.60.1.2
    e1portPer15mCurMonValue OBJECT-TYPE
        SYNTAX OCTET STRING
        MAX-ACCESS read-only
        STATUS current
        DESCRIPTION
            "perMonValue."
        ::= { e1portPer15mCurEntry 2 }

    -- 1.3.6.1.4.1.2011.2.25.3.70.10.91.60.1.3
    e1portPer15mCurVldty OBJECT-TYPE
        SYNTAX ValidflagType
        MAX-ACCESS read-only
        STATUS current
        DESCRIPTION
            "perVldty."
        ::= { e1portPer15mCurEntry 3 }

    -- 1.3.6.1.4.1.2011.2.25.3.70.10.91.60.1.4
    e1portPer15mCurDatetime OBJECT-TYPE
        SYNTAX DateAndTime
        MAX-ACCESS read-only
        STATUS current
        DESCRIPTION
            "perDateTime."
        ::= { e1portPer15mCurEntry 4 }

    -- 1.3.6.1.4.1.2011.2.25.3.70.10.91.60.1.5
    e1portPer15mCurParaLen OBJECT-TYPE
        SYNTAX Unsigned32
        MAX-ACCESS read-only
        STATUS current
        DESCRIPTION
            "perParaLen."
        ::= { e1portPer15mCurEntry 5 }

    -- 1.3.6.1.4.1.2011.2.25.3.70.10.91.60.1.6
    e1portPer15mCurPara OBJECT-TYPE
        SYNTAX OCTET STRING
        MAX-ACCESS read-only
        STATUS current
        DESCRIPTION
            "perPara."
        ::= { e1portPer15mCurEntry 6 }

    -- 1.3.6.1.4.1.2011.2.25.3.70.10.91.70
    e1portPer15mHisTable OBJECT-TYPE
        SYNTAX SEQUENCE OF E1portPer15mHisEntry
        MAX-ACCESS not-accessible
        STATUS current
        DESCRIPTION
            "e1portPer15mHis."
        ::= { e1port 70 }

    -- 1.3.6.1.4.1.2011.2.25.3.70.10.91.70.1
    e1portPer15mHisEntry OBJECT-TYPE
        SYNTAX E1portPer15mHisEntry
        MAX-ACCESS not-accessible
        STATUS current
        DESCRIPTION
            "e1portPer15mHis."
        INDEX{ e1portPer15mHisEid,e1portPer15mHisParaLen,e1portPer15mHisPara,e1portPer15mHisStartTime,e1portPer15mHisEndTime }
        ::= { e1portPer15mHisTable 1 }

    E1portPer15mHisEntry ::=
        SEQUENCE {
            e1portPer15mHisEid
                PerformanceEventType,
            e1portPer15mHisParaLen
                Unsigned32,
            e1portPer15mHisPara
                OCTET STRING,
            e1portPer15mHisMonValue
                OCTET STRING,
            e1portPer15mHisStartTime
                DateAndTime,
            e1portPer15mHisEndTime
                DateAndTime,
            e1portPer15mHisVldty
                ValidflagType
        }

    -- 1.3.6.1.4.1.2011.2.25.3.70.10.91.70.1.1
    e1portPer15mHisEid OBJECT-TYPE
        SYNTAX PerformanceEventType
        MAX-ACCESS read-only
        STATUS current
        DESCRIPTION
            "perEid."
        ::= { e1portPer15mHisEntry 1 }

    -- 1.3.6.1.4.1.2011.2.25.3.70.10.91.70.1.2
    e1portPer15mHisParaLen OBJECT-TYPE
        SYNTAX Unsigned32
        MAX-ACCESS read-only
        STATUS current
        DESCRIPTION
            "perParaLen."
        ::= { e1portPer15mHisEntry 2 }

    -- 1.3.6.1.4.1.2011.2.25.3.70.10.91.70.1.3
    e1portPer15mHisPara OBJECT-TYPE
        SYNTAX OCTET STRING
        MAX-ACCESS read-only
        STATUS current
        DESCRIPTION
            "perPara."
        ::= { e1portPer15mHisEntry 3 }

    -- 1.3.6.1.4.1.2011.2.25.3.70.10.91.70.1.4
    e1portPer15mHisMonValue OBJECT-TYPE
        SYNTAX OCTET STRING
        MAX-ACCESS read-only
        STATUS current
        DESCRIPTION
            "perMonValue."
        ::= { e1portPer15mHisEntry 4 }

    -- 1.3.6.1.4.1.2011.2.25.3.70.10.91.70.1.5
    e1portPer15mHisStartTime OBJECT-TYPE
        SYNTAX DateAndTime
        MAX-ACCESS read-only
        STATUS current
        DESCRIPTION
            "perDateTimeStart."
        ::= { e1portPer15mHisEntry 5 }

    -- 1.3.6.1.4.1.2011.2.25.3.70.10.91.70.1.6
    e1portPer15mHisEndTime OBJECT-TYPE
        SYNTAX DateAndTime
        MAX-ACCESS read-only
        STATUS current
        DESCRIPTION
            "perDateTimeEnd."
        ::= { e1portPer15mHisEntry 6 }

    -- 1.3.6.1.4.1.2011.2.25.3.70.10.91.70.1.7
    e1portPer15mHisVldty OBJECT-TYPE
        SYNTAX ValidflagType
        MAX-ACCESS read-only
        STATUS current
        DESCRIPTION
            "perVldty."
        ::= { e1portPer15mHisEntry 7 }

    -- 1.3.6.1.4.1.2011.2.25.3.70.10.91.80
    e1portPer24hCurTable OBJECT-TYPE
        SYNTAX SEQUENCE OF E1portPer24hCurEntry
        MAX-ACCESS not-accessible
        STATUS current
        DESCRIPTION
            "e1portPer24hCur."
        ::= { e1port 80 }

    -- 1.3.6.1.4.1.2011.2.25.3.70.10.91.80.1
    e1portPer24hCurEntry OBJECT-TYPE
        SYNTAX E1portPer24hCurEntry
        MAX-ACCESS not-accessible
        STATUS current
        DESCRIPTION
            "e1portPer24hCur."
        INDEX{ e1portPer24hCurEid,e1portPer24hCurPara }
        ::= { e1portPer24hCurTable 1 }

    E1portPer24hCurEntry ::=
        SEQUENCE {
            e1portPer24hCurEid
                PerformanceEventType,
            e1portPer24hCurMonValue
                OCTET STRING,
            e1portPer24hCurVldty
                ValidflagType,
            e1portPer24hCurDatetime
                DateAndTime,
            e1portPer24hCurParaLen
                Unsigned32,
            e1portPer24hCurPara
                OCTET STRING
        }

    -- 1.3.6.1.4.1.2011.2.25.3.70.10.91.80.1.1
    e1portPer24hCurEid OBJECT-TYPE
        SYNTAX PerformanceEventType
        MAX-ACCESS read-only
        STATUS current
        DESCRIPTION
            "perEid."
        ::= { e1portPer24hCurEntry 1 }

    -- 1.3.6.1.4.1.2011.2.25.3.70.10.91.80.1.2
    e1portPer24hCurMonValue OBJECT-TYPE
        SYNTAX OCTET STRING
        MAX-ACCESS read-only
        STATUS current
        DESCRIPTION
            "perMonValue."
        ::= { e1portPer24hCurEntry 2 }

    -- 1.3.6.1.4.1.2011.2.25.3.70.10.91.80.1.3
    e1portPer24hCurVldty OBJECT-TYPE
        SYNTAX ValidflagType
        MAX-ACCESS read-only
        STATUS current
        DESCRIPTION
            "perVldty."
        ::= { e1portPer24hCurEntry 3 }

    -- 1.3.6.1.4.1.2011.2.25.3.70.10.91.80.1.4
    e1portPer24hCurDatetime OBJECT-TYPE
        SYNTAX DateAndTime
        MAX-ACCESS read-only
        STATUS current
        DESCRIPTION
            "perDateTime."
        ::= { e1portPer24hCurEntry 4 }

    -- 1.3.6.1.4.1.2011.2.25.3.70.10.91.80.1.5
    e1portPer24hCurParaLen OBJECT-TYPE
        SYNTAX Unsigned32
        MAX-ACCESS read-only
        STATUS current
        DESCRIPTION
            "perParaLen."
        ::= { e1portPer24hCurEntry 5 }

    -- 1.3.6.1.4.1.2011.2.25.3.70.10.91.80.1.6
    e1portPer24hCurPara OBJECT-TYPE
        SYNTAX OCTET STRING
        MAX-ACCESS read-only
        STATUS current
        DESCRIPTION
            "perPara."
        ::= { e1portPer24hCurEntry 6 }

    -- 1.3.6.1.4.1.2011.2.25.3.70.10.91.90
    e1portPer24hHisTable OBJECT-TYPE
        SYNTAX SEQUENCE OF E1portPer24hHisEntry
        MAX-ACCESS not-accessible
        STATUS current
        DESCRIPTION
            "e1portPer24hHis."
        ::= { e1port 90 }

    -- 1.3.6.1.4.1.2011.2.25.3.70.10.91.90.1
    e1portPer24hHisEntry OBJECT-TYPE
        SYNTAX E1portPer24hHisEntry
        MAX-ACCESS not-accessible
        STATUS current
        DESCRIPTION
            "e1portPer24hHis."
        INDEX{ e1portPer24hHisEid,e1portPer24hHisParaLen,e1portPer24hHisPara,e1portPer24hHisStartTime,e1portPer24hHisEndTime }
        ::= { e1portPer24hHisTable 1 }

    E1portPer24hHisEntry ::=
        SEQUENCE {
            e1portPer24hHisEid
                PerformanceEventType,
            e1portPer24hHisParaLen
                Unsigned32,
            e1portPer24hHisPara
                OCTET STRING,
            e1portPer24hHisMonValue
                OCTET STRING,
            e1portPer24hHisStartTime
                DateAndTime,
            e1portPer24hHisEndTime
                DateAndTime,
            e1portPer24hHisVldty
                ValidflagType
        }

    -- 1.3.6.1.4.1.2011.2.25.3.70.10.91.90.1.1
    e1portPer24hHisEid OBJECT-TYPE
        SYNTAX PerformanceEventType
        MAX-ACCESS read-only
        STATUS current
        DESCRIPTION
            "perEid."
        ::= { e1portPer24hHisEntry 1 }

    -- 1.3.6.1.4.1.2011.2.25.3.70.10.91.90.1.2
    e1portPer24hHisParaLen OBJECT-TYPE
        SYNTAX Unsigned32
        MAX-ACCESS read-only
        STATUS current
        DESCRIPTION
            "perParaLen."
        ::= { e1portPer24hHisEntry 2 }

    -- 1.3.6.1.4.1.2011.2.25.3.70.10.91.90.1.3
    e1portPer24hHisPara OBJECT-TYPE
        SYNTAX OCTET STRING
        MAX-ACCESS read-only
        STATUS current
        DESCRIPTION
            "perPara."
        ::= { e1portPer24hHisEntry 3 }

    -- 1.3.6.1.4.1.2011.2.25.3.70.10.91.90.1.4
    e1portPer24hHisMonValue OBJECT-TYPE
        SYNTAX OCTET STRING
        MAX-ACCESS read-only
        STATUS current
        DESCRIPTION
            "perMonValue."
        ::= { e1portPer24hHisEntry 4 }

    -- 1.3.6.1.4.1.2011.2.25.3.70.10.91.90.1.5
    e1portPer24hHisStartTime OBJECT-TYPE
        SYNTAX DateAndTime
        MAX-ACCESS read-only
        STATUS current
        DESCRIPTION
            "perDateTimeStart."
        ::= { e1portPer24hHisEntry 5 }

    -- 1.3.6.1.4.1.2011.2.25.3.70.10.91.90.1.6
    e1portPer24hHisEndTime OBJECT-TYPE
        SYNTAX DateAndTime
        MAX-ACCESS read-only
        STATUS current
        DESCRIPTION
            "perDateTimeEnd."
        ::= { e1portPer24hHisEntry 6 }

    -- 1.3.6.1.4.1.2011.2.25.3.70.10.91.90.1.7
    e1portPer24hHisVldty OBJECT-TYPE
        SYNTAX ValidflagType
        MAX-ACCESS read-only
        STATUS current
        DESCRIPTION
            "perVldty."
        ::= { e1portPer24hHisEntry 7 }

    -- 1.3.6.1.4.1.2011.2.25.3.70.10.92
    group1j1 OBJECT IDENTIFIER ::= { rtnPerformance 92 }

    -- 1.3.6.1.4.1.2011.2.25.3.70.10.92.60
    group1j1Per15mCurTable OBJECT-TYPE
        SYNTAX SEQUENCE OF Group1j1Per15mCurEntry
        MAX-ACCESS not-accessible
        STATUS current
        DESCRIPTION
            "group1j1Per15mCur."
        ::= { group1j1 60 }

    -- 1.3.6.1.4.1.2011.2.25.3.70.10.92.60.1
    group1j1Per15mCurEntry OBJECT-TYPE
        SYNTAX Group1j1Per15mCurEntry
        MAX-ACCESS not-accessible
        STATUS current
        DESCRIPTION
            "group1j1Per15mCur."
        INDEX{ group1j1Per15mCurEid,group1j1Per15mCurPara }
        ::= { group1j1Per15mCurTable 1 }

    Group1j1Per15mCurEntry ::=
        SEQUENCE {
            group1j1Per15mCurEid
                PerformanceEventType,
            group1j1Per15mCurMonValue
                OCTET STRING,
            group1j1Per15mCurVldty
                ValidflagType,
            group1j1Per15mCurDatetime
                DateAndTime,
            group1j1Per15mCurParaLen
                Unsigned32,
            group1j1Per15mCurPara
                OCTET STRING
        }

    -- 1.3.6.1.4.1.2011.2.25.3.70.10.92.60.1.1
    group1j1Per15mCurEid OBJECT-TYPE
        SYNTAX PerformanceEventType
        MAX-ACCESS read-only
        STATUS current
        DESCRIPTION
            "perEid."
        ::= { group1j1Per15mCurEntry 1 }

    -- 1.3.6.1.4.1.2011.2.25.3.70.10.92.60.1.2
    group1j1Per15mCurMonValue OBJECT-TYPE
        SYNTAX OCTET STRING
        MAX-ACCESS read-only
        STATUS current
        DESCRIPTION
            "perMonValue."
        ::= { group1j1Per15mCurEntry 2 }

    -- 1.3.6.1.4.1.2011.2.25.3.70.10.92.60.1.3
    group1j1Per15mCurVldty OBJECT-TYPE
        SYNTAX ValidflagType
        MAX-ACCESS read-only
        STATUS current
        DESCRIPTION
            "perVldty."
        ::= { group1j1Per15mCurEntry 3 }

    -- 1.3.6.1.4.1.2011.2.25.3.70.10.92.60.1.4
    group1j1Per15mCurDatetime OBJECT-TYPE
        SYNTAX DateAndTime
        MAX-ACCESS read-only
        STATUS current
        DESCRIPTION
            "perDateTime."
        ::= { group1j1Per15mCurEntry 4 }

    -- 1.3.6.1.4.1.2011.2.25.3.70.10.92.60.1.5
    group1j1Per15mCurParaLen OBJECT-TYPE
        SYNTAX Unsigned32
        MAX-ACCESS read-only
        STATUS current
        DESCRIPTION
            "perParaLen."
        ::= { group1j1Per15mCurEntry 5 }

    -- 1.3.6.1.4.1.2011.2.25.3.70.10.92.60.1.6
    group1j1Per15mCurPara OBJECT-TYPE
        SYNTAX OCTET STRING
        MAX-ACCESS read-only
        STATUS current
        DESCRIPTION
            "perPara."
        ::= { group1j1Per15mCurEntry 6 }

    -- 1.3.6.1.4.1.2011.2.25.3.70.10.92.70
    group1j1Per15mHisTable OBJECT-TYPE
        SYNTAX SEQUENCE OF Group1j1Per15mHisEntry
        MAX-ACCESS not-accessible
        STATUS current
        DESCRIPTION
            "group1j1Per15mHis."
        ::= { group1j1 70 }

    -- 1.3.6.1.4.1.2011.2.25.3.70.10.92.70.1
    group1j1Per15mHisEntry OBJECT-TYPE
        SYNTAX Group1j1Per15mHisEntry
        MAX-ACCESS not-accessible
        STATUS current
        DESCRIPTION
            "group1j1Per15mHis."
        INDEX{ group1j1Per15mHisEid,group1j1Per15mHisParaLen,group1j1Per15mHisPara,group1j1Per15mHisStartTime,group1j1Per15mHisEndTime }
        ::= { group1j1Per15mHisTable 1 }

    Group1j1Per15mHisEntry ::=
        SEQUENCE {
            group1j1Per15mHisEid
                PerformanceEventType,
            group1j1Per15mHisParaLen
                Unsigned32,
            group1j1Per15mHisPara
                OCTET STRING,
            group1j1Per15mHisMonValue
                OCTET STRING,
            group1j1Per15mHisStartTime
                DateAndTime,
            group1j1Per15mHisEndTime
                DateAndTime,
            group1j1Per15mHisVldty
                ValidflagType
        }

    -- 1.3.6.1.4.1.2011.2.25.3.70.10.92.70.1.1
    group1j1Per15mHisEid OBJECT-TYPE
        SYNTAX PerformanceEventType
        MAX-ACCESS read-only
        STATUS current
        DESCRIPTION
            "perEid."
        ::= { group1j1Per15mHisEntry 1 }

    -- 1.3.6.1.4.1.2011.2.25.3.70.10.92.70.1.2
    group1j1Per15mHisParaLen OBJECT-TYPE
        SYNTAX Unsigned32
        MAX-ACCESS read-only
        STATUS current
        DESCRIPTION
            "perParaLen."
        ::= { group1j1Per15mHisEntry 2 }

    -- 1.3.6.1.4.1.2011.2.25.3.70.10.92.70.1.3
    group1j1Per15mHisPara OBJECT-TYPE
        SYNTAX OCTET STRING
        MAX-ACCESS read-only
        STATUS current
        DESCRIPTION
            "perPara."
        ::= { group1j1Per15mHisEntry 3 }

    -- 1.3.6.1.4.1.2011.2.25.3.70.10.92.70.1.4
    group1j1Per15mHisMonValue OBJECT-TYPE
        SYNTAX OCTET STRING
        MAX-ACCESS read-only
        STATUS current
        DESCRIPTION
            "perMonValue."
        ::= { group1j1Per15mHisEntry 4 }

    -- 1.3.6.1.4.1.2011.2.25.3.70.10.92.70.1.5
    group1j1Per15mHisStartTime OBJECT-TYPE
        SYNTAX DateAndTime
        MAX-ACCESS read-only
        STATUS current
        DESCRIPTION
            "perDateTimeStart."
        ::= { group1j1Per15mHisEntry 5 }

    -- 1.3.6.1.4.1.2011.2.25.3.70.10.92.70.1.6
    group1j1Per15mHisEndTime OBJECT-TYPE
        SYNTAX DateAndTime
        MAX-ACCESS read-only
        STATUS current
        DESCRIPTION
            "perDateTimeEnd."
        ::= { group1j1Per15mHisEntry 6 }

    -- 1.3.6.1.4.1.2011.2.25.3.70.10.92.70.1.7
    group1j1Per15mHisVldty OBJECT-TYPE
        SYNTAX ValidflagType
        MAX-ACCESS read-only
        STATUS current
        DESCRIPTION
            "perVldty."
        ::= { group1j1Per15mHisEntry 7 }

    -- 1.3.6.1.4.1.2011.2.25.3.70.10.92.80
    group1j1Per24hCurTable OBJECT-TYPE
        SYNTAX SEQUENCE OF Group1j1Per24hCurEntry
        MAX-ACCESS not-accessible
        STATUS current
        DESCRIPTION
            "group1j1Per24hCur."
        ::= { group1j1 80 }

    -- 1.3.6.1.4.1.2011.2.25.3.70.10.92.80.1
    group1j1Per24hCurEntry OBJECT-TYPE
        SYNTAX Group1j1Per24hCurEntry
        MAX-ACCESS not-accessible
        STATUS current
        DESCRIPTION
            "group1j1Per24hCur."
        INDEX{ group1j1Per24hCurEid,group1j1Per24hCurPara }
        ::= { group1j1Per24hCurTable 1 }

    Group1j1Per24hCurEntry ::=
        SEQUENCE {
            group1j1Per24hCurEid
                PerformanceEventType,
            group1j1Per24hCurMonValue
                OCTET STRING,
            group1j1Per24hCurVldty
                ValidflagType,
            group1j1Per24hCurDatetime
                DateAndTime,
            group1j1Per24hCurParaLen
                Unsigned32,
            group1j1Per24hCurPara
                OCTET STRING
        }

    -- 1.3.6.1.4.1.2011.2.25.3.70.10.92.80.1.1
    group1j1Per24hCurEid OBJECT-TYPE
        SYNTAX PerformanceEventType
        MAX-ACCESS read-only
        STATUS current
        DESCRIPTION
            "perEid."
        ::= { group1j1Per24hCurEntry 1 }

    -- 1.3.6.1.4.1.2011.2.25.3.70.10.92.80.1.2
    group1j1Per24hCurMonValue OBJECT-TYPE
        SYNTAX OCTET STRING
        MAX-ACCESS read-only
        STATUS current
        DESCRIPTION
            "perMonValue."
        ::= { group1j1Per24hCurEntry 2 }

    -- 1.3.6.1.4.1.2011.2.25.3.70.10.92.80.1.3
    group1j1Per24hCurVldty OBJECT-TYPE
        SYNTAX ValidflagType
        MAX-ACCESS read-only
        STATUS current
        DESCRIPTION
            "perVldty."
        ::= { group1j1Per24hCurEntry 3 }

    -- 1.3.6.1.4.1.2011.2.25.3.70.10.92.80.1.4
    group1j1Per24hCurDatetime OBJECT-TYPE
        SYNTAX DateAndTime
        MAX-ACCESS read-only
        STATUS current
        DESCRIPTION
            "perDateTime."
        ::= { group1j1Per24hCurEntry 4 }

    -- 1.3.6.1.4.1.2011.2.25.3.70.10.92.80.1.5
    group1j1Per24hCurParaLen OBJECT-TYPE
        SYNTAX Unsigned32
        MAX-ACCESS read-only
        STATUS current
        DESCRIPTION
            "perParaLen."
        ::= { group1j1Per24hCurEntry 5 }

    -- 1.3.6.1.4.1.2011.2.25.3.70.10.92.80.1.6
    group1j1Per24hCurPara OBJECT-TYPE
        SYNTAX OCTET STRING
        MAX-ACCESS read-only
        STATUS current
        DESCRIPTION
            "perPara."
        ::= { group1j1Per24hCurEntry 6 }

    -- 1.3.6.1.4.1.2011.2.25.3.70.10.92.90
    group1j1Per24hHisTable OBJECT-TYPE
        SYNTAX SEQUENCE OF Group1j1Per24hHisEntry
        MAX-ACCESS not-accessible
        STATUS current
        DESCRIPTION
            "group1j1Per24hHis."
        ::= { group1j1 90 }

    -- 1.3.6.1.4.1.2011.2.25.3.70.10.92.90.1
    group1j1Per24hHisEntry OBJECT-TYPE
        SYNTAX Group1j1Per24hHisEntry
        MAX-ACCESS not-accessible
        STATUS current
        DESCRIPTION
            "group1j1Per24hHis."
        INDEX{ group1j1Per24hHisEid,group1j1Per24hHisParaLen,group1j1Per24hHisPara,group1j1Per24hHisStartTime,group1j1Per24hHisEndTime }
        ::= { group1j1Per24hHisTable 1 }

    Group1j1Per24hHisEntry ::=
        SEQUENCE {
            group1j1Per24hHisEid
                PerformanceEventType,
            group1j1Per24hHisParaLen
                Unsigned32,
            group1j1Per24hHisPara
                OCTET STRING,
            group1j1Per24hHisMonValue
                OCTET STRING,
            group1j1Per24hHisStartTime
                DateAndTime,
            group1j1Per24hHisEndTime
                DateAndTime,
            group1j1Per24hHisVldty
                ValidflagType
        }

    -- 1.3.6.1.4.1.2011.2.25.3.70.10.92.90.1.1
    group1j1Per24hHisEid OBJECT-TYPE
        SYNTAX PerformanceEventType
        MAX-ACCESS read-only
        STATUS current
        DESCRIPTION
            "perEid."
        ::= { group1j1Per24hHisEntry 1 }

    -- 1.3.6.1.4.1.2011.2.25.3.70.10.92.90.1.2
    group1j1Per24hHisParaLen OBJECT-TYPE
        SYNTAX Unsigned32
        MAX-ACCESS read-only
        STATUS current
        DESCRIPTION
            "perParaLen."
        ::= { group1j1Per24hHisEntry 2 }

    -- 1.3.6.1.4.1.2011.2.25.3.70.10.92.90.1.3
    group1j1Per24hHisPara OBJECT-TYPE
        SYNTAX OCTET STRING
        MAX-ACCESS read-only
        STATUS current
        DESCRIPTION
            "perPara."
        ::= { group1j1Per24hHisEntry 3 }

    -- 1.3.6.1.4.1.2011.2.25.3.70.10.92.90.1.4
    group1j1Per24hHisMonValue OBJECT-TYPE
        SYNTAX OCTET STRING
        MAX-ACCESS read-only
        STATUS current
        DESCRIPTION
            "perMonValue."
        ::= { group1j1Per24hHisEntry 4 }

    -- 1.3.6.1.4.1.2011.2.25.3.70.10.92.90.1.5
    group1j1Per24hHisStartTime OBJECT-TYPE
        SYNTAX DateAndTime
        MAX-ACCESS read-only
        STATUS current
        DESCRIPTION
            "perDateTimeStart."
        ::= { group1j1Per24hHisEntry 5 }

    -- 1.3.6.1.4.1.2011.2.25.3.70.10.92.90.1.6
    group1j1Per24hHisEndTime OBJECT-TYPE
        SYNTAX DateAndTime
        MAX-ACCESS read-only
        STATUS current
        DESCRIPTION
            "perDateTimeEnd."
        ::= { group1j1Per24hHisEntry 6 }

    -- 1.3.6.1.4.1.2011.2.25.3.70.10.92.90.1.7
    group1j1Per24hHisVldty OBJECT-TYPE
        SYNTAX ValidflagType
        MAX-ACCESS read-only
        STATUS current
        DESCRIPTION
            "perVldty."
        ::= { group1j1Per24hHisEntry 7 }

    -- 1.3.6.1.4.1.2011.2.25.3.70.10.100
    sdhpath OBJECT IDENTIFIER ::= { rtnPerformance 100 }

    -- 1.3.6.1.4.1.2011.2.25.3.70.10.100.60
    sdhpathPer15mCurTable OBJECT-TYPE
        SYNTAX SEQUENCE OF SdhpathPer15mCurEntry
        MAX-ACCESS not-accessible
        STATUS current
        DESCRIPTION
            "sdhpathPer15mCur."
        ::= { sdhpath 60 }

    -- 1.3.6.1.4.1.2011.2.25.3.70.10.100.60.1
    sdhpathPer15mCurEntry OBJECT-TYPE
        SYNTAX SdhpathPer15mCurEntry
        MAX-ACCESS not-accessible
        STATUS current
        DESCRIPTION
            "sdhpathPer15mCur."
        INDEX{ sdhpathPer15mCurEid,sdhpathPer15mCurPara }
        ::= { sdhpathPer15mCurTable 1 }

    SdhpathPer15mCurEntry ::=
        SEQUENCE {
            sdhpathPer15mCurEid
                PerformanceEventType,
            sdhpathPer15mCurMonValue
                OCTET STRING,
            sdhpathPer15mCurVldty
                ValidflagType,
            sdhpathPer15mCurDatetime
                DateAndTime,
            sdhpathPer15mCurParaLen
                Unsigned32,
            sdhpathPer15mCurPara
                OCTET STRING
        }

    -- 1.3.6.1.4.1.2011.2.25.3.70.10.100.60.1.1
    sdhpathPer15mCurEid OBJECT-TYPE
        SYNTAX PerformanceEventType
        MAX-ACCESS read-only
        STATUS current
        DESCRIPTION
            "perEid."
        ::= { sdhpathPer15mCurEntry 1 }

    -- 1.3.6.1.4.1.2011.2.25.3.70.10.100.60.1.2
    sdhpathPer15mCurMonValue OBJECT-TYPE
        SYNTAX OCTET STRING
        MAX-ACCESS read-only
        STATUS current
        DESCRIPTION
            "perMonValue."
        ::= { sdhpathPer15mCurEntry 2 }

    -- 1.3.6.1.4.1.2011.2.25.3.70.10.100.60.1.3
    sdhpathPer15mCurVldty OBJECT-TYPE
        SYNTAX ValidflagType
        MAX-ACCESS read-only
        STATUS current
        DESCRIPTION
            "perVldty."
        ::= { sdhpathPer15mCurEntry 3 }

    -- 1.3.6.1.4.1.2011.2.25.3.70.10.100.60.1.4
    sdhpathPer15mCurDatetime OBJECT-TYPE
        SYNTAX DateAndTime
        MAX-ACCESS read-only
        STATUS current
        DESCRIPTION
            "perDateTime."
        ::= { sdhpathPer15mCurEntry 4 }

    -- 1.3.6.1.4.1.2011.2.25.3.70.10.100.60.1.5
    sdhpathPer15mCurParaLen OBJECT-TYPE
        SYNTAX Unsigned32
        MAX-ACCESS read-only
        STATUS current
        DESCRIPTION
            "perParaLen."
        ::= { sdhpathPer15mCurEntry 5 }

    -- 1.3.6.1.4.1.2011.2.25.3.70.10.100.60.1.6
    sdhpathPer15mCurPara OBJECT-TYPE
        SYNTAX OCTET STRING
        MAX-ACCESS read-only
        STATUS current
        DESCRIPTION
            "perPara."
        ::= { sdhpathPer15mCurEntry 6 }

    -- 1.3.6.1.4.1.2011.2.25.3.70.10.100.70
    sdhpathPer15mHisTable OBJECT-TYPE
        SYNTAX SEQUENCE OF SdhpathPer15mHisEntry
        MAX-ACCESS not-accessible
        STATUS current
        DESCRIPTION
            "sdhpathPer15mHis."
        ::= { sdhpath 70 }

    -- 1.3.6.1.4.1.2011.2.25.3.70.10.100.70.1
    sdhpathPer15mHisEntry OBJECT-TYPE
        SYNTAX SdhpathPer15mHisEntry
        MAX-ACCESS not-accessible
        STATUS current
        DESCRIPTION
            "sdhpathPer15mHis."
        INDEX{ sdhpathPer15mHisEid,sdhpathPer15mHisParaLen,sdhpathPer15mHisPara,sdhpathPer15mHisStartTime,sdhpathPer15mHisEndTime }
        ::= { sdhpathPer15mHisTable 1 }

    SdhpathPer15mHisEntry ::=
        SEQUENCE {
            sdhpathPer15mHisEid
                PerformanceEventType,
            sdhpathPer15mHisParaLen
                Unsigned32,
            sdhpathPer15mHisPara
                OCTET STRING,
            sdhpathPer15mHisMonValue
                OCTET STRING,
            sdhpathPer15mHisStartTime
                DateAndTime,
            sdhpathPer15mHisEndTime
                DateAndTime,
            sdhpathPer15mHisVldty
                ValidflagType
        }

    -- 1.3.6.1.4.1.2011.2.25.3.70.10.100.70.1.1
    sdhpathPer15mHisEid OBJECT-TYPE
        SYNTAX PerformanceEventType
        MAX-ACCESS read-only
        STATUS current
        DESCRIPTION
            "perEid."
        ::= { sdhpathPer15mHisEntry 1 }

    -- 1.3.6.1.4.1.2011.2.25.3.70.10.100.70.1.2
    sdhpathPer15mHisParaLen OBJECT-TYPE
        SYNTAX Unsigned32
        MAX-ACCESS read-only
        STATUS current
        DESCRIPTION
            "perParaLen."
        ::= { sdhpathPer15mHisEntry 2 }

    -- 1.3.6.1.4.1.2011.2.25.3.70.10.100.70.1.3
    sdhpathPer15mHisPara OBJECT-TYPE
        SYNTAX OCTET STRING
        MAX-ACCESS read-only
        STATUS current
        DESCRIPTION
            "perPara."
        ::= { sdhpathPer15mHisEntry 3 }

    -- 1.3.6.1.4.1.2011.2.25.3.70.10.100.70.1.4
    sdhpathPer15mHisMonValue OBJECT-TYPE
        SYNTAX OCTET STRING
        MAX-ACCESS read-only
        STATUS current
        DESCRIPTION
            "perMonValue."
        ::= { sdhpathPer15mHisEntry 4 }

    -- 1.3.6.1.4.1.2011.2.25.3.70.10.100.70.1.5
    sdhpathPer15mHisStartTime OBJECT-TYPE
        SYNTAX DateAndTime
        MAX-ACCESS read-only
        STATUS current
        DESCRIPTION
            "perDateTimeStart."
        ::= { sdhpathPer15mHisEntry 5 }

    -- 1.3.6.1.4.1.2011.2.25.3.70.10.100.70.1.6
    sdhpathPer15mHisEndTime OBJECT-TYPE
        SYNTAX DateAndTime
        MAX-ACCESS read-only
        STATUS current
        DESCRIPTION
            "perDateTimeEnd."
        ::= { sdhpathPer15mHisEntry 6 }

    -- 1.3.6.1.4.1.2011.2.25.3.70.10.100.70.1.7
    sdhpathPer15mHisVldty OBJECT-TYPE
        SYNTAX ValidflagType
        MAX-ACCESS read-only
        STATUS current
        DESCRIPTION
            "perVldty."
        ::= { sdhpathPer15mHisEntry 7 }

    -- 1.3.6.1.4.1.2011.2.25.3.70.10.100.80
    sdhpathPer24hCurTable OBJECT-TYPE
        SYNTAX SEQUENCE OF SdhpathPer24hCurEntry
        MAX-ACCESS not-accessible
        STATUS current
        DESCRIPTION
            "sdhpathPer24hCur."
        ::= { sdhpath 80 }

    -- 1.3.6.1.4.1.2011.2.25.3.70.10.100.80.1
    sdhpathPer24hCurEntry OBJECT-TYPE
        SYNTAX SdhpathPer24hCurEntry
        MAX-ACCESS not-accessible
        STATUS current
        DESCRIPTION
            "sdhpathPer24hCur."
        INDEX{ sdhpathPer24hCurEid,sdhpathPer24hCurPara }
        ::= { sdhpathPer24hCurTable 1 }

    SdhpathPer24hCurEntry ::=
        SEQUENCE {
            sdhpathPer24hCurEid
                PerformanceEventType,
            sdhpathPer24hCurMonValue
                OCTET STRING,
            sdhpathPer24hCurVldty
                ValidflagType,
            sdhpathPer24hCurDatetime
                DateAndTime,
            sdhpathPer24hCurParaLen
                Unsigned32,
            sdhpathPer24hCurPara
                OCTET STRING
        }

    -- 1.3.6.1.4.1.2011.2.25.3.70.10.100.80.1.1
    sdhpathPer24hCurEid OBJECT-TYPE
        SYNTAX PerformanceEventType
        MAX-ACCESS read-only
        STATUS current
        DESCRIPTION
            "perEid."
        ::= { sdhpathPer24hCurEntry 1 }

    -- 1.3.6.1.4.1.2011.2.25.3.70.10.100.80.1.2
    sdhpathPer24hCurMonValue OBJECT-TYPE
        SYNTAX OCTET STRING
        MAX-ACCESS read-only
        STATUS current
        DESCRIPTION
            "perMonValue."
        ::= { sdhpathPer24hCurEntry 2 }

    -- 1.3.6.1.4.1.2011.2.25.3.70.10.100.80.1.3
    sdhpathPer24hCurVldty OBJECT-TYPE
        SYNTAX ValidflagType
        MAX-ACCESS read-only
        STATUS current
        DESCRIPTION
            "perVldty."
        ::= { sdhpathPer24hCurEntry 3 }

    -- 1.3.6.1.4.1.2011.2.25.3.70.10.100.80.1.4
    sdhpathPer24hCurDatetime OBJECT-TYPE
        SYNTAX DateAndTime
        MAX-ACCESS read-only
        STATUS current
        DESCRIPTION
            "perDateTime."
        ::= { sdhpathPer24hCurEntry 4 }

    -- 1.3.6.1.4.1.2011.2.25.3.70.10.100.80.1.5
    sdhpathPer24hCurParaLen OBJECT-TYPE
        SYNTAX Unsigned32
        MAX-ACCESS read-only
        STATUS current
        DESCRIPTION
            "perParaLen."
        ::= { sdhpathPer24hCurEntry 5 }

    -- 1.3.6.1.4.1.2011.2.25.3.70.10.100.80.1.6
    sdhpathPer24hCurPara OBJECT-TYPE
        SYNTAX OCTET STRING
        MAX-ACCESS read-only
        STATUS current
        DESCRIPTION
            "perPara."
        ::= { sdhpathPer24hCurEntry 6 }

    -- 1.3.6.1.4.1.2011.2.25.3.70.10.100.90
    sdhpathPer24hHisTable OBJECT-TYPE
        SYNTAX SEQUENCE OF SdhpathPer24hHisEntry
        MAX-ACCESS not-accessible
        STATUS current
        DESCRIPTION
            "sdhpathPer24hHis."
        ::= { sdhpath 90 }

    -- 1.3.6.1.4.1.2011.2.25.3.70.10.100.90.1
    sdhpathPer24hHisEntry OBJECT-TYPE
        SYNTAX SdhpathPer24hHisEntry
        MAX-ACCESS not-accessible
        STATUS current
        DESCRIPTION
            "sdhpathPer24hHis."
        INDEX{ sdhpathPer24hHisEid,sdhpathPer24hHisParaLen,sdhpathPer24hHisPara,sdhpathPer24hHisStartTime,sdhpathPer24hHisEndTime }
        ::= { sdhpathPer24hHisTable 1 }

    SdhpathPer24hHisEntry ::=
        SEQUENCE {
            sdhpathPer24hHisEid
                PerformanceEventType,
            sdhpathPer24hHisParaLen
                Unsigned32,
            sdhpathPer24hHisPara
                OCTET STRING,
            sdhpathPer24hHisMonValue
                OCTET STRING,
            sdhpathPer24hHisStartTime
                DateAndTime,
            sdhpathPer24hHisEndTime
                DateAndTime,
            sdhpathPer24hHisVldty
                ValidflagType
        }

    -- 1.3.6.1.4.1.2011.2.25.3.70.10.100.90.1.1
    sdhpathPer24hHisEid OBJECT-TYPE
        SYNTAX PerformanceEventType
        MAX-ACCESS read-only
        STATUS current
        DESCRIPTION
            "perEid."
        ::= { sdhpathPer24hHisEntry 1 }

    -- 1.3.6.1.4.1.2011.2.25.3.70.10.100.90.1.2
    sdhpathPer24hHisParaLen OBJECT-TYPE
        SYNTAX Unsigned32
        MAX-ACCESS read-only
        STATUS current
        DESCRIPTION
            "perParaLen."
        ::= { sdhpathPer24hHisEntry 2 }

    -- 1.3.6.1.4.1.2011.2.25.3.70.10.100.90.1.3
    sdhpathPer24hHisPara OBJECT-TYPE
        SYNTAX OCTET STRING
        MAX-ACCESS read-only
        STATUS current
        DESCRIPTION
            "perPara."
        ::= { sdhpathPer24hHisEntry 3 }

    -- 1.3.6.1.4.1.2011.2.25.3.70.10.100.90.1.4
    sdhpathPer24hHisMonValue OBJECT-TYPE
        SYNTAX OCTET STRING
        MAX-ACCESS read-only
        STATUS current
        DESCRIPTION
            "perMonValue."
        ::= { sdhpathPer24hHisEntry 4 }

    -- 1.3.6.1.4.1.2011.2.25.3.70.10.100.90.1.5
    sdhpathPer24hHisStartTime OBJECT-TYPE
        SYNTAX DateAndTime
        MAX-ACCESS read-only
        STATUS current
        DESCRIPTION
            "perDateTimeStart."
        ::= { sdhpathPer24hHisEntry 5 }

    -- 1.3.6.1.4.1.2011.2.25.3.70.10.100.90.1.6
    sdhpathPer24hHisEndTime OBJECT-TYPE
        SYNTAX DateAndTime
        MAX-ACCESS read-only
        STATUS current
        DESCRIPTION
            "perDateTimeEnd."
        ::= { sdhpathPer24hHisEntry 6 }

    -- 1.3.6.1.4.1.2011.2.25.3.70.10.100.90.1.7
    sdhpathPer24hHisVldty OBJECT-TYPE
        SYNTAX ValidflagType
        MAX-ACCESS read-only
        STATUS current
        DESCRIPTION
            "perVldty."
        ::= { sdhpathPer24hHisEntry 7 }

    -- 1.3.6.1.4.1.2011.2.25.3.70.10.110
    vc12path OBJECT IDENTIFIER ::= { rtnPerformance 110 }

    -- 1.3.6.1.4.1.2011.2.25.3.70.10.110.60
    vc12pathPer15mCurTable OBJECT-TYPE
        SYNTAX SEQUENCE OF Vc12pathPer15mCurEntry
        MAX-ACCESS not-accessible
        STATUS current
        DESCRIPTION
            "vc12pathPer15mCur."
        ::= { vc12path 60 }

    -- 1.3.6.1.4.1.2011.2.25.3.70.10.110.60.1
    vc12pathPer15mCurEntry OBJECT-TYPE
        SYNTAX Vc12pathPer15mCurEntry
        MAX-ACCESS not-accessible
        STATUS current
        DESCRIPTION
            "vc12pathPer15mCur."
        INDEX{ vc12pathPer15mCurEid,vc12pathPer15mCurPara }
        ::= { vc12pathPer15mCurTable 1 }

    Vc12pathPer15mCurEntry ::=
        SEQUENCE {
            vc12pathPer15mCurEid
                PerformanceEventType,
            vc12pathPer15mCurMonValue
                OCTET STRING,
            vc12pathPer15mCurVldty
                ValidflagType,
            vc12pathPer15mCurDatetime
                DateAndTime,
            vc12pathPer15mCurParaLen
                Unsigned32,
            vc12pathPer15mCurPara
                OCTET STRING
        }

    -- 1.3.6.1.4.1.2011.2.25.3.70.10.110.60.1.1
    vc12pathPer15mCurEid OBJECT-TYPE
        SYNTAX PerformanceEventType
        MAX-ACCESS read-only
        STATUS current
        DESCRIPTION
            "perEid."
        ::= { vc12pathPer15mCurEntry 1 }

    -- 1.3.6.1.4.1.2011.2.25.3.70.10.110.60.1.2
    vc12pathPer15mCurMonValue OBJECT-TYPE
        SYNTAX OCTET STRING
        MAX-ACCESS read-only
        STATUS current
        DESCRIPTION
            "perMonValue."
        ::= { vc12pathPer15mCurEntry 2 }

    -- 1.3.6.1.4.1.2011.2.25.3.70.10.110.60.1.3
    vc12pathPer15mCurVldty OBJECT-TYPE
        SYNTAX ValidflagType
        MAX-ACCESS read-only
        STATUS current
        DESCRIPTION
            "perVldty."
        ::= { vc12pathPer15mCurEntry 3 }

    -- 1.3.6.1.4.1.2011.2.25.3.70.10.110.60.1.4
    vc12pathPer15mCurDatetime OBJECT-TYPE
        SYNTAX DateAndTime
        MAX-ACCESS read-only
        STATUS current
        DESCRIPTION
            "perDateTime."
        ::= { vc12pathPer15mCurEntry 4 }

    -- 1.3.6.1.4.1.2011.2.25.3.70.10.110.60.1.5
    vc12pathPer15mCurParaLen OBJECT-TYPE
        SYNTAX Unsigned32
        MAX-ACCESS read-only
        STATUS current
        DESCRIPTION
            "perParaLen."
        ::= { vc12pathPer15mCurEntry 5 }

    -- 1.3.6.1.4.1.2011.2.25.3.70.10.110.60.1.6
    vc12pathPer15mCurPara OBJECT-TYPE
        SYNTAX OCTET STRING
        MAX-ACCESS read-only
        STATUS current
        DESCRIPTION
            "perPara."
        ::= { vc12pathPer15mCurEntry 6 }

    -- 1.3.6.1.4.1.2011.2.25.3.70.10.110.70
    vc12pathPer15mHisTable OBJECT-TYPE
        SYNTAX SEQUENCE OF Vc12pathPer15mHisEntry
        MAX-ACCESS not-accessible
        STATUS current
        DESCRIPTION
            "vc12pathPer15mHis."
        ::= { vc12path 70 }

    -- 1.3.6.1.4.1.2011.2.25.3.70.10.110.70.1
    vc12pathPer15mHisEntry OBJECT-TYPE
        SYNTAX Vc12pathPer15mHisEntry
        MAX-ACCESS not-accessible
        STATUS current
        DESCRIPTION
            "vc12pathPer15mHis."
        INDEX{ vc12pathPer15mHisEid,vc12pathPer15mHisParaLen,vc12pathPer15mHisPara,vc12pathPer15mHisStartTime,vc12pathPer15mHisEndTime }
        ::= { vc12pathPer15mHisTable 1 }

    Vc12pathPer15mHisEntry ::=
        SEQUENCE {
            vc12pathPer15mHisEid
                PerformanceEventType,
            vc12pathPer15mHisParaLen
                Unsigned32,
            vc12pathPer15mHisPara
                OCTET STRING,
            vc12pathPer15mHisMonValue
                OCTET STRING,
            vc12pathPer15mHisStartTime
                DateAndTime,
            vc12pathPer15mHisEndTime
                DateAndTime,
            vc12pathPer15mHisVldty
                ValidflagType
        }

    -- 1.3.6.1.4.1.2011.2.25.3.70.10.110.70.1.1
    vc12pathPer15mHisEid OBJECT-TYPE
        SYNTAX PerformanceEventType
        MAX-ACCESS read-only
        STATUS current
        DESCRIPTION
            "perEid."
        ::= { vc12pathPer15mHisEntry 1 }

    -- 1.3.6.1.4.1.2011.2.25.3.70.10.110.70.1.2
    vc12pathPer15mHisParaLen OBJECT-TYPE
        SYNTAX Unsigned32
        MAX-ACCESS read-only
        STATUS current
        DESCRIPTION
            "perParaLen."
        ::= { vc12pathPer15mHisEntry 2 }

    -- 1.3.6.1.4.1.2011.2.25.3.70.10.110.70.1.3
    vc12pathPer15mHisPara OBJECT-TYPE
        SYNTAX OCTET STRING
        MAX-ACCESS read-only
        STATUS current
        DESCRIPTION
            "perPara."
        ::= { vc12pathPer15mHisEntry 3 }

    -- 1.3.6.1.4.1.2011.2.25.3.70.10.110.70.1.4
    vc12pathPer15mHisMonValue OBJECT-TYPE
        SYNTAX OCTET STRING
        MAX-ACCESS read-only
        STATUS current
        DESCRIPTION
            "perMonValue."
        ::= { vc12pathPer15mHisEntry 4 }

    -- 1.3.6.1.4.1.2011.2.25.3.70.10.110.70.1.5
    vc12pathPer15mHisStartTime OBJECT-TYPE
        SYNTAX DateAndTime
        MAX-ACCESS read-only
        STATUS current
        DESCRIPTION
            "perDateTimeStart."
        ::= { vc12pathPer15mHisEntry 5 }

    -- 1.3.6.1.4.1.2011.2.25.3.70.10.110.70.1.6
    vc12pathPer15mHisEndTime OBJECT-TYPE
        SYNTAX DateAndTime
        MAX-ACCESS read-only
        STATUS current
        DESCRIPTION
            "perDateTimeEnd."
        ::= { vc12pathPer15mHisEntry 6 }

    -- 1.3.6.1.4.1.2011.2.25.3.70.10.110.70.1.7
    vc12pathPer15mHisVldty OBJECT-TYPE
        SYNTAX ValidflagType
        MAX-ACCESS read-only
        STATUS current
        DESCRIPTION
            "perVldty."
        ::= { vc12pathPer15mHisEntry 7 }

    -- 1.3.6.1.4.1.2011.2.25.3.70.10.110.80
    vc12pathPer24hCurTable OBJECT-TYPE
        SYNTAX SEQUENCE OF Vc12pathPer24hCurEntry
        MAX-ACCESS not-accessible
        STATUS current
        DESCRIPTION
            "vc12pathPer24hCur."
        ::= { vc12path 80 }

    -- 1.3.6.1.4.1.2011.2.25.3.70.10.110.80.1
    vc12pathPer24hCurEntry OBJECT-TYPE
        SYNTAX Vc12pathPer24hCurEntry
        MAX-ACCESS not-accessible
        STATUS current
        DESCRIPTION
            "vc12pathPer24hCur."
        INDEX{ vc12pathPer24hCurEid,vc12pathPer24hCurPara }
        ::= { vc12pathPer24hCurTable 1 }

    Vc12pathPer24hCurEntry ::=
        SEQUENCE {
            vc12pathPer24hCurEid
                PerformanceEventType,
            vc12pathPer24hCurMonValue
                OCTET STRING,
            vc12pathPer24hCurVldty
                ValidflagType,
            vc12pathPer24hCurDatetime
                DateAndTime,
            vc12pathPer24hCurParaLen
                Unsigned32,
            vc12pathPer24hCurPara
                OCTET STRING
        }

    -- 1.3.6.1.4.1.2011.2.25.3.70.10.110.80.1.1
    vc12pathPer24hCurEid OBJECT-TYPE
        SYNTAX PerformanceEventType
        MAX-ACCESS read-only
        STATUS current
        DESCRIPTION
            "perEid."
        ::= { vc12pathPer24hCurEntry 1 }

    -- 1.3.6.1.4.1.2011.2.25.3.70.10.110.80.1.2
    vc12pathPer24hCurMonValue OBJECT-TYPE
        SYNTAX OCTET STRING
        MAX-ACCESS read-only
        STATUS current
        DESCRIPTION
            "perMonValue."
        ::= { vc12pathPer24hCurEntry 2 }

    -- 1.3.6.1.4.1.2011.2.25.3.70.10.110.80.1.3
    vc12pathPer24hCurVldty OBJECT-TYPE
        SYNTAX ValidflagType
        MAX-ACCESS read-only
        STATUS current
        DESCRIPTION
            "perVldty."
        ::= { vc12pathPer24hCurEntry 3 }

    -- 1.3.6.1.4.1.2011.2.25.3.70.10.110.80.1.4
    vc12pathPer24hCurDatetime OBJECT-TYPE
        SYNTAX DateAndTime
        MAX-ACCESS read-only
        STATUS current
        DESCRIPTION
            "perDateTime."
        ::= { vc12pathPer24hCurEntry 4 }

    -- 1.3.6.1.4.1.2011.2.25.3.70.10.110.80.1.5
    vc12pathPer24hCurParaLen OBJECT-TYPE
        SYNTAX Unsigned32
        MAX-ACCESS read-only
        STATUS current
        DESCRIPTION
            "perParaLen."
        ::= { vc12pathPer24hCurEntry 5 }

    -- 1.3.6.1.4.1.2011.2.25.3.70.10.110.80.1.6
    vc12pathPer24hCurPara OBJECT-TYPE
        SYNTAX OCTET STRING
        MAX-ACCESS read-only
        STATUS current
        DESCRIPTION
            "perPara."
        ::= { vc12pathPer24hCurEntry 6 }

    -- 1.3.6.1.4.1.2011.2.25.3.70.10.110.90
    vc12pathPer24hHisTable OBJECT-TYPE
        SYNTAX SEQUENCE OF Vc12pathPer24hHisEntry
        MAX-ACCESS not-accessible
        STATUS current
        DESCRIPTION
            "vc12pathPer24hHis."
        ::= { vc12path 90 }

    -- 1.3.6.1.4.1.2011.2.25.3.70.10.110.90.1
    vc12pathPer24hHisEntry OBJECT-TYPE
        SYNTAX Vc12pathPer24hHisEntry
        MAX-ACCESS not-accessible
        STATUS current
        DESCRIPTION
            "vc12pathPer24hHis."
        INDEX{ vc12pathPer24hHisEid,vc12pathPer24hHisParaLen,vc12pathPer24hHisPara,vc12pathPer24hHisStartTime,vc12pathPer24hHisEndTime }
        ::= { vc12pathPer24hHisTable 1 }

    Vc12pathPer24hHisEntry ::=
        SEQUENCE {
            vc12pathPer24hHisEid
                PerformanceEventType,
            vc12pathPer24hHisParaLen
                Unsigned32,
            vc12pathPer24hHisPara
                OCTET STRING,
            vc12pathPer24hHisMonValue
                OCTET STRING,
            vc12pathPer24hHisStartTime
                DateAndTime,
            vc12pathPer24hHisEndTime
                DateAndTime,
            vc12pathPer24hHisVldty
                ValidflagType
        }

    -- 1.3.6.1.4.1.2011.2.25.3.70.10.110.90.1.1
    vc12pathPer24hHisEid OBJECT-TYPE
        SYNTAX PerformanceEventType
        MAX-ACCESS read-only
        STATUS current
        DESCRIPTION
            "perEid."
        ::= { vc12pathPer24hHisEntry 1 }

    -- 1.3.6.1.4.1.2011.2.25.3.70.10.110.90.1.2
    vc12pathPer24hHisParaLen OBJECT-TYPE
        SYNTAX Unsigned32
        MAX-ACCESS read-only
        STATUS current
        DESCRIPTION
            "perParaLen."
        ::= { vc12pathPer24hHisEntry 2 }

    -- 1.3.6.1.4.1.2011.2.25.3.70.10.110.90.1.3
    vc12pathPer24hHisPara OBJECT-TYPE
        SYNTAX OCTET STRING
        MAX-ACCESS read-only
        STATUS current
        DESCRIPTION
            "perPara."
        ::= { vc12pathPer24hHisEntry 3 }

    -- 1.3.6.1.4.1.2011.2.25.3.70.10.110.90.1.4
    vc12pathPer24hHisMonValue OBJECT-TYPE
        SYNTAX OCTET STRING
        MAX-ACCESS read-only
        STATUS current
        DESCRIPTION
            "perMonValue."
        ::= { vc12pathPer24hHisEntry 4 }

    -- 1.3.6.1.4.1.2011.2.25.3.70.10.110.90.1.5
    vc12pathPer24hHisStartTime OBJECT-TYPE
        SYNTAX DateAndTime
        MAX-ACCESS read-only
        STATUS current
        DESCRIPTION
            "perDateTimeStart."
        ::= { vc12pathPer24hHisEntry 5 }

    -- 1.3.6.1.4.1.2011.2.25.3.70.10.110.90.1.6
    vc12pathPer24hHisEndTime OBJECT-TYPE
        SYNTAX DateAndTime
        MAX-ACCESS read-only
        STATUS current
        DESCRIPTION
            "perDateTimeEnd."
        ::= { vc12pathPer24hHisEntry 6 }

    -- 1.3.6.1.4.1.2011.2.25.3.70.10.110.90.1.7
    vc12pathPer24hHisVldty OBJECT-TYPE
        SYNTAX ValidflagType
        MAX-ACCESS read-only
        STATUS current
        DESCRIPTION
            "perVldty."
        ::= { vc12pathPer24hHisEntry 7 }

    -- 1.3.6.1.4.1.2011.2.25.3.70.10.120
    vc3path OBJECT IDENTIFIER ::= { rtnPerformance 120 }

    -- 1.3.6.1.4.1.2011.2.25.3.70.10.120.60
    vc3pathPer15mCurTable OBJECT-TYPE
        SYNTAX SEQUENCE OF Vc3pathPer15mCurEntry
        MAX-ACCESS not-accessible
        STATUS current
        DESCRIPTION
            "vc3pathPer15mCur."
        ::= { vc3path 60 }

    -- 1.3.6.1.4.1.2011.2.25.3.70.10.120.60.1
    vc3pathPer15mCurEntry OBJECT-TYPE
        SYNTAX Vc3pathPer15mCurEntry
        MAX-ACCESS not-accessible
        STATUS current
        DESCRIPTION
            "vc3pathPer15mCur."
        INDEX{ vc3pathPer15mCurEid,vc3pathPer15mCurPara }
        ::= { vc3pathPer15mCurTable 1 }

    Vc3pathPer15mCurEntry ::=
        SEQUENCE {
            vc3pathPer15mCurEid
                PerformanceEventType,
            vc3pathPer15mCurMonValue
                OCTET STRING,
            vc3pathPer15mCurVldty
                ValidflagType,
            vc3pathPer15mCurDatetime
                DateAndTime,
            vc3pathPer15mCurParaLen
                Unsigned32,
            vc3pathPer15mCurPara
                OCTET STRING
        }

    -- 1.3.6.1.4.1.2011.2.25.3.70.10.120.60.1.1
    vc3pathPer15mCurEid OBJECT-TYPE
        SYNTAX PerformanceEventType
        MAX-ACCESS read-only
        STATUS current
        DESCRIPTION
            "perEid."
        ::= { vc3pathPer15mCurEntry 1 }

    -- 1.3.6.1.4.1.2011.2.25.3.70.10.120.60.1.2
    vc3pathPer15mCurMonValue OBJECT-TYPE
        SYNTAX OCTET STRING
        MAX-ACCESS read-only
        STATUS current
        DESCRIPTION
            "perMonValue."
        ::= { vc3pathPer15mCurEntry 2 }

    -- 1.3.6.1.4.1.2011.2.25.3.70.10.120.60.1.3
    vc3pathPer15mCurVldty OBJECT-TYPE
        SYNTAX ValidflagType
        MAX-ACCESS read-only
        STATUS current
        DESCRIPTION
            "perVldty."
        ::= { vc3pathPer15mCurEntry 3 }

    -- 1.3.6.1.4.1.2011.2.25.3.70.10.120.60.1.4
    vc3pathPer15mCurDatetime OBJECT-TYPE
        SYNTAX DateAndTime
        MAX-ACCESS read-only
        STATUS current
        DESCRIPTION
            "perDateTime."
        ::= { vc3pathPer15mCurEntry 4 }

    -- 1.3.6.1.4.1.2011.2.25.3.70.10.120.60.1.5
    vc3pathPer15mCurParaLen OBJECT-TYPE
        SYNTAX Unsigned32
        MAX-ACCESS read-only
        STATUS current
        DESCRIPTION
            "perParaLen."
        ::= { vc3pathPer15mCurEntry 5 }

    -- 1.3.6.1.4.1.2011.2.25.3.70.10.120.60.1.6
    vc3pathPer15mCurPara OBJECT-TYPE
        SYNTAX OCTET STRING
        MAX-ACCESS read-only
        STATUS current
        DESCRIPTION
            "perPara."
        ::= { vc3pathPer15mCurEntry 6 }

    -- 1.3.6.1.4.1.2011.2.25.3.70.10.120.70
    vc3pathPer15mHisTable OBJECT-TYPE
        SYNTAX SEQUENCE OF Vc3pathPer15mHisEntry
        MAX-ACCESS not-accessible
        STATUS current
        DESCRIPTION
            "vc3pathPer15mHis."
        ::= { vc3path 70 }

    -- 1.3.6.1.4.1.2011.2.25.3.70.10.120.70.1
    vc3pathPer15mHisEntry OBJECT-TYPE
        SYNTAX Vc3pathPer15mHisEntry
        MAX-ACCESS not-accessible
        STATUS current
        DESCRIPTION
            "vc3pathPer15mHis."
        INDEX{ vc3pathPer15mHisEid,vc3pathPer15mHisParaLen,vc3pathPer15mHisPara,vc3pathPer15mHisStartTime,vc3pathPer15mHisEndTime }
        ::= { vc3pathPer15mHisTable 1 }

    Vc3pathPer15mHisEntry ::=
        SEQUENCE {
            vc3pathPer15mHisEid
                PerformanceEventType,
            vc3pathPer15mHisParaLen
                Unsigned32,
            vc3pathPer15mHisPara
                OCTET STRING,
            vc3pathPer15mHisMonValue
                OCTET STRING,
            vc3pathPer15mHisStartTime
                DateAndTime,
            vc3pathPer15mHisEndTime
                DateAndTime,
            vc3pathPer15mHisVldty
                ValidflagType
        }

    -- 1.3.6.1.4.1.2011.2.25.3.70.10.120.70.1.1
    vc3pathPer15mHisEid OBJECT-TYPE
        SYNTAX PerformanceEventType
        MAX-ACCESS read-only
        STATUS current
        DESCRIPTION
            "perEid."
        ::= { vc3pathPer15mHisEntry 1 }

    -- 1.3.6.1.4.1.2011.2.25.3.70.10.120.70.1.2
    vc3pathPer15mHisParaLen OBJECT-TYPE
        SYNTAX Unsigned32
        MAX-ACCESS read-only
        STATUS current
        DESCRIPTION
            "perParaLen."
        ::= { vc3pathPer15mHisEntry 2 }

    -- 1.3.6.1.4.1.2011.2.25.3.70.10.120.70.1.3
    vc3pathPer15mHisPara OBJECT-TYPE
        SYNTAX OCTET STRING
        MAX-ACCESS read-only
        STATUS current
        DESCRIPTION
            "perPara."
        ::= { vc3pathPer15mHisEntry 3 }

    -- 1.3.6.1.4.1.2011.2.25.3.70.10.120.70.1.4
    vc3pathPer15mHisMonValue OBJECT-TYPE
        SYNTAX OCTET STRING
        MAX-ACCESS read-only
        STATUS current
        DESCRIPTION
            "perMonValue."
        ::= { vc3pathPer15mHisEntry 4 }

    -- 1.3.6.1.4.1.2011.2.25.3.70.10.120.70.1.5
    vc3pathPer15mHisStartTime OBJECT-TYPE
        SYNTAX DateAndTime
        MAX-ACCESS read-only
        STATUS current
        DESCRIPTION
            "perDateTimeStart."
        ::= { vc3pathPer15mHisEntry 5 }

    -- 1.3.6.1.4.1.2011.2.25.3.70.10.120.70.1.6
    vc3pathPer15mHisEndTime OBJECT-TYPE
        SYNTAX DateAndTime
        MAX-ACCESS read-only
        STATUS current
        DESCRIPTION
            "perDateTimeEnd."
        ::= { vc3pathPer15mHisEntry 6 }

    -- 1.3.6.1.4.1.2011.2.25.3.70.10.120.70.1.7
    vc3pathPer15mHisVldty OBJECT-TYPE
        SYNTAX ValidflagType
        MAX-ACCESS read-only
        STATUS current
        DESCRIPTION
            "perVldty."
        ::= { vc3pathPer15mHisEntry 7 }

    -- 1.3.6.1.4.1.2011.2.25.3.70.10.120.80
    vc3pathPer24hCurTable OBJECT-TYPE
        SYNTAX SEQUENCE OF Vc3pathPer24hCurEntry
        MAX-ACCESS not-accessible
        STATUS current
        DESCRIPTION
            "vc3pathPer24hCur."
        ::= { vc3path 80 }

    -- 1.3.6.1.4.1.2011.2.25.3.70.10.120.80.1
    vc3pathPer24hCurEntry OBJECT-TYPE
        SYNTAX Vc3pathPer24hCurEntry
        MAX-ACCESS not-accessible
        STATUS current
        DESCRIPTION
            "vc3pathPer24hCur."
        INDEX{ vc3pathPer24hCurEid,vc3pathPer24hCurPara }
        ::= { vc3pathPer24hCurTable 1 }

    Vc3pathPer24hCurEntry ::=
        SEQUENCE {
            vc3pathPer24hCurEid
                PerformanceEventType,
            vc3pathPer24hCurMonValue
                OCTET STRING,
            vc3pathPer24hCurVldty
                ValidflagType,
            vc3pathPer24hCurDatetime
                DateAndTime,
            vc3pathPer24hCurParaLen
                Unsigned32,
            vc3pathPer24hCurPara
                OCTET STRING
        }

    -- 1.3.6.1.4.1.2011.2.25.3.70.10.120.80.1.1
    vc3pathPer24hCurEid OBJECT-TYPE
        SYNTAX PerformanceEventType
        MAX-ACCESS read-only
        STATUS current
        DESCRIPTION
            "perEid."
        ::= { vc3pathPer24hCurEntry 1 }

    -- 1.3.6.1.4.1.2011.2.25.3.70.10.120.80.1.2
    vc3pathPer24hCurMonValue OBJECT-TYPE
        SYNTAX OCTET STRING
        MAX-ACCESS read-only
        STATUS current
        DESCRIPTION
            "perMonValue."
        ::= { vc3pathPer24hCurEntry 2 }

    -- 1.3.6.1.4.1.2011.2.25.3.70.10.120.80.1.3
    vc3pathPer24hCurVldty OBJECT-TYPE
        SYNTAX ValidflagType
        MAX-ACCESS read-only
        STATUS current
        DESCRIPTION
            "perVldty."
        ::= { vc3pathPer24hCurEntry 3 }

    -- 1.3.6.1.4.1.2011.2.25.3.70.10.120.80.1.4
    vc3pathPer24hCurDatetime OBJECT-TYPE
        SYNTAX DateAndTime
        MAX-ACCESS read-only
        STATUS current
        DESCRIPTION
            "perDateTime."
        ::= { vc3pathPer24hCurEntry 4 }

    -- 1.3.6.1.4.1.2011.2.25.3.70.10.120.80.1.5
    vc3pathPer24hCurParaLen OBJECT-TYPE
        SYNTAX Unsigned32
        MAX-ACCESS read-only
        STATUS current
        DESCRIPTION
            "perParaLen."
        ::= { vc3pathPer24hCurEntry 5 }

    -- 1.3.6.1.4.1.2011.2.25.3.70.10.120.80.1.6
    vc3pathPer24hCurPara OBJECT-TYPE
        SYNTAX OCTET STRING
        MAX-ACCESS read-only
        STATUS current
        DESCRIPTION
            "perPara."
        ::= { vc3pathPer24hCurEntry 6 }

    -- 1.3.6.1.4.1.2011.2.25.3.70.10.120.90
    vc3pathPer24hHisTable OBJECT-TYPE
        SYNTAX SEQUENCE OF Vc3pathPer24hHisEntry
        MAX-ACCESS not-accessible
        STATUS current
        DESCRIPTION
            "vc3pathPer24hHis."
        ::= { vc3path 90 }

    -- 1.3.6.1.4.1.2011.2.25.3.70.10.120.90.1
    vc3pathPer24hHisEntry OBJECT-TYPE
        SYNTAX Vc3pathPer24hHisEntry
        MAX-ACCESS not-accessible
        STATUS current
        DESCRIPTION
            "vc3pathPer24hHis."
        INDEX{ vc3pathPer24hHisEid,vc3pathPer24hHisParaLen,vc3pathPer24hHisPara,vc3pathPer24hHisStartTime,vc3pathPer24hHisEndTime }
        ::= { vc3pathPer24hHisTable 1 }

    Vc3pathPer24hHisEntry ::=
        SEQUENCE {
            vc3pathPer24hHisEid
                PerformanceEventType,
            vc3pathPer24hHisParaLen
                Unsigned32,
            vc3pathPer24hHisPara
                OCTET STRING,
            vc3pathPer24hHisMonValue
                OCTET STRING,
            vc3pathPer24hHisStartTime
                DateAndTime,
            vc3pathPer24hHisEndTime
                DateAndTime,
            vc3pathPer24hHisVldty
                ValidflagType
        }

    -- 1.3.6.1.4.1.2011.2.25.3.70.10.120.90.1.1
    vc3pathPer24hHisEid OBJECT-TYPE
        SYNTAX PerformanceEventType
        MAX-ACCESS read-only
        STATUS current
        DESCRIPTION
            "perEid."
        ::= { vc3pathPer24hHisEntry 1 }

    -- 1.3.6.1.4.1.2011.2.25.3.70.10.120.90.1.2
    vc3pathPer24hHisParaLen OBJECT-TYPE
        SYNTAX Unsigned32
        MAX-ACCESS read-only
        STATUS current
        DESCRIPTION
            "perParaLen."
        ::= { vc3pathPer24hHisEntry 2 }

    -- 1.3.6.1.4.1.2011.2.25.3.70.10.120.90.1.3
    vc3pathPer24hHisPara OBJECT-TYPE
        SYNTAX OCTET STRING
        MAX-ACCESS read-only
        STATUS current
        DESCRIPTION
            "perPara."
        ::= { vc3pathPer24hHisEntry 3 }

    -- 1.3.6.1.4.1.2011.2.25.3.70.10.120.90.1.4
    vc3pathPer24hHisMonValue OBJECT-TYPE
        SYNTAX OCTET STRING
        MAX-ACCESS read-only
        STATUS current
        DESCRIPTION
            "perMonValue."
        ::= { vc3pathPer24hHisEntry 4 }

    -- 1.3.6.1.4.1.2011.2.25.3.70.10.120.90.1.5
    vc3pathPer24hHisStartTime OBJECT-TYPE
        SYNTAX DateAndTime
        MAX-ACCESS read-only
        STATUS current
        DESCRIPTION
            "perDateTimeStart."
        ::= { vc3pathPer24hHisEntry 5 }

    -- 1.3.6.1.4.1.2011.2.25.3.70.10.120.90.1.6
    vc3pathPer24hHisEndTime OBJECT-TYPE
        SYNTAX DateAndTime
        MAX-ACCESS read-only
        STATUS current
        DESCRIPTION
            "perDateTimeEnd."
        ::= { vc3pathPer24hHisEntry 6 }

    -- 1.3.6.1.4.1.2011.2.25.3.70.10.120.90.1.7
    vc3pathPer24hHisVldty OBJECT-TYPE
        SYNTAX ValidflagType
        MAX-ACCESS read-only
        STATUS current
        DESCRIPTION
            "perVldty."
        ::= { vc3pathPer24hHisEntry 7 }

    -- 1.3.6.1.4.1.2011.2.25.3.70.10.130
    cprilaser OBJECT IDENTIFIER ::= { rtnPerformance 130 }

    -- 1.3.6.1.4.1.2011.2.25.3.70.10.130.60
    cprilaserPer15mCurTable OBJECT-TYPE
        SYNTAX SEQUENCE OF CprilaserPer15mCurEntry
        MAX-ACCESS not-accessible
        STATUS current
        DESCRIPTION
            "Current 15-minute performance of  CPRI laser"
        ::= { cprilaser 60 }

    -- 1.3.6.1.4.1.2011.2.25.3.70.10.130.60.1
    cprilaserPer15mCurEntry OBJECT-TYPE
        SYNTAX CprilaserPer15mCurEntry
        MAX-ACCESS not-accessible
        STATUS current
        DESCRIPTION
            "Current 15-minute performance of CPRI laser"
        INDEX{ cprilaserPer15mCurPara }
        ::= { cprilaserPer15mCurTable 1 }

    CprilaserPer15mCurEntry ::=
        SEQUENCE {
            cprilaserPer15mCurEid
                PerformanceEventType,
            cprilaserPer15mCurMonValue
                OCTET STRING,
            cprilaserPer15mCurVldty
                ValidflagType,
            cprilaserPer15mCurDatetime
                DateAndTime,
            cprilaserPer15mCurParaLen
                Unsigned32,
            cprilaserPer15mCurPara
                OCTET STRING
        }

    -- 1.3.6.1.4.1.2011.2.25.3.70.10.130.60.1.1
    cprilaserPer15mCurEid OBJECT-TYPE
        SYNTAX PerformanceEventType
        MAX-ACCESS read-only
        STATUS current
        DESCRIPTION
            "Event ID of a current 15-minute performanceof CPRI laser"
        ::= { cprilaserPer15mCurEntry 1 }

    -- 1.3.6.1.4.1.2011.2.25.3.70.10.130.60.1.2
    cprilaserPer15mCurMonValue OBJECT-TYPE
        SYNTAX OCTET STRING
        MAX-ACCESS read-only
        STATUS current
        DESCRIPTION
            "Statistics of current 15-minute performance of CPRI laser"
        ::= { cprilaserPer15mCurEntry 2 }

    -- 1.3.6.1.4.1.2011.2.25.3.70.10.130.60.1.3
    cprilaserPer15mCurVldty OBJECT-TYPE
        SYNTAX ValidflagType
        MAX-ACCESS read-only
        STATUS current
        DESCRIPTION
            "Validity flag of current 15-minute performance of  CPRI laser"
        ::= { cprilaserPer15mCurEntry 3 }

    -- 1.3.6.1.4.1.2011.2.25.3.70.10.130.60.1.4
    cprilaserPer15mCurDatetime OBJECT-TYPE
        SYNTAX DateAndTime
        MAX-ACCESS read-only
        STATUS current
        DESCRIPTION
            "Time information of current 15-minute performance of  CPRI laser"
        ::= { cprilaserPer15mCurEntry 4 }

    -- 1.3.6.1.4.1.2011.2.25.3.70.10.130.60.1.5
    cprilaserPer15mCurParaLen OBJECT-TYPE
        SYNTAX Unsigned32
        MAX-ACCESS read-only
        STATUS current
        DESCRIPTION
            "Parameter length of current 15-minute performance of  CPRI laser"
        ::= { cprilaserPer15mCurEntry 5 }

    -- 1.3.6.1.4.1.2011.2.25.3.70.10.130.60.1.6
    cprilaserPer15mCurPara OBJECT-TYPE
        SYNTAX OCTET STRING
        MAX-ACCESS read-only
        STATUS current
        DESCRIPTION
            "Parameters of current 15-minute performance of  CPRI laser"
        ::= { cprilaserPer15mCurEntry 6 }

    -- 1.3.6.1.4.1.2011.2.25.3.70.10.130.70
    cprilaserPer15mHisTable OBJECT-TYPE
        SYNTAX SEQUENCE OF CprilaserPer15mHisEntry
        MAX-ACCESS not-accessible
        STATUS current
        DESCRIPTION
            "Historical 15-minute performance of  CPRI laser"
        ::= { cprilaser 70 }

    -- 1.3.6.1.4.1.2011.2.25.3.70.10.130.70.1
    cprilaserPer15mHisEntry OBJECT-TYPE
        SYNTAX CprilaserPer15mHisEntry
        MAX-ACCESS not-accessible
        STATUS current
        DESCRIPTION
            "Historical 15-minute performance of  CPRI laser"
        INDEX{ cprilaserPer15mHisEid, cprilaserPer15mHisParaLen, cprilaserPer15mHisPara, cprilaserPer15mHisStartTime, cprilaserPer15mHisEndTime }
        ::= { cprilaserPer15mHisTable 1 }

    CprilaserPer15mHisEntry ::=
        SEQUENCE {
            cprilaserPer15mHisEid
                PerformanceEventType,
            cprilaserPer15mHisParaLen
                Unsigned32,
            cprilaserPer15mHisPara
                OCTET STRING,
            cprilaserPer15mHisMonValue
                OCTET STRING,
            cprilaserPer15mHisStartTime
                DateAndTime,
            cprilaserPer15mHisEndTime
                DateAndTime,
            cprilaserPer15mHisVldty
                ValidflagType
        }

    -- 1.3.6.1.4.1.2011.2.25.3.70.10.130.70.1.1
    cprilaserPer15mHisEid OBJECT-TYPE
        SYNTAX PerformanceEventType
        MAX-ACCESS read-only
        STATUS current
        DESCRIPTION
            "Event ID of a historical 15-minute performance of CPRI laser"
        ::= { cprilaserPer15mHisEntry 1 }

    -- 1.3.6.1.4.1.2011.2.25.3.70.10.130.70.1.2
    cprilaserPer15mHisParaLen OBJECT-TYPE
        SYNTAX Unsigned32
        MAX-ACCESS read-only
        STATUS current
        DESCRIPTION
            "Parameter length of historical 15-minute performance of  CPRI laser"
        ::= { cprilaserPer15mHisEntry 2 }

    -- 1.3.6.1.4.1.2011.2.25.3.70.10.130.70.1.3
    cprilaserPer15mHisPara OBJECT-TYPE
        SYNTAX OCTET STRING
        MAX-ACCESS read-only
        STATUS current
        DESCRIPTION
            "Parameters of historical 15-minute performance of  CPRI laser"
        ::= { cprilaserPer15mHisEntry 3 }

    -- 1.3.6.1.4.1.2011.2.25.3.70.10.130.70.1.4
    cprilaserPer15mHisMonValue OBJECT-TYPE
        SYNTAX OCTET STRING
        MAX-ACCESS read-only
        STATUS current
        DESCRIPTION
            "Statistics of historical 15-minute performance of CPRI laser"
        ::= { cprilaserPer15mHisEntry 4 }

    -- 1.3.6.1.4.1.2011.2.25.3.70.10.130.70.1.5
    cprilaserPer15mHisStartTime OBJECT-TYPE
        SYNTAX DateAndTime
        MAX-ACCESS read-only
        STATUS current
        DESCRIPTION
            "Start time of historical 15-minute performance of  CPRI laser"
        ::= { cprilaserPer15mHisEntry 5 }

    -- 1.3.6.1.4.1.2011.2.25.3.70.10.130.70.1.6
    cprilaserPer15mHisEndTime OBJECT-TYPE
        SYNTAX DateAndTime
        MAX-ACCESS read-only
        STATUS current
        DESCRIPTION
            "End time of historical 15-minute performance of  CPRI laser"
        ::= { cprilaserPer15mHisEntry 6 }

    -- 1.3.6.1.4.1.2011.2.25.3.70.10.130.70.1.7
    cprilaserPer15mHisVldty OBJECT-TYPE
        SYNTAX ValidflagType
        MAX-ACCESS read-only
        STATUS current
        DESCRIPTION
            "Validity flag of historical 15-minute performance of  CPRI laser"
        ::= { cprilaserPer15mHisEntry 7 }

    -- 1.3.6.1.4.1.2011.2.25.3.70.10.130.80
    cprilaserPer24hCurTable OBJECT-TYPE
        SYNTAX SEQUENCE OF CprilaserPer24hCurEntry
        MAX-ACCESS not-accessible
        STATUS current
        DESCRIPTION
            "Current 24-hour performance of  CPRI laser"
        ::= { cprilaser 80 }

    -- 1.3.6.1.4.1.2011.2.25.3.70.10.130.80.1
    cprilaserPer24hCurEntry OBJECT-TYPE
        SYNTAX CprilaserPer24hCurEntry
        MAX-ACCESS not-accessible
        STATUS current
        DESCRIPTION
            "Current 24-hour performance of  CPRI laser"
        INDEX{ cprilaserPer24hCurEid, cprilaserPer24hCurPara }
        ::= { cprilaserPer24hCurTable 1 }

    CprilaserPer24hCurEntry ::=
        SEQUENCE {
            cprilaserPer24hCurEid
                PerformanceEventType,
            cprilaserPer24hCurMonValue
                OCTET STRING,
            cprilaserPer24hCurVldty
                ValidflagType,
            cprilaserPer24hCurDatetime
                DateAndTime,
            cprilaserPer24hCurParaLen
                Unsigned32,
            cprilaserPer24hCurPara
                OCTET STRING
        }

    -- 1.3.6.1.4.1.2011.2.25.3.70.10.130.80.1.1
    cprilaserPer24hCurEid OBJECT-TYPE
        SYNTAX PerformanceEventType
        MAX-ACCESS read-only
        STATUS current
        DESCRIPTION
            "Event ID of a current 24-hour performance of CPRI laser"
        ::= { cprilaserPer24hCurEntry 1 }

    -- 1.3.6.1.4.1.2011.2.25.3.70.10.130.80.1.2
    cprilaserPer24hCurMonValue OBJECT-TYPE
        SYNTAX OCTET STRING
        MAX-ACCESS read-only
        STATUS current
        DESCRIPTION
            "Statistics of current 24-hour performance of CPRI laser"
        ::= { cprilaserPer24hCurEntry 2 }

    -- 1.3.6.1.4.1.2011.2.25.3.70.10.130.80.1.3
    cprilaserPer24hCurVldty OBJECT-TYPE
        SYNTAX ValidflagType
        MAX-ACCESS read-only
        STATUS current
        DESCRIPTION
            "Validity flag of current 24-hour performance of  CPRI laser"
        ::= { cprilaserPer24hCurEntry 3 }

    -- 1.3.6.1.4.1.2011.2.25.3.70.10.130.80.1.4
    cprilaserPer24hCurDatetime OBJECT-TYPE
        SYNTAX DateAndTime
        MAX-ACCESS read-only
        STATUS current
        DESCRIPTION
            "Time information of current 24-hour performance of  CPRI laser"
        ::= { cprilaserPer24hCurEntry 4 }

    -- 1.3.6.1.4.1.2011.2.25.3.70.10.130.80.1.5
    cprilaserPer24hCurParaLen OBJECT-TYPE
        SYNTAX Unsigned32
        MAX-ACCESS read-only
        STATUS current
        DESCRIPTION
            "Parameter length of current 24-hour performance of  CPRI laser"
        ::= { cprilaserPer24hCurEntry 5 }

    -- 1.3.6.1.4.1.2011.2.25.3.70.10.130.80.1.6
    cprilaserPer24hCurPara OBJECT-TYPE
        SYNTAX OCTET STRING
        MAX-ACCESS read-only
        STATUS current
        DESCRIPTION
            "Parameters of current 24-hour performance of  CPRI laser"
        ::= { cprilaserPer24hCurEntry 6 }

    -- 1.3.6.1.4.1.2011.2.25.3.70.10.130.90
    cprilaserPer24hHisTable OBJECT-TYPE
        SYNTAX SEQUENCE OF CprilaserPer24hHisEntry
        MAX-ACCESS not-accessible
        STATUS current
        DESCRIPTION
            "Historical 24-hour performance of  CPRI laser"
        ::= { cprilaser 90 }

    -- 1.3.6.1.4.1.2011.2.25.3.70.10.130.90.1
    cprilaserPer24hHisEntry OBJECT-TYPE
        SYNTAX CprilaserPer24hHisEntry
        MAX-ACCESS not-accessible
        STATUS current
        DESCRIPTION
            "Historical 24-hour performance of  CPRI laser"
        INDEX{ cprilaserPer24hHisEid, cprilaserPer24hHisParaLen, cprilaserPer24hHisPara, cprilaserPer24hHisStartTime, cprilaserPer24hHisEndTime }
        ::= { cprilaserPer24hHisTable 1 }

    CprilaserPer24hHisEntry ::=
        SEQUENCE {
            cprilaserPer24hHisEid
                PerformanceEventType,
            cprilaserPer24hHisParaLen
                Unsigned32,
            cprilaserPer24hHisPara
                OCTET STRING,
            cprilaserPer24hHisMonValue
                OCTET STRING,
            cprilaserPer24hHisStartTime
                DateAndTime,
            cprilaserPer24hHisEndTime
                DateAndTime,
            cprilaserPer24hHisVldty
                ValidflagType
        }

    -- 1.3.6.1.4.1.2011.2.25.3.70.10.130.90.1.1
    cprilaserPer24hHisEid OBJECT-TYPE
        SYNTAX PerformanceEventType
        MAX-ACCESS read-only
        STATUS current
        DESCRIPTION
            "Event ID of a historical 24-hour performance of CPRI laser"
        ::= { cprilaserPer24hHisEntry 1 }

    -- 1.3.6.1.4.1.2011.2.25.3.70.10.130.90.1.2
    cprilaserPer24hHisParaLen OBJECT-TYPE
        SYNTAX Unsigned32
        MAX-ACCESS read-only
        STATUS current
        DESCRIPTION
            "Parameter length of historical 24-hour performance of  CPRI laser"
        ::= { cprilaserPer24hHisEntry 2 }

    -- 1.3.6.1.4.1.2011.2.25.3.70.10.130.90.1.3
    cprilaserPer24hHisPara OBJECT-TYPE
        SYNTAX OCTET STRING
        MAX-ACCESS read-only
        STATUS current
        DESCRIPTION
            "Parameters of historical 24-hour performance of  CPRI laser"
        ::= { cprilaserPer24hHisEntry 3 }

    -- 1.3.6.1.4.1.2011.2.25.3.70.10.130.90.1.4
    cprilaserPer24hHisMonValue OBJECT-TYPE
        SYNTAX OCTET STRING
        MAX-ACCESS read-only
        STATUS current
        DESCRIPTION
            "Statistics of historical 24-hour performance of CPRI laser"
        ::= { cprilaserPer24hHisEntry 4 }

    -- 1.3.6.1.4.1.2011.2.25.3.70.10.130.90.1.5
    cprilaserPer24hHisStartTime OBJECT-TYPE
        SYNTAX DateAndTime
        MAX-ACCESS read-only
        STATUS current
        DESCRIPTION
            "Start time of historical 24-hour performance of  CPRI laser"
        ::= { cprilaserPer24hHisEntry 5 }

    -- 1.3.6.1.4.1.2011.2.25.3.70.10.130.90.1.6
    cprilaserPer24hHisEndTime OBJECT-TYPE
        SYNTAX DateAndTime
        MAX-ACCESS read-only
        STATUS current
        DESCRIPTION
            "End time of historical 24-hour performance of CPRI laser"
        ::= { cprilaserPer24hHisEntry 6 }

    -- 1.3.6.1.4.1.2011.2.25.3.70.10.130.90.1.7
    cprilaserPer24hHisVldty OBJECT-TYPE
        SYNTAX ValidflagType
        MAX-ACCESS read-only
        STATUS current
        DESCRIPTION
            "Validity flag of historical 24-hour performance of  CPRI laser"
        ::= { cprilaserPer24hHisEntry 7 }

    -- 1.3.6.1.4.1.2011.2.25.3.70.10.140
    sysClock OBJECT IDENTIFIER ::= { rtnPerformance 140 }

    -- 1.3.6.1.4.1.2011.2.25.3.70.10.140.60
    sysClockPer15mCurTable OBJECT-TYPE
        SYNTAX SEQUENCE OF SysClockPer15mCurEntry
        MAX-ACCESS not-accessible
        STATUS current
        DESCRIPTION
            "sysClockPer15mCur."
        ::= { sysClock 60 }

    -- 1.3.6.1.4.1.2011.2.25.3.70.10.140.60.1
    sysClockPer15mCurEntry OBJECT-TYPE
        SYNTAX SysClockPer15mCurEntry
        MAX-ACCESS not-accessible
        STATUS current
        DESCRIPTION
            "sysClockPer15mCur."
        INDEX{ sysClockPer15mCurEid,sysClockPer15mCurPara }
        ::= { sysClockPer15mCurTable 1 }

    SysClockPer15mCurEntry ::=
        SEQUENCE {
            sysClockPer15mCurEid
                PerformanceEventType,
            sysClockPer15mCurMonValue
                OCTET STRING,
            sysClockPer15mCurVldty
                ValidflagType,
            sysClockPer15mCurDatetime
                DateAndTime,
            sysClockPer15mCurParaLen
                Unsigned32,
            sysClockPer15mCurPara
                OCTET STRING
        }

    -- 1.3.6.1.4.1.2011.2.25.3.70.10.140.60.1.1
    sysClockPer15mCurEid OBJECT-TYPE
        SYNTAX PerformanceEventType
        MAX-ACCESS read-only
        STATUS current
        DESCRIPTION
            "perEid."
        ::= { sysClockPer15mCurEntry 1 }

    -- 1.3.6.1.4.1.2011.2.25.3.70.10.140.60.1.2
    sysClockPer15mCurMonValue OBJECT-TYPE
        SYNTAX OCTET STRING
        MAX-ACCESS read-only
        STATUS current
        DESCRIPTION
            "perMonValue."
        ::= { sysClockPer15mCurEntry 2 }

    -- 1.3.6.1.4.1.2011.2.25.3.70.10.140.60.1.3
    sysClockPer15mCurVldty OBJECT-TYPE
        SYNTAX ValidflagType
        MAX-ACCESS read-only
        STATUS current
        DESCRIPTION
            "perVldty."
        ::= { sysClockPer15mCurEntry 3 }

    -- 1.3.6.1.4.1.2011.2.25.3.70.10.140.60.1.4
    sysClockPer15mCurDatetime OBJECT-TYPE
        SYNTAX DateAndTime
        MAX-ACCESS read-only
        STATUS current
        DESCRIPTION
            "perDateTime."
        ::= { sysClockPer15mCurEntry 4 }

    -- 1.3.6.1.4.1.2011.2.25.3.70.10.140.60.1.5
    sysClockPer15mCurParaLen OBJECT-TYPE
        SYNTAX Unsigned32
        MAX-ACCESS read-only
        STATUS current
        DESCRIPTION
            "perParaLen."
        ::= { sysClockPer15mCurEntry 5 }

    -- 1.3.6.1.4.1.2011.2.25.3.70.10.140.60.1.6
    sysClockPer15mCurPara OBJECT-TYPE
        SYNTAX OCTET STRING
        MAX-ACCESS read-only
        STATUS current
        DESCRIPTION
            "perPara."
        ::= { sysClockPer15mCurEntry 6 }

    -- 1.3.6.1.4.1.2011.2.25.3.70.10.140.70
    sysClockPer15mHisTable OBJECT-TYPE
        SYNTAX SEQUENCE OF SysClockPer15mHisEntry
        MAX-ACCESS not-accessible
        STATUS current
        DESCRIPTION
            "sysClockPer15mHis."
        ::= { sysClock 70 }

    -- 1.3.6.1.4.1.2011.2.25.3.70.10.140.70.1
    sysClockPer15mHisEntry OBJECT-TYPE
        SYNTAX SysClockPer15mHisEntry
        MAX-ACCESS not-accessible
        STATUS current
        DESCRIPTION
            "sysClockPer15mHis."
        INDEX{ sysClockPer15mHisEid,sysClockPer15mHisParaLen,sysClockPer15mHisPara,sysClockPer15mHisStartTime,sysClockPer15mHisEndTime }
        ::= { sysClockPer15mHisTable 1 }

    SysClockPer15mHisEntry ::=
        SEQUENCE {
            sysClockPer15mHisEid
                PerformanceEventType,
            sysClockPer15mHisParaLen
                Unsigned32,
            sysClockPer15mHisPara
                OCTET STRING,
            sysClockPer15mHisMonValue
                OCTET STRING,
            sysClockPer15mHisStartTime
                DateAndTime,
            sysClockPer15mHisEndTime
                DateAndTime,
            sysClockPer15mHisVldty
                ValidflagType
        }

    -- 1.3.6.1.4.1.2011.2.25.3.70.10.140.70.1.1
    sysClockPer15mHisEid OBJECT-TYPE
        SYNTAX PerformanceEventType
        MAX-ACCESS read-only
        STATUS current
        DESCRIPTION
            "perEid."
        ::= { sysClockPer15mHisEntry 1 }

    -- 1.3.6.1.4.1.2011.2.25.3.70.10.140.70.1.2
    sysClockPer15mHisParaLen OBJECT-TYPE
        SYNTAX Unsigned32
        MAX-ACCESS read-only
        STATUS current
        DESCRIPTION
            "perParaLen."
        ::= { sysClockPer15mHisEntry 2 }

    -- 1.3.6.1.4.1.2011.2.25.3.70.10.140.70.1.3
    sysClockPer15mHisPara OBJECT-TYPE
        SYNTAX OCTET STRING
        MAX-ACCESS read-only
        STATUS current
        DESCRIPTION
            "perPara."
        ::= { sysClockPer15mHisEntry 3 }

    -- 1.3.6.1.4.1.2011.2.25.3.70.10.140.70.1.4
    sysClockPer15mHisMonValue OBJECT-TYPE
        SYNTAX OCTET STRING
        MAX-ACCESS read-only
        STATUS current
        DESCRIPTION
            "perMonValue."
        ::= { sysClockPer15mHisEntry 4 }

    -- 1.3.6.1.4.1.2011.2.25.3.70.10.140.70.1.5
    sysClockPer15mHisStartTime OBJECT-TYPE
        SYNTAX DateAndTime
        MAX-ACCESS read-only
        STATUS current
        DESCRIPTION
            "perDateTimeStart."
        ::= { sysClockPer15mHisEntry 5 }

    -- 1.3.6.1.4.1.2011.2.25.3.70.10.140.70.1.6
    sysClockPer15mHisEndTime OBJECT-TYPE
        SYNTAX DateAndTime
        MAX-ACCESS read-only
        STATUS current
        DESCRIPTION
            "perDateTimeEnd."
        ::= { sysClockPer15mHisEntry 6 }

    -- 1.3.6.1.4.1.2011.2.25.3.70.10.140.70.1.7
    sysClockPer15mHisVldty OBJECT-TYPE
        SYNTAX ValidflagType
        MAX-ACCESS read-only
        STATUS current
        DESCRIPTION
            "perVldty."
        ::= { sysClockPer15mHisEntry 7 }

    -- 1.3.6.1.4.1.2011.2.25.3.70.10.140.80
    sysClockPer24hCurTable OBJECT-TYPE
        SYNTAX SEQUENCE OF SysClockPer24hCurEntry
        MAX-ACCESS not-accessible
        STATUS current
        DESCRIPTION
            "sysClockPer24hCur."
        ::= { sysClock 80 }

    -- 1.3.6.1.4.1.2011.2.25.3.70.10.140.80.1
    sysClockPer24hCurEntry OBJECT-TYPE
        SYNTAX SysClockPer24hCurEntry
        MAX-ACCESS not-accessible
        STATUS current
        DESCRIPTION
            "sysClockPer24hCur."
        INDEX{ sysClockPer24hCurEid,sysClockPer24hCurPara }
        ::= { sysClockPer24hCurTable 1 }

    SysClockPer24hCurEntry ::=
        SEQUENCE {
            sysClockPer24hCurEid
                PerformanceEventType,
            sysClockPer24hCurMonValue
                OCTET STRING,
            sysClockPer24hCurVldty
                ValidflagType,
            sysClockPer24hCurDatetime
                DateAndTime,
            sysClockPer24hCurParaLen
                Unsigned32,
            sysClockPer24hCurPara
                OCTET STRING
        }

    -- 1.3.6.1.4.1.2011.2.25.3.70.10.140.80.1.1
    sysClockPer24hCurEid OBJECT-TYPE
        SYNTAX PerformanceEventType
        MAX-ACCESS read-only
        STATUS current
        DESCRIPTION
            "perEid."
        ::= { sysClockPer24hCurEntry 1 }

    -- 1.3.6.1.4.1.2011.2.25.3.70.10.140.80.1.2
    sysClockPer24hCurMonValue OBJECT-TYPE
        SYNTAX OCTET STRING
        MAX-ACCESS read-only
        STATUS current
        DESCRIPTION
            "perMonValue."
        ::= { sysClockPer24hCurEntry 2 }

    -- 1.3.6.1.4.1.2011.2.25.3.70.10.140.80.1.3
    sysClockPer24hCurVldty OBJECT-TYPE
        SYNTAX ValidflagType
        MAX-ACCESS read-only
        STATUS current
        DESCRIPTION
            "perVldty."
        ::= { sysClockPer24hCurEntry 3 }

    -- 1.3.6.1.4.1.2011.2.25.3.70.10.140.80.1.4
    sysClockPer24hCurDatetime OBJECT-TYPE
        SYNTAX DateAndTime
        MAX-ACCESS read-only
        STATUS current
        DESCRIPTION
            "perDateTime."
        ::= { sysClockPer24hCurEntry 4 }

    -- 1.3.6.1.4.1.2011.2.25.3.70.10.140.80.1.5
    sysClockPer24hCurParaLen OBJECT-TYPE
        SYNTAX Unsigned32
        MAX-ACCESS read-only
        STATUS current
        DESCRIPTION
            "perParaLen."
        ::= { sysClockPer24hCurEntry 5 }

    -- 1.3.6.1.4.1.2011.2.25.3.70.10.140.80.1.6
    sysClockPer24hCurPara OBJECT-TYPE
        SYNTAX OCTET STRING
        MAX-ACCESS read-only
        STATUS current
        DESCRIPTION
            "perPara."
        ::= { sysClockPer24hCurEntry 6 }

    -- 1.3.6.1.4.1.2011.2.25.3.70.10.140.90
    sysClockPer24hHisTable OBJECT-TYPE
        SYNTAX SEQUENCE OF SysClockPer24hHisEntry
        MAX-ACCESS not-accessible
        STATUS current
        DESCRIPTION
            "sysClockPer24hHis."
        ::= { sysClock 90 }

    -- 1.3.6.1.4.1.2011.2.25.3.70.10.140.90.1
    sysClockPer24hHisEntry OBJECT-TYPE
        SYNTAX SysClockPer24hHisEntry
        MAX-ACCESS not-accessible
        STATUS current
        DESCRIPTION
            "sysClockPer24hHis."
        INDEX{ sysClockPer24hHisEid,sysClockPer24hHisParaLen,sysClockPer24hHisPara,sysClockPer24hHisStartTime,sysClockPer24hHisEndTime }
        ::= { sysClockPer24hHisTable 1 }

    SysClockPer24hHisEntry ::=
        SEQUENCE {
            sysClockPer24hHisEid
                PerformanceEventType,
            sysClockPer24hHisParaLen
                Unsigned32,
            sysClockPer24hHisPara
                OCTET STRING,
            sysClockPer24hHisMonValue
                OCTET STRING,
            sysClockPer24hHisStartTime
                DateAndTime,
            sysClockPer24hHisEndTime
                DateAndTime,
            sysClockPer24hHisVldty
                ValidflagType
        }

    -- 1.3.6.1.4.1.2011.2.25.3.70.10.140.90.1.1
    sysClockPer24hHisEid OBJECT-TYPE
        SYNTAX PerformanceEventType
        MAX-ACCESS read-only
        STATUS current
        DESCRIPTION
            "perEid."
        ::= { sysClockPer24hHisEntry 1 }

    -- 1.3.6.1.4.1.2011.2.25.3.70.10.140.90.1.2
    sysClockPer24hHisParaLen OBJECT-TYPE
        SYNTAX Unsigned32
        MAX-ACCESS read-only
        STATUS current
        DESCRIPTION
            "perParaLen."
        ::= { sysClockPer24hHisEntry 2 }

    -- 1.3.6.1.4.1.2011.2.25.3.70.10.140.90.1.3
    sysClockPer24hHisPara OBJECT-TYPE
        SYNTAX OCTET STRING
        MAX-ACCESS read-only
        STATUS current
        DESCRIPTION
            "perPara."
        ::= { sysClockPer24hHisEntry 3 }

    -- 1.3.6.1.4.1.2011.2.25.3.70.10.140.90.1.4
    sysClockPer24hHisMonValue OBJECT-TYPE
        SYNTAX OCTET STRING
        MAX-ACCESS read-only
        STATUS current
        DESCRIPTION
            "perMonValue."
        ::= { sysClockPer24hHisEntry 4 }

    -- 1.3.6.1.4.1.2011.2.25.3.70.10.140.90.1.5
    sysClockPer24hHisStartTime OBJECT-TYPE
        SYNTAX DateAndTime
        MAX-ACCESS read-only
        STATUS current
        DESCRIPTION
            "perDateTimeStart."
        ::= { sysClockPer24hHisEntry 5 }

    -- 1.3.6.1.4.1.2011.2.25.3.70.10.140.90.1.6
    sysClockPer24hHisEndTime OBJECT-TYPE
        SYNTAX DateAndTime
        MAX-ACCESS read-only
        STATUS current
        DESCRIPTION
            "perDateTimeEnd."
        ::= { sysClockPer24hHisEntry 6 }

    -- 1.3.6.1.4.1.2011.2.25.3.70.10.140.90.1.7
    sysClockPer24hHisVldty OBJECT-TYPE
        SYNTAX ValidflagType
        MAX-ACCESS read-only
        STATUS current
        DESCRIPTION
            "perVldty."
        ::= { sysClockPer24hHisEntry 7 }

    -- 1.3.6.1.4.1.2011.2.25.3.70.10.150
    cpriport OBJECT IDENTIFIER ::= { rtnPerformance 150 }

    -- 1.3.6.1.4.1.2011.2.25.3.70.10.150.60
    cpriportPer15mCurTable OBJECT-TYPE
        SYNTAX SEQUENCE OF CpriportPer15mCurEntry
        MAX-ACCESS not-accessible
        STATUS current
        DESCRIPTION
            "Current 15-minute performance of CPRI port"
        ::= { cpriport 60 }

    -- 1.3.6.1.4.1.2011.2.25.3.70.10.150.60.1
    cpriportPer15mCurEntry OBJECT-TYPE
        SYNTAX CpriportPer15mCurEntry
        MAX-ACCESS not-accessible
        STATUS current
        DESCRIPTION
            "Current 15-minute performance of CPRI port"
        INDEX{ cpriportPer15mCurPara }
        ::= { cpriportPer15mCurTable 1 }

    CpriportPer15mCurEntry ::=
        SEQUENCE {
            cpriportPer15mCurEid
                PerformanceEventType,
            cpriportPer15mCurMonValue
                OCTET STRING,
            cpriportPer15mCurVldty
                ValidflagType,
            cpriportPer15mCurDatetime
                DateAndTime,
            cpriportPer15mCurParaLen
                Unsigned32,
            cpriportPer15mCurPara
                OCTET STRING
        }

    -- 1.3.6.1.4.1.2011.2.25.3.70.10.150.60.1.1
    cpriportPer15mCurEid OBJECT-TYPE
        SYNTAX PerformanceEventType
        MAX-ACCESS read-only
        STATUS current
        DESCRIPTION
            "Event ID of a current 15-minute performance of CPRI port"
        ::= { cpriportPer15mCurEntry 1 }

    -- 1.3.6.1.4.1.2011.2.25.3.70.10.150.60.1.2
    cpriportPer15mCurMonValue OBJECT-TYPE
        SYNTAX OCTET STRING
        MAX-ACCESS read-only
        STATUS current
        DESCRIPTION
            "Statistics of current 15-minute performance of CPRI port"
        ::= { cpriportPer15mCurEntry 2 }

    -- 1.3.6.1.4.1.2011.2.25.3.70.10.150.60.1.3
    cpriportPer15mCurVldty OBJECT-TYPE
        SYNTAX ValidflagType
        MAX-ACCESS read-only
        STATUS current
        DESCRIPTION
            "Validity flag of current 15-minute performance of CPRI port"
        ::= { cpriportPer15mCurEntry 3 }

    -- 1.3.6.1.4.1.2011.2.25.3.70.10.150.60.1.4
    cpriportPer15mCurDatetime OBJECT-TYPE
        SYNTAX DateAndTime
        MAX-ACCESS read-only
        STATUS current
        DESCRIPTION
            "Time information of current 15-minute performance of CPRI port"
        ::= { cpriportPer15mCurEntry 4 }

    -- 1.3.6.1.4.1.2011.2.25.3.70.10.150.60.1.5
    cpriportPer15mCurParaLen OBJECT-TYPE
        SYNTAX Unsigned32
        MAX-ACCESS read-only
        STATUS current
        DESCRIPTION
            "Parameter length of current 15-minute performance of CPRI port"
        ::= { cpriportPer15mCurEntry 5 }

    -- 1.3.6.1.4.1.2011.2.25.3.70.10.150.60.1.6
    cpriportPer15mCurPara OBJECT-TYPE
        SYNTAX OCTET STRING
        MAX-ACCESS read-only
        STATUS current
        DESCRIPTION
            "Parameters of current 15-minute performance of CPRI port"
        ::= { cpriportPer15mCurEntry 6 }

    -- 1.3.6.1.4.1.2011.2.25.3.70.10.150.70
    cpriportPer15mHisTable OBJECT-TYPE
        SYNTAX SEQUENCE OF CpriportPer15mHisEntry
        MAX-ACCESS not-accessible
        STATUS current
        DESCRIPTION
            "Historical 15-minute performance of CPRI port"
        ::= { cpriport 70 }

    -- 1.3.6.1.4.1.2011.2.25.3.70.10.150.70.1
    cpriportPer15mHisEntry OBJECT-TYPE
        SYNTAX CpriportPer15mHisEntry
        MAX-ACCESS not-accessible
        STATUS current
        DESCRIPTION
            "Historical 15-minute performance of CPRI port"
        INDEX{ cpriportPer15mHisEid,cpriportPer15mHisParaLen,cpriportPer15mHisPara,cpriportPer15mHisStartTime,cpriportPer15mHisEndTime }
        ::= { cpriportPer15mHisTable 1 }

    CpriportPer15mHisEntry ::=
        SEQUENCE {
            cpriportPer15mHisEid
                PerformanceEventType,
            cpriportPer15mHisParaLen
                Unsigned32,
            cpriportPer15mHisPara
                OCTET STRING,
            cpriportPer15mHisMonValue
                OCTET STRING,
            cpriportPer15mHisStartTime
                DateAndTime,
            cpriportPer15mHisEndTime
                DateAndTime,
            cpriportPer15mHisVldty
                ValidflagType
        }

    -- 1.3.6.1.4.1.2011.2.25.3.70.10.150.70.1.1
    cpriportPer15mHisEid OBJECT-TYPE
        SYNTAX PerformanceEventType
        MAX-ACCESS read-only
        STATUS current
        DESCRIPTION
            "Event ID of a historical 15-minute performance of CPRI port"
        ::= { cpriportPer15mHisEntry 1 }

    -- 1.3.6.1.4.1.2011.2.25.3.70.10.150.70.1.2
    cpriportPer15mHisParaLen OBJECT-TYPE
        SYNTAX Unsigned32
        MAX-ACCESS read-only
        STATUS current
        DESCRIPTION
            "Parameter length of historical 15-minute performance of CPRI port"
        ::= { cpriportPer15mHisEntry 2 }

    -- 1.3.6.1.4.1.2011.2.25.3.70.10.150.70.1.3
    cpriportPer15mHisPara OBJECT-TYPE
        SYNTAX OCTET STRING
        MAX-ACCESS read-only
        STATUS current
        DESCRIPTION
            "Parameters of historical 15-minute performance of CPRI port"
        ::= { cpriportPer15mHisEntry 3 }

    -- 1.3.6.1.4.1.2011.2.25.3.70.10.150.70.1.4
    cpriportPer15mHisMonValue OBJECT-TYPE
        SYNTAX OCTET STRING
        MAX-ACCESS read-only
        STATUS current
        DESCRIPTION
            "Statistics of historical 15-minute performance of CPRI port"
        ::= { cpriportPer15mHisEntry 4 }

    -- 1.3.6.1.4.1.2011.2.25.3.70.10.150.70.1.5
    cpriportPer15mHisStartTime OBJECT-TYPE
        SYNTAX DateAndTime
        MAX-ACCESS read-only
        STATUS current
        DESCRIPTION
            "Start time of historical 15-minute performance of CPRI port"
        ::= { cpriportPer15mHisEntry 5 }

    -- 1.3.6.1.4.1.2011.2.25.3.70.10.150.70.1.6
    cpriportPer15mHisEndTime OBJECT-TYPE
        SYNTAX DateAndTime
        MAX-ACCESS read-only
        STATUS current
        DESCRIPTION
            "End time of historical 15-minute performance of CPRI port"
        ::= { cpriportPer15mHisEntry 6 }

    -- 1.3.6.1.4.1.2011.2.25.3.70.10.150.70.1.7
    cpriportPer15mHisVldty OBJECT-TYPE
        SYNTAX ValidflagType
        MAX-ACCESS read-only
        STATUS current
        DESCRIPTION
            "Validity flag of historical 15-minute performance of CPRI port"
        ::= { cpriportPer15mHisEntry 7 }

    -- 1.3.6.1.4.1.2011.2.25.3.70.10.150.80
    cpriportPer24hCurTable OBJECT-TYPE
        SYNTAX SEQUENCE OF CpriportPer24hCurEntry
        MAX-ACCESS not-accessible
        STATUS current
        DESCRIPTION
            "Current 24-hour performance of CPRI port"
        ::= { cpriport 80 }

    -- 1.3.6.1.4.1.2011.2.25.3.70.10.150.80.1
    cpriportPer24hCurEntry OBJECT-TYPE
        SYNTAX CpriportPer24hCurEntry
        MAX-ACCESS not-accessible
        STATUS current
        DESCRIPTION
            "Current 24-hour performance of CPRI port"
        INDEX{ cpriportPer24hCurEid,cpriportPer24hCurPara }
        ::= { cpriportPer24hCurTable 1 }

    CpriportPer24hCurEntry ::=
        SEQUENCE {
            cpriportPer24hCurEid
                PerformanceEventType,
            cpriportPer24hCurMonValue
                OCTET STRING,
            cpriportPer24hCurVldty
                ValidflagType,
            cpriportPer24hCurDatetime
                DateAndTime,
            cpriportPer24hCurParaLen
                Unsigned32,
            cpriportPer24hCurPara
                OCTET STRING
        }

    -- 1.3.6.1.4.1.2011.2.25.3.70.10.150.80.1.1
    cpriportPer24hCurEid OBJECT-TYPE
        SYNTAX PerformanceEventType
        MAX-ACCESS read-only
        STATUS current
        DESCRIPTION
            "Event ID of a current 24-hour performance of CPRI port"
        ::= { cpriportPer24hCurEntry 1 }

    -- 1.3.6.1.4.1.2011.2.25.3.70.10.150.80.1.2
    cpriportPer24hCurMonValue OBJECT-TYPE
        SYNTAX OCTET STRING
        MAX-ACCESS read-only
        STATUS current
        DESCRIPTION
            "Statistics of current 24-hour performance of CPRI port"
        ::= { cpriportPer24hCurEntry 2 }

    -- 1.3.6.1.4.1.2011.2.25.3.70.10.150.80.1.3
    cpriportPer24hCurVldty OBJECT-TYPE
        SYNTAX ValidflagType
        MAX-ACCESS read-only
        STATUS current
        DESCRIPTION
            "Validity flag of current 24-hour performance of CPRI port"
        ::= { cpriportPer24hCurEntry 3 }

    -- 1.3.6.1.4.1.2011.2.25.3.70.10.150.80.1.4
    cpriportPer24hCurDatetime OBJECT-TYPE
        SYNTAX DateAndTime
        MAX-ACCESS read-only
        STATUS current
        DESCRIPTION
            "Time information of current 24-hour performance of CPRI port"
        ::= { cpriportPer24hCurEntry 4 }

    -- 1.3.6.1.4.1.2011.2.25.3.70.10.150.80.1.5
    cpriportPer24hCurParaLen OBJECT-TYPE
        SYNTAX Unsigned32
        MAX-ACCESS read-only
        STATUS current
        DESCRIPTION
            "Parameter length of current 24-hour performance of CPRI port"
        ::= { cpriportPer24hCurEntry 5 }

    -- 1.3.6.1.4.1.2011.2.25.3.70.10.150.80.1.6
    cpriportPer24hCurPara OBJECT-TYPE
        SYNTAX OCTET STRING
        MAX-ACCESS read-only
        STATUS current
        DESCRIPTION
            "Parameters of current 24-hour performance of CPRI port"
        ::= { cpriportPer24hCurEntry 6 }

    -- 1.3.6.1.4.1.2011.2.25.3.70.10.150.90
    cpriportPer24hHisTable OBJECT-TYPE
        SYNTAX SEQUENCE OF CpriportPer24hHisEntry
        MAX-ACCESS not-accessible
        STATUS current
        DESCRIPTION
            "Historical 24-hour performance of CPRI port"
        ::= { cpriport 90 }

    -- 1.3.6.1.4.1.2011.2.25.3.70.10.150.90.1
    cpriportPer24hHisEntry OBJECT-TYPE
        SYNTAX CpriportPer24hHisEntry
        MAX-ACCESS not-accessible
        STATUS current
        DESCRIPTION
            "Historical 24-hour performance of CPRI port"
        INDEX{ cpriportPer24hHisEid,cpriportPer24hHisParaLen,cpriportPer24hHisPara,cpriportPer24hHisStartTime,cpriportPer24hHisEndTime }
        ::= { cpriportPer24hHisTable 1 }

    CpriportPer24hHisEntry ::=
        SEQUENCE {
            cpriportPer24hHisEid
                PerformanceEventType,
            cpriportPer24hHisParaLen
                Unsigned32,
            cpriportPer24hHisPara
                OCTET STRING,
            cpriportPer24hHisMonValue
                OCTET STRING,
            cpriportPer24hHisStartTime
                DateAndTime,
            cpriportPer24hHisEndTime
                DateAndTime,
            cpriportPer24hHisVldty
                ValidflagType
        }

    -- 1.3.6.1.4.1.2011.2.25.3.70.10.150.90.1.1
    cpriportPer24hHisEid OBJECT-TYPE
        SYNTAX PerformanceEventType
        MAX-ACCESS read-only
        STATUS current
        DESCRIPTION
            "Event ID of a historical 24-hour performance of CPRI port"
        ::= { cpriportPer24hHisEntry 1 }

    -- 1.3.6.1.4.1.2011.2.25.3.70.10.150.90.1.2
    cpriportPer24hHisParaLen OBJECT-TYPE
        SYNTAX Unsigned32
        MAX-ACCESS read-only
        STATUS current
        DESCRIPTION
            "Parameter length of historical 24-hour performance of CPRI port"
        ::= { cpriportPer24hHisEntry 2 }

    -- 1.3.6.1.4.1.2011.2.25.3.70.10.150.90.1.3
    cpriportPer24hHisPara OBJECT-TYPE
        SYNTAX OCTET STRING
        MAX-ACCESS read-only
        STATUS current
        DESCRIPTION
            "Parameters of historical 24-hour performance of CPRI port"
        ::= { cpriportPer24hHisEntry 3 }

    -- 1.3.6.1.4.1.2011.2.25.3.70.10.150.90.1.4
    cpriportPer24hHisMonValue OBJECT-TYPE
        SYNTAX OCTET STRING
        MAX-ACCESS read-only
        STATUS current
        DESCRIPTION
            "Statistics of historical 24-hour performance of CPRI port"
        ::= { cpriportPer24hHisEntry 4 }

    -- 1.3.6.1.4.1.2011.2.25.3.70.10.150.90.1.5
    cpriportPer24hHisStartTime OBJECT-TYPE
        SYNTAX DateAndTime
        MAX-ACCESS read-only
        STATUS current
        DESCRIPTION
            "Start time of historical 24-hour performance of CPRI port"
        ::= { cpriportPer24hHisEntry 5 }

    -- 1.3.6.1.4.1.2011.2.25.3.70.10.150.90.1.6
    cpriportPer24hHisEndTime OBJECT-TYPE
        SYNTAX DateAndTime
        MAX-ACCESS read-only
        STATUS current
        DESCRIPTION
            "End time of historical 24-hour performance of CPRI port"
        ::= { cpriportPer24hHisEntry 6 }

    -- 1.3.6.1.4.1.2011.2.25.3.70.10.150.90.1.7
    cpriportPer24hHisVldty OBJECT-TYPE
        SYNTAX ValidflagType
        MAX-ACCESS read-only
        STATUS current
        DESCRIPTION
            "Validity flag of historical 24-hour performance of CPRI port"
        ::= { cpriportPer24hHisEntry 7 }

    -- 1.3.6.1.4.1.2011.2.25.3.70.10.170
    obsailaser OBJECT IDENTIFIER ::= { rtnPerformance 170 }

    -- 1.3.6.1.4.1.2011.2.25.3.70.10.170.60
    obsailaserPer15mCurTable OBJECT-TYPE
        SYNTAX SEQUENCE OF ObsailaserPer15mCurEntry
        MAX-ACCESS not-accessible
        STATUS current
        DESCRIPTION
            "Current 15-minute performance of  OBSAI laser"
        ::= { obsailaser 60 }

    -- 1.3.6.1.4.1.2011.2.25.3.70.10.170.60.1
    obsailaserPer15mCurEntry OBJECT-TYPE
        SYNTAX ObsailaserPer15mCurEntry
        MAX-ACCESS not-accessible
        STATUS current
        DESCRIPTION
            "Current 15-minute performance of OBSAI laser"
        INDEX{ obsailaserPer15mCurPara }
        ::= { obsailaserPer15mCurTable 1 }

    ObsailaserPer15mCurEntry ::=
        SEQUENCE {
            obsailaserPer15mCurEid
                PerformanceEventType,
            obsailaserPer15mCurMonValue
                OCTET STRING,
            obsailaserPer15mCurVldty
                ValidflagType,
            obsailaserPer15mCurDatetime
                DateAndTime,
            obsailaserPer15mCurParaLen
                Unsigned32,
            obsailaserPer15mCurPara
                OCTET STRING
        }

    -- 1.3.6.1.4.1.2011.2.25.3.70.10.170.60.1.1
    obsailaserPer15mCurEid OBJECT-TYPE
        SYNTAX PerformanceEventType
        MAX-ACCESS read-only
        STATUS current
        DESCRIPTION
            "Event ID of a current 15-minute performanceof OBSAI laser"
        ::= { obsailaserPer15mCurEntry 1 }

    -- 1.3.6.1.4.1.2011.2.25.3.70.10.170.60.1.2
    obsailaserPer15mCurMonValue OBJECT-TYPE
        SYNTAX OCTET STRING
        MAX-ACCESS read-only
        STATUS current
        DESCRIPTION
            "Statistics of current 15-minute performance of OBSAI laser"
        ::= { obsailaserPer15mCurEntry 2 }

    -- 1.3.6.1.4.1.2011.2.25.3.70.10.170.60.1.3
    obsailaserPer15mCurVldty OBJECT-TYPE
        SYNTAX ValidflagType
        MAX-ACCESS read-only
        STATUS current
        DESCRIPTION
            "Validity flag of current 15-minute performance of  OBSAI laser"
        ::= { obsailaserPer15mCurEntry 3 }

    -- 1.3.6.1.4.1.2011.2.25.3.70.10.170.60.1.4
    obsailaserPer15mCurDatetime OBJECT-TYPE
        SYNTAX DateAndTime
        MAX-ACCESS read-only
        STATUS current
        DESCRIPTION
            "Time information of current 15-minute performance of  OBSAI laser"
        ::= { obsailaserPer15mCurEntry 4 }

    -- 1.3.6.1.4.1.2011.2.25.3.70.10.170.60.1.5
    obsailaserPer15mCurParaLen OBJECT-TYPE
        SYNTAX Unsigned32
        MAX-ACCESS read-only
        STATUS current
        DESCRIPTION
            "Parameter length of current 15-minute performance of  OBSAI laser"
        ::= { obsailaserPer15mCurEntry 5 }

    -- 1.3.6.1.4.1.2011.2.25.3.70.10.170.60.1.6
    obsailaserPer15mCurPara OBJECT-TYPE
        SYNTAX OCTET STRING
        MAX-ACCESS read-only
        STATUS current
        DESCRIPTION
            "Parameters of current 15-minute performance of  OBSAI laser"
        ::= { obsailaserPer15mCurEntry 6 }

    -- 1.3.6.1.4.1.2011.2.25.3.70.10.170.70
    obsailaserPer15mHisTable OBJECT-TYPE
        SYNTAX SEQUENCE OF ObsailaserPer15mHisEntry
        MAX-ACCESS not-accessible
        STATUS current
        DESCRIPTION
            "Historical 15-minute performance of  OBSAI laser"
        ::= { obsailaser 70 }

    -- 1.3.6.1.4.1.2011.2.25.3.70.10.170.70.1
    obsailaserPer15mHisEntry OBJECT-TYPE
        SYNTAX ObsailaserPer15mHisEntry
        MAX-ACCESS not-accessible
        STATUS current
        DESCRIPTION
            "Historical 15-minute performance of  OBSAI laser"
        INDEX{ obsailaserPer15mHisEid, obsailaserPer15mHisParaLen, obsailaserPer15mHisPara, obsailaserPer15mHisStartTime, obsailaserPer15mHisEndTime }
        ::= { obsailaserPer15mHisTable 1 }

    ObsailaserPer15mHisEntry ::=
        SEQUENCE {
            obsailaserPer15mHisEid
                PerformanceEventType,
            obsailaserPer15mHisParaLen
                Unsigned32,
            obsailaserPer15mHisPara
                OCTET STRING,
            obsailaserPer15mHisMonValue
                OCTET STRING,
            obsailaserPer15mHisStartTime
                DateAndTime,
            obsailaserPer15mHisEndTime
                DateAndTime,
            obsailaserPer15mHisVldty
                ValidflagType
        }

    -- 1.3.6.1.4.1.2011.2.25.3.70.10.170.70.1.1
    obsailaserPer15mHisEid OBJECT-TYPE
        SYNTAX PerformanceEventType
        MAX-ACCESS read-only
        STATUS current
        DESCRIPTION
            "Event ID of a historical 15-minute performance of OBSAI laser"
        ::= { obsailaserPer15mHisEntry 1 }

    -- 1.3.6.1.4.1.2011.2.25.3.70.10.170.70.1.2
    obsailaserPer15mHisParaLen OBJECT-TYPE
        SYNTAX Unsigned32
        MAX-ACCESS read-only
        STATUS current
        DESCRIPTION
            "Parameter length of historical 15-minute performance of  OBSAI laser"
        ::= { obsailaserPer15mHisEntry 2 }

    -- 1.3.6.1.4.1.2011.2.25.3.70.10.170.70.1.3
    obsailaserPer15mHisPara OBJECT-TYPE
        SYNTAX OCTET STRING
        MAX-ACCESS read-only
        STATUS current
        DESCRIPTION
            "Parameters of historical 15-minute performance of  OBSAI laser"
        ::= { obsailaserPer15mHisEntry 3 }

    -- 1.3.6.1.4.1.2011.2.25.3.70.10.170.70.1.4
    obsailaserPer15mHisMonValue OBJECT-TYPE
        SYNTAX OCTET STRING
        MAX-ACCESS read-only
        STATUS current
        DESCRIPTION
            "Statistics of historical 15-minute performance of OBSAI laser"
        ::= { obsailaserPer15mHisEntry 4 }

    -- 1.3.6.1.4.1.2011.2.25.3.70.10.170.70.1.5
    obsailaserPer15mHisStartTime OBJECT-TYPE
        SYNTAX DateAndTime
        MAX-ACCESS read-only
        STATUS current
        DESCRIPTION
            "Start time of historical 15-minute performance of  OBSAI laser"
        ::= { obsailaserPer15mHisEntry 5 }

    -- 1.3.6.1.4.1.2011.2.25.3.70.10.170.70.1.6
    obsailaserPer15mHisEndTime OBJECT-TYPE
        SYNTAX DateAndTime
        MAX-ACCESS read-only
        STATUS current
        DESCRIPTION
            "End time of historical 15-minute performance of  OBSAI laser"
        ::= { obsailaserPer15mHisEntry 6 }

    -- 1.3.6.1.4.1.2011.2.25.3.70.10.170.70.1.7
    obsailaserPer15mHisVldty OBJECT-TYPE
        SYNTAX ValidflagType
        MAX-ACCESS read-only
        STATUS current
        DESCRIPTION
            "Validity flag of historical 15-minute performance of  OBSAI laser"
        ::= { obsailaserPer15mHisEntry 7 }

    -- 1.3.6.1.4.1.2011.2.25.3.70.10.170.80
    obsailaserPer24hCurTable OBJECT-TYPE
        SYNTAX SEQUENCE OF ObsailaserPer24hCurEntry
        MAX-ACCESS not-accessible
        STATUS current
        DESCRIPTION
            "Current 24-hour performance of  OBSAI laser"
        ::= { obsailaser 80 }

    -- 1.3.6.1.4.1.2011.2.25.3.70.10.170.80.1
    obsailaserPer24hCurEntry OBJECT-TYPE
        SYNTAX ObsailaserPer24hCurEntry
        MAX-ACCESS not-accessible
        STATUS current
        DESCRIPTION
            "Current 24-hour performance of  OBSAI laser"
        INDEX{ obsailaserPer24hCurEid, obsailaserPer24hCurPara }
        ::= { obsailaserPer24hCurTable 1 }

    ObsailaserPer24hCurEntry ::=
        SEQUENCE {
            obsailaserPer24hCurEid
                PerformanceEventType,
            obsailaserPer24hCurMonValue
                OCTET STRING,
            obsailaserPer24hCurVldty
                ValidflagType,
            obsailaserPer24hCurDatetime
                DateAndTime,
            obsailaserPer24hCurParaLen
                Unsigned32,
            obsailaserPer24hCurPara
                OCTET STRING
        }

    -- 1.3.6.1.4.1.2011.2.25.3.70.10.170.80.1.1
    obsailaserPer24hCurEid OBJECT-TYPE
        SYNTAX PerformanceEventType
        MAX-ACCESS read-only
        STATUS current
        DESCRIPTION
            "Event ID of a current 24-hour performance of OBSAI laser"
        ::= { obsailaserPer24hCurEntry 1 }

    -- 1.3.6.1.4.1.2011.2.25.3.70.10.170.80.1.2
    obsailaserPer24hCurMonValue OBJECT-TYPE
        SYNTAX OCTET STRING
        MAX-ACCESS read-only
        STATUS current
        DESCRIPTION
            "Statistics of current 24-hour performance of OBSAI laser"
        ::= { obsailaserPer24hCurEntry 2 }

    -- 1.3.6.1.4.1.2011.2.25.3.70.10.170.80.1.3
    obsailaserPer24hCurVldty OBJECT-TYPE
        SYNTAX ValidflagType
        MAX-ACCESS read-only
        STATUS current
        DESCRIPTION
            "Validity flag of current 24-hour performance of  OBSAI laser"
        ::= { obsailaserPer24hCurEntry 3 }

    -- 1.3.6.1.4.1.2011.2.25.3.70.10.170.80.1.4
    obsailaserPer24hCurDatetime OBJECT-TYPE
        SYNTAX DateAndTime
        MAX-ACCESS read-only
        STATUS current
        DESCRIPTION
            "Time information of current 24-hour performance of  OBSAI laser"
        ::= { obsailaserPer24hCurEntry 4 }

    -- 1.3.6.1.4.1.2011.2.25.3.70.10.170.80.1.5
    obsailaserPer24hCurParaLen OBJECT-TYPE
        SYNTAX Unsigned32
        MAX-ACCESS read-only
        STATUS current
        DESCRIPTION
            "Parameter length of current 24-hour performance of  OBSAI laser"
        ::= { obsailaserPer24hCurEntry 5 }

    -- 1.3.6.1.4.1.2011.2.25.3.70.10.170.80.1.6
    obsailaserPer24hCurPara OBJECT-TYPE
        SYNTAX OCTET STRING
        MAX-ACCESS read-only
        STATUS current
        DESCRIPTION
            "Parameters of current 24-hour performance of  OBSAI laser"
        ::= { obsailaserPer24hCurEntry 6 }

    -- 1.3.6.1.4.1.2011.2.25.3.70.10.170.90
    obsailaserPer24hHisTable OBJECT-TYPE
        SYNTAX SEQUENCE OF ObsailaserPer24hHisEntry
        MAX-ACCESS not-accessible
        STATUS current
        DESCRIPTION
            "Historical 24-hour performance of  OBSAI laser"
        ::= { obsailaser 90 }

    -- 1.3.6.1.4.1.2011.2.25.3.70.10.170.90.1
    obsailaserPer24hHisEntry OBJECT-TYPE
        SYNTAX ObsailaserPer24hHisEntry
        MAX-ACCESS not-accessible
        STATUS current
        DESCRIPTION
            "Historical 24-hour performance of  OBSAI laser"
        INDEX{ obsailaserPer24hHisEid, obsailaserPer24hHisParaLen, obsailaserPer24hHisPara, obsailaserPer24hHisStartTime, obsailaserPer24hHisEndTime }
        ::= { obsailaserPer24hHisTable 1 }

    ObsailaserPer24hHisEntry ::=
        SEQUENCE {
            obsailaserPer24hHisEid
                PerformanceEventType,
            obsailaserPer24hHisParaLen
                Unsigned32,
            obsailaserPer24hHisPara
                OCTET STRING,
            obsailaserPer24hHisMonValue
                OCTET STRING,
            obsailaserPer24hHisStartTime
                DateAndTime,
            obsailaserPer24hHisEndTime
                DateAndTime,
            obsailaserPer24hHisVldty
                ValidflagType
        }

    -- 1.3.6.1.4.1.2011.2.25.3.70.10.170.90.1.1
    obsailaserPer24hHisEid OBJECT-TYPE
        SYNTAX PerformanceEventType
        MAX-ACCESS read-only
        STATUS current
        DESCRIPTION
            "Event ID of a historical 24-hour performance of OBSAI laser"
        ::= { obsailaserPer24hHisEntry 1 }

    -- 1.3.6.1.4.1.2011.2.25.3.70.10.170.90.1.2
    obsailaserPer24hHisParaLen OBJECT-TYPE
        SYNTAX Unsigned32
        MAX-ACCESS read-only
        STATUS current
        DESCRIPTION
            "Parameter length of historical 24-hour performance of  OBSAI laser"
        ::= { obsailaserPer24hHisEntry 2 }

    -- 1.3.6.1.4.1.2011.2.25.3.70.10.170.90.1.3
    obsailaserPer24hHisPara OBJECT-TYPE
        SYNTAX OCTET STRING
        MAX-ACCESS read-only
        STATUS current
        DESCRIPTION
            "Parameters of historical 24-hour performance of  OBSAI laser"
        ::= { obsailaserPer24hHisEntry 3 }

    -- 1.3.6.1.4.1.2011.2.25.3.70.10.170.90.1.4
    obsailaserPer24hHisMonValue OBJECT-TYPE
        SYNTAX OCTET STRING
        MAX-ACCESS read-only
        STATUS current
        DESCRIPTION
            "Statistics of historical 24-hour performance of OBSAI laser"
        ::= { obsailaserPer24hHisEntry 4 }

    -- 1.3.6.1.4.1.2011.2.25.3.70.10.170.90.1.5
    obsailaserPer24hHisStartTime OBJECT-TYPE
        SYNTAX DateAndTime
        MAX-ACCESS read-only
        STATUS current
        DESCRIPTION
            "Start time of historical 24-hour performance of  OBSAI laser"
        ::= { obsailaserPer24hHisEntry 5 }

    -- 1.3.6.1.4.1.2011.2.25.3.70.10.170.90.1.6
    obsailaserPer24hHisEndTime OBJECT-TYPE
        SYNTAX DateAndTime
        MAX-ACCESS read-only
        STATUS current
        DESCRIPTION
            "End time of historical 24-hour performance of OBSAI laser"
        ::= { obsailaserPer24hHisEntry 6 }

    -- 1.3.6.1.4.1.2011.2.25.3.70.10.170.90.1.7
    obsailaserPer24hHisVldty OBJECT-TYPE
        SYNTAX ValidflagType
        MAX-ACCESS read-only
        STATUS current
        DESCRIPTION
            "Validity flag of historical 24-hour performance of  OBSAI laser"
        ::= { obsailaserPer24hHisEntry 7 }

    -- 1.3.6.1.4.1.2011.2.25.3.70.10.180
    obsaiport OBJECT IDENTIFIER ::= { rtnPerformance 180 }

    -- 1.3.6.1.4.1.2011.2.25.3.70.10.180.60
    obsaiportPer15mCurTable OBJECT-TYPE
        SYNTAX SEQUENCE OF ObsaiportPer15mCurEntry
        MAX-ACCESS not-accessible
        STATUS current
        DESCRIPTION
            "Current 15-minute performance of OBSAI port"
        ::= { obsaiport 60 }

    -- 1.3.6.1.4.1.2011.2.25.3.70.10.180.60.1
    obsaiportPer15mCurEntry OBJECT-TYPE
        SYNTAX ObsaiportPer15mCurEntry
        MAX-ACCESS not-accessible
        STATUS current
        DESCRIPTION
            "Current 15-minute performance of OBSAI port"
        INDEX{ obsaiportPer15mCurPara }
        ::= { obsaiportPer15mCurTable 1 }

    ObsaiportPer15mCurEntry ::=
        SEQUENCE {
            obsaiportPer15mCurEid
                PerformanceEventType,
            obsaiportPer15mCurMonValue
                OCTET STRING,
            obsaiportPer15mCurVldty
                ValidflagType,
            obsaiportPer15mCurDatetime
                DateAndTime,
            obsaiportPer15mCurParaLen
                Unsigned32,
            obsaiportPer15mCurPara
                OCTET STRING
        }

    -- 1.3.6.1.4.1.2011.2.25.3.70.10.180.60.1.1
    obsaiportPer15mCurEid OBJECT-TYPE
        SYNTAX PerformanceEventType
        MAX-ACCESS read-only
        STATUS current
        DESCRIPTION
            "Event ID of a current 15-minute performance of OBSAI port"
        ::= { obsaiportPer15mCurEntry 1 }

    -- 1.3.6.1.4.1.2011.2.25.3.70.10.180.60.1.2
    obsaiportPer15mCurMonValue OBJECT-TYPE
        SYNTAX OCTET STRING
        MAX-ACCESS read-only
        STATUS current
        DESCRIPTION
            "Statistics of current 15-minute performance of OBSAI port"
        ::= { obsaiportPer15mCurEntry 2 }

    -- 1.3.6.1.4.1.2011.2.25.3.70.10.180.60.1.3
    obsaiportPer15mCurVldty OBJECT-TYPE
        SYNTAX ValidflagType
        MAX-ACCESS read-only
        STATUS current
        DESCRIPTION
            "Validity flag of current 15-minute performance of OBSAI port"
        ::= { obsaiportPer15mCurEntry 3 }

    -- 1.3.6.1.4.1.2011.2.25.3.70.10.180.60.1.4
    obsaiportPer15mCurDatetime OBJECT-TYPE
        SYNTAX DateAndTime
        MAX-ACCESS read-only
        STATUS current
        DESCRIPTION
            "Time information of current 15-minute performance of OBSAI port"
        ::= { obsaiportPer15mCurEntry 4 }

    -- 1.3.6.1.4.1.2011.2.25.3.70.10.180.60.1.5
    obsaiportPer15mCurParaLen OBJECT-TYPE
        SYNTAX Unsigned32
        MAX-ACCESS read-only
        STATUS current
        DESCRIPTION
            "Parameter length of current 15-minute performance of OBSAI port"
        ::= { obsaiportPer15mCurEntry 5 }

    -- 1.3.6.1.4.1.2011.2.25.3.70.10.180.60.1.6
    obsaiportPer15mCurPara OBJECT-TYPE
        SYNTAX OCTET STRING
        MAX-ACCESS read-only
        STATUS current
        DESCRIPTION
            "Parameters of current 15-minute performance of OBSAI port"
        ::= { obsaiportPer15mCurEntry 6 }

    -- 1.3.6.1.4.1.2011.2.25.3.70.10.180.70
    obsaiportPer15mHisTable OBJECT-TYPE
        SYNTAX SEQUENCE OF ObsaiportPer15mHisEntry
        MAX-ACCESS not-accessible
        STATUS current
        DESCRIPTION
            "Historical 15-minute performance of OBSAI port"
        ::= { obsaiport 70 }

    -- 1.3.6.1.4.1.2011.2.25.3.70.10.180.70.1
    obsaiportPer15mHisEntry OBJECT-TYPE
        SYNTAX ObsaiportPer15mHisEntry
        MAX-ACCESS not-accessible
        STATUS current
        DESCRIPTION
            "Historical 15-minute performance of OBSAI port"
        INDEX{ obsaiportPer15mHisEid,obsaiportPer15mHisParaLen,obsaiportPer15mHisPara,obsaiportPer15mHisStartTime,obsaiportPer15mHisEndTime }
        ::= { obsaiportPer15mHisTable 1 }

    ObsaiportPer15mHisEntry ::=
        SEQUENCE {
            obsaiportPer15mHisEid
                PerformanceEventType,
            obsaiportPer15mHisParaLen
                Unsigned32,
            obsaiportPer15mHisPara
                OCTET STRING,
            obsaiportPer15mHisMonValue
                OCTET STRING,
            obsaiportPer15mHisStartTime
                DateAndTime,
            obsaiportPer15mHisEndTime
                DateAndTime,
            obsaiportPer15mHisVldty
                ValidflagType
        }

    -- 1.3.6.1.4.1.2011.2.25.3.70.10.180.70.1.1
    obsaiportPer15mHisEid OBJECT-TYPE
        SYNTAX PerformanceEventType
        MAX-ACCESS read-only
        STATUS current
        DESCRIPTION
            "Event ID of a historical 15-minute performance of OBSAI port"
        ::= { obsaiportPer15mHisEntry 1 }

    -- 1.3.6.1.4.1.2011.2.25.3.70.10.180.70.1.2
    obsaiportPer15mHisParaLen OBJECT-TYPE
        SYNTAX Unsigned32
        MAX-ACCESS read-only
        STATUS current
        DESCRIPTION
            "Parameter length of historical 15-minute performance of OBSAI port"
        ::= { obsaiportPer15mHisEntry 2 }

    -- 1.3.6.1.4.1.2011.2.25.3.70.10.180.70.1.3
    obsaiportPer15mHisPara OBJECT-TYPE
        SYNTAX OCTET STRING
        MAX-ACCESS read-only
        STATUS current
        DESCRIPTION
            "Parameters of historical 15-minute performance of OBSAI port"
        ::= { obsaiportPer15mHisEntry 3 }

    -- 1.3.6.1.4.1.2011.2.25.3.70.10.180.70.1.4
    obsaiportPer15mHisMonValue OBJECT-TYPE
        SYNTAX OCTET STRING
        MAX-ACCESS read-only
        STATUS current
        DESCRIPTION
            "Statistics of historical 15-minute performance of OBSAI port"
        ::= { obsaiportPer15mHisEntry 4 }

    -- 1.3.6.1.4.1.2011.2.25.3.70.10.180.70.1.5
    obsaiportPer15mHisStartTime OBJECT-TYPE
        SYNTAX DateAndTime
        MAX-ACCESS read-only
        STATUS current
        DESCRIPTION
            "Start time of historical 15-minute performance of OBSAI port"
        ::= { obsaiportPer15mHisEntry 5 }

    -- 1.3.6.1.4.1.2011.2.25.3.70.10.180.70.1.6
    obsaiportPer15mHisEndTime OBJECT-TYPE
        SYNTAX DateAndTime
        MAX-ACCESS read-only
        STATUS current
        DESCRIPTION
            "End time of historical 15-minute performance of OBSAI port"
        ::= { obsaiportPer15mHisEntry 6 }

    -- 1.3.6.1.4.1.2011.2.25.3.70.10.180.70.1.7
    obsaiportPer15mHisVldty OBJECT-TYPE
        SYNTAX ValidflagType
        MAX-ACCESS read-only
        STATUS current
        DESCRIPTION
            "Validity flag of historical 15-minute performance of OBSAI port"
        ::= { obsaiportPer15mHisEntry 7 }

    -- 1.3.6.1.4.1.2011.2.25.3.70.10.180.80
    obsaiportPer24hCurTable OBJECT-TYPE
        SYNTAX SEQUENCE OF ObsaiportPer24hCurEntry
        MAX-ACCESS not-accessible
        STATUS current
        DESCRIPTION
            "Current 24-hour performance of OBSAI port"
        ::= { obsaiport 80 }

    -- 1.3.6.1.4.1.2011.2.25.3.70.10.180.80.1
    obsaiportPer24hCurEntry OBJECT-TYPE
        SYNTAX ObsaiportPer24hCurEntry
        MAX-ACCESS not-accessible
        STATUS current
        DESCRIPTION
            "Current 24-hour performance of OBSAI port"
        INDEX{ obsaiportPer24hCurEid,obsaiportPer24hCurPara }
        ::= { obsaiportPer24hCurTable 1 }

    ObsaiportPer24hCurEntry ::=
        SEQUENCE {
            obsaiportPer24hCurEid
                PerformanceEventType,
            obsaiportPer24hCurMonValue
                OCTET STRING,
            obsaiportPer24hCurVldty
                ValidflagType,
            obsaiportPer24hCurDatetime
                DateAndTime,
            obsaiportPer24hCurParaLen
                Unsigned32,
            obsaiportPer24hCurPara
                OCTET STRING
        }

    -- 1.3.6.1.4.1.2011.2.25.3.70.10.180.80.1.1
    obsaiportPer24hCurEid OBJECT-TYPE
        SYNTAX PerformanceEventType
        MAX-ACCESS read-only
        STATUS current
        DESCRIPTION
            "Event ID of a current 24-hour performance of OBSAI port"
        ::= { obsaiportPer24hCurEntry 1 }

    -- 1.3.6.1.4.1.2011.2.25.3.70.10.180.80.1.2
    obsaiportPer24hCurMonValue OBJECT-TYPE
        SYNTAX OCTET STRING
        MAX-ACCESS read-only
        STATUS current
        DESCRIPTION
            "Statistics of current 24-hour performance of OBSAI port"
        ::= { obsaiportPer24hCurEntry 2 }

    -- 1.3.6.1.4.1.2011.2.25.3.70.10.180.80.1.3
    obsaiportPer24hCurVldty OBJECT-TYPE
        SYNTAX ValidflagType
        MAX-ACCESS read-only
        STATUS current
        DESCRIPTION
            "Validity flag of current 24-hour performance of OBSAI port"
        ::= { obsaiportPer24hCurEntry 3 }

    -- 1.3.6.1.4.1.2011.2.25.3.70.10.180.80.1.4
    obsaiportPer24hCurDatetime OBJECT-TYPE
        SYNTAX DateAndTime
        MAX-ACCESS read-only
        STATUS current
        DESCRIPTION
            "Time information of current 24-hour performance of OBSAI port"
        ::= { obsaiportPer24hCurEntry 4 }

    -- 1.3.6.1.4.1.2011.2.25.3.70.10.180.80.1.5
    obsaiportPer24hCurParaLen OBJECT-TYPE
        SYNTAX Unsigned32
        MAX-ACCESS read-only
        STATUS current
        DESCRIPTION
            "Parameter length of current 24-hour performance of OBSAI port"
        ::= { obsaiportPer24hCurEntry 5 }

    -- 1.3.6.1.4.1.2011.2.25.3.70.10.180.80.1.6
    obsaiportPer24hCurPara OBJECT-TYPE
        SYNTAX OCTET STRING
        MAX-ACCESS read-only
        STATUS current
        DESCRIPTION
            "Parameters of current 24-hour performance of OBSAI port"
        ::= { obsaiportPer24hCurEntry 6 }

    -- 1.3.6.1.4.1.2011.2.25.3.70.10.180.90
    obsaiportPer24hHisTable OBJECT-TYPE
        SYNTAX SEQUENCE OF ObsaiportPer24hHisEntry
        MAX-ACCESS not-accessible
        STATUS current
        DESCRIPTION
            "Historical 24-hour performance of OBSAI port"
        ::= { obsaiport 90 }

    -- 1.3.6.1.4.1.2011.2.25.3.70.10.180.90.1
    obsaiportPer24hHisEntry OBJECT-TYPE
        SYNTAX ObsaiportPer24hHisEntry
        MAX-ACCESS not-accessible
        STATUS current
        DESCRIPTION
            "Historical 24-hour performance of OBSAI port"
        INDEX{ obsaiportPer24hHisEid,obsaiportPer24hHisParaLen,obsaiportPer24hHisPara,obsaiportPer24hHisStartTime,obsaiportPer24hHisEndTime }
        ::= { obsaiportPer24hHisTable 1 }

    ObsaiportPer24hHisEntry ::=
        SEQUENCE {
            obsaiportPer24hHisEid
                PerformanceEventType,
            obsaiportPer24hHisParaLen
                Unsigned32,
            obsaiportPer24hHisPara
                OCTET STRING,
            obsaiportPer24hHisMonValue
                OCTET STRING,
            obsaiportPer24hHisStartTime
                DateAndTime,
            obsaiportPer24hHisEndTime
                DateAndTime,
            obsaiportPer24hHisVldty
                ValidflagType
        }

    -- 1.3.6.1.4.1.2011.2.25.3.70.10.180.90.1.1
    obsaiportPer24hHisEid OBJECT-TYPE
        SYNTAX PerformanceEventType
        MAX-ACCESS read-only
        STATUS current
        DESCRIPTION
            "Event ID of a historical 24-hour performance of OBSAI port"
        ::= { obsaiportPer24hHisEntry 1 }

    -- 1.3.6.1.4.1.2011.2.25.3.70.10.180.90.1.2
    obsaiportPer24hHisParaLen OBJECT-TYPE
        SYNTAX Unsigned32
        MAX-ACCESS read-only
        STATUS current
        DESCRIPTION
            "Parameter length of historical 24-hour performance of OBSAI port"
        ::= { obsaiportPer24hHisEntry 2 }

    -- 1.3.6.1.4.1.2011.2.25.3.70.10.180.90.1.3
    obsaiportPer24hHisPara OBJECT-TYPE
        SYNTAX OCTET STRING
        MAX-ACCESS read-only
        STATUS current
        DESCRIPTION
            "Parameters of historical 24-hour performance of OBSAI port"
        ::= { obsaiportPer24hHisEntry 3 }

    -- 1.3.6.1.4.1.2011.2.25.3.70.10.180.90.1.4
    obsaiportPer24hHisMonValue OBJECT-TYPE
        SYNTAX OCTET STRING
        MAX-ACCESS read-only
        STATUS current
        DESCRIPTION
            "Statistics of historical 24-hour performance of OBSAI port"
        ::= { obsaiportPer24hHisEntry 4 }

    -- 1.3.6.1.4.1.2011.2.25.3.70.10.180.90.1.5
    obsaiportPer24hHisStartTime OBJECT-TYPE
        SYNTAX DateAndTime
        MAX-ACCESS read-only
        STATUS current
        DESCRIPTION
            "Start time of historical 24-hour performance of OBSAI port"
        ::= { obsaiportPer24hHisEntry 5 }

    -- 1.3.6.1.4.1.2011.2.25.3.70.10.180.90.1.6
    obsaiportPer24hHisEndTime OBJECT-TYPE
        SYNTAX DateAndTime
        MAX-ACCESS read-only
        STATUS current
        DESCRIPTION
            "End time of historical 24-hour performance of OBSAI port"
        ::= { obsaiportPer24hHisEntry 6 }

    -- 1.3.6.1.4.1.2011.2.25.3.70.10.180.90.1.7
    obsaiportPer24hHisVldty OBJECT-TYPE
        SYNTAX ValidflagType
        MAX-ACCESS read-only
        STATUS current
        DESCRIPTION
            "Validity flag of historical 24-hour performance of OBSAI port"
        ::= { obsaiportPer24hHisEntry 7 }

    -- 1.3.6.1.4.1.2011.2.25.3.70.10.227
    grouppla OBJECT IDENTIFIER ::= { rtnPerformance 227 }

    -- 1.3.6.1.4.1.2011.2.25.3.70.10.227.60
    groupplaPer15mCurTable OBJECT-TYPE
        SYNTAX SEQUENCE OF GroupplaPer15mCurEntry
        MAX-ACCESS not-accessible
        STATUS current
        DESCRIPTION
            "groupplaPer15mCur."
        ::= { grouppla 60 }

    -- 1.3.6.1.4.1.2011.2.25.3.70.10.227.60.1
    groupplaPer15mCurEntry OBJECT-TYPE
        SYNTAX GroupplaPer15mCurEntry
        MAX-ACCESS not-accessible
        STATUS current
        DESCRIPTION
            "groupplaPer15mCur."
        INDEX{ groupplaPer15mCurEid,groupplaPer15mCurPara }
        ::= { groupplaPer15mCurTable 1 }

    GroupplaPer15mCurEntry ::=
        SEQUENCE {
            groupplaPer15mCurEid
                PerformanceEventType,
            groupplaPer15mCurMonValue
                OCTET STRING,
            groupplaPer15mCurVldty
                ValidflagType,
            groupplaPer15mCurDatetime
                DateAndTime,
            groupplaPer15mCurParaLen
                Unsigned32,
            groupplaPer15mCurPara
                OCTET STRING
        }

    -- 1.3.6.1.4.1.2011.2.25.3.70.10.227.60.1.1
    groupplaPer15mCurEid OBJECT-TYPE
        SYNTAX PerformanceEventType
        MAX-ACCESS read-only
        STATUS current
        DESCRIPTION
            "perEid."
        ::= { groupplaPer15mCurEntry 1 }

    -- 1.3.6.1.4.1.2011.2.25.3.70.10.227.60.1.2
    groupplaPer15mCurMonValue OBJECT-TYPE
        SYNTAX OCTET STRING
        MAX-ACCESS read-only
        STATUS current
        DESCRIPTION
            "perMonValue."
        ::= { groupplaPer15mCurEntry 2 }

    -- 1.3.6.1.4.1.2011.2.25.3.70.10.227.60.1.3
    groupplaPer15mCurVldty OBJECT-TYPE
        SYNTAX ValidflagType
        MAX-ACCESS read-only
        STATUS current
        DESCRIPTION
            "perVldty."
        ::= { groupplaPer15mCurEntry 3 }

    -- 1.3.6.1.4.1.2011.2.25.3.70.10.227.60.1.4
    groupplaPer15mCurDatetime OBJECT-TYPE
        SYNTAX DateAndTime
        MAX-ACCESS read-only
        STATUS current
        DESCRIPTION
            "perDateTime."
        ::= { groupplaPer15mCurEntry 4 }

    -- 1.3.6.1.4.1.2011.2.25.3.70.10.227.60.1.5
    groupplaPer15mCurParaLen OBJECT-TYPE
        SYNTAX Unsigned32
        MAX-ACCESS read-only
        STATUS current
        DESCRIPTION
            "perParaLen."
        ::= { groupplaPer15mCurEntry 5 }

    -- 1.3.6.1.4.1.2011.2.25.3.70.10.227.60.1.6
    groupplaPer15mCurPara OBJECT-TYPE
        SYNTAX OCTET STRING
        MAX-ACCESS read-only
        STATUS current
        DESCRIPTION
            "perPara."
        ::= { groupplaPer15mCurEntry 6 }

    -- 1.3.6.1.4.1.2011.2.25.3.70.10.227.70
    groupplaPer15mHisTable OBJECT-TYPE
        SYNTAX SEQUENCE OF GroupplaPer15mHisEntry
        MAX-ACCESS not-accessible
        STATUS current
        DESCRIPTION
            "groupplaPer15mHis."
        ::= { grouppla 70 }

    -- 1.3.6.1.4.1.2011.2.25.3.70.10.227.70.1
    groupplaPer15mHisEntry OBJECT-TYPE
        SYNTAX GroupplaPer15mHisEntry
        MAX-ACCESS not-accessible
        STATUS current
        DESCRIPTION
            "groupplaPer15mHis."
        INDEX{ groupplaPer15mHisEid,groupplaPer15mHisParaLen,groupplaPer15mHisPara,groupplaPer15mHisStartTime,groupplaPer15mHisEndTime }
        ::= { groupplaPer15mHisTable 1 }

    GroupplaPer15mHisEntry ::=
        SEQUENCE {
            groupplaPer15mHisEid
                PerformanceEventType,
            groupplaPer15mHisParaLen
                Unsigned32,
            groupplaPer15mHisPara
                OCTET STRING,
            groupplaPer15mHisMonValue
                OCTET STRING,
            groupplaPer15mHisStartTime
                DateAndTime,
            groupplaPer15mHisEndTime
                DateAndTime,
            groupplaPer15mHisVldty
                ValidflagType
        }

    -- 1.3.6.1.4.1.2011.2.25.3.70.10.227.70.1.1
    groupplaPer15mHisEid OBJECT-TYPE
        SYNTAX PerformanceEventType
        MAX-ACCESS read-only
        STATUS current
        DESCRIPTION
            "perEid."
        ::= { groupplaPer15mHisEntry 1 }

    -- 1.3.6.1.4.1.2011.2.25.3.70.10.227.70.1.2
    groupplaPer15mHisParaLen OBJECT-TYPE
        SYNTAX Unsigned32
        MAX-ACCESS read-only
        STATUS current
        DESCRIPTION
            "perParaLen."
        ::= { groupplaPer15mHisEntry 2 }

    -- 1.3.6.1.4.1.2011.2.25.3.70.10.227.70.1.3
    groupplaPer15mHisPara OBJECT-TYPE
        SYNTAX OCTET STRING
        MAX-ACCESS read-only
        STATUS current
        DESCRIPTION
            "perPara."
        ::= { groupplaPer15mHisEntry 3 }

    -- 1.3.6.1.4.1.2011.2.25.3.70.10.227.70.1.4
    groupplaPer15mHisMonValue OBJECT-TYPE
        SYNTAX OCTET STRING
        MAX-ACCESS read-only
        STATUS current
        DESCRIPTION
            "perMonValue."
        ::= { groupplaPer15mHisEntry 4 }

    -- 1.3.6.1.4.1.2011.2.25.3.70.10.227.70.1.5
    groupplaPer15mHisStartTime OBJECT-TYPE
        SYNTAX DateAndTime
        MAX-ACCESS read-only
        STATUS current
        DESCRIPTION
            "perDateTimeStart."
        ::= { groupplaPer15mHisEntry 5 }

    -- 1.3.6.1.4.1.2011.2.25.3.70.10.227.70.1.6
    groupplaPer15mHisEndTime OBJECT-TYPE
        SYNTAX DateAndTime
        MAX-ACCESS read-only
        STATUS current
        DESCRIPTION
            "perDateTimeEnd."
        ::= { groupplaPer15mHisEntry 6 }

    -- 1.3.6.1.4.1.2011.2.25.3.70.10.227.70.1.7
    groupplaPer15mHisVldty OBJECT-TYPE
        SYNTAX ValidflagType
        MAX-ACCESS read-only
        STATUS current
        DESCRIPTION
            "perVldty."
        ::= { groupplaPer15mHisEntry 7 }

    -- 1.3.6.1.4.1.2011.2.25.3.70.10.227.80
    groupplaPer24hCurTable OBJECT-TYPE
        SYNTAX SEQUENCE OF GroupplaPer24hCurEntry
        MAX-ACCESS not-accessible
        STATUS current
        DESCRIPTION
            "groupplaPer24hCur."
        ::= { grouppla 80 }

    -- 1.3.6.1.4.1.2011.2.25.3.70.10.227.80.1
    groupplaPer24hCurEntry OBJECT-TYPE
        SYNTAX GroupplaPer24hCurEntry
        MAX-ACCESS not-accessible
        STATUS current
        DESCRIPTION
            "groupplaPer24hCur."
        INDEX{ groupplaPer24hCurEid,groupplaPer24hCurPara }
        ::= { groupplaPer24hCurTable 1 }

    GroupplaPer24hCurEntry ::=
        SEQUENCE {
            groupplaPer24hCurEid
                PerformanceEventType,
            groupplaPer24hCurMonValue
                OCTET STRING,
            groupplaPer24hCurVldty
                ValidflagType,
            groupplaPer24hCurDatetime
                DateAndTime,
            groupplaPer24hCurParaLen
                Unsigned32,
            groupplaPer24hCurPara
                OCTET STRING
        }

    -- 1.3.6.1.4.1.2011.2.25.3.70.10.227.80.1.1
    groupplaPer24hCurEid OBJECT-TYPE
        SYNTAX PerformanceEventType
        MAX-ACCESS read-only
        STATUS current
        DESCRIPTION
            "perEid."
        ::= { groupplaPer24hCurEntry 1 }

    -- 1.3.6.1.4.1.2011.2.25.3.70.10.227.80.1.2
    groupplaPer24hCurMonValue OBJECT-TYPE
        SYNTAX OCTET STRING
        MAX-ACCESS read-only
        STATUS current
        DESCRIPTION
            "perMonValue."
        ::= { groupplaPer24hCurEntry 2 }

    -- 1.3.6.1.4.1.2011.2.25.3.70.10.227.80.1.3
    groupplaPer24hCurVldty OBJECT-TYPE
        SYNTAX ValidflagType
        MAX-ACCESS read-only
        STATUS current
        DESCRIPTION
            "perVldty."
        ::= { groupplaPer24hCurEntry 3 }

    -- 1.3.6.1.4.1.2011.2.25.3.70.10.227.80.1.4
    groupplaPer24hCurDatetime OBJECT-TYPE
        SYNTAX DateAndTime
        MAX-ACCESS read-only
        STATUS current
        DESCRIPTION
            "perDateTime."
        ::= { groupplaPer24hCurEntry 4 }

    -- 1.3.6.1.4.1.2011.2.25.3.70.10.227.80.1.5
    groupplaPer24hCurParaLen OBJECT-TYPE
        SYNTAX Unsigned32
        MAX-ACCESS read-only
        STATUS current
        DESCRIPTION
            "perParaLen."
        ::= { groupplaPer24hCurEntry 5 }

    -- 1.3.6.1.4.1.2011.2.25.3.70.10.227.80.1.6
    groupplaPer24hCurPara OBJECT-TYPE
        SYNTAX OCTET STRING
        MAX-ACCESS read-only
        STATUS current
        DESCRIPTION
            "perPara."
        ::= { groupplaPer24hCurEntry 6 }

    -- 1.3.6.1.4.1.2011.2.25.3.70.10.227.90
    groupplaPer24hHisTable OBJECT-TYPE
        SYNTAX SEQUENCE OF GroupplaPer24hHisEntry
        MAX-ACCESS not-accessible
        STATUS current
        DESCRIPTION
            "groupplaPer24hHis."
        ::= { grouppla 90 }

    -- 1.3.6.1.4.1.2011.2.25.3.70.10.227.90.1
    groupplaPer24hHisEntry OBJECT-TYPE
        SYNTAX GroupplaPer24hHisEntry
        MAX-ACCESS not-accessible
        STATUS current
        DESCRIPTION
            "groupplaPer24hHis."
        INDEX{ groupplaPer24hHisEid,groupplaPer24hHisParaLen,groupplaPer24hHisPara,groupplaPer24hHisStartTime,groupplaPer24hHisEndTime }
        ::= { groupplaPer24hHisTable 1 }

    GroupplaPer24hHisEntry ::=
        SEQUENCE {
            groupplaPer24hHisEid
                PerformanceEventType,
            groupplaPer24hHisParaLen
                Unsigned32,
            groupplaPer24hHisPara
                OCTET STRING,
            groupplaPer24hHisMonValue
                OCTET STRING,
            groupplaPer24hHisStartTime
                DateAndTime,
            groupplaPer24hHisEndTime
                DateAndTime,
            groupplaPer24hHisVldty
                ValidflagType
        }

    -- 1.3.6.1.4.1.2011.2.25.3.70.10.227.90.1.1
    groupplaPer24hHisEid OBJECT-TYPE
        SYNTAX PerformanceEventType
        MAX-ACCESS read-only
        STATUS current
        DESCRIPTION
            "perEid."
        ::= { groupplaPer24hHisEntry 1 }

    -- 1.3.6.1.4.1.2011.2.25.3.70.10.227.90.1.2
    groupplaPer24hHisParaLen OBJECT-TYPE
        SYNTAX Unsigned32
        MAX-ACCESS read-only
        STATUS current
        DESCRIPTION
            "perParaLen."
        ::= { groupplaPer24hHisEntry 2 }

    -- 1.3.6.1.4.1.2011.2.25.3.70.10.227.90.1.3
    groupplaPer24hHisPara OBJECT-TYPE
        SYNTAX OCTET STRING
        MAX-ACCESS read-only
        STATUS current
        DESCRIPTION
            "perPara."
        ::= { groupplaPer24hHisEntry 3 }

    -- 1.3.6.1.4.1.2011.2.25.3.70.10.227.90.1.4
    groupplaPer24hHisMonValue OBJECT-TYPE
        SYNTAX OCTET STRING
        MAX-ACCESS read-only
        STATUS current
        DESCRIPTION
            "perMonValue."
        ::= { groupplaPer24hHisEntry 4 }

    -- 1.3.6.1.4.1.2011.2.25.3.70.10.227.90.1.5
    groupplaPer24hHisStartTime OBJECT-TYPE
        SYNTAX DateAndTime
        MAX-ACCESS read-only
        STATUS current
        DESCRIPTION
            "perDateTimeStart."
        ::= { groupplaPer24hHisEntry 5 }

    -- 1.3.6.1.4.1.2011.2.25.3.70.10.227.90.1.6
    groupplaPer24hHisEndTime OBJECT-TYPE
        SYNTAX DateAndTime
        MAX-ACCESS read-only
        STATUS current
        DESCRIPTION
            "perDateTimeEnd."
        ::= { groupplaPer24hHisEntry 6 }

    -- 1.3.6.1.4.1.2011.2.25.3.70.10.227.90.1.7
    groupplaPer24hHisVldty OBJECT-TYPE
        SYNTAX ValidflagType
        MAX-ACCESS read-only
        STATUS current
        DESCRIPTION
            "perVldty."
        ::= { groupplaPer24hHisEntry 7 }

    -- 1.3.6.1.4.1.2011.2.25.3.70.10.299
    oducarrier OBJECT IDENTIFIER ::= { rtnPerformance 299 }

    -- 1.3.6.1.4.1.2011.2.25.3.70.10.299.60
    oducarrierPer15mCurTable OBJECT-TYPE
        SYNTAX SEQUENCE OF OduCarrierPer15mCurEntry
        MAX-ACCESS not-accessible
        STATUS current
        DESCRIPTION
            "oducarrierPer15mCur."
        ::= { oducarrier 60 }

    -- 1.3.6.1.4.1.2011.2.25.3.70.10.299.60.1
    oducarrierPer15mCurEntry OBJECT-TYPE
        SYNTAX OduCarrierPer15mCurEntry
        MAX-ACCESS not-accessible
        STATUS current
        DESCRIPTION
            "oducarrierPer15mCur."
        INDEX{ oducarrierPer15mCurEid,oducarrierPer15mCurPara }
        ::= { oducarrierPer15mCurTable 1 }

    OduCarrierPer15mCurEntry ::=
        SEQUENCE {
            oducarrierPer15mCurEid
                PerformanceEventType,
            oducarrierPer15mCurMonValue
                OCTET STRING,
            oducarrierPer15mCurVldty
                ValidflagType,
            oducarrierPer15mCurDatetime
                DateAndTime,
            oducarrierPer15mCurParaLen
                Unsigned32,
            oducarrierPer15mCurPara
                OCTET STRING
        }

    -- 1.3.6.1.4.1.2011.2.25.3.70.10.299.60.1.1
    oducarrierPer15mCurEid OBJECT-TYPE
        SYNTAX PerformanceEventType
        MAX-ACCESS read-only
        STATUS current
        DESCRIPTION
            "perEid."
        ::= { oducarrierPer15mCurEntry 1 }

    -- 1.3.6.1.4.1.2011.2.25.3.70.10.299.60.1.2
    oducarrierPer15mCurMonValue OBJECT-TYPE
        SYNTAX OCTET STRING
        MAX-ACCESS read-only
        STATUS current
        DESCRIPTION
            "perMonValue."
        ::= { oducarrierPer15mCurEntry 2 }

    -- 1.3.6.1.4.1.2011.2.25.3.70.10.299.60.1.3
    oducarrierPer15mCurVldty OBJECT-TYPE
        SYNTAX ValidflagType
        MAX-ACCESS read-only
        STATUS current
        DESCRIPTION
            "perVldty."
        ::= { oducarrierPer15mCurEntry 3 }

    -- 1.3.6.1.4.1.2011.2.25.3.70.10.299.60.1.4
    oducarrierPer15mCurDatetime OBJECT-TYPE
        SYNTAX DateAndTime
        MAX-ACCESS read-only
        STATUS current
        DESCRIPTION
            "perDateTime."
        ::= { oducarrierPer15mCurEntry 4 }

    -- 1.3.6.1.4.1.2011.2.25.3.70.10.299.60.1.5
    oducarrierPer15mCurParaLen OBJECT-TYPE
        SYNTAX Unsigned32
        MAX-ACCESS read-only
        STATUS current
        DESCRIPTION
            "perParaLen."
        ::= { oducarrierPer15mCurEntry 5 }

    -- 1.3.6.1.4.1.2011.2.25.3.70.10.299.60.1.6
    oducarrierPer15mCurPara OBJECT-TYPE
        SYNTAX OCTET STRING
        MAX-ACCESS read-only
        STATUS current
        DESCRIPTION
            "perPara."
        ::= { oducarrierPer15mCurEntry 6 }

    -- 1.3.6.1.4.1.2011.2.25.3.70.10.299.70
    oducarrierPer15mHisTable OBJECT-TYPE
        SYNTAX SEQUENCE OF OduCarrierPer15mHisEntry
        MAX-ACCESS not-accessible
        STATUS current
        DESCRIPTION
            "oducarrierPer15mHis."
        ::= { oducarrier 70 }

    -- 1.3.6.1.4.1.2011.2.25.3.70.10.299.70.1
    oducarrierPer15mHisEntry OBJECT-TYPE
        SYNTAX OduCarrierPer15mHisEntry
        MAX-ACCESS not-accessible
        STATUS current
        DESCRIPTION
            "oducarrierPer15mHis."
        INDEX{ oducarrierPer15mHisEid,oducarrierPer15mHisParaLen,oducarrierPer15mHisPara,oducarrierPer15mHisStartTime,oducarrierPer15mHisEndTime }
        ::= { oducarrierPer15mHisTable 1 }

    OduCarrierPer15mHisEntry ::=
        SEQUENCE {
            oducarrierPer15mHisEid
                PerformanceEventType,
            oducarrierPer15mHisParaLen
                Unsigned32,
            oducarrierPer15mHisPara
                OCTET STRING,
            oducarrierPer15mHisMonValue
                OCTET STRING,
            oducarrierPer15mHisStartTime
                DateAndTime,
            oducarrierPer15mHisEndTime
                DateAndTime,
            oducarrierPer15mHisVldty
                ValidflagType
        }

    -- 1.3.6.1.4.1.2011.2.25.3.70.10.299.70.1.1
    oducarrierPer15mHisEid OBJECT-TYPE
        SYNTAX PerformanceEventType
        MAX-ACCESS read-only
        STATUS current
        DESCRIPTION
            "perEid."
        ::= { oducarrierPer15mHisEntry 1 }

    -- 1.3.6.1.4.1.2011.2.25.3.70.10.299.70.1.2
    oducarrierPer15mHisParaLen OBJECT-TYPE
        SYNTAX Unsigned32
        MAX-ACCESS read-only
        STATUS current
        DESCRIPTION
            "perParaLen."
        ::= { oducarrierPer15mHisEntry 2 }

    -- 1.3.6.1.4.1.2011.2.25.3.70.10.299.70.1.3
    oducarrierPer15mHisPara OBJECT-TYPE
        SYNTAX OCTET STRING
        MAX-ACCESS read-only
        STATUS current
        DESCRIPTION
            "perPara."
        ::= { oducarrierPer15mHisEntry 3 }

    -- 1.3.6.1.4.1.2011.2.25.3.70.10.299.70.1.4
    oducarrierPer15mHisMonValue OBJECT-TYPE
        SYNTAX OCTET STRING
        MAX-ACCESS read-only
        STATUS current
        DESCRIPTION
            "perMonValue."
        ::= { oducarrierPer15mHisEntry 4 }

    -- 1.3.6.1.4.1.2011.2.25.3.70.10.299.70.1.5
    oducarrierPer15mHisStartTime OBJECT-TYPE
        SYNTAX DateAndTime
        MAX-ACCESS read-only
        STATUS current
        DESCRIPTION
            "perDateTimeStart."
        ::= { oducarrierPer15mHisEntry 5 }

    -- 1.3.6.1.4.1.2011.2.25.3.70.10.299.70.1.6
    oducarrierPer15mHisEndTime OBJECT-TYPE
        SYNTAX DateAndTime
        MAX-ACCESS read-only
        STATUS current
        DESCRIPTION
            "perDateTimeEnd."
        ::= { oducarrierPer15mHisEntry 6 }

    -- 1.3.6.1.4.1.2011.2.25.3.70.10.299.70.1.7
    oducarrierPer15mHisVldty OBJECT-TYPE
        SYNTAX ValidflagType
        MAX-ACCESS read-only
        STATUS current
        DESCRIPTION
            "perVldty."
        ::= { oducarrierPer15mHisEntry 7 }

    -- 1.3.6.1.4.1.2011.2.25.3.70.10.299.80
    oducarrierPer24hCurTable OBJECT-TYPE
        SYNTAX SEQUENCE OF OduCarrierPer24hCurEntry
        MAX-ACCESS not-accessible
        STATUS current
        DESCRIPTION
            "oducarrierPer24hCur."
        ::= { oducarrier 80 }

    -- 1.3.6.1.4.1.2011.2.25.3.70.10.299.80.1
    oducarrierPer24hCurEntry OBJECT-TYPE
        SYNTAX OduCarrierPer24hCurEntry
        MAX-ACCESS not-accessible
        STATUS current
        DESCRIPTION
            "oducarrierPer24hCur."
        INDEX{ oducarrierPer24hCurEid,oducarrierPer24hCurPara }
        ::= { oducarrierPer24hCurTable 1 }

    OduCarrierPer24hCurEntry ::=
        SEQUENCE {
            oducarrierPer24hCurEid
                PerformanceEventType,
            oducarrierPer24hCurMonValue
                OCTET STRING,
            oducarrierPer24hCurVldty
                ValidflagType,
            oducarrierPer24hCurDatetime
                DateAndTime,
            oducarrierPer24hCurParaLen
                Unsigned32,
            oducarrierPer24hCurPara
                OCTET STRING
        }

    -- 1.3.6.1.4.1.2011.2.25.3.70.10.299.80.1.1
    oducarrierPer24hCurEid OBJECT-TYPE
        SYNTAX PerformanceEventType
        MAX-ACCESS read-only
        STATUS current
        DESCRIPTION
            "perEid."
        ::= { oducarrierPer24hCurEntry 1 }

    -- 1.3.6.1.4.1.2011.2.25.3.70.10.299.80.1.2
    oducarrierPer24hCurMonValue OBJECT-TYPE
        SYNTAX OCTET STRING
        MAX-ACCESS read-only
        STATUS current
        DESCRIPTION
            "perMonValue."
        ::= { oducarrierPer24hCurEntry 2 }

    -- 1.3.6.1.4.1.2011.2.25.3.70.10.299.80.1.3
    oducarrierPer24hCurVldty OBJECT-TYPE
        SYNTAX ValidflagType
        MAX-ACCESS read-only
        STATUS current
        DESCRIPTION
            "perVldty."
        ::= { oducarrierPer24hCurEntry 3 }

    -- 1.3.6.1.4.1.2011.2.25.3.70.10.299.80.1.4
    oducarrierPer24hCurDatetime OBJECT-TYPE
        SYNTAX DateAndTime
        MAX-ACCESS read-only
        STATUS current
        DESCRIPTION
            "perDateTime."
        ::= { oducarrierPer24hCurEntry 4 }

    -- 1.3.6.1.4.1.2011.2.25.3.70.10.299.80.1.5
    oducarrierPer24hCurParaLen OBJECT-TYPE
        SYNTAX Unsigned32
        MAX-ACCESS read-only
        STATUS current
        DESCRIPTION
            "perParaLen."
        ::= { oducarrierPer24hCurEntry 5 }

    -- 1.3.6.1.4.1.2011.2.25.3.70.10.299.80.1.6
    oducarrierPer24hCurPara OBJECT-TYPE
        SYNTAX OCTET STRING
        MAX-ACCESS read-only
        STATUS current
        DESCRIPTION
            "perPara."
        ::= { oducarrierPer24hCurEntry 6 }

    -- 1.3.6.1.4.1.2011.2.25.3.70.10.299.90
    oducarrierPer24hHisTable OBJECT-TYPE
        SYNTAX SEQUENCE OF OduCarrierPer24hHisEntry
        MAX-ACCESS not-accessible
        STATUS current
        DESCRIPTION
            "oducarrierPer24hHis."
        ::= { oducarrier 90 }

    -- 1.3.6.1.4.1.2011.2.25.3.70.10.299.90.1
    oducarrierPer24hHisEntry OBJECT-TYPE
        SYNTAX OduCarrierPer24hHisEntry
        MAX-ACCESS not-accessible
        STATUS current
        DESCRIPTION
            "oducarrierPer24hHis."
        INDEX{ oducarrierPer24hHisEid,oducarrierPer24hHisParaLen,oducarrierPer24hHisPara,oducarrierPer24hHisStartTime,oducarrierPer24hHisEndTime }
        ::= { oducarrierPer24hHisTable 1 }

    OduCarrierPer24hHisEntry ::=
        SEQUENCE {
            oducarrierPer24hHisEid
                PerformanceEventType,
            oducarrierPer24hHisParaLen
                Unsigned32,
            oducarrierPer24hHisPara
                OCTET STRING,
            oducarrierPer24hHisMonValue
                OCTET STRING,
            oducarrierPer24hHisStartTime
                DateAndTime,
            oducarrierPer24hHisEndTime
                DateAndTime,
            oducarrierPer24hHisVldty
                ValidflagType
        }

    -- 1.3.6.1.4.1.2011.2.25.3.70.10.299.90.1.1
    oducarrierPer24hHisEid OBJECT-TYPE
        SYNTAX PerformanceEventType
        MAX-ACCESS read-only
        STATUS current
        DESCRIPTION
            "perEid."
        ::= { oducarrierPer24hHisEntry 1 }

    -- 1.3.6.1.4.1.2011.2.25.3.70.10.299.90.1.2
    oducarrierPer24hHisParaLen OBJECT-TYPE
        SYNTAX Unsigned32
        MAX-ACCESS read-only
        STATUS current
        DESCRIPTION
            "perParaLen."
        ::= { oducarrierPer24hHisEntry 2 }

    -- 1.3.6.1.4.1.2011.2.25.3.70.10.299.90.1.3
    oducarrierPer24hHisPara OBJECT-TYPE
        SYNTAX OCTET STRING
        MAX-ACCESS read-only
        STATUS current
        DESCRIPTION
            "perPara."
        ::= { oducarrierPer24hHisEntry 3 }

    -- 1.3.6.1.4.1.2011.2.25.3.70.10.299.90.1.4
    oducarrierPer24hHisMonValue OBJECT-TYPE
        SYNTAX OCTET STRING
        MAX-ACCESS read-only
        STATUS current
        DESCRIPTION
            "perMonValue."
        ::= { oducarrierPer24hHisEntry 4 }

    -- 1.3.6.1.4.1.2011.2.25.3.70.10.299.90.1.5
    oducarrierPer24hHisStartTime OBJECT-TYPE
        SYNTAX DateAndTime
        MAX-ACCESS read-only
        STATUS current
        DESCRIPTION
            "perDateTimeStart."
        ::= { oducarrierPer24hHisEntry 5 }

    -- 1.3.6.1.4.1.2011.2.25.3.70.10.299.90.1.6
    oducarrierPer24hHisEndTime OBJECT-TYPE
        SYNTAX DateAndTime
        MAX-ACCESS read-only
        STATUS current
        DESCRIPTION
            "perDateTimeEnd."
        ::= { oducarrierPer24hHisEntry 6 }

    -- 1.3.6.1.4.1.2011.2.25.3.70.10.299.90.1.7
    oducarrierPer24hHisVldty OBJECT-TYPE
        SYNTAX ValidflagType
        MAX-ACCESS read-only
        STATUS current
        DESCRIPTION
            "perVldty."
        ::= { oducarrierPer24hHisEntry 7 }  		
	
    -- 1.3.6.1.4.1.2011.2.25.3.70.10.301
    groupmimo OBJECT IDENTIFIER ::= { rtnPerformance 301 }

    -- 1.3.6.1.4.1.2011.2.25.3.70.10.301.60
    groupmimoPer15mCurTable OBJECT-TYPE
        SYNTAX SEQUENCE OF GroupmimoPer15mCurEntry
        MAX-ACCESS not-accessible
        STATUS current
        DESCRIPTION
            "groupmimoPer15mCur."
        ::= { groupmimo 60 }

    -- 1.3.6.1.4.1.2011.2.25.3.70.10.301.60.1
    groupmimoPer15mCurEntry OBJECT-TYPE
        SYNTAX GroupmimoPer15mCurEntry
        MAX-ACCESS not-accessible
        STATUS current
        DESCRIPTION
            "groupmimoPer15mCur."
        INDEX{ groupmimoPer15mCurEid,groupmimoPer15mCurPara }
        ::= { groupmimoPer15mCurTable 1 }

    GroupmimoPer15mCurEntry ::=
        SEQUENCE {
            groupmimoPer15mCurEid
                PerformanceEventType,
            groupmimoPer15mCurMonValue
                OCTET STRING,
            groupmimoPer15mCurVldty
                ValidflagType,
            groupmimoPer15mCurDatetime
                DateAndTime,
            groupmimoPer15mCurParaLen
                Unsigned32,
            groupmimoPer15mCurPara
                OCTET STRING
        }

    -- 1.3.6.1.4.1.2011.2.25.3.70.10.301.60.1.1
    groupmimoPer15mCurEid OBJECT-TYPE
        SYNTAX PerformanceEventType
        MAX-ACCESS read-only
        STATUS current
        DESCRIPTION
            "perEid."
        ::= { groupmimoPer15mCurEntry 1 }

    -- 1.3.6.1.4.1.2011.2.25.3.70.10.301.60.1.2
    groupmimoPer15mCurMonValue OBJECT-TYPE
        SYNTAX OCTET STRING
        MAX-ACCESS read-only
        STATUS current
        DESCRIPTION
            "perMonValue."
        ::= { groupmimoPer15mCurEntry 2 }

    -- 1.3.6.1.4.1.2011.2.25.3.70.10.301.60.1.3
    groupmimoPer15mCurVldty OBJECT-TYPE
        SYNTAX ValidflagType
        MAX-ACCESS read-only
        STATUS current
        DESCRIPTION
            "perVldty."
        ::= { groupmimoPer15mCurEntry 3 }

    -- 1.3.6.1.4.1.2011.2.25.3.70.10.301.60.1.4
    groupmimoPer15mCurDatetime OBJECT-TYPE
        SYNTAX DateAndTime
        MAX-ACCESS read-only
        STATUS current
        DESCRIPTION
            "perDateTime."
        ::= { groupmimoPer15mCurEntry 4 }

    -- 1.3.6.1.4.1.2011.2.25.3.70.10.301.60.1.5
    groupmimoPer15mCurParaLen OBJECT-TYPE
        SYNTAX Unsigned32
        MAX-ACCESS read-only
        STATUS current
        DESCRIPTION
            "perParaLen."
        ::= { groupmimoPer15mCurEntry 5 }

    -- 1.3.6.1.4.1.2011.2.25.3.70.10.301.60.1.6
    groupmimoPer15mCurPara OBJECT-TYPE
        SYNTAX OCTET STRING
        MAX-ACCESS read-only
        STATUS current
        DESCRIPTION
            "perPara."
        ::= { groupmimoPer15mCurEntry 6 }

    -- 1.3.6.1.4.1.2011.2.25.3.70.10.301.70
    groupmimoPer15mHisTable OBJECT-TYPE
        SYNTAX SEQUENCE OF GroupmimoPer15mHisEntry
        MAX-ACCESS not-accessible
        STATUS current
        DESCRIPTION
            "groupmimoPer15mHis."
        ::= { groupmimo 70 }

    -- 1.3.6.1.4.1.2011.2.25.3.70.10.301.70.1
    groupmimoPer15mHisEntry OBJECT-TYPE
        SYNTAX GroupmimoPer15mHisEntry
        MAX-ACCESS not-accessible
        STATUS current
        DESCRIPTION
            "groupmimoPer15mHis."
        INDEX{ groupmimoPer15mHisEid,groupmimoPer15mHisParaLen,groupmimoPer15mHisPara,groupmimoPer15mHisStartTime,groupmimoPer15mHisEndTime }
        ::= { groupmimoPer15mHisTable 1 }

    GroupmimoPer15mHisEntry ::=
        SEQUENCE {
            groupmimoPer15mHisEid
                PerformanceEventType,
            groupmimoPer15mHisParaLen
                Unsigned32,
            groupmimoPer15mHisPara
                OCTET STRING,
            groupmimoPer15mHisMonValue
                OCTET STRING,
            groupmimoPer15mHisStartTime
                DateAndTime,
            groupmimoPer15mHisEndTime
                DateAndTime,
            groupmimoPer15mHisVldty
                ValidflagType
        }

    -- 1.3.6.1.4.1.2011.2.25.3.70.10.301.70.1.1
    groupmimoPer15mHisEid OBJECT-TYPE
        SYNTAX PerformanceEventType
        MAX-ACCESS read-only
        STATUS current
        DESCRIPTION
            "perEid."
        ::= { groupmimoPer15mHisEntry 1 }

    -- 1.3.6.1.4.1.2011.2.25.3.70.10.301.70.1.2
    groupmimoPer15mHisParaLen OBJECT-TYPE
        SYNTAX Unsigned32
        MAX-ACCESS read-only
        STATUS current
        DESCRIPTION
            "perParaLen."
        ::= { groupmimoPer15mHisEntry 2 }

    -- 1.3.6.1.4.1.2011.2.25.3.70.10.301.70.1.3
    groupmimoPer15mHisPara OBJECT-TYPE
        SYNTAX OCTET STRING
        MAX-ACCESS read-only
        STATUS current
        DESCRIPTION
            "perPara."
        ::= { groupmimoPer15mHisEntry 3 }

    -- 1.3.6.1.4.1.2011.2.25.3.70.10.301.70.1.4
    groupmimoPer15mHisMonValue OBJECT-TYPE
        SYNTAX OCTET STRING
        MAX-ACCESS read-only
        STATUS current
        DESCRIPTION
            "perMonValue."
        ::= { groupmimoPer15mHisEntry 4 }

    -- 1.3.6.1.4.1.2011.2.25.3.70.10.301.70.1.5
    groupmimoPer15mHisStartTime OBJECT-TYPE
        SYNTAX DateAndTime
        MAX-ACCESS read-only
        STATUS current
        DESCRIPTION
            "perDateTimeStart."
        ::= { groupmimoPer15mHisEntry 5 }

    -- 1.3.6.1.4.1.2011.2.25.3.70.10.301.70.1.6
    groupmimoPer15mHisEndTime OBJECT-TYPE
        SYNTAX DateAndTime
        MAX-ACCESS read-only
        STATUS current
        DESCRIPTION
            "perDateTimeEnd."
        ::= { groupmimoPer15mHisEntry 6 }

    -- 1.3.6.1.4.1.2011.2.25.3.70.10.301.70.1.7
    groupmimoPer15mHisVldty OBJECT-TYPE
        SYNTAX ValidflagType
        MAX-ACCESS read-only
        STATUS current
        DESCRIPTION
            "perVldty."
        ::= { groupmimoPer15mHisEntry 7 }

    -- 1.3.6.1.4.1.2011.2.25.3.70.10.301.80
    groupmimoPer24hCurTable OBJECT-TYPE
        SYNTAX SEQUENCE OF GroupmimoPer24hCurEntry
        MAX-ACCESS not-accessible
        STATUS current
        DESCRIPTION
            "groupmimoPer24hCur."
        ::= { groupmimo 80 }

    -- 1.3.6.1.4.1.2011.2.25.3.70.10.301.80.1
    groupmimoPer24hCurEntry OBJECT-TYPE
        SYNTAX GroupmimoPer24hCurEntry
        MAX-ACCESS not-accessible
        STATUS current
        DESCRIPTION
            "groupmimoPer24hCur."
        INDEX{ groupmimoPer24hCurEid,groupmimoPer24hCurPara }
        ::= { groupmimoPer24hCurTable 1 }

    GroupmimoPer24hCurEntry ::=
        SEQUENCE {
            groupmimoPer24hCurEid
                PerformanceEventType,
            groupmimoPer24hCurMonValue
                OCTET STRING,
            groupmimoPer24hCurVldty
                ValidflagType,
            groupmimoPer24hCurDatetime
                DateAndTime,
            groupmimoPer24hCurParaLen
                Unsigned32,
            groupmimoPer24hCurPara
                OCTET STRING
        }

    -- 1.3.6.1.4.1.2011.2.25.3.70.10.301.80.1.1
    groupmimoPer24hCurEid OBJECT-TYPE
        SYNTAX PerformanceEventType
        MAX-ACCESS read-only
        STATUS current
        DESCRIPTION
            "perEid."
        ::= { groupmimoPer24hCurEntry 1 }

    -- 1.3.6.1.4.1.2011.2.25.3.70.10.301.80.1.2
    groupmimoPer24hCurMonValue OBJECT-TYPE
        SYNTAX OCTET STRING
        MAX-ACCESS read-only
        STATUS current
        DESCRIPTION
            "perMonValue."
        ::= { groupmimoPer24hCurEntry 2 }

    -- 1.3.6.1.4.1.2011.2.25.3.70.10.301.80.1.3
    groupmimoPer24hCurVldty OBJECT-TYPE
        SYNTAX ValidflagType
        MAX-ACCESS read-only
        STATUS current
        DESCRIPTION
            "perVldty."
        ::= { groupmimoPer24hCurEntry 3 }

    -- 1.3.6.1.4.1.2011.2.25.3.70.10.301.80.1.4
    groupmimoPer24hCurDatetime OBJECT-TYPE
        SYNTAX DateAndTime
        MAX-ACCESS read-only
        STATUS current
        DESCRIPTION
            "perDateTime."
        ::= { groupmimoPer24hCurEntry 4 }

    -- 1.3.6.1.4.1.2011.2.25.3.70.10.301.80.1.5
    groupmimoPer24hCurParaLen OBJECT-TYPE
        SYNTAX Unsigned32
        MAX-ACCESS read-only
        STATUS current
        DESCRIPTION
            "perParaLen."
        ::= { groupmimoPer24hCurEntry 5 }

    -- 1.3.6.1.4.1.2011.2.25.3.70.10.301.80.1.6
    groupmimoPer24hCurPara OBJECT-TYPE
        SYNTAX OCTET STRING
        MAX-ACCESS read-only
        STATUS current
        DESCRIPTION
            "perPara."
        ::= { groupmimoPer24hCurEntry 6 }

    -- 1.3.6.1.4.1.2011.2.25.3.70.10.301.90
    groupmimoPer24hHisTable OBJECT-TYPE
        SYNTAX SEQUENCE OF GroupmimoPer24hHisEntry
        MAX-ACCESS not-accessible
        STATUS current
        DESCRIPTION
            "groupmimoPer24hHis."
        ::= { groupmimo 90 }

    -- 1.3.6.1.4.1.2011.2.25.3.70.10.301.90.1
    groupmimoPer24hHisEntry OBJECT-TYPE
        SYNTAX GroupmimoPer24hHisEntry
        MAX-ACCESS not-accessible
        STATUS current
        DESCRIPTION
            "groupmimoPer24hHis."
        INDEX{ groupmimoPer24hHisEid,groupmimoPer24hHisParaLen,groupmimoPer24hHisPara,groupmimoPer24hHisStartTime,groupmimoPer24hHisEndTime }
        ::= { groupmimoPer24hHisTable 1 }

    GroupmimoPer24hHisEntry ::=
        SEQUENCE {
            groupmimoPer24hHisEid
                PerformanceEventType,
            groupmimoPer24hHisParaLen
                Unsigned32,
            groupmimoPer24hHisPara
                OCTET STRING,
            groupmimoPer24hHisMonValue
                OCTET STRING,
            groupmimoPer24hHisStartTime
                DateAndTime,
            groupmimoPer24hHisEndTime
                DateAndTime,
            groupmimoPer24hHisVldty
                ValidflagType
        }

    -- 1.3.6.1.4.1.2011.2.25.3.70.10.301.90.1.1
    groupmimoPer24hHisEid OBJECT-TYPE
        SYNTAX PerformanceEventType
        MAX-ACCESS read-only
        STATUS current
        DESCRIPTION
            "perEid."
        ::= { groupmimoPer24hHisEntry 1 }

    -- 1.3.6.1.4.1.2011.2.25.3.70.10.301.90.1.2
    groupmimoPer24hHisParaLen OBJECT-TYPE
        SYNTAX Unsigned32
        MAX-ACCESS read-only
        STATUS current
        DESCRIPTION
            "perParaLen."
        ::= { groupmimoPer24hHisEntry 2 }

    -- 1.3.6.1.4.1.2011.2.25.3.70.10.301.90.1.3
    groupmimoPer24hHisPara OBJECT-TYPE
        SYNTAX OCTET STRING
        MAX-ACCESS read-only
        STATUS current
        DESCRIPTION
            "perPara."
        ::= { groupmimoPer24hHisEntry 3 }

    -- 1.3.6.1.4.1.2011.2.25.3.70.10.301.90.1.4
    groupmimoPer24hHisMonValue OBJECT-TYPE
        SYNTAX OCTET STRING
        MAX-ACCESS read-only
        STATUS current
        DESCRIPTION
            "perMonValue."
        ::= { groupmimoPer24hHisEntry 4 }

    -- 1.3.6.1.4.1.2011.2.25.3.70.10.301.90.1.5
    groupmimoPer24hHisStartTime OBJECT-TYPE
        SYNTAX DateAndTime
        MAX-ACCESS read-only
        STATUS current
        DESCRIPTION
            "perDateTimeStart."
        ::= { groupmimoPer24hHisEntry 5 }

    -- 1.3.6.1.4.1.2011.2.25.3.70.10.301.90.1.6
    groupmimoPer24hHisEndTime OBJECT-TYPE
        SYNTAX DateAndTime
        MAX-ACCESS read-only
        STATUS current
        DESCRIPTION
            "perDateTimeEnd."
        ::= { groupmimoPer24hHisEntry 6 }

    -- 1.3.6.1.4.1.2011.2.25.3.70.10.301.90.1.7
    groupmimoPer24hHisVldty OBJECT-TYPE
        SYNTAX ValidflagType
        MAX-ACCESS read-only
        STATUS current
        DESCRIPTION
            "perVldty."
        ::= { groupmimoPer24hHisEntry 7 }
		
    -- 1.3.6.1.4.1.2011.2.25.3.70.10.300
    optixRtnPerConformance OBJECT IDENTIFIER ::= { rtnPerformance 300 }

    -- 1.3.6.1.4.1.2011.2.25.3.70.10.300.1
    optixRtnPerGroups OBJECT IDENTIFIER ::= { optixRtnPerConformance 1 }

    -- 1.3.6.1.4.1.2011.2.25.3.70.10.300.1.1
    optixRtnPerObjectGroup OBJECT-GROUP
        OBJECTS { laserPer15mCursEid,laserPer15mCurMonValue,laserPer15mCurVldty,laserPer15mCurDatetime,laserPer15mCurParaLen,laserPer15mCurPara,laserPer15mHisEid,laserPer15mHisMonValue,laserPer15mHisVldty,laserPer15mHisDatetime,laserPer15mHisParaLen,laserPer15mhisPara,laserPer24hCurEid,laserPer24hCurMonValue,laserPer24hCurVldty,laserPer24hCurDatetime,laserPer24hCurParaLen,laserPer24hCurPara,laserPer24hHisEid,laserPer24hHisMonValue,laserPer24hHisVldty,laserPer24hHisDatetime,laserPer24hHisParaLen,laserPer24hHisPara,wpidLaserPer15mCurEid,wpidLaserPer15mCurMonValue,wpidLaserPer15mCurVldty,wpidLaserPer15mCurDatetime,wpidLaserPer15mCurParaLen,wpidLaserPer15mCurPara,pathPer15mCursEid,pathPer15mCurMonValue,pathPer15mCurVldty,pathPer15mCurDatetime,pathPer15mCurParaLen,pathPer15mCurPara,pathPer15mHisEid,pathPer15mHisMonValue,pathPer15mHisVldty,pathPer15mHisDatetime,pathPer15mHisParaLen,pathPer15mhisPara,pathPer24hCurEid,pathPer24hCurMonValue,pathPer24hCurVldty,pathPer24hCurDatetime,pathPer24hCurParaLen,
pathPer24hCurPara,pathPer24hHisEid,pathPer24hHisMonValue,pathPer24hHisVldty,pathPer24hHisDatetime,pathPer24hHisParaLen,pathPer24hHisPara,portPer15mCursEid,portPer15mCurMonValue,portPer15mCurVldty,portPer15mCurDatetime,portPer15mCurParaLen,portPer15mCurPara,portPer15mHisEid,portPer15mHisMonValue,portPer15mHisVldty,portPer15mHisDatetime,portPer15mHisParaLen,portPer15mhisPara,portPer24hCurEid,portPer24hCurMonValue,portPer24hCurVldty,portPer24hCurDatetime,portPer24hCurParaLen,portPer24hCurPara,portPer24hHisEid,portPer24hHisMonValue,portPer24hHisVldty,portPer24hHisDatetime,portPer24hHisParaLen,portPer24hHisPara,ifportPer15mCursEid,ifportPer15mCurMonValue,ifportPer15mCurVldty,ifportPer15mCurDatetime,ifportPer15mCurParaLen,ifportPer15mCurPara,ifportPer15mHisEid,ifportPer15mHisMonValue,ifportPer15mHisVldty,ifportPer15mHisDatetime,ifportPer15mHisParaLen,ifportPer15mhisPara,ifportPer24hCurEid,ifportPer24hCurMonValue,ifportPer24hCurVldty,ifportPer24hCurDatetime,ifportPer24hCurParaLen,ifportPer24hCurPara,
ifportPer24hHisEid,ifportPer24hHisMonValue,ifportPer24hHisVldty,ifportPer24hHisDatetime,ifportPer24hHisParaLen,ifportPer24hHisPara,oduportPer15mCursEid,oduportPer15mCurMonValue,oduportPer15mCurVldty,oduportPer15mCurDatetime,oduportPer15mCurParaLen,oduportPer15mCurPara,oduportPer15mHisEid,oduportPer15mHisMonValue,oduportPer15mHisVldty,oduportPer15mHisDatetime,oduportPer15mHisParaLen,oduportPer15mhisPara,oduportPer24hCurEid,oduportPer24hCurMonValue,oduportPer24hCurVldty,oduportPer24hCurDatetime,oduportPer24hCurParaLen,oduportPer24hCurPara,oduportPer24hHisEid,oduportPer24hHisMonValue,oduportPer24hHisVldty,oduportPer24hHisDatetime,oduportPer24hHisParaLen,oduportPer24hHisPara,ifboardPer15mCursEid,ifboardPer15mCurMonValue,ifboardPer15mCurVldty,ifboardPer15mCurDatetime,ifboardPer15mCurParaLen,ifboardPer15mCurPara,ifboardPer15mHisEid,ifboardPer15mHisMonValue,ifboardPer15mHisVldty,ifboardPer15mHisDatetime,ifboardPer15mHisParaLen,ifboardPer15mhisPara,ifboardPer24hCurEid,ifboardPer24hCurMonValue,ifboardPer24hCurVldty,
ifboardPer24hCurDatetime,ifboardPer24hCurParaLen,ifboardPer24hCurPara,ifboardPer24hHisEid,ifboardPer24hHisMonValue,ifboardPer24hHisVldty,ifboardPer24hHisDatetime,ifboardPer24hHisParaLen,ifboardPer24hHisPara,sdhportPer15mCursEid,sdhportPer15mCurMonValue,sdhportPer15mCurVldty,sdhportPer15mCurDatetime,sdhportPer15mCurParaLen,sdhportPer15mCurPara,sdhportPer15mHisEid,sdhportPer15mHisMonValue,sdhportPer15mHisVldty,sdhportPer15mHisDatetime,sdhportPer15mHisParaLen,sdhportPer15mhisPara,sdhportPer24hCurEid,sdhportPer24hCurMonValue,sdhportPer24hCurVldty,sdhportPer24hCurDatetime,sdhportPer24hCurParaLen,sdhportPer24hCurPara,sdhportPer24hHisEid,sdhportPer24hHisMonValue,sdhportPer24hHisVldty,sdhportPer24hHisDatetime,sdhportPer24hHisParaLen,sdhportPer24hHisPara,e1portPer15mCursEid,e1portPer15mCurMonValue,e1portPer15mCurVldty,e1portPer15mCurDatetime,e1portPer15mCurParaLen,e1portPer15mCurPara,e1portPer15mHisEid,e1portPer15mHisMonValue,e1portPer15mHisVldty,e1portPer15mHisDatetime,e1portPer15mHisParaLen,e1portPer15mhisPara,
e1portPer24hCurEid,e1portPer24hCurMonValue,e1portPer24hCurVldty,e1portPer24hCurDatetime,e1portPer24hCurParaLen,e1portPer24hCurPara,e1portPer24hHisEid,e1portPer24hHisMonValue,e1portPer24hHisVldty,e1portPer24hHisDatetime,e1portPer24hHisParaLen,e1portPer24hHisPara,group1j1Per15mCursEid,group1j1Per15mCurMonValue,group1j1Per15mCurVldty,group1j1Per15mCurDatetime,group1j1Per15mCurParaLen,group1j1Per15mCurPara,group1j1Per15mHisEid,group1j1Per15mHisMonValue,group1j1Per15mHisVldty,group1j1Per15mHisDatetime,group1j1Per15mHisParaLen,group1j1Per15mhisPara,group1j1Per24hCurEid,group1j1Per24hCurMonValue,group1j1Per24hCurVldty,group1j1Per24hCurDatetime,group1j1Per24hCurParaLen,group1j1Per24hCurPara,group1j1Per24hHisEid,group1j1Per24hHisMonValue,group1j1Per24hHisVldty,group1j1Per24hHisDatetime,group1j1Per24hHisParaLen,group1j1Per24hHisPara,vc12pathPer15mCursEid,vc12pathPer15mCurMonValue,vc12pathPer15mCurVldty,vc12pathPer15mCurDatetime,vc12pathPer15mCurParaLen,vc12pathPer15mCurPara,vc12pathPer15mHisEid,
vc12pathPer15mHisMonValue,vc12pathPer15mHisVldty,vc12pathPer15mHisDatetime,vc12pathPer15mHisParaLen,vc12pathPer15mhisPara,vc12pathPer24hCurEid,vc12pathPer24hCurMonValue,vc12pathPer24hCurVldty,vc12pathPer24hCurDatetime,vc12pathPer24hCurParaLen,vc12pathPer24hCurPara,vc12pathPer24hHisEid,vc12pathPer24hHisMonValue,vc12pathPer24hHisVldty,vc12pathPer24hHisDatetime,vc12pathPer24hHisParaLen,vc12pathPer24hHisPara,vc3pathPer15mCursEid,vc3pathPer15mCurMonValue,vc3pathPer15mCurVldty,vc3pathPer15mCurDatetime,vc3pathPer15mCurParaLen,vc3pathPer15mCurPara,vc3pathPer15mHisEid,vc3pathPer15mHisMonValue,vc3pathPer15mHisVldty,vc3pathPer15mHisDatetime,vc3pathPer15mHisParaLen,vc3pathPer15mhisPara,vc3pathPer24hCurEid,vc3pathPer24hCurMonValue,vc3pathPer24hCurVldty,vc3pathPer24hCurDatetime,vc3pathPer24hCurParaLen,vc3pathPer24hCurPara,vc3pathPer24hHisEid,vc3pathPer24hHisMonValue,vc3pathPer24hHisVldty,vc3pathPer24hHisDatetime,vc3pathPer24hHisParaLen,vc3pathPer24hHisPara,sysClockPer15mCursEid,sysClockPer15mCurMonValue,
sysClockPer15mCurVldty,sysClockPer15mCurDatetime,sysClockPer15mCurParaLen,sysClockPer15mCurPara,sysClockPer15mHisEid,sysClockPer15mHisMonValue,sysClockPer15mHisVldty,sysClockPer15mHisDatetime,sysClockPer15mHisParaLen,sysClockPer15mhisPara,sysClockPer24hCurEid,sysClockPer24hCurMonValue,sysClockPer24hCurVldty,sysClockPer24hCurDatetime,sysClockPer24hCurParaLen,sysClockPer24hCurPara,sysClockPer24hHisEid,sysClockPer24hHisMonValue,sysClockPer24hHisVldty,sysClockPer24hHisDatetime,sysClockPer24hHisParaLen,sysClockPer24hHisPara,pwofatmPer15mCursEid,pwofatmPer15mCurMonValue,pwofatmPer15mCurVldty,pwofatmPer15mCurDatetime,pwofatmPer15mCurParaLen,pwofatmPer15mCurPara,pwofatmPer15mHisEid,pwofatmPer15mHisMonValue,pwofatmPer15mHisVldty,pwofatmPer15mHisDatetime,pwofatmPer15mHisParaLen,pwofatmPer15mhisPara,pwofatmPer24hCurEid,pwofatmPer24hCurMonValue,pwofatmPer24hCurVldty,pwofatmPer24hCurDatetime,pwofatmPer24hCurParaLen,pwofatmPer24hCurPara,pwofatmPer24hHisEid,pwofatmPer24hHisMonValue,pwofatmPer24hHisVldty,
pwofatmPer24hHisDatetime,pwofatmPer24hHisParaLen,pwofatmPer24hHisPara,boardPer24hHisPara,boardPer24hHisParaLen,boardPer24hHisDatetime,boardPer24hHisVldty,boardPer24hHisMonValue,boardPer24hHisEid,boardPer24hCurPara,boardPer24hCurParaLen,boardPer24hCurDatetime,boardPer24hCurVldty,boardPer24hCurMonValue,boardPer24hCurEid,boardPer15mHisPara,boardPer15mHisParaLen,boardPer15mHisDatetime,boardPer15mHisVldty,boardPer15mHisMonValue,boardPer15mHisEid,boardPer15mCurPara,boardPer15mCurParaLen,boardPer15mCurDatetime,boardPer15mCurVldty,boardPer15mCurMonValue,
tunnelPer15mCurEid,tunnelPer15mCurMonValue,tunnelPer15mCurVldty,tunnelPer15mCurDatetime,tunnelPer15mCurParaLen,tunnelPer15mCurPara,
tunnelPer15mHisEid,tunnelPer15mHisParaLen,tunnelPer15mHisPara,tunnelPer15mHisMonValue,tunnelPer15mHisStartTime,tunnelPer15mHisEndTime,tunnelPer15mHisVldty,
tunnelPer24hCurEid,tunnelPer24hCurMonValue,tunnelPer24hCurVldty,tunnelPer24hCurDatetime,tunnelPer24hCurParaLen,tunnelPer24hCurPara,
tunnelPer24hHisEid,tunnelPer24hHisParaLen,tunnelPer24hHisPara,tunnelPer24hHisMonValue,tunnelPer24hHisStartTime,tunnelPer24hHisEndTime,tunnelPer24hHisVldty,
pwofl2vpnPer15mCurEid,pwofl2vpnPer15mCurMonValue,pwofl2vpnPer15mCurVldty,pwofl2vpnPer15mCurDatetime,pwofl2vpnPer15mCurParaLen,pwofl2vpnPer15mCurPara,
pwofl2vpnPer15mHisEid,pwofl2vpnPer15mHisParaLen,pwofl2vpnPer15mHisPara,pwofl2vpnPer15mHisMonValue,pwofl2vpnPer15mHisStartTime,pwofl2vpnPer15mHisEndTime,pwofl2vpnPer15mHisVldty,
pwofl2vpnPer24hCurEid,pwofl2vpnPer24hCurMonValue,pwofl2vpnPer24hCurVldty,pwofl2vpnPer24hCurDatetime,pwofl2vpnPer24hCurParaLen,pwofl2vpnPer24hCurPara,
pwofl2vpnPer24hHisEid,pwofl2vpnPer24hHisParaLen,pwofl2vpnPer24hHisPara,pwofl2vpnPer24hHisMonValue,pwofl2vpnPer24hHisStartTime,pwofl2vpnPer24hHisEndTime,pwofl2vpnPer24hHisVldty,
groupplaPer15mCurEid,groupplaPer15mCurMonValue,groupplaPer15mCurVldty,groupplaPer15mCurDatetime,groupplaPer15mCurParaLen,groupplaPer15mCurPara,
groupplaPer15mHisEid,groupplaPer15mHisParaLen,groupplaPer15mHisPara,groupplaPer15mHisMonValue,groupplaPer15mHisStartTime,groupplaPer15mHisEndTime,groupplaPer15mHisVldty,
groupplaPer24hCurEid,groupplaPer24hCurMonValue,groupplaPer24hCurVldty,groupplaPer24hCurDatetime,groupplaPer24hCurParaLen,groupplaPer24hCurPara,
groupplaPer24hHisEid,groupplaPer24hHisParaLen,groupplaPer24hHisPara,groupplaPer24hHisMonValue,groupplaPer24hHisStartTime,groupplaPer24hHisEndTime,groupplaPer24hHisVldty,
synSourcePer15mCurEid,synSourcePer15mCurMonValue,synSourcePer15mCurVldty,synSourcePer15mCurDatetime,synSourcePer15mCurParaLen,synSourcePer15mCurPara,
synSourcePer15mHisEid,synSourcePer15mHisParaLen,synSourcePer15mHisPara,synSourcePer15mHisMonValue,synSourcePer15mHisStartTime,synSourcePer15mHisEndTime,synSourcePer15mHisVldty,
synSourcePer24hCurEid,synSourcePer24hCurMonValue,synSourcePer24hCurVldty,synSourcePer24hCurDatetime,synSourcePer24hCurParaLen,synSourcePer24hCurPara,
synSourcePer24hHisEid,synSourcePer24hHisParaLen,synSourcePer24hHisPara,synSourcePer24hHisMonValue,synSourcePer24hHisStartTime,synSourcePer24hHisEndTime,synSourcePer24hHisVldty,
boardPer15mCursEid,
oducarrierPer15mCurEid,oducarrierPer15mCurMonValue,oducarrierPer15mCurVldty,oducarrierPer15mCurDatetime,oducarrierPer15mCurParaLen,oducarrierPer15mCurPara,
oducarrierPer15mHisEid,oducarrierPer15mHisParaLen,oducarrierPer15mHisPara,oducarrierPer15mHisMonValue,oducarrierPer15mHisStartTime,oducarrierPer15mHisEndTime,oducarrierPer15mHisVldty,
oducarrierPer24hCurEid,oducarrierPer24hCurMonValue,oducarrierPer24hCurVldty,oducarrierPer24hCurDatetime,oducarrierPer24hCurParaLen,oducarrierPer24hCurPara,
oducarrierPer24hHisEid,oducarrierPer24hHisParaLen,oducarrierPer24hHisPara,oducarrierPer24hHisMonValue,oducarrierPer24hHisStartTime,oducarrierPer24hHisEndTime,oducarrierPer24hHisVldty,
cprilaser,cprilaserPer15mCurTable,cprilaserPer15mCurEntry,cprilaserPer15mCurEid,cprilaserPer15mCurMonValue,cprilaserPer15mCurVldty,cprilaserPer15mCurDatetime,cprilaserPer15mCurParaLen,cprilaserPer15mCurPara,cprilaserPer15mHisTable,cprilaserPer15mHisEntry,cprilaserPer15mHisEid,cprilaserPer15mHisParaLen,cprilaserPer15mHisPara,cprilaserPer15mHisMonValue,cprilaserPer15mHisStartTime,cprilaserPer15mHisEndTime,cprilaserPer15mHisVldty,cprilaserPer24hCurTable,cprilaserPer24hCurEntry,cprilaserPer24hCurEid,cprilaserPer24hCurMonValue,cprilaserPer24hCurVldty,cprilaserPer24hCurDatetime,cprilaserPer24hCurParaLen,cprilaserPer24hCurPara,cprilaserPer24hHisTable,cprilaserPer24hHisEntry,cprilaserPer24hHisEid,cprilaserPer24hHisParaLen,cprilaserPer24hHisPara,cprilaserPer24hHisMonValue,cprilaserPer24hHisStartTime,cprilaserPer24hHisEndTime,cprilaserPer24hHisVldty,
cpriport,cpriportPer15mCurTable,cpriportPer15mCurEntry,cpriportPer15mCurEid,cpriportPer15mCurMonValue,cpriportPer15mCurVldty,cpriportPer15mCurDatetime,cpriportPer15mCurParaLen,cpriportPer15mCurPara,cpriportPer15mHisTable,cpriportPer15mHisEntry,cpriportPer15mHisEid,
cpriportPer15mHisParaLen,cpriportPer15mHisPara,cpriportPer15mHisMonValue,cpriportPer15mHisStartTime,cpriportPer15mHisEndTime,cpriportPer15mHisVldty,cpriportPer24hCurTable,cpriportPer24hCurEntry,cpriportPer24hCurEid,cpriportPer24hCurMonValue,cpriportPer24hCurVldty,cpriportPer24hCurDatetime,cpriportPer24hCurParaLen,cpriportPer24hCurPara,cpriportPer24hHisTable,cpriportPer24hHisEntry,cpriportPer24hHisEid,cpriportPer24hHisParaLen,cpriportPer24hHisPara,cpriportPer24hHisMonValue,cpriportPer24hHisStartTime,cpriportPer24hHisEndTime, cpriportPer24hHisVldty,
obsailaser,obsailaserPer15mCurTable,obsailaserPer15mCurEntry,obsailaserPer15mCurEid,obsailaserPer15mCurMonValue,obsailaserPer15mCurVldty,obsailaserPer15mCurDatetime,obsailaserPer15mCurParaLen,obsailaserPer15mCurPara,obsailaserPer15mHisTable,obsailaserPer15mHisEntry,obsailaserPer15mHisEid,obsailaserPer15mHisParaLen,obsailaserPer15mHisPara,obsailaserPer15mHisMonValue,obsailaserPer15mHisStartTime,obsailaserPer15mHisEndTime,obsailaserPer15mHisVldty,obsailaserPer24hCurTable,obsailaserPer24hCurEntry,obsailaserPer24hCurEid,obsailaserPer24hCurMonValue,obsailaserPer24hCurVldty,obsailaserPer24hCurDatetime,obsailaserPer24hCurParaLen,obsailaserPer24hCurPara,obsailaserPer24hHisTable,obsailaserPer24hHisEntry,obsailaserPer24hHisEid,obsailaserPer24hHisParaLen,obsailaserPer24hHisPara,obsailaserPer24hHisMonValue,obsailaserPer24hHisStartTime,obsailaserPer24hHisEndTime,obsailaserPer24hHisVldty,
obsaiport,obsaiportPer15mCurTable,obsaiportPer15mCurEntry,obsaiportPer15mCurEid,obsaiportPer15mCurMonValue,obsaiportPer15mCurVldty,obsaiportPer15mCurDatetime,obsaiportPer15mCurParaLen,obsaiportPer15mCurPara,obsaiportPer15mHisTable,obsaiportPer15mHisEntry,obsaiportPer15mHisEid,obsaiportPer15mHisParaLen,obsaiportPer15mHisPara,obsaiportPer15mHisMonValue,obsaiportPer15mHisStartTime,obsaiportPer15mHisEndTime,obsaiportPer15mHisVldty,obsaiportPer24hCurTable,obsaiportPer24hCurEntry,obsaiportPer24hCurEid,obsaiportPer24hCurMonValue,obsaiportPer24hCurVldty,obsaiportPer24hCurDatetime,obsaiportPer24hCurParaLen,obsaiportPer24hCurPara,obsaiportPer24hHisTable,obsaiportPer24hHisEntry,obsaiportPer24hHisEid,obsaiportPer24hHisParaLen,obsaiportPer24hHisPara,obsaiportPer24hHisMonValue,obsaiportPer24hHisStartTime,obsaiportPer24hHisEndTime,obsaiportPer24hHisVldty,
groupmimoPer15mCurEid,groupmimoPer15mCurMonValue,groupmimoPer15mCurVldty,groupmimoPer15mCurDatetime,groupmimoPer15mCurParaLen,groupmimoPer15mCurPara,
groupmimoPer15mHisEid,groupmimoPer15mHisParaLen,groupmimoPer15mHisPara,groupmimoPer15mHisMonValue,groupmimoPer15mHisStartTime,groupmimoPer15mHisEndTime,groupmimoPer15mHisVldty,
groupmimoPer24hCurEid,groupmimoPer24hCurMonValue,groupmimoPer24hCurVldty,groupmimoPer24hCurDatetime,groupmimoPer24hCurParaLen,groupmimoPer24hCurPara,
groupmimoPer24hHisEid,groupmimoPer24hHisParaLen,groupmimoPer24hHisPara,groupmimoPer24hHisMonValue,groupmimoPer24hHisStartTime,groupmimoPer24hHisEndTime,groupmimoPer24hHisVldty}
        STATUS current
        DESCRIPTION
            "Enter the description of the created OBJECT-GROUP."
        ::= { optixRtnPerGroups 1 }

    -- 1.3.6.1.4.1.2011.2.25.3.70.10.300.2
    optixRtnPerCompliances OBJECT IDENTIFIER ::= { optixRtnPerConformance 2 }

    -- 1.3.6.1.4.1.2011.2.25.3.70.10.300.2.1
    optixRtnPerbasicCompliance MODULE-COMPLIANCE
        STATUS current
        DESCRIPTION
            "Enter the description of the created MODULE-COMPLIANCE."
        MODULE -- this module
            MANDATORY-GROUPS { optixRtnPerObjectGroup }
        ::= { optixRtnPerCompliances 1 }

END
