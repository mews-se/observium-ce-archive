-- OPTIX-GLOBAL-PM-TRAPS-RTN-MIB
-- MIB generated by ExcelToMIB tool 1.0
-- 
-- =================================================================
--  Copyright (C) 2012 by HUAWEI TECHNOLOGIES. All rights reserved
--  
--  Description:This MIB describes the Data		pmformance interface of Huawei macrowave transmit
--  Reference:
--  Version: V1.00
--  History:
--  <author>,<date>,<contents>
-- =================================================================
--
OPTIX-GLOBAL-PM-TRAPS-RTN-MIB DEFINITIONS ::= BEGIN
 
		IMPORTS
        optixCommonGlobal
            FROM OPTIX-OID-MIB
        PerformanceEventType,ValidflagType,ObjType,AlarmEventType,AlmDataSrvEffType,AlmDataNtfcnCdeType,DataPmEventType
            FROM OPTIX-GLOBAL-TC-MIB
        OBJECT-GROUP,MODULE-COMPLIANCE
            FROM SNMPv2-CONF
        Integer32,Unsigned32,OBJECT-TYPE,MODULE-IDENTITY,NOTIFICATION-TYPE
            FROM SNMPv2-SMI
        DateAndTime,DisplayString
            FROM SNMPv2-TC
        optixGlobalTrap,rptEvtDateTime,rptEvtMonValue,rptEvtThValue,rptEvtPeriod,rptEvtVldty,rptEvtValue,rptEvtObjType,rptEvtParaLen,rptEvtPara,rptEvtDataPmName
            FROM OPTIX-GLOBAL-TRAPS-MIB
        ;

    -- 1.3.6.1.4.1.2011.2.25.3.40.40.20
    optixTrapsPM OBJECT IDENTIFIER ::= { optixGlobalTrap 20 }

    -- 1.3.6.1.4.1.2011.2.25.3.40.40.20.101
    pmRXPKT64 NOTIFICATION-TYPE
        OBJECTS{ rptEvtPeriod,rptEvtValue,rptEvtVldty,rptEvtDateTime,rptEvtObjType,rptEvtParaLen,rptEvtPara }
        STATUS current
        DESCRIPTION
            "The total number of received packets (including bad packets) whose length is 64 bytes (excluding framing bits, but including FCS bytes)."
        ::= { optixTrapsPM 101 }

    -- 1.3.6.1.4.1.2011.2.25.3.40.40.20.102
    pmRXPKT65 NOTIFICATION-TYPE
        OBJECTS{ rptEvtPeriod,rptEvtValue,rptEvtVldty,rptEvtDateTime,rptEvtObjType,rptEvtParaLen,rptEvtPara }
        STATUS current
        DESCRIPTION
            "The total number of received packets (including bad packets) whose length is between 65 and 127 bytes (excluding framing bits, but including FCS bytes)."
        ::= { optixTrapsPM 102 }

    -- 1.3.6.1.4.1.2011.2.25.3.40.40.20.103
    pmRXPKT128 NOTIFICATION-TYPE
        OBJECTS{ rptEvtPeriod,rptEvtValue,rptEvtVldty,rptEvtDateTime,rptEvtObjType,rptEvtParaLen,rptEvtPara }
        STATUS current
        DESCRIPTION
            "The total number of received packets (including bad packets) whose length is between 128 and 255 bytes (excluding framing bits, but including FCS bytes)."
        ::= { optixTrapsPM 103 }

    -- 1.3.6.1.4.1.2011.2.25.3.40.40.20.104
    pmRXPKT256 NOTIFICATION-TYPE
        OBJECTS{ rptEvtPeriod,rptEvtValue,rptEvtVldty,rptEvtDateTime,rptEvtObjType,rptEvtParaLen,rptEvtPara }
        STATUS current
        DESCRIPTION
            "The total number of received packets (including bad packets) whose length is between 256 and 511 bytes (excluding framing bits, but including FCS bytes)."
        ::= { optixTrapsPM 104 }

    -- 1.3.6.1.4.1.2011.2.25.3.40.40.20.105
    pmRXPKT512 NOTIFICATION-TYPE
        OBJECTS{ rptEvtPeriod,rptEvtValue,rptEvtVldty,rptEvtDateTime,rptEvtObjType,rptEvtParaLen,rptEvtPara }
        STATUS current
        DESCRIPTION
            "The total number of received packets (including bad packets) whose length is between 512 and 1023 bytes (excluding framing bits, but including FCS bytes)."
        ::= { optixTrapsPM 105 }

    -- 1.3.6.1.4.1.2011.2.25.3.40.40.20.106
    pmRXPKT1024 NOTIFICATION-TYPE
        OBJECTS{ rptEvtPeriod,rptEvtValue,rptEvtVldty,rptEvtDateTime,rptEvtObjType,rptEvtParaLen,rptEvtPara }
        STATUS current
        DESCRIPTION
            "The total number of received packets (including bad packets) whose length is between 1024 and 1518 bytes (excluding framing bits, but including FCS bytes)."
        ::= { optixTrapsPM 106 }

    -- 1.3.6.1.4.1.2011.2.25.3.40.40.20.107
    pmTXPKT64 NOTIFICATION-TYPE
        OBJECTS{ rptEvtPeriod,rptEvtValue,rptEvtVldty,rptEvtDateTime,rptEvtObjType,rptEvtParaLen,rptEvtPara }
        STATUS current
        DESCRIPTION
            "The total number of transmitted packets (including bad packets) whose length is between 64 bytes (excluding framing bits, but including FCS bytes)."
        ::= { optixTrapsPM 107 }

    -- 1.3.6.1.4.1.2011.2.25.3.40.40.20.108
    pmTXPKT65 NOTIFICATION-TYPE
        OBJECTS{ rptEvtPeriod,rptEvtValue,rptEvtVldty,rptEvtDateTime,rptEvtObjType,rptEvtParaLen,rptEvtPara }
        STATUS current
        DESCRIPTION
            "The total number of transmitted packets (including bad packets) whose length is between 65 and 127 bytes (excluding framing bits, but including FCS bytes)."
        ::= { optixTrapsPM 108 }

    -- 1.3.6.1.4.1.2011.2.25.3.40.40.20.109
    pmTXPKT128 NOTIFICATION-TYPE
        OBJECTS{ rptEvtPeriod,rptEvtValue,rptEvtVldty,rptEvtDateTime,rptEvtObjType,rptEvtParaLen,rptEvtPara }
        STATUS current
        DESCRIPTION
            "The total number of transmitted packets (including bad packets) whose length is between 128 and 255 bytes (excluding framing bits, but including FCS bytes)."
        ::= { optixTrapsPM 109 }

    -- 1.3.6.1.4.1.2011.2.25.3.40.40.20.110
    pmTXPKT256 NOTIFICATION-TYPE
        OBJECTS{ rptEvtPeriod,rptEvtValue,rptEvtVldty,rptEvtDateTime,rptEvtObjType,rptEvtParaLen,rptEvtPara }
        STATUS current
        DESCRIPTION
            "The total number of transmitted packets (including bad packets) whose length is between 256 and 511 bytes (excluding framing bits, but including FCS bytes)."
        ::= { optixTrapsPM 110 }

    -- 1.3.6.1.4.1.2011.2.25.3.40.40.20.111
    pmTXPKT512 NOTIFICATION-TYPE
        OBJECTS{ rptEvtPeriod,rptEvtValue,rptEvtVldty,rptEvtDateTime,rptEvtObjType,rptEvtParaLen,rptEvtPara }
        STATUS current
        DESCRIPTION
            "The total number of transmitted packets (including bad packets) whose length is between 512 and 1023 bytes (excluding framing bits, but including FCS bytes)."
        ::= { optixTrapsPM 111 }

    -- 1.3.6.1.4.1.2011.2.25.3.40.40.20.112
    pmTXPKT1024 NOTIFICATION-TYPE
        OBJECTS{ rptEvtPeriod,rptEvtValue,rptEvtVldty,rptEvtDateTime,rptEvtObjType,rptEvtParaLen,rptEvtPara }
        STATUS current
        DESCRIPTION
            "The total number of transmitted packets (including bad packets) whose length is between 1024 and 1518 bytes (excluding framing bits, but including FCS bytes)."
        ::= { optixTrapsPM 112 }

    -- 1.3.6.1.4.1.2011.2.25.3.40.40.20.113
    pmRXUNICAST NOTIFICATION-TYPE
        OBJECTS{ rptEvtPeriod,rptEvtValue,rptEvtVldty,rptEvtDateTime,rptEvtObjType,rptEvtParaLen,rptEvtPara }
        STATUS current
        DESCRIPTION
            "The total number of unicast good packets received."
        ::= { optixTrapsPM 113 }

    -- 1.3.6.1.4.1.2011.2.25.3.40.40.20.114
    pmRXMULCAST NOTIFICATION-TYPE
        OBJECTS{ rptEvtPeriod,rptEvtValue,rptEvtVldty,rptEvtDateTime,rptEvtObjType,rptEvtParaLen,rptEvtPara }
        STATUS current
        DESCRIPTION
            "The total number of received good packets (excluding broadcast packets) whose destination address is a multicast address."
        ::= { optixTrapsPM 114 }

    -- 1.3.6.1.4.1.2011.2.25.3.40.40.20.115
    pmRXBRDCAST NOTIFICATION-TYPE
        OBJECTS{ rptEvtPeriod,rptEvtValue,rptEvtVldty,rptEvtDateTime,rptEvtObjType,rptEvtParaLen,rptEvtPara }
        STATUS current
        DESCRIPTION
            "The total number of received good packets (excluding multicast packets) whose destination address is the broadcast address."
        ::= { optixTrapsPM 115 }

    -- 1.3.6.1.4.1.2011.2.25.3.40.40.20.116
    pmTXUNICAST NOTIFICATION-TYPE
        OBJECTS{ rptEvtPeriod,rptEvtValue,rptEvtVldty,rptEvtDateTime,rptEvtObjType,rptEvtParaLen,rptEvtPara }
        STATUS current
        DESCRIPTION
            "The total number of transmitted unicast packets, including packets that are discarded and are not successfully transmitted."
        ::= { optixTrapsPM 116 }

    -- 1.3.6.1.4.1.2011.2.25.3.40.40.20.117
    pmTXMULCAST NOTIFICATION-TYPE
        OBJECTS{ rptEvtPeriod,rptEvtValue,rptEvtVldty,rptEvtDateTime,rptEvtObjType,rptEvtParaLen,rptEvtPara }
        STATUS current
        DESCRIPTION
            "The total number of transmitted multicast packets, including packets that are discarded and are not successfully transmitted."
        ::= { optixTrapsPM 117 }

    -- 1.3.6.1.4.1.2011.2.25.3.40.40.20.118
    pmTXBRDCAST NOTIFICATION-TYPE
        OBJECTS{ rptEvtPeriod,rptEvtValue,rptEvtVldty,rptEvtDateTime,rptEvtObjType,rptEvtParaLen,rptEvtPara }
        STATUS current
        DESCRIPTION
            "The total number of transmitted broadcast packets, including packets that are discarded and are not successfully transmitted."
        ::= { optixTrapsPM 118 }

    -- 1.3.6.1.4.1.2011.2.25.3.40.40.20.119
    pmRXPAUSE NOTIFICATION-TYPE
        OBJECTS{ rptEvtPeriod,rptEvtValue,rptEvtVldty,rptEvtDateTime,rptEvtObjType,rptEvtParaLen,rptEvtPara }
        STATUS current
        DESCRIPTION
            "A count of received MAC flow control frames that have the PAUSE operation code."
        ::= { optixTrapsPM 119 }

    -- 1.3.6.1.4.1.2011.2.25.3.40.40.20.120
    pmTXPAUSE NOTIFICATION-TYPE
        OBJECTS{ rptEvtPeriod,rptEvtValue,rptEvtVldty,rptEvtDateTime,rptEvtObjType,rptEvtParaLen,rptEvtPara }
        STATUS current
        DESCRIPTION
            "A count of transmitted MAC flow control frames that have the PAUSE operation code."
        ::= { optixTrapsPM 120 }

    -- 1.3.6.1.4.1.2011.2.25.3.40.40.20.121
    pmETHDROP NOTIFICATION-TYPE
        OBJECTS{ rptEvtPeriod,rptEvtValue,rptEvtVldty,rptEvtDateTime,rptEvtObjType,rptEvtParaLen,rptEvtPara }
        STATUS current
        DESCRIPTION
            "The number of events in which packet loss occurs due to lack of resources. Note that this number is not necessarily the number of discarded packets; it is just the number of times for which this condition has been detected."
        ::= { optixTrapsPM 121 }

    -- 1.3.6.1.4.1.2011.2.25.3.40.40.20.122
    pmETHUNDER NOTIFICATION-TYPE
        OBJECTS{ rptEvtPeriod,rptEvtValue,rptEvtVldty,rptEvtDateTime,rptEvtObjType,rptEvtParaLen,rptEvtPara }
        STATUS current
        DESCRIPTION
            "The total number of received packets (excluding framing bits, but including FCS bytes) that have a length of smaller than 64 bytes, and that do not have any other errors."
        ::= { optixTrapsPM 122 }

    -- 1.3.6.1.4.1.2011.2.25.3.40.40.20.123
    pmETHOVER NOTIFICATION-TYPE
        OBJECTS{ rptEvtPeriod,rptEvtValue,rptEvtVldty,rptEvtDateTime,rptEvtObjType,rptEvtParaLen,rptEvtPara }
        STATUS current
        DESCRIPTION
            "The total number of received packets (excluding framing bits, but including FCS bytes) that have a length of greater than 1518 bytes, and that do not have any other errors."
        ::= { optixTrapsPM 123 }

    -- 1.3.6.1.4.1.2011.2.25.3.40.40.20.124
    pmETHFRG NOTIFICATION-TYPE
        OBJECTS{ rptEvtPeriod,rptEvtValue,rptEvtVldty,rptEvtDateTime,rptEvtObjType,rptEvtParaLen,rptEvtPara }
        STATUS current
        DESCRIPTION
            "The total number of received packets (excluding framing bits, but including FCS bytes) that have a length of smaller than 64 bytes, and that have FCS errors or alignment errors. Due to the existence of noise collision, the increase of this number is normal."
        ::= { optixTrapsPM 124 }

    -- 1.3.6.1.4.1.2011.2.25.3.40.40.20.125
    pmETHJAB NOTIFICATION-TYPE
        OBJECTS{ rptEvtPeriod,rptEvtValue,rptEvtVldty,rptEvtDateTime,rptEvtObjType,rptEvtParaLen,rptEvtPara }
        STATUS current
        DESCRIPTION
            "The total number of received packets (excluding framing bits, but including FCS bytes) that have a length of greater than 1518 bytes, and that have FCS errors or alignment errors."
        ::= { optixTrapsPM 125 }

    -- 1.3.6.1.4.1.2011.2.25.3.40.40.20.126
    pmRXBGOOD NOTIFICATION-TYPE
        OBJECTS{ rptEvtPeriod,rptEvtValue,rptEvtVldty,rptEvtDateTime,rptEvtObjType,rptEvtParaLen,rptEvtPara }
        STATUS current
        DESCRIPTION
            "The total number of octets of good packets received on the network (excluding framing bits but including FCS octets)."
        ::= { optixTrapsPM 126 }

    -- 1.3.6.1.4.1.2011.2.25.3.40.40.20.127
    pmTXBGOOD NOTIFICATION-TYPE
        OBJECTS{ rptEvtPeriod,rptEvtValue,rptEvtVldty,rptEvtDateTime,rptEvtObjType,rptEvtParaLen,rptEvtPara }
        STATUS current
        DESCRIPTION
            "The total number of octets of good packets transmitted on the network (excluding framing bits but including FCS octets)."
        ::= { optixTrapsPM 127 }

    -- 1.3.6.1.4.1.2011.2.25.3.40.40.20.128
    pmRXBBAD NOTIFICATION-TYPE
        OBJECTS{ rptEvtPeriod,rptEvtValue,rptEvtVldty,rptEvtDateTime,rptEvtObjType,rptEvtParaLen,rptEvtPara }
        STATUS current
        DESCRIPTION
            "The total number of received bad-packet bytes (excluding framing bits, but including FCS bytes)."
        ::= { optixTrapsPM 128 }

    -- 1.3.6.1.4.1.2011.2.25.3.40.40.20.129
    pmTXBBAD NOTIFICATION-TYPE
        OBJECTS{ rptEvtPeriod,rptEvtValue,rptEvtVldty,rptEvtDateTime,rptEvtObjType,rptEvtParaLen,rptEvtPara }
        STATUS current
        DESCRIPTION
            "The total number of transmitted bad-packet bytes (excluding framing bits, but including FCS bytes)."
        ::= { optixTrapsPM 129 }

    -- 1.3.6.1.4.1.2011.2.25.3.40.40.20.130
    pmETHCOL NOTIFICATION-TYPE
        OBJECTS{ rptEvtPeriod,rptEvtValue,rptEvtVldty,rptEvtDateTime,rptEvtObjType,rptEvtParaLen,rptEvtPara }
        STATUS current
        DESCRIPTION
            "The best evaluation of the total number of collisions."
        ::= { optixTrapsPM 130 }

    -- 1.3.6.1.4.1.2011.2.25.3.40.40.20.131
    pmETHALI NOTIFICATION-TYPE
        OBJECTS{ rptEvtPeriod,rptEvtValue,rptEvtVldty,rptEvtDateTime,rptEvtObjType,rptEvtParaLen,rptEvtPara }
        STATUS current
        DESCRIPTION
            "The number of received frames that have alignment errors. An alignment errored frame cannot pass the FCS check because the frame contains a non-integer number of bytes."
        ::= { optixTrapsPM 131 }

    -- 1.3.6.1.4.1.2011.2.25.3.40.40.20.132
    pmETHFCS NOTIFICATION-TYPE
        OBJECTS{ rptEvtPeriod,rptEvtValue,rptEvtVldty,rptEvtDateTime,rptEvtObjType,rptEvtParaLen,rptEvtPara }
        STATUS current
        DESCRIPTION
            "A count of received frames that are an integer number of bytes in length and have FCS errors. This count does not include oversize and undersize frames."
        ::= { optixTrapsPM 132 }

    -- 1.3.6.1.4.1.2011.2.25.3.40.40.20.133
    pmETHUNICOL NOTIFICATION-TYPE
        OBJECTS{ rptEvtPeriod,rptEvtValue,rptEvtVldty,rptEvtDateTime,rptEvtObjType,rptEvtParaLen,rptEvtPara }
        STATUS current
        DESCRIPTION
            "Single Collision Frames"
        ::= { optixTrapsPM 133 }

    -- 1.3.6.1.4.1.2011.2.25.3.40.40.20.134
    pmETHMULCOL NOTIFICATION-TYPE
        OBJECTS{ rptEvtPeriod,rptEvtValue,rptEvtVldty,rptEvtDateTime,rptEvtObjType,rptEvtParaLen,rptEvtPara }
        STATUS current
        DESCRIPTION
            "MultipleCollisionFrames"
        ::= { optixTrapsPM 134 }

    -- 1.3.6.1.4.1.2011.2.25.3.40.40.20.135
    pmETHLATECOL NOTIFICATION-TYPE
        OBJECTS{ rptEvtPeriod,rptEvtValue,rptEvtVldty,rptEvtDateTime,rptEvtObjType,rptEvtParaLen,rptEvtPara }
        STATUS current
        DESCRIPTION
            "The number of times for which a collision is detected after a length of more than one timeslot. A later collision is an obvious indication that the LAN diameter is overlarge."
        ::= { optixTrapsPM 135 }

    -- 1.3.6.1.4.1.2011.2.25.3.40.40.20.136
    pmETHEXCCOL NOTIFICATION-TYPE
        OBJECTS{ rptEvtPeriod,rptEvtValue,rptEvtVldty,rptEvtDateTime,rptEvtObjType,rptEvtParaLen,rptEvtPara }
        STATUS current
        DESCRIPTION
            "A count of frames that are unsuccessfully transmitted after successive collisions."
        ::= { optixTrapsPM 136 }

    -- 1.3.6.1.4.1.2011.2.25.3.40.40.20.137
    pmTXDEFFRM NOTIFICATION-TYPE
        OBJECTS{ rptEvtPeriod,rptEvtValue,rptEvtVldty,rptEvtDateTime,rptEvtObjType,rptEvtParaLen,rptEvtPara }
        STATUS current
        DESCRIPTION
            "A count of frames whose first transmission is delayed because the transmission media is busy. This count does not include collision related frames."
        ::= { optixTrapsPM 137 }

    -- 1.3.6.1.4.1.2011.2.25.3.40.40.20.138
    pmETHCARERR NOTIFICATION-TYPE
        OBJECTS{ rptEvtPeriod,rptEvtValue,rptEvtVldty,rptEvtDateTime,rptEvtObjType,rptEvtParaLen,rptEvtPara }
        STATUS current
        DESCRIPTION
            "Carrier Sense Errors"
        ::= { optixTrapsPM 138 }

    -- 1.3.6.1.4.1.2011.2.25.3.40.40.20.139
    pmRXPKT1519 NOTIFICATION-TYPE
        OBJECTS{ rptEvtPeriod,rptEvtValue,rptEvtVldty,rptEvtDateTime,rptEvtObjType,rptEvtParaLen,rptEvtPara }
        STATUS current
        DESCRIPTION
            "The number of receive packets,with lengths between 1519 bytes and the maximum packet size,including bad packets."
        ::= { optixTrapsPM 139 }

    -- 1.3.6.1.4.1.2011.2.25.3.40.40.20.140
    pmTXPKT1519 NOTIFICATION-TYPE
        OBJECTS{ rptEvtPeriod,rptEvtValue,rptEvtVldty,rptEvtDateTime,rptEvtObjType,rptEvtParaLen,rptEvtPara }
        STATUS current
        DESCRIPTION
            "The Number Of Transmitted Packets Larger than 1518 Bytes, Including Bad Packets."
        ::= { optixTrapsPM 140 }

    -- 1.3.6.1.4.1.2011.2.25.3.40.40.20.141
    pmPKT64 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 64 bytes (excluding framing bits, but including FCS bytes)."
        ::= { optixTrapsPM 141 }

    -- 1.3.6.1.4.1.2011.2.25.3.40.40.20.142
    pmPKT65 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 65 and 127 bytes (excluding framing bits, but including FCS bytes)."
        ::= { optixTrapsPM 142 }

    -- 1.3.6.1.4.1.2011.2.25.3.40.40.20.143
    pmPKT128 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 128 and 255 bytes (excluding framing bits, but including FCS bytes)."
        ::= { optixTrapsPM 143 }

    -- 1.3.6.1.4.1.2011.2.25.3.40.40.20.144
    pmPKT256 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 256 and 511 bytes (excluding framing bits, but including FCS bytes)."
        ::= { optixTrapsPM 144 }

    -- 1.3.6.1.4.1.2011.2.25.3.40.40.20.145
    pmPKT512 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 512 and 1023 bytes (excluding framing bits, but including FCS bytes)."
        ::= { optixTrapsPM 145 }

    -- 1.3.6.1.4.1.2011.2.25.3.40.40.20.146
    pmPKT1024 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 1024 and 1518 bytes (excluding framing bits, but including FCS bytes)."
        ::= { optixTrapsPM 146 }

    -- 1.3.6.1.4.1.2011.2.25.3.40.40.20.147
    pmPKT1519 NOTIFICATION-TYPE
        OBJECTS{ rptEvtPeriod,rptEvtValue,rptEvtVldty,rptEvtDateTime,rptEvtObjType,rptEvtParaLen,rptEvtPara }
        STATUS current
        DESCRIPTION
            "The total number of received and transmitted packets (including bad packets) whose length is between 1519 and MTU bytes (excluding framing bits, but including FCS bytes)."
        ::= { optixTrapsPM 147 }

    -- 1.3.6.1.4.1.2011.2.25.3.40.40.20.190
    pmRXGOODFULLFRAMESPEED NOTIFICATION-TYPE
        OBJECTS{ rptEvtPeriod,rptEvtValue,rptEvtVldty,rptEvtDateTime,rptEvtObjType,rptEvtParaLen,rptEvtPara }
        STATUS current
        DESCRIPTION
            "The rate of received good packets, including framing bits (20 bytes) and FCS bytes."
        ::= { optixTrapsPM 190 }

    -- 1.3.6.1.4.1.2011.2.25.3.40.40.20.191
    pmTXGOODFULLFRAMESPEED NOTIFICATION-TYPE
        OBJECTS{ rptEvtPeriod,rptEvtValue,rptEvtVldty,rptEvtDateTime,rptEvtObjType,rptEvtParaLen,rptEvtPara }
        STATUS current
        DESCRIPTION
            "The rate of transmitted good packets, including framing bits (20 bytes) and FCS bytes."
        ::= { optixTrapsPM 191 }

    -- 1.3.6.1.4.1.2011.2.25.3.40.40.20.192
    pmRXFULLBGOOD NOTIFICATION-TYPE
        OBJECTS{ rptEvtPeriod,rptEvtValue,rptEvtVldty,rptEvtDateTime,rptEvtObjType,rptEvtParaLen,rptEvtPara }
        STATUS current
        DESCRIPTION
            "The total number of received good packets, including framing bits (20 bytes) and FCS bytes."
        ::= { optixTrapsPM 192 }

    -- 1.3.6.1.4.1.2011.2.25.3.40.40.20.193
    pmTXFULLBGOOD NOTIFICATION-TYPE
        OBJECTS{ rptEvtPeriod,rptEvtValue,rptEvtVldty,rptEvtDateTime,rptEvtObjType,rptEvtParaLen,rptEvtPara }
        STATUS current
        DESCRIPTION
            "The total number of transmitted good packets, including framing bits (20 bytes) and FCS bytes."
        ::= { optixTrapsPM 193 }

    -- 1.3.6.1.4.1.2011.2.25.3.40.40.20.194
    pmRXCTLPKTS NOTIFICATION-TYPE
        OBJECTS{ rptEvtPeriod,rptEvtValue,rptEvtVldty,rptEvtDateTime,rptEvtObjType,rptEvtParaLen,rptEvtPara }
        STATUS current
        DESCRIPTION
            "A count of received control frames"
        ::= { optixTrapsPM 194 }

    -- 1.3.6.1.4.1.2011.2.25.3.40.40.20.195
    pmTXCTLPKTS NOTIFICATION-TYPE
        OBJECTS{ rptEvtPeriod,rptEvtValue,rptEvtVldty,rptEvtDateTime,rptEvtObjType,rptEvtParaLen,rptEvtPara }
        STATUS current
        DESCRIPTION
            "A count of transmitted control frames"
        ::= { optixTrapsPM 195 }

    -- 1.3.6.1.4.1.2011.2.25.3.40.40.20.196
    pmTXETHDROP NOTIFICATION-TYPE
        OBJECTS{ rptEvtPeriod,rptEvtValue,rptEvtVldty,rptEvtDateTime,rptEvtObjType,rptEvtParaLen,rptEvtPara }
        STATUS current
        DESCRIPTION
            "Transmitting packet loss events."
        ::= { optixTrapsPM 196 }

    -- 1.3.6.1.4.1.2011.2.25.3.40.40.20.197
    pmTXETHOVER NOTIFICATION-TYPE
        OBJECTS{ rptEvtPeriod,rptEvtValue,rptEvtVldty,rptEvtDateTime,rptEvtObjType,rptEvtParaLen,rptEvtPara }
        STATUS current
        DESCRIPTION
            "Oversize packets transmitted."
        ::= { optixTrapsPM 197 }

    -- 1.3.6.1.4.1.2011.2.25.3.40.40.20.198
    pmTXPKTS NOTIFICATION-TYPE
        OBJECTS{ rptEvtPeriod,rptEvtValue,rptEvtVldty,rptEvtDateTime,rptEvtObjType,rptEvtParaLen,rptEvtPara }
        STATUS current
        DESCRIPTION
            "The total number of transmitted packets (including bad packets, broadcast packets, and multicast packets)."
        ::= { optixTrapsPM 198 }

    -- 1.3.6.1.4.1.2011.2.25.3.40.40.20.199
    pmTXOCTETS NOTIFICATION-TYPE
        OBJECTS{ rptEvtPeriod,rptEvtValue,rptEvtVldty,rptEvtDateTime,rptEvtObjType,rptEvtParaLen,rptEvtPara }
        STATUS current
        DESCRIPTION
            "The total number of transmitted bytes (including bad-packet bytes and FCS bytes, and excluding framing bits)."
        ::= { optixTrapsPM 199 }

    -- 1.3.6.1.4.1.2011.2.25.3.40.40.20.200
    pmRXOCTETS NOTIFICATION-TYPE
        OBJECTS{ rptEvtPeriod,rptEvtValue,rptEvtVldty,rptEvtDateTime,rptEvtObjType,rptEvtParaLen,rptEvtPara }
        STATUS current
        DESCRIPTION
            "The total number of received bytes (including bad-packet bytes and FCS bytes, and excluding framing bits)."
        ::= { optixTrapsPM 200 }

    -- 1.3.6.1.4.1.2011.2.25.3.40.40.20.201
    pmRXPKTS NOTIFICATION-TYPE
        OBJECTS{ rptEvtPeriod,rptEvtValue,rptEvtVldty,rptEvtDateTime,rptEvtObjType,rptEvtParaLen,rptEvtPara }
        STATUS current
        DESCRIPTION
            "The total number of received packets (including bad packets, broadcast packets, and multicast packets)."
        ::= { optixTrapsPM 201 }

    -- 1.3.6.1.4.1.2011.2.25.3.40.40.20.202
    pmETHCRCALI NOTIFICATION-TYPE
        OBJECTS{ rptEvtPeriod,rptEvtValue,rptEvtVldty,rptEvtDateTime,rptEvtObjType,rptEvtParaLen,rptEvtPara }
        STATUS current
        DESCRIPTION
            "The total number of received packets that have a length of 64 to 1518 bytes, and that have FCS errors or alignment errors (for a non-integer number of bytes)."
        ::= { optixTrapsPM 202 }

    -- 1.3.6.1.4.1.2011.2.25.3.40.40.20.203
    pmETHUTILIZ NOTIFICATION-TYPE
        OBJECTS{ rptEvtPeriod,rptEvtValue,rptEvtVldty,rptEvtDateTime,rptEvtObjType,rptEvtParaLen,rptEvtPara }
        STATUS current
        DESCRIPTION
            "The percent utilization of the ethernet."
        ::= { optixTrapsPM 203 }

    -- 1.3.6.1.4.1.2011.2.25.3.40.40.20.350
    pmVCGRXOCTETS NOTIFICATION-TYPE
        OBJECTS{ rptEvtPeriod,rptEvtValue,rptEvtVldty,rptEvtDateTime,rptEvtObjType,rptEvtParaLen,rptEvtPara }
        STATUS current
        DESCRIPTION
            "The total number of received bytes on the VCG side(including bad-packet bytes and FCS bytes, and excluding framing bits)."
        ::= { optixTrapsPM 350 }

    -- 1.3.6.1.4.1.2011.2.25.3.40.40.20.351
    pmVCGTXOCTETS NOTIFICATION-TYPE
        OBJECTS{ rptEvtPeriod,rptEvtValue,rptEvtVldty,rptEvtDateTime,rptEvtObjType,rptEvtParaLen,rptEvtPara }
        STATUS current
        DESCRIPTION
            "The total number of transmitted bytes on the VCG side(including bad-packet bytes and FCS bytes, and excluding framing bits)."
        ::= { optixTrapsPM 351 }

    -- 1.3.6.1.4.1.2011.2.25.3.40.40.20.352
    pmVCGRXPACKETS NOTIFICATION-TYPE
        OBJECTS{ rptEvtPeriod,rptEvtValue,rptEvtVldty,rptEvtDateTime,rptEvtObjType,rptEvtParaLen,rptEvtPara }
        STATUS current
        DESCRIPTION
            "The total number of received packets on the VCG side(including bad packets, broadcast packets, and multicast packets)."
        ::= { optixTrapsPM 352 }

    -- 1.3.6.1.4.1.2011.2.25.3.40.40.20.353
    pmVCGTXPACKETS NOTIFICATION-TYPE
        OBJECTS{ rptEvtPeriod,rptEvtValue,rptEvtVldty,rptEvtDateTime,rptEvtObjType,rptEvtParaLen,rptEvtPara }
        STATUS current
        DESCRIPTION
            "The total number of transmitted packets on the VCG side(including bad packets, broadcast packets, and multicast packets)."
        ::= { optixTrapsPM 353 }

    -- 1.3.6.1.4.1.2011.2.25.3.40.40.20.354
    pmVCGRXGOODPACKETS NOTIFICATION-TYPE
        OBJECTS{ rptEvtPeriod,rptEvtValue,rptEvtVldty,rptEvtDateTime,rptEvtObjType,rptEvtParaLen,rptEvtPara }
        STATUS current
        DESCRIPTION
            "The total number of octets of good packets received on the network on the VCG side(excluding framing bits but including FCS octets)."
        ::= { optixTrapsPM 354 }

    -- 1.3.6.1.4.1.2011.2.25.3.40.40.20.355
    pmVCGTXGOODPACKETS NOTIFICATION-TYPE
        OBJECTS{ rptEvtPeriod,rptEvtValue,rptEvtVldty,rptEvtDateTime,rptEvtObjType,rptEvtParaLen,rptEvtPara }
        STATUS current
        DESCRIPTION
            "The total number of octets of good packets transmitted on the network on the VCG side(excluding framing bits but including FCS octets)."
        ::= { optixTrapsPM 355 }

    -- 1.3.6.1.4.1.2011.2.25.3.40.40.20.356
    pmVCGRXSPEED NOTIFICATION-TYPE
        OBJECTS{ rptEvtPeriod,rptEvtValue,rptEvtVldty,rptEvtDateTime,rptEvtObjType,rptEvtParaLen,rptEvtPara }
        STATUS current
        DESCRIPTION
            "The rate of received packetson the VCG side(including bad packets, broadcast packets, and multicast packets,excluding framing bits but including FCS octets)."
        ::= { optixTrapsPM 356 }

    -- 1.3.6.1.4.1.2011.2.25.3.40.40.20.357
    pmVCGTXSPEED NOTIFICATION-TYPE
        OBJECTS{ rptEvtPeriod,rptEvtValue,rptEvtVldty,rptEvtDateTime,rptEvtObjType,rptEvtParaLen,rptEvtPara }
        STATUS current
        DESCRIPTION
            "The rate of transmitted packetson the VCG side(including bad packets, broadcast packets, and multicast packets,excluding framing bits but including FCS octets)."
        ::= { optixTrapsPM 357 }

    -- 1.3.6.1.4.1.2011.2.25.3.40.40.20.450
    pmCESLOSPKTS NOTIFICATION-TYPE
        OBJECTS{ rptEvtPeriod,rptEvtValue,rptEvtVldty,rptEvtDateTime,rptEvtObjType,rptEvtParaLen,rptEvtPara }
        STATUS current
        DESCRIPTION
            "the count of packets lost in a period"
        ::= { optixTrapsPM 450 }

    -- 1.3.6.1.4.1.2011.2.25.3.40.40.20.451
    pmCESMISORDERPKTS NOTIFICATION-TYPE
        OBJECTS{ rptEvtPeriod,rptEvtValue,rptEvtVldty,rptEvtDateTime,rptEvtObjType,rptEvtParaLen,rptEvtPara }
        STATUS current
        DESCRIPTION
            "the count of lost out-of-order CES packets in a period"
        ::= { optixTrapsPM 451 }

    -- 1.3.6.1.4.1.2011.2.25.3.40.40.20.452
    pmCESSTRAYPKTS NOTIFICATION-TYPE
        OBJECTS{ rptEvtPeriod,rptEvtValue,rptEvtVldty,rptEvtDateTime,rptEvtObjType,rptEvtParaLen,rptEvtPara }
        STATUS current
        DESCRIPTION
            "the count of mis-connected packets in a period"
        ::= { optixTrapsPM 452 }

    -- 1.3.6.1.4.1.2011.2.25.3.40.40.20.453
    pmCESMALPKTS NOTIFICATION-TYPE
        OBJECTS{ rptEvtPeriod,rptEvtValue,rptEvtVldty,rptEvtDateTime,rptEvtObjType,rptEvtParaLen,rptEvtPara }
        STATUS current
        DESCRIPTION
            "the count of deformed CES packets in a period"
        ::= { optixTrapsPM 453 }

    -- 1.3.6.1.4.1.2011.2.25.3.40.40.20.454
    pmCESJTRUDR NOTIFICATION-TYPE
        OBJECTS{ rptEvtPeriod,rptEvtValue,rptEvtVldty,rptEvtDateTime,rptEvtObjType,rptEvtParaLen,rptEvtPara }
        STATUS current
        DESCRIPTION
            "the count of jitter buffer underflow times"
        ::= { optixTrapsPM 454 }

    -- 1.3.6.1.4.1.2011.2.25.3.40.40.20.455
    pmCESJTROVR NOTIFICATION-TYPE
        OBJECTS{ rptEvtPeriod,rptEvtValue,rptEvtVldty,rptEvtDateTime,rptEvtObjType,rptEvtParaLen,rptEvtPara }
        STATUS current
        DESCRIPTION
            "the count of jitter buffer overflow times"
        ::= { optixTrapsPM 455 }

    -- 1.3.6.1.4.1.2011.2.25.3.40.40.20.465
    pmVUNIRCVPKTS NOTIFICATION-TYPE
        OBJECTS{ rptEvtPeriod,rptEvtValue,rptEvtVldty,rptEvtDateTime,rptEvtObjType,rptEvtParaLen,rptEvtPara }
        STATUS current
        DESCRIPTION
            "the number of packets received at the V-UNI port of an Ethernet service"
        ::= { optixTrapsPM 465 }

    -- 1.3.6.1.4.1.2011.2.25.3.40.40.20.466
    pmVUNIRCVBYTES NOTIFICATION-TYPE
        OBJECTS{ rptEvtPeriod,rptEvtValue,rptEvtVldty,rptEvtDateTime,rptEvtObjType,rptEvtParaLen,rptEvtPara }
        STATUS current
        DESCRIPTION
            "the number of bytes received at the V-UNI port of an Ethernet service"
        ::= { optixTrapsPM 466 }

    -- 1.3.6.1.4.1.2011.2.25.3.40.40.20.467
    pmVUNISNDPKTS NOTIFICATION-TYPE
        OBJECTS{ rptEvtPeriod,rptEvtValue,rptEvtVldty,rptEvtDateTime,rptEvtObjType,rptEvtParaLen,rptEvtPara }
        STATUS current
        DESCRIPTION
            "The number of packets transmitted at the specified V-UNI of the specified service."
        ::= { optixTrapsPM 467 }

    -- 1.3.6.1.4.1.2011.2.25.3.40.40.20.468
    pmVUNISNDBYTES NOTIFICATION-TYPE
        OBJECTS{ rptEvtPeriod,rptEvtValue,rptEvtVldty,rptEvtDateTime,rptEvtObjType,rptEvtParaLen,rptEvtPara }
        STATUS current
        DESCRIPTION
            "The number of bytes transmitted at the specified V-UNI of the specified service."
        ::= { optixTrapsPM 468 }

    -- 1.3.6.1.4.1.2011.2.25.3.40.40.20.469
    pmTUNNELRCVPKTS NOTIFICATION-TYPE
        OBJECTS{ rptEvtPeriod,rptEvtValue,rptEvtVldty,rptEvtDateTime,rptEvtObjType,rptEvtParaLen,rptEvtPara }
        STATUS current
        DESCRIPTION
            "Count of packets received on tunnel"
        ::= { optixTrapsPM 469 }

    -- 1.3.6.1.4.1.2011.2.25.3.40.40.20.470
    pmTUNNELRCVBYTES NOTIFICATION-TYPE
        OBJECTS{ rptEvtPeriod,rptEvtValue,rptEvtVldty,rptEvtDateTime,rptEvtObjType,rptEvtParaLen,rptEvtPara }
        STATUS current
        DESCRIPTION
            "Count of bytes received on tunnel"
        ::= { optixTrapsPM 470 }

    -- 1.3.6.1.4.1.2011.2.25.3.40.40.20.471
    pmTUNNELSNDPKTS NOTIFICATION-TYPE
        OBJECTS{ rptEvtPeriod,rptEvtValue,rptEvtVldty,rptEvtDateTime,rptEvtObjType,rptEvtParaLen,rptEvtPara }
        STATUS current
        DESCRIPTION
            "Count of packets transmitted on tunnel"
        ::= { optixTrapsPM 471 }

    -- 1.3.6.1.4.1.2011.2.25.3.40.40.20.472
    pmTUNNELSNDBYTES NOTIFICATION-TYPE
        OBJECTS{ rptEvtPeriod,rptEvtValue,rptEvtVldty,rptEvtDateTime,rptEvtObjType,rptEvtParaLen,rptEvtPara }
        STATUS current
        DESCRIPTION
            "Count of bytes transmitted on tunnel"
        ::= { optixTrapsPM 472 }

    -- 1.3.6.1.4.1.2011.2.25.3.40.40.20.473
    pmPWRCVPKTS NOTIFICATION-TYPE
        OBJECTS{ rptEvtPeriod,rptEvtValue,rptEvtVldty,rptEvtDateTime,rptEvtObjType,rptEvtParaLen,rptEvtPara }
        STATUS current
        DESCRIPTION
            "Count of packets received on PW"
        ::= { optixTrapsPM 473 }

    -- 1.3.6.1.4.1.2011.2.25.3.40.40.20.474
    pmPWRCVBYTES NOTIFICATION-TYPE
        OBJECTS{ rptEvtPeriod,rptEvtValue,rptEvtVldty,rptEvtDateTime,rptEvtObjType,rptEvtParaLen,rptEvtPara }
        STATUS current
        DESCRIPTION
            "Count of bytes received on PW"
        ::= { optixTrapsPM 474 }

    -- 1.3.6.1.4.1.2011.2.25.3.40.40.20.475
    pmPWSNDPKTS NOTIFICATION-TYPE
        OBJECTS{ rptEvtPeriod,rptEvtValue,rptEvtVldty,rptEvtDateTime,rptEvtObjType,rptEvtParaLen,rptEvtPara }
        STATUS current
        DESCRIPTION
            "Count of packets transmitted on PW"
        ::= { optixTrapsPM 475 }

    -- 1.3.6.1.4.1.2011.2.25.3.40.40.20.476
    pmPWSNDBYTES NOTIFICATION-TYPE
        OBJECTS{ rptEvtPeriod,rptEvtValue,rptEvtVldty,rptEvtDateTime,rptEvtObjType,rptEvtParaLen,rptEvtPara }
        STATUS current
        DESCRIPTION
            "Count of bytes transmitted on PW"
        ::= { optixTrapsPM 476 }

    -- 1.3.6.1.4.1.2011.2.25.3.40.40.20.477
    pmQOSSTRMMATCHPKTS NOTIFICATION-TYPE
        OBJECTS{ rptEvtPeriod,rptEvtValue,rptEvtVldty,rptEvtDateTime,rptEvtObjType,rptEvtParaLen,rptEvtPara }
        STATUS current
        DESCRIPTION
            "Packets matching flow classification"
        ::= { optixTrapsPM 477 }

    -- 1.3.6.1.4.1.2011.2.25.3.40.40.20.478
    pmQOSSTRMMATCHBYTES NOTIFICATION-TYPE
        OBJECTS{ rptEvtPeriod,rptEvtValue,rptEvtVldty,rptEvtDateTime,rptEvtObjType,rptEvtParaLen,rptEvtPara }
        STATUS current
        DESCRIPTION
            "Bytes matching flow classification"
        ::= { optixTrapsPM 478 }

    -- 1.3.6.1.4.1.2011.2.25.3.40.40.20.479
    pmQOSCARGRNPKTS NOTIFICATION-TYPE
        OBJECTS{ rptEvtPeriod,rptEvtValue,rptEvtVldty,rptEvtDateTime,rptEvtObjType,rptEvtParaLen,rptEvtPara }
        STATUS current
        DESCRIPTION
            "Packets marked green"
        ::= { optixTrapsPM 479 }

    -- 1.3.6.1.4.1.2011.2.25.3.40.40.20.480
    pmQOSCARGRNBYTES NOTIFICATION-TYPE
        OBJECTS{ rptEvtPeriod,rptEvtValue,rptEvtVldty,rptEvtDateTime,rptEvtObjType,rptEvtParaLen,rptEvtPara }
        STATUS current
        DESCRIPTION
            "Bytes marked green"
        ::= { optixTrapsPM 480 }

    -- 1.3.6.1.4.1.2011.2.25.3.40.40.20.481
    pmQOSCARYLWPKTS NOTIFICATION-TYPE
        OBJECTS{ rptEvtPeriod,rptEvtValue,rptEvtVldty,rptEvtDateTime,rptEvtObjType,rptEvtParaLen,rptEvtPara }
        STATUS current
        DESCRIPTION
            "Packets marked yellow"
        ::= { optixTrapsPM 481 }

    -- 1.3.6.1.4.1.2011.2.25.3.40.40.20.482
    pmQOSCARYLWBYTES NOTIFICATION-TYPE
        OBJECTS{ rptEvtPeriod,rptEvtValue,rptEvtVldty,rptEvtDateTime,rptEvtObjType,rptEvtParaLen,rptEvtPara }
        STATUS current
        DESCRIPTION
            "Bytes marked yellow"
        ::= { optixTrapsPM 482 }

    -- 1.3.6.1.4.1.2011.2.25.3.40.40.20.483
    pmQOSCARREDPKTS NOTIFICATION-TYPE
        OBJECTS{ rptEvtPeriod,rptEvtValue,rptEvtVldty,rptEvtDateTime,rptEvtObjType,rptEvtParaLen,rptEvtPara }
        STATUS current
        DESCRIPTION
            "Packets marked red"
        ::= { optixTrapsPM 483 }

    -- 1.3.6.1.4.1.2011.2.25.3.40.40.20.484
    pmQOSCARREDBYTES NOTIFICATION-TYPE
        OBJECTS{ rptEvtPeriod,rptEvtValue,rptEvtVldty,rptEvtDateTime,rptEvtObjType,rptEvtParaLen,rptEvtPara }
        STATUS current
        DESCRIPTION
            "Bytes marked red"
        ::= { optixTrapsPM 484 }

    -- 1.3.6.1.4.1.2011.2.25.3.40.40.20.485
    pmMPLSTUNNELFLR NOTIFICATION-TYPE
        OBJECTS{ rptEvtPeriod,rptEvtValue,rptEvtVldty,rptEvtDateTime,rptEvtObjType,rptEvtParaLen,rptEvtPara }
        STATUS current
        DESCRIPTION
            "The tunnel packet loss ratio in a time unit, that is, (number of data packets transmitted at the source - number of data packets received at the end)/number of data packets transmitted at the source."
        ::= { optixTrapsPM 485 }

    -- 1.3.6.1.4.1.2011.2.25.3.40.40.20.486
    pmMPLSTUNNELFL NOTIFICATION-TYPE
        OBJECTS{ rptEvtPeriod,rptEvtValue,rptEvtVldty,rptEvtDateTime,rptEvtObjType,rptEvtParaLen,rptEvtPara }
        STATUS current
        DESCRIPTION
            "The difference of number of data packets transmitted at the source minus number of data packets received at the end. This difference is detected by the PM mechanism of OAM."
        ::= { optixTrapsPM 486 }

    -- 1.3.6.1.4.1.2011.2.25.3.40.40.20.487
    pmMPLSTUNNELFD NOTIFICATION-TYPE
        OBJECTS{ rptEvtPeriod,rptEvtValue,rptEvtVldty,rptEvtDateTime,rptEvtObjType,rptEvtParaLen,rptEvtPara }
        STATUS current
        DESCRIPTION
            "The difference between the time when request packets are transmitted at the tunnel source and the time when response packets are received at the tunnel source."
        ::= { optixTrapsPM 487 }

    -- 1.3.6.1.4.1.2011.2.25.3.40.40.20.488
    pmMPLSTUNNELFDV NOTIFICATION-TYPE
        OBJECTS{ rptEvtPeriod,rptEvtValue,rptEvtVldty,rptEvtDateTime,rptEvtObjType,rptEvtParaLen,rptEvtPara }
        STATUS current
        DESCRIPTION
            "The difference of the results in two frame delay tests."
        ::= { optixTrapsPM 488 }

    -- 1.3.6.1.4.1.2011.2.25.3.40.40.20.489
    pmETHCFMFLR NOTIFICATION-TYPE
        OBJECTS{ rptEvtPeriod,rptEvtValue,rptEvtVldty,rptEvtDateTime,rptEvtObjType,rptEvtParaLen,rptEvtPara }
        STATUS current
        DESCRIPTION
            "The E-Line service packet loss ratio in a time unit, that is, (number of data packets transmitted at the source MEP - number of data packets received at the end MEP)/number of data packets transmitted at the source MEP."
        ::= { optixTrapsPM 489 }

    -- 1.3.6.1.4.1.2011.2.25.3.40.40.20.490
    pmETHCFMFL NOTIFICATION-TYPE
        OBJECTS{ rptEvtPeriod,rptEvtValue,rptEvtVldty,rptEvtDateTime,rptEvtObjType,rptEvtParaLen,rptEvtPara }
        STATUS current
        DESCRIPTION
            "The difference of number of data packets transmitted at the source minus number of data packets received at the end. The number of data packets transmitted at the source is detected by the PM mechanism of OAM."
        ::= { optixTrapsPM 490 }

    -- 1.3.6.1.4.1.2011.2.25.3.40.40.20.491
    pmETHCFMFD NOTIFICATION-TYPE
        OBJECTS{ rptEvtPeriod,rptEvtValue,rptEvtVldty,rptEvtDateTime,rptEvtObjType,rptEvtParaLen,rptEvtPara }
        STATUS current
        DESCRIPTION
            "The difference between the time when request packets are transmitted at the tunnel source and the time when response packets are received at the tunnel source."
        ::= { optixTrapsPM 491 }

    -- 1.3.6.1.4.1.2011.2.25.3.40.40.20.492
    pmETHCFGFDV NOTIFICATION-TYPE
        OBJECTS{ rptEvtPeriod,rptEvtValue,rptEvtVldty,rptEvtDateTime,rptEvtObjType,rptEvtParaLen,rptEvtPara }
        STATUS current
        DESCRIPTION
            "The difference of the results in two frame delay tests."
        ::= { optixTrapsPM 492 }

    -- 1.3.6.1.4.1.2011.2.25.3.40.40.20.493
    pmAtmpwLospkts NOTIFICATION-TYPE
        OBJECTS{ rptEvtPeriod,rptEvtValue,rptEvtVldty,rptEvtDateTime,rptEvtObjType,rptEvtParaLen,rptEvtPara }
        STATUS current
        DESCRIPTION
            "Lost packets"
        ::= { optixTrapsPM 493 }

    -- 1.3.6.1.4.1.2011.2.25.3.40.40.20.494
    pmAtmpwMisorderpkts NOTIFICATION-TYPE
        OBJECTS{ rptEvtPeriod,rptEvtValue,rptEvtVldty,rptEvtDateTime,rptEvtObjType,rptEvtParaLen,rptEvtPara }
        STATUS current
        DESCRIPTION
            "Out-of-order packets"
        ::= { optixTrapsPM 494 }

    -- 1.3.6.1.4.1.2011.2.25.3.40.40.20.495
    pmATMPWSNDCELLS NOTIFICATION-TYPE
        OBJECTS{ rptEvtPeriod,rptEvtValue,rptEvtVldty,rptEvtDateTime,rptEvtObjType,rptEvtParaLen,rptEvtPara }
        STATUS current
        DESCRIPTION
            "Count of transmitted cells"
        ::= { optixTrapsPM 495 }

    -- 1.3.6.1.4.1.2011.2.25.3.40.40.20.496
    pmATMPWRCVCELLS NOTIFICATION-TYPE
        OBJECTS{ rptEvtPeriod,rptEvtValue,rptEvtVldty,rptEvtDateTime,rptEvtObjType,rptEvtParaLen,rptEvtPara }
        STATUS current
        DESCRIPTION
            "Count of received cells"
        ::= { optixTrapsPM 496 }

    -- 1.3.6.1.4.1.2011.2.25.3.40.40.20.497
    pmATMPWUNKNOWNCELLS NOTIFICATION-TYPE
        OBJECTS{ rptEvtPeriod,rptEvtValue,rptEvtVldty,rptEvtDateTime,rptEvtObjType,rptEvtParaLen,rptEvtPara }
        STATUS current
        DESCRIPTION
            "Count of unknown cells"
        ::= { optixTrapsPM 497 }

    -- 1.3.6.1.4.1.2011.2.25.3.40.40.20.498
    pmATMUNI1INCELLS NOTIFICATION-TYPE
        OBJECTS{ rptEvtPeriod,rptEvtValue,rptEvtVldty,rptEvtDateTime,rptEvtObjType,rptEvtParaLen,rptEvtPara }
        STATUS current
        DESCRIPTION
            "The number of normal cells received by the ATM connection through UNI1. This number helps determine whether the connection service is normal."
        ::= { optixTrapsPM 498 }

    -- 1.3.6.1.4.1.2011.2.25.3.40.40.20.499
    pmATMUNI1OUTCELLS NOTIFICATION-TYPE
        OBJECTS{ rptEvtPeriod,rptEvtValue,rptEvtVldty,rptEvtDateTime,rptEvtObjType,rptEvtParaLen,rptEvtPara }
        STATUS current
        DESCRIPTION
            "The number of normal cells transmitted by the ATM connection through UNI1. This number helps determine whether the connection service is normal."
        ::= { optixTrapsPM 499 }

    -- 1.3.6.1.4.1.2011.2.25.3.40.40.20.500
    pmATMCORRECTEDHCSERR NOTIFICATION-TYPE
        OBJECTS{ rptEvtPeriod,rptEvtValue,rptEvtVldty,rptEvtDateTime,rptEvtObjType,rptEvtParaLen,rptEvtPara }
        STATUS current
        DESCRIPTION
            "the number of cells that are received by an ATM port and contain correctable header check sequence (HCS) errors"
        ::= { optixTrapsPM 500 }

    -- 1.3.6.1.4.1.2011.2.25.3.40.40.20.501
    pmATMUNCORRECTEDHCSERR NOTIFICATION-TYPE
        OBJECTS{ rptEvtPeriod,rptEvtValue,rptEvtVldty,rptEvtDateTime,rptEvtObjType,rptEvtParaLen,rptEvtPara }
        STATUS current
        DESCRIPTION
            "the number of cells that are received by an ATM port and contain uncorrectable header check sequence (HCS) errors"
        ::= { optixTrapsPM 501 }

    -- 1.3.6.1.4.1.2011.2.25.3.40.40.20.502
    pmATMRCVCELLS NOTIFICATION-TYPE
        OBJECTS{ rptEvtPeriod,rptEvtValue,rptEvtVldty,rptEvtDateTime,rptEvtObjType,rptEvtParaLen,rptEvtPara }
        STATUS current
        DESCRIPTION
            "Count of total cells received"
        ::= { optixTrapsPM 502 }

    -- 1.3.6.1.4.1.2011.2.25.3.40.40.20.503
    pmATMRCVIDLECELLS NOTIFICATION-TYPE
        OBJECTS{ rptEvtPeriod,rptEvtValue,rptEvtVldty,rptEvtDateTime,rptEvtObjType,rptEvtParaLen,rptEvtPara }
        STATUS current
        DESCRIPTION
            "Count of total idle cells received"
        ::= { optixTrapsPM 503 }

    -- 1.3.6.1.4.1.2011.2.25.3.40.40.20.504
    pmATMSNDCELLS NOTIFICATION-TYPE
        OBJECTS{ rptEvtPeriod,rptEvtValue,rptEvtVldty,rptEvtDateTime,rptEvtObjType,rptEvtParaLen,rptEvtPara }
        STATUS current
        DESCRIPTION
            "Count of total cells transmitted"
        ::= { optixTrapsPM 504 }

    -- 1.3.6.1.4.1.2011.2.25.3.40.40.20.506
    pmPWDROPPKTS NOTIFICATION-TYPE
        OBJECTS{ rptEvtPeriod,rptEvtValue,rptEvtVldty,rptEvtDateTime,rptEvtObjType,rptEvtParaLen,rptEvtPara }
        STATUS current
        DESCRIPTION
            "Count of packets discarded on PW"
        ::= { optixTrapsPM 506 }

    -- 1.3.6.1.4.1.2011.2.25.3.40.40.20.507
    pmPWDROPBYTES NOTIFICATION-TYPE
        OBJECTS{ rptEvtPeriod,rptEvtValue,rptEvtVldty,rptEvtDateTime,rptEvtObjType,rptEvtParaLen,rptEvtPara }
        STATUS current
        DESCRIPTION
            "Count of bytes discarded on PW"
        ::= { optixTrapsPM 507 }

    -- 1.3.6.1.4.1.2011.2.25.3.40.40.20.510
    pmQOSPRIDROPPKTS NOTIFICATION-TYPE
        OBJECTS{ rptEvtPeriod,rptEvtValue,rptEvtVldty,rptEvtDateTime,rptEvtObjType,rptEvtParaLen,rptEvtPara }
        STATUS current
        DESCRIPTION
            "The number of discarded packets of different service priorities."
        ::= { optixTrapsPM 510 }

    -- 1.3.6.1.4.1.2011.2.25.3.40.40.20.511
    pmQOSPRIDROPBYTES NOTIFICATION-TYPE
        OBJECTS{ rptEvtPeriod,rptEvtValue,rptEvtVldty,rptEvtDateTime,rptEvtObjType,rptEvtParaLen,rptEvtPara }
        STATUS current
        DESCRIPTION
            "The number of bytes of different service priorities."
        ::= { optixTrapsPM 511 }

    -- 1.3.6.1.4.1.2011.2.25.3.40.40.20.513
    pmATMIFINRATEMAX NOTIFICATION-TYPE
        OBJECTS{ rptEvtPeriod,rptEvtValue,rptEvtVldty,rptEvtDateTime,rptEvtObjType,rptEvtParaLen,rptEvtPara }
        STATUS current
        DESCRIPTION
            "Maximum rate of normal cells received by the port"
        ::= { optixTrapsPM 513 }

    -- 1.3.6.1.4.1.2011.2.25.3.40.40.20.514
    pmATMIFINRATEMIN NOTIFICATION-TYPE
        OBJECTS{ rptEvtPeriod,rptEvtValue,rptEvtVldty,rptEvtDateTime,rptEvtObjType,rptEvtParaLen,rptEvtPara }
        STATUS current
        DESCRIPTION
            "Minimum rate of normal cells received by the port"
        ::= { optixTrapsPM 514 }

    -- 1.3.6.1.4.1.2011.2.25.3.40.40.20.515
    pmATMIFINRATEAVG NOTIFICATION-TYPE
        OBJECTS{ rptEvtPeriod,rptEvtValue,rptEvtVldty,rptEvtDateTime,rptEvtObjType,rptEvtParaLen,rptEvtPara }
        STATUS current
        DESCRIPTION
            "Average rate of normal cells received by the port"
        ::= { optixTrapsPM 515 }

    -- 1.3.6.1.4.1.2011.2.25.3.40.40.20.516
    pmATMIFOUTRATEMAX NOTIFICATION-TYPE
        OBJECTS{ rptEvtPeriod,rptEvtValue,rptEvtVldty,rptEvtDateTime,rptEvtObjType,rptEvtParaLen,rptEvtPara }
        STATUS current
        DESCRIPTION
            "Maximum rate of normal cells transmitted by the port"
        ::= { optixTrapsPM 516 }

    -- 1.3.6.1.4.1.2011.2.25.3.40.40.20.517
    pmATMIFOUTRATEMIN NOTIFICATION-TYPE
        OBJECTS{ rptEvtPeriod,rptEvtValue,rptEvtVldty,rptEvtDateTime,rptEvtObjType,rptEvtParaLen,rptEvtPara }
        STATUS current
        DESCRIPTION
            "Minimum rate of normal cells transmitted by the port"
        ::= { optixTrapsPM 517 }

    -- 1.3.6.1.4.1.2011.2.25.3.40.40.20.518
    pmATMIFOUTRATEAVG NOTIFICATION-TYPE
        OBJECTS{ rptEvtPeriod,rptEvtValue,rptEvtVldty,rptEvtDateTime,rptEvtObjType,rptEvtParaLen,rptEvtPara }
        STATUS current
        DESCRIPTION
            "Average rate of normal cells transmitted by the port"
        ::= { optixTrapsPM 518 }

    -- 1.3.6.1.4.1.2011.2.25.3.40.40.20.519
    pmATMCELLAVAILABILITY NOTIFICATION-TYPE
        OBJECTS{ rptEvtPeriod,rptEvtValue,rptEvtVldty,rptEvtDateTime,rptEvtObjType,rptEvtParaLen,rptEvtPara }
        STATUS current
        DESCRIPTION
            "Availability of cells in percentage"
        ::= { optixTrapsPM 519 }

    -- 1.3.6.1.4.1.2011.2.25.3.40.40.20.520
    pmATMUNI1INRATEMAX NOTIFICATION-TYPE
        OBJECTS{ rptEvtPeriod,rptEvtValue,rptEvtVldty,rptEvtDateTime,rptEvtObjType,rptEvtParaLen,rptEvtPara }
        STATUS current
        DESCRIPTION
            "Maximum rate of normal cells received by the UNI1"
        ::= { optixTrapsPM 520 }

    -- 1.3.6.1.4.1.2011.2.25.3.40.40.20.521
    pmATMUNI1INRATEMIN NOTIFICATION-TYPE
        OBJECTS{ rptEvtPeriod,rptEvtValue,rptEvtVldty,rptEvtDateTime,rptEvtObjType,rptEvtParaLen,rptEvtPara }
        STATUS current
        DESCRIPTION
            "Minimum rate of normal cells received by the UNI1"
        ::= { optixTrapsPM 521 }

    -- 1.3.6.1.4.1.2011.2.25.3.40.40.20.522
    pmATMUNI1INRATEAVG NOTIFICATION-TYPE
        OBJECTS{ rptEvtPeriod,rptEvtValue,rptEvtVldty,rptEvtDateTime,rptEvtObjType,rptEvtParaLen,rptEvtPara }
        STATUS current
        DESCRIPTION
            "Average rate of normal cells received by the UNI1"
        ::= { optixTrapsPM 522 }

    -- 1.3.6.1.4.1.2011.2.25.3.40.40.20.523
    pmATMUNI1OUTRATEMAX NOTIFICATION-TYPE
        OBJECTS{ rptEvtPeriod,rptEvtValue,rptEvtVldty,rptEvtDateTime,rptEvtObjType,rptEvtParaLen,rptEvtPara }
        STATUS current
        DESCRIPTION
            "Maximum rate of normal cells transmitted by the UNI1"
        ::= { optixTrapsPM 523 }

    -- 1.3.6.1.4.1.2011.2.25.3.40.40.20.524
    pmATMUNI1OUTRATEMIN NOTIFICATION-TYPE
        OBJECTS{ rptEvtPeriod,rptEvtValue,rptEvtVldty,rptEvtDateTime,rptEvtObjType,rptEvtParaLen,rptEvtPara }
        STATUS current
        DESCRIPTION
            "Minimum rate of normal cells transmitted by the UNI1"
        ::= { optixTrapsPM 524 }

    -- 1.3.6.1.4.1.2011.2.25.3.40.40.20.525
    pmATMUNI1OUTRATEAVG NOTIFICATION-TYPE
        OBJECTS{ rptEvtPeriod,rptEvtValue,rptEvtVldty,rptEvtDateTime,rptEvtObjType,rptEvtParaLen,rptEvtPara }
        STATUS current
        DESCRIPTION
            "Average rate of normal cells transmitted by the UNI1"
        ::= { optixTrapsPM 525 }

    -- 1.3.6.1.4.1.2011.2.25.3.40.40.20.532
    pmCESRXPKTS NOTIFICATION-TYPE
        OBJECTS{ rptEvtPeriod,rptEvtValue,rptEvtVldty,rptEvtDateTime,rptEvtObjType,rptEvtParaLen,rptEvtPara }
        STATUS current
        DESCRIPTION
            "the number of packets received at the CES"
        ::= { optixTrapsPM 532 }

    -- 1.3.6.1.4.1.2011.2.25.3.40.40.20.534
    pmPPPTXPKTS NOTIFICATION-TYPE
        OBJECTS{ rptEvtPeriod,rptEvtValue,rptEvtVldty,rptEvtDateTime,rptEvtObjType,rptEvtParaLen,rptEvtPara }
        STATUS current
        DESCRIPTION
            "transmitted ppp packets."
        ::= { optixTrapsPM 534 }

    -- 1.3.6.1.4.1.2011.2.25.3.40.40.20.535
    pmPPPTXBYTES NOTIFICATION-TYPE
        OBJECTS{ rptEvtPeriod,rptEvtValue,rptEvtVldty,rptEvtDateTime,rptEvtObjType,rptEvtParaLen,rptEvtPara }
        STATUS current
        DESCRIPTION
            "transmitted ppp bytes."
        ::= { optixTrapsPM 535 }

    -- 1.3.6.1.4.1.2011.2.25.3.40.40.20.536
    pmPPPRXPKTS NOTIFICATION-TYPE
        OBJECTS{ rptEvtPeriod,rptEvtValue,rptEvtVldty,rptEvtDateTime,rptEvtObjType,rptEvtParaLen,rptEvtPara }
        STATUS current
        DESCRIPTION
            "received ppp packets."
        ::= { optixTrapsPM 536 }

    -- 1.3.6.1.4.1.2011.2.25.3.40.40.20.537
    pmPPPRXBYTES NOTIFICATION-TYPE
        OBJECTS{ rptEvtPeriod,rptEvtValue,rptEvtVldty,rptEvtDateTime,rptEvtObjType,rptEvtParaLen,rptEvtPara }
        STATUS current
        DESCRIPTION
            "received ppp bytes."
        ::= { optixTrapsPM 537 }

    -- 1.3.6.1.4.1.2011.2.25.3.40.40.20.538
    pmPPPRXFCSPKTS NOTIFICATION-TYPE
        OBJECTS{ rptEvtPeriod,rptEvtValue,rptEvtVldty,rptEvtDateTime,rptEvtObjType,rptEvtParaLen,rptEvtPara }
        STATUS current
        DESCRIPTION
            "received fcs packets."
        ::= { optixTrapsPM 538 }

    -- 1.3.6.1.4.1.2011.2.25.3.40.40.20.547
    pmPPPTXLOSPKTS NOTIFICATION-TYPE
        OBJECTS{ rptEvtPeriod,rptEvtValue,rptEvtVldty,rptEvtDateTime,rptEvtObjType,rptEvtParaLen,rptEvtPara }
        STATUS current
        DESCRIPTION
            "transmitted single lost ppp packets."
        ::= { optixTrapsPM 547 }

    -- 1.3.6.1.4.1.2011.2.25.3.40.40.20.548
    pmPPPRXLOSPKTS NOTIFICATION-TYPE
        OBJECTS{ rptEvtPeriod,rptEvtValue,rptEvtVldty,rptEvtDateTime,rptEvtObjType,rptEvtParaLen,rptEvtPara }
        STATUS current
        DESCRIPTION
            "received single lost ppp packet."
        ::= { optixTrapsPM 548 }

    -- 1.3.6.1.4.1.2011.2.25.3.40.40.20.549
    pmPPPRXBWUTILIZATION NOTIFICATION-TYPE
        OBJECTS{ rptEvtPeriod,rptEvtValue,rptEvtVldty,rptEvtDateTime,rptEvtObjType,rptEvtParaLen,rptEvtPara }
        STATUS current
        DESCRIPTION
            "received ppp bandwidth utilization."
        ::= { optixTrapsPM 549 }

    -- 1.3.6.1.4.1.2011.2.25.3.40.40.20.550
    pmPPPTXBWUTILIZATION NOTIFICATION-TYPE
        OBJECTS{ rptEvtPeriod,rptEvtValue,rptEvtVldty,rptEvtDateTime,rptEvtObjType,rptEvtParaLen,rptEvtPara }
        STATUS current
        DESCRIPTION
            "received ppp bandwidth utilization."
        ::= { optixTrapsPM 550 }

    -- 1.3.6.1.4.1.2011.2.25.3.40.40.20.551
    pmMPTXPKTS NOTIFICATION-TYPE
        OBJECTS{ rptEvtPeriod,rptEvtValue,rptEvtVldty,rptEvtDateTime,rptEvtObjType,rptEvtParaLen,rptEvtPara }
        STATUS current
        DESCRIPTION
            "transmitted mp service packets."
        ::= { optixTrapsPM 551 }

    -- 1.3.6.1.4.1.2011.2.25.3.40.40.20.552
    pmMPTXBYTES NOTIFICATION-TYPE
        OBJECTS{ rptEvtPeriod,rptEvtValue,rptEvtVldty,rptEvtDateTime,rptEvtObjType,rptEvtParaLen,rptEvtPara }
        STATUS current
        DESCRIPTION
            "transmitted mp bytes."
        ::= { optixTrapsPM 552 }

    -- 1.3.6.1.4.1.2011.2.25.3.40.40.20.553
    pmMPRXPKTS NOTIFICATION-TYPE
        OBJECTS{ rptEvtPeriod,rptEvtValue,rptEvtVldty,rptEvtDateTime,rptEvtObjType,rptEvtParaLen,rptEvtPara }
        STATUS current
        DESCRIPTION
            "received mp service packets."
        ::= { optixTrapsPM 553 }

    -- 1.3.6.1.4.1.2011.2.25.3.40.40.20.554
    pmMPRXBYTES NOTIFICATION-TYPE
        OBJECTS{ rptEvtPeriod,rptEvtValue,rptEvtVldty,rptEvtDateTime,rptEvtObjType,rptEvtParaLen,rptEvtPara }
        STATUS current
        DESCRIPTION
            "received mp bytes."
        ::= { optixTrapsPM 554 }

    -- 1.3.6.1.4.1.2011.2.25.3.40.40.20.555
    pmMPRXERRPKTS NOTIFICATION-TYPE
        OBJECTS{ rptEvtPeriod,rptEvtValue,rptEvtVldty,rptEvtDateTime,rptEvtObjType,rptEvtParaLen,rptEvtPara }
        STATUS current
        DESCRIPTION
            "received errored mp packets."
        ::= { optixTrapsPM 555 }

    -- 1.3.6.1.4.1.2011.2.25.3.40.40.20.556
    pmMPTXTOTALPKTS NOTIFICATION-TYPE
        OBJECTS{ rptEvtPeriod,rptEvtValue,rptEvtVldty,rptEvtDateTime,rptEvtObjType,rptEvtParaLen,rptEvtPara }
        STATUS current
        DESCRIPTION
            "transmitted total mp packets."
        ::= { optixTrapsPM 556 }

    -- 1.3.6.1.4.1.2011.2.25.3.40.40.20.557
    pmMPRXTOTALPKTS NOTIFICATION-TYPE
        OBJECTS{ rptEvtPeriod,rptEvtValue,rptEvtVldty,rptEvtDateTime,rptEvtObjType,rptEvtParaLen,rptEvtPara }
        STATUS current
        DESCRIPTION
            "received total mp packets."
        ::= { optixTrapsPM 557 }

    -- 1.3.6.1.4.1.2011.2.25.3.40.40.20.558
    pmMPRXBWUTILIZATION NOTIFICATION-TYPE
        OBJECTS{ rptEvtPeriod,rptEvtValue,rptEvtVldty,rptEvtDateTime,rptEvtObjType,rptEvtParaLen,rptEvtPara }
        STATUS current
        DESCRIPTION
            "received mp BW utilization."
        ::= { optixTrapsPM 558 }

    -- 1.3.6.1.4.1.2011.2.25.3.40.40.20.559
    pmMPTXBWUTILIZATION NOTIFICATION-TYPE
        OBJECTS{ rptEvtPeriod,rptEvtValue,rptEvtVldty,rptEvtDateTime,rptEvtObjType,rptEvtParaLen,rptEvtPara }
        STATUS current
        DESCRIPTION
            "transmitted mp BW utilization."
        ::= { optixTrapsPM 559 }

    -- 1.3.6.1.4.1.2011.2.25.3.40.40.20.567
    pmPORTRXBWUTILIZATION NOTIFICATION-TYPE
        OBJECTS{ rptEvtPeriod,rptEvtValue,rptEvtVldty,rptEvtDateTime,rptEvtObjType,rptEvtParaLen,rptEvtPara }
        STATUS current
        DESCRIPTION
            "The bandwidth utilization of the received port"
        ::= { optixTrapsPM 567 }

    -- 1.3.6.1.4.1.2011.2.25.3.40.40.20.568
    pmPORTTXBWUTILIZATION NOTIFICATION-TYPE
        OBJECTS{ rptEvtPeriod,rptEvtValue,rptEvtVldty,rptEvtDateTime,rptEvtObjType,rptEvtParaLen,rptEvtPara }
        STATUS current
        DESCRIPTION
            "The bandwidth utilization of the transmitted port"
        ::= { optixTrapsPM 568 }

    -- 1.3.6.1.4.1.2011.2.25.3.40.40.20.578
    pmATMUNI2INCELLS NOTIFICATION-TYPE
        OBJECTS{ rptEvtPeriod,rptEvtValue,rptEvtVldty,rptEvtDateTime,rptEvtObjType,rptEvtParaLen,rptEvtPara }
        STATUS current
        DESCRIPTION
            "The number of normal cells received by the ATM connection through UNI2. This number helps determine whether the connection service is normal."
        ::= { optixTrapsPM 578 }

    -- 1.3.6.1.4.1.2011.2.25.3.40.40.20.579
    pmATMUNI2OUTCELLS NOTIFICATION-TYPE
        OBJECTS{ rptEvtPeriod,rptEvtValue,rptEvtVldty,rptEvtDateTime,rptEvtObjType,rptEvtParaLen,rptEvtPara }
        STATUS current
        DESCRIPTION
            "The number of normal cells transmitted by the ATM connection through UNI2. This number helps determine whether the connection service is normal."
        ::= { optixTrapsPM 579 }

    -- 1.3.6.1.4.1.2011.2.25.3.40.40.20.580
    pmATMUNI2INRATEMAX NOTIFICATION-TYPE
        OBJECTS{ rptEvtPeriod,rptEvtValue,rptEvtVldty,rptEvtDateTime,rptEvtObjType,rptEvtParaLen,rptEvtPara }
        STATUS current
        DESCRIPTION
            "Maximum rate of normal cells received by the UNI2"
        ::= { optixTrapsPM 580 }

    -- 1.3.6.1.4.1.2011.2.25.3.40.40.20.581
    pmATMUNI2INRATEMIN NOTIFICATION-TYPE
        OBJECTS{ rptEvtPeriod,rptEvtValue,rptEvtVldty,rptEvtDateTime,rptEvtObjType,rptEvtParaLen,rptEvtPara }
        STATUS current
        DESCRIPTION
            "Minimum rate of normal cells received by the UNI2"
        ::= { optixTrapsPM 581 }

    -- 1.3.6.1.4.1.2011.2.25.3.40.40.20.582
    pmATMUNI2INRATEAVG NOTIFICATION-TYPE
        OBJECTS{ rptEvtPeriod,rptEvtValue,rptEvtVldty,rptEvtDateTime,rptEvtObjType,rptEvtParaLen,rptEvtPara }
        STATUS current
        DESCRIPTION
            "Average rate of normal cells received by the UNI2"
        ::= { optixTrapsPM 582 }

    -- 1.3.6.1.4.1.2011.2.25.3.40.40.20.583
    pmATMUNI2OUTRATEMAX NOTIFICATION-TYPE
        OBJECTS{ rptEvtPeriod,rptEvtValue,rptEvtVldty,rptEvtDateTime,rptEvtObjType,rptEvtParaLen,rptEvtPara }
        STATUS current
        DESCRIPTION
            "Maximum rate of normal cells transmitted by the UNI2"
        ::= { optixTrapsPM 583 }

    -- 1.3.6.1.4.1.2011.2.25.3.40.40.20.584
    pmATMUNI2OUTRATEMIN NOTIFICATION-TYPE
        OBJECTS{ rptEvtPeriod,rptEvtValue,rptEvtVldty,rptEvtDateTime,rptEvtObjType,rptEvtParaLen,rptEvtPara }
        STATUS current
        DESCRIPTION
            "Minimum rate of normal cells transmitted by the UNI2"
        ::= { optixTrapsPM 584 }

    -- 1.3.6.1.4.1.2011.2.25.3.40.40.20.585
    pmATMUNI2OUTRATEAVG NOTIFICATION-TYPE
        OBJECTS{ rptEvtPeriod,rptEvtValue,rptEvtVldty,rptEvtDateTime,rptEvtObjType,rptEvtParaLen,rptEvtPara }
        STATUS current
        DESCRIPTION
            "Average rate of normal cells transmitted by the UNI2"
        ::= { optixTrapsPM 585 }

    -- 1.3.6.1.4.1.2011.2.25.3.40.40.20.586
    pmTUNNELREVERSESNDPKTS NOTIFICATION-TYPE
        OBJECTS{ rptEvtPeriod,rptEvtValue,rptEvtVldty,rptEvtDateTime,rptEvtObjType,rptEvtParaLen,rptEvtPara }
        STATUS current
        DESCRIPTION
            "Count of reverse packets transmitted on tunnel"
        ::= { optixTrapsPM 586 }

    -- 1.3.6.1.4.1.2011.2.25.3.40.40.20.587
    pmTUNNELREVERSESNDBYTES NOTIFICATION-TYPE
        OBJECTS{ rptEvtPeriod,rptEvtValue,rptEvtVldty,rptEvtDateTime,rptEvtObjType,rptEvtParaLen,rptEvtPara }
        STATUS current
        DESCRIPTION
            "Count of reverse bytes transmitted on tunnel"
        ::= { optixTrapsPM 587 }

    -- 1.3.6.1.4.1.2011.2.25.3.40.40.20.588
    pmTUNNELREVERSERCVPKTS NOTIFICATION-TYPE
        OBJECTS{ rptEvtPeriod,rptEvtValue,rptEvtVldty,rptEvtDateTime,rptEvtObjType,rptEvtParaLen,rptEvtPara }
        STATUS current
        DESCRIPTION
            "the number of packets received on the reverse tunnel"
        ::= { optixTrapsPM 588 }

    -- 1.3.6.1.4.1.2011.2.25.3.40.40.20.589
    pmTUNNELREVERSERCVBYTES NOTIFICATION-TYPE
        OBJECTS{ rptEvtPeriod,rptEvtValue,rptEvtVldty,rptEvtDateTime,rptEvtObjType,rptEvtParaLen,rptEvtPara }
        STATUS current
        DESCRIPTION
            "the number of bytes received on the reverse tunnel"
        ::= { optixTrapsPM 589 }

    -- 1.3.6.1.4.1.2011.2.25.3.40.40.20.590
    pmMPLSPWFLR NOTIFICATION-TYPE
        OBJECTS{ rptEvtPeriod,rptEvtValue,rptEvtVldty,rptEvtDateTime,rptEvtObjType,rptEvtParaLen,rptEvtPara }
        STATUS current
        DESCRIPTION
            "PW packet loss ratio."
        ::= { optixTrapsPM 590 }

    -- 1.3.6.1.4.1.2011.2.25.3.40.40.20.591
    pmMPLSPWFL NOTIFICATION-TYPE
        OBJECTS{ rptEvtPeriod,rptEvtValue,rptEvtVldty,rptEvtDateTime,rptEvtObjType,rptEvtParaLen,rptEvtPara }
        STATUS current
        DESCRIPTION
            "Number of lost PW packets."
        ::= { optixTrapsPM 591 }

    -- 1.3.6.1.4.1.2011.2.25.3.40.40.20.592
    pmMPLSPWFD NOTIFICATION-TYPE
        OBJECTS{ rptEvtPeriod,rptEvtValue,rptEvtVldty,rptEvtDateTime,rptEvtObjType,rptEvtParaLen,rptEvtPara }
        STATUS current
        DESCRIPTION
            "PW delay."
        ::= { optixTrapsPM 592 }

    -- 1.3.6.1.4.1.2011.2.25.3.40.40.20.593
    pmMPLSPWFDV NOTIFICATION-TYPE
        OBJECTS{ rptEvtPeriod,rptEvtValue,rptEvtVldty,rptEvtDateTime,rptEvtObjType,rptEvtParaLen,rptEvtPara }
        STATUS current
        DESCRIPTION
            "PW delay variation."
        ::= { optixTrapsPM 593 }

    -- 1.3.6.1.4.1.2011.2.25.3.40.40.20.614
    pmQOSPORTSTRMRCVMATCHPKTS NOTIFICATION-TYPE
        OBJECTS{ rptEvtPeriod,rptEvtValue,rptEvtVldty,rptEvtDateTime,rptEvtObjType,rptEvtParaLen,rptEvtPara }
        STATUS current
        DESCRIPTION
            "The number of received packets match flow classification on the port."
        ::= { optixTrapsPM 614 }

    -- 1.3.6.1.4.1.2011.2.25.3.40.40.20.615
    pmQOSPORTSTRMRCVMATCHBYTES NOTIFICATION-TYPE
        OBJECTS{ rptEvtPeriod,rptEvtValue,rptEvtVldty,rptEvtDateTime,rptEvtObjType,rptEvtParaLen,rptEvtPara }
        STATUS current
        DESCRIPTION
            "The number of bytes in the received packets match flow classification on the port."
        ::= { optixTrapsPM 615 }

    -- 1.3.6.1.4.1.2011.2.25.3.40.40.20.616
    pmQOSPORTSTRMSNDMATCHPKTS NOTIFICATION-TYPE
        OBJECTS{ rptEvtPeriod,rptEvtValue,rptEvtVldty,rptEvtDateTime,rptEvtObjType,rptEvtParaLen,rptEvtPara }
        STATUS current
        DESCRIPTION
            "The number of transmitted packets match flow classification on the port."
        ::= { optixTrapsPM 616 }

    -- 1.3.6.1.4.1.2011.2.25.3.40.40.20.617
    pmQOSPORTSTRMSNDMATCHBYTES NOTIFICATION-TYPE
        OBJECTS{ rptEvtPeriod,rptEvtValue,rptEvtVldty,rptEvtDateTime,rptEvtObjType,rptEvtParaLen,rptEvtPara }
        STATUS current
        DESCRIPTION
            "The number of bytes in the transmitted packets match flow classification on the port."
        ::= { optixTrapsPM 617 }

    -- 1.3.6.1.4.1.2011.2.25.3.40.40.20.618
    pmQOSPORTCARMarkedRedPKTS NOTIFICATION-TYPE
        OBJECTS{ rptEvtPeriod,rptEvtValue,rptEvtVldty,rptEvtDateTime,rptEvtObjType,rptEvtParaLen,rptEvtPara }
        STATUS current
        DESCRIPTION
            "Indicates the number of packets marked red in traffic classification defined in port policy."
        ::= { optixTrapsPM 618 }

    -- 1.3.6.1.4.1.2011.2.25.3.40.40.20.620
    pmQOSPORTCARMarkedYellowPKTS NOTIFICATION-TYPE
        OBJECTS{ rptEvtPeriod,rptEvtValue,rptEvtVldty,rptEvtDateTime,rptEvtObjType,rptEvtParaLen,rptEvtPara }
        STATUS current
        DESCRIPTION
            "Indicates the number of packets marked yellow in traffic classification defined in port policy."
        ::= { optixTrapsPM 620 }

    -- 1.3.6.1.4.1.2011.2.25.3.40.40.20.622
    pmQOSPORTCARMarkedGreenPKTS NOTIFICATION-TYPE
        OBJECTS{ rptEvtPeriod,rptEvtValue,rptEvtVldty,rptEvtDateTime,rptEvtObjType,rptEvtParaLen,rptEvtPara }
        STATUS current
        DESCRIPTION
            "Indicates the number of packets marked green in traffic classification defined in port policy."
        ::= { optixTrapsPM 622 }

    -- 1.3.6.1.4.1.2011.2.25.3.40.40.20.624
    pmMPLSTUNNEL1WFD NOTIFICATION-TYPE
        OBJECTS{ rptEvtPeriod,rptEvtValue,rptEvtVldty,rptEvtDateTime,rptEvtObjType,rptEvtParaLen,rptEvtPara }
        STATUS current
        DESCRIPTION
            "Tunnel one-way delay."
        ::= { optixTrapsPM  624 }

    -- 1.3.6.1.4.1.2011.2.25.3.40.40.20.625
    pmMPLSTUNNEL1WFDV NOTIFICATION-TYPE
        OBJECTS{ rptEvtPeriod,rptEvtValue,rptEvtVldty,rptEvtDateTime,rptEvtObjType,rptEvtParaLen,rptEvtPara }
        STATUS current
        DESCRIPTION
            "Tunnel one-way delay variation."
        ::= { optixTrapsPM  625 }

    -- 1.3.6.1.4.1.2011.2.25.3.40.40.20.626
    pmMPLSPW1WFD NOTIFICATION-TYPE
        OBJECTS{ rptEvtPeriod,rptEvtValue,rptEvtVldty,rptEvtDateTime,rptEvtObjType,rptEvtParaLen,rptEvtPara }
        STATUS current
        DESCRIPTION
            "PW one-way delay."
        ::= { optixTrapsPM  626 }

    -- 1.3.6.1.4.1.2011.2.25.3.40.40.20.627
    pmMPLSPW1WFDV NOTIFICATION-TYPE
        OBJECTS{ rptEvtPeriod,rptEvtValue,rptEvtVldty,rptEvtDateTime,rptEvtObjType,rptEvtParaLen,rptEvtPara }
        STATUS current
        DESCRIPTION
            "PW one-way delay variation."
        ::= { optixTrapsPM  627 }

    -- 1.3.6.1.4.1.2011.2.25.3.40.40.20.638
    pmDSCVLANPRIPKTS NOTIFICATION-TYPE
        OBJECTS{ rptEvtPeriod,rptEvtValue,rptEvtVldty,rptEvtDateTime,rptEvtObjType,rptEvtParaLen,rptEvtPara }
        STATUS current
        DESCRIPTION
            "The number of received packets match different cvlan priorities on the port."
        ::= { optixTrapsPM 638 }

    -- 1.3.6.1.4.1.2011.2.25.3.40.40.20.639
    pmDSCVLANPRIBYTES NOTIFICATION-TYPE
        OBJECTS{ rptEvtPeriod,rptEvtValue,rptEvtVldty,rptEvtDateTime,rptEvtObjType,rptEvtParaLen,rptEvtPara }
        STATUS current
        DESCRIPTION
            "The number of bytes in the received packets match different cvlan priorities on the port."
        ::= { optixTrapsPM 639 }

    -- 1.3.6.1.4.1.2011.2.25.3.40.40.20.640
    pmDSSVLANPRIPKTS NOTIFICATION-TYPE
        OBJECTS{ rptEvtPeriod,rptEvtValue,rptEvtVldty,rptEvtDateTime,rptEvtObjType,rptEvtParaLen,rptEvtPara }
        STATUS current
        DESCRIPTION
            "The number of received packets match different svlan priorities on the port."
        ::= { optixTrapsPM 640 }

    -- 1.3.6.1.4.1.2011.2.25.3.40.40.20.641
    pmDSSVLANPRIBYTES NOTIFICATION-TYPE
        OBJECTS{ rptEvtPeriod,rptEvtValue,rptEvtVldty,rptEvtDateTime,rptEvtObjType,rptEvtParaLen,rptEvtPara }
        STATUS current
        DESCRIPTION
            "The number of bytes in the received packets match different svlan priorities on the port."
        ::= { optixTrapsPM 641 }

    -- 1.3.6.1.4.1.2011.2.25.3.40.40.20.642
    pmDSDSCPPKTS NOTIFICATION-TYPE
        OBJECTS{ rptEvtPeriod,rptEvtValue,rptEvtVldty,rptEvtDateTime,rptEvtObjType,rptEvtParaLen,rptEvtPara }
        STATUS current
        DESCRIPTION
            "The number of received packets match different ip dscp priorities on the port."
        ::= { optixTrapsPM 642 }

    -- 1.3.6.1.4.1.2011.2.25.3.40.40.20.643
    pmDSDSCPBYTES NOTIFICATION-TYPE
        OBJECTS{ rptEvtPeriod,rptEvtValue,rptEvtVldty,rptEvtDateTime,rptEvtObjType,rptEvtParaLen,rptEvtPara }
        STATUS current
        DESCRIPTION
            "The number of bytes in the received packets match different ip dscp priorities on the port."
        ::= { optixTrapsPM 643 }

    -- 1.3.6.1.4.1.2011.2.25.3.40.40.20.644
    pmVLANRCVPKTS NOTIFICATION-TYPE
        OBJECTS{ rptEvtPeriod,rptEvtValue,rptEvtVldty,rptEvtDateTime,rptEvtObjType,rptEvtParaLen,rptEvtPara }
        STATUS current
        DESCRIPTION
            "The number of received packets match some vlan id at the specified V-UNI of the specified service."
        ::= { optixTrapsPM 644 }

    -- 1.3.6.1.4.1.2011.2.25.3.40.40.20.645
    pmVLANRCVBYTES NOTIFICATION-TYPE
        OBJECTS{ rptEvtPeriod,rptEvtValue,rptEvtVldty,rptEvtDateTime,rptEvtObjType,rptEvtParaLen,rptEvtPara }
        STATUS current
        DESCRIPTION
            "The number of bytes in the transmitted packets match some vlan id at the specified V-UNI of the specified service."
        ::= { optixTrapsPM 645 }

    -- 1.3.6.1.4.1.2011.2.25.3.40.40.20.646
    pmVLANSNDPKTS NOTIFICATION-TYPE
        OBJECTS{ rptEvtPeriod,rptEvtValue,rptEvtVldty,rptEvtDateTime,rptEvtObjType,rptEvtParaLen,rptEvtPara }
        STATUS current
        DESCRIPTION
            "The number of received packets match some vlan id at the specified V-UNI of the specified service."
        ::= { optixTrapsPM 646 }

    -- 1.3.6.1.4.1.2011.2.25.3.40.40.20.647
    pmVLANSNDBYTES NOTIFICATION-TYPE
        OBJECTS{ rptEvtPeriod,rptEvtValue,rptEvtVldty,rptEvtDateTime,rptEvtObjType,rptEvtParaLen,rptEvtPara }
        STATUS current
        DESCRIPTION
            "The number of bytes in the transmitted packets match some vlan id at the specified V-UNI of the specified service."
        ::= { optixTrapsPM 647 }

    -- 1.3.6.1.4.1.2011.2.25.3.40.40.20.648
    pmPORTPRISNDPKTS NOTIFICATION-TYPE
        OBJECTS{ rptEvtPeriod,rptEvtValue,rptEvtVldty,rptEvtDateTime,rptEvtObjType,rptEvtParaLen,rptEvtPara }
        STATUS current
        DESCRIPTION
            "The number of transmitted packets match the specified PHB service class on the port."
        ::= { optixTrapsPM 648 }

    -- 1.3.6.1.4.1.2011.2.25.3.40.40.20.649
    pmPORTPRISNDBYTES NOTIFICATION-TYPE
        OBJECTS{ rptEvtPeriod,rptEvtValue,rptEvtVldty,rptEvtDateTime,rptEvtObjType,rptEvtParaLen,rptEvtPara }
        STATUS current
        DESCRIPTION
            "The number of bytes in the transmitted packets match the specified PHB service class on the port."
        ::= { optixTrapsPM 649 }

    -- 1.3.6.1.4.1.2011.2.25.3.40.40.20.650
    pmPORTSTRMSHAPINGDROPPKTS NOTIFICATION-TYPE
        OBJECTS{ rptEvtPeriod,rptEvtValue,rptEvtVldty,rptEvtDateTime,rptEvtObjType,rptEvtParaLen,rptEvtPara }
        STATUS current
        DESCRIPTION
            "The number of discarded packets match flow classification for shaping on the port in the egress direction."
        ::= { optixTrapsPM 650 }

    -- 1.3.6.1.4.1.2011.2.25.3.40.40.20.652
    pmPORTSTRMSHAPINGDROPRATIO NOTIFICATION-TYPE
        OBJECTS{ rptEvtPeriod,rptEvtValue,rptEvtVldty,rptEvtDateTime,rptEvtObjType,rptEvtParaLen,rptEvtPara }
        STATUS current
        DESCRIPTION
            "The ratio of discarded packets match flow classification for shaping on the port in the egress direction."
        ::= { optixTrapsPM 652 }

    -- 1.3.6.1.4.1.2011.2.25.3.40.40.20.653
    pmQOSPORTCARMarkedRedRATIO NOTIFICATION-TYPE
        OBJECTS{ rptEvtPeriod,rptEvtValue,rptEvtVldty,rptEvtDateTime,rptEvtObjType,rptEvtParaLen,rptEvtPara }
        STATUS current
        DESCRIPTION
            "Indicates the ratio of packets marked red in traffic classification defined in port policy."
        ::= { optixTrapsPM 653 }

    -- 1.3.6.1.4.1.2011.2.25.3.40.40.20.654
    pmQOSPORTQUEUEDROPRATIO NOTIFICATION-TYPE
        OBJECTS{ rptEvtPeriod,rptEvtValue,rptEvtVldty,rptEvtDateTime,rptEvtObjType,rptEvtParaLen,rptEvtPara }
        STATUS current
        DESCRIPTION
            "Indicates the ratio of idscarded packets in the transmitted packets match the specified PHB service class on the port."
        ::= { optixTrapsPM 654 }

    -- 1.3.6.1.4.1.2011.2.25.3.40.40.20.655
    pmFLOWRXUTILIZATION NOTIFICATION-TYPE
        OBJECTS{ rptEvtPeriod,rptEvtValue,rptEvtVldty,rptEvtDateTime,rptEvtObjType,rptEvtParaLen,rptEvtPara }
        STATUS current
        DESCRIPTION
            "received flow classifier bandwidth utilization"
        ::= { optixTrapsPM 655 }

    -- 1.3.6.1.4.1.2011.2.25.3.40.40.20.657
    pmVUNITXUTILIZATION NOTIFICATION-TYPE
        OBJECTS{ rptEvtPeriod,rptEvtValue,rptEvtVldty,rptEvtDateTime,rptEvtObjType,rptEvtParaLen,rptEvtPara }
        STATUS current
        DESCRIPTION
            "transmitted VUNI bandwidth utilization"
        ::= { optixTrapsPM 657 }

    -- 1.3.6.1.4.1.2011.2.25.3.40.40.20.658
    pmVUNIGROUPSNDPKTS NOTIFICATION-TYPE
        OBJECTS{ rptEvtPeriod,rptEvtValue,rptEvtVldty,rptEvtDateTime,rptEvtObjType,rptEvtParaLen,rptEvtPara }
        STATUS current
        DESCRIPTION
            "Packets transmitted matching VUNI GROUP"
        ::= { optixTrapsPM 658 }

    -- 1.3.6.1.4.1.2011.2.25.3.40.40.20.659
    pmVUNIGROUPSNDBYTES NOTIFICATION-TYPE
        OBJECTS{ rptEvtPeriod,rptEvtValue,rptEvtVldty,rptEvtDateTime,rptEvtObjType,rptEvtParaLen,rptEvtPara }
        STATUS current
        DESCRIPTION
            "Bytes transmitted  matching VUNI GROUP"
        ::= { optixTrapsPM 659 }

    -- 1.3.6.1.4.1.2011.2.25.3.40.40.20.662
    pmVGROUPTXUTILIZATION NOTIFICATION-TYPE
        OBJECTS{ rptEvtPeriod,rptEvtValue,rptEvtVldty,rptEvtDateTime,rptEvtObjType,rptEvtParaLen,rptEvtPara }
        STATUS current
        DESCRIPTION
            "transmitted VUNI GROUP bandwidth utilization"
        ::= { optixTrapsPM 662 }

    -- 1.3.6.1.4.1.2011.2.25.3.40.40.20.663
    pmVUNIQUEUESNDDROPPKTS NOTIFICATION-TYPE
        OBJECTS{ rptEvtPeriod,rptEvtValue,rptEvtVldty,rptEvtDateTime,rptEvtObjType,rptEvtParaLen,rptEvtPara }
        STATUS current
        DESCRIPTION
            "Packets discarded on the VUNI queues in the egress direction"
        ::= { optixTrapsPM 663 }

    -- 1.3.6.1.4.1.2011.2.25.3.40.40.20.664
    pmVUNIQUEUESNDDROPBYTES NOTIFICATION-TYPE
        OBJECTS{ rptEvtPeriod,rptEvtValue,rptEvtVldty,rptEvtDateTime,rptEvtObjType,rptEvtParaLen,rptEvtPara }
        STATUS current
        DESCRIPTION
            "Bytes discarded on the VUNI queues in the egress direction"
        ::= { optixTrapsPM 664 }

    -- 1.3.6.1.4.1.2011.2.25.3.40.40.20.665
    pmVUNIQUEUESNDDROPRATIO NOTIFICATION-TYPE
        OBJECTS{ rptEvtPeriod,rptEvtValue,rptEvtVldty,rptEvtDateTime,rptEvtObjType,rptEvtParaLen,rptEvtPara }
        STATUS current
        DESCRIPTION
            "Ratio discarded on the VUNI queues in the egress direction"
        ::= { optixTrapsPM 665 }

    -- 1.3.6.1.4.1.2011.2.25.3.40.40.20.666
    pmVUNIGROUPSNDDROPPKTS NOTIFICATION-TYPE
        OBJECTS{ rptEvtPeriod,rptEvtValue,rptEvtVldty,rptEvtDateTime,rptEvtObjType,rptEvtParaLen,rptEvtPara }
        STATUS current
        DESCRIPTION
            "Packets discarded on the VUNI GROUP in the egress direction"
        ::= { optixTrapsPM 666 }

    -- 1.3.6.1.4.1.2011.2.25.3.40.40.20.667
    pmVUNIGROUPSNDDROPBYTES NOTIFICATION-TYPE
        OBJECTS{ rptEvtPeriod,rptEvtValue,rptEvtVldty,rptEvtDateTime,rptEvtObjType,rptEvtParaLen,rptEvtPara }
        STATUS current
        DESCRIPTION
            "Bytes discarded on the VUNI GROUP in the egress direction"
        ::= { optixTrapsPM 667 }

    -- 1.3.6.1.4.1.2011.2.25.3.40.40.20.668
    pmVUNIGROUPSNDDROPRATIO NOTIFICATION-TYPE
        OBJECTS{ rptEvtPeriod,rptEvtValue,rptEvtVldty,rptEvtDateTime,rptEvtObjType,rptEvtParaLen,rptEvtPara }
        STATUS current
        DESCRIPTION
            "Ratio discarded on the VUNI GROUP  in the egress direction"
        ::= { optixTrapsPM 668 }

    -- 1.3.6.1.4.1.2011.2.25.3.40.40.20.669
    pmPWQUEUESNDDROPPKTS NOTIFICATION-TYPE
        OBJECTS{ rptEvtPeriod,rptEvtValue,rptEvtVldty,rptEvtDateTime,rptEvtObjType,rptEvtParaLen,rptEvtPara }
        STATUS current
        DESCRIPTION
            "Packets discarded on the PW in the Ingress direction"
        ::= { optixTrapsPM 669 }

    -- 1.3.6.1.4.1.2011.2.25.3.40.40.20.670
    pmPWQUEUESNDDROPBYTES NOTIFICATION-TYPE
        OBJECTS{ rptEvtPeriod,rptEvtValue,rptEvtVldty,rptEvtDateTime,rptEvtObjType,rptEvtParaLen,rptEvtPara }
        STATUS current
        DESCRIPTION
            "Bytes discarded on the PW in the Ingress direction"
        ::= { optixTrapsPM 670 }

    -- 1.3.6.1.4.1.2011.2.25.3.40.40.20.671
    pmPWQUEUESNDDROPRATIO NOTIFICATION-TYPE
        OBJECTS{ rptEvtPeriod,rptEvtValue,rptEvtVldty,rptEvtDateTime,rptEvtObjType,rptEvtParaLen,rptEvtPara }
        STATUS current
        DESCRIPTION
            "Ratio discarded on PW in the Ingress direction"
        ::= { optixTrapsPM 671 }

    -- 1.3.6.1.4.1.2011.2.25.3.40.40.20.672
    pmTNLSNDDROPPKTS NOTIFICATION-TYPE
        OBJECTS{ rptEvtPeriod,rptEvtValue,rptEvtVldty,rptEvtDateTime,rptEvtObjType,rptEvtParaLen,rptEvtPara }
        STATUS current
        DESCRIPTION
            "Packets discarded on the PW in the Ingress direction"
        ::= { optixTrapsPM 672 }

    -- 1.3.6.1.4.1.2011.2.25.3.40.40.20.673
    pmTNLSNDDROPBYTES NOTIFICATION-TYPE
        OBJECTS{ rptEvtPeriod,rptEvtValue,rptEvtVldty,rptEvtDateTime,rptEvtObjType,rptEvtParaLen,rptEvtPara }
        STATUS current
        DESCRIPTION
            "Bytes discarded on the PW in the Ingress direction"
        ::= { optixTrapsPM 673 }

    -- 1.3.6.1.4.1.2011.2.25.3.40.40.20.674
    pmTNLSNDDROPRATIO NOTIFICATION-TYPE
        OBJECTS{ rptEvtPeriod,rptEvtValue,rptEvtVldty,rptEvtDateTime,rptEvtObjType,rptEvtParaLen,rptEvtPara }
        STATUS current
        DESCRIPTION
            "Ratio discarded on PW in the Ingress direction"
        ::= { optixTrapsPM 674 }

    -- 1.3.6.1.4.1.2011.2.25.3.40.40.20.675
    pmQOSCARREDRATIO NOTIFICATION-TYPE
        OBJECTS{ rptEvtPeriod,rptEvtValue,rptEvtVldty,rptEvtDateTime,rptEvtObjType,rptEvtParaLen,rptEvtPara }
        STATUS current
        DESCRIPTION
            "Ratio of packets marked red"
        ::= { optixTrapsPM 675 }

    -- 1.3.6.1.4.1.2011.2.25.3.40.40.20.676
    pmTNLREVERSESNDDROPPKTS NOTIFICATION-TYPE
        OBJECTS{ rptEvtPeriod,rptEvtValue,rptEvtVldty,rptEvtDateTime,rptEvtObjType,rptEvtParaLen,rptEvtPara }
        STATUS current
        DESCRIPTION
            "Packets discarded on the reverse tunnel in the Ingress direction"
        ::= { optixTrapsPM 676 }

    -- 1.3.6.1.4.1.2011.2.25.3.40.40.20.677
    pmTNLREVERSESNDDROPBYTES NOTIFICATION-TYPE
        OBJECTS{ rptEvtPeriod,rptEvtValue,rptEvtVldty,rptEvtDateTime,rptEvtObjType,rptEvtParaLen,rptEvtPara }
        STATUS current
        DESCRIPTION
            "Bytes discarded on the reverse tunnel in the Ingress direction"
        ::= { optixTrapsPM 677 }

    -- 1.3.6.1.4.1.2011.2.25.3.40.40.20.678
    pmTNLREVERSESNDDROPRATIO NOTIFICATION-TYPE
        OBJECTS{ rptEvtPeriod,rptEvtValue,rptEvtVldty,rptEvtDateTime,rptEvtObjType,rptEvtParaLen,rptEvtPara }
        STATUS current
        DESCRIPTION
            "Ratio discarded on reverse tunnel in the Ingress direction"
        ::= { optixTrapsPM 678 }

    -- 1.3.6.1.4.1.2011.2.25.3.40.40.20.679
    pmRXBPS NOTIFICATION-TYPE
        OBJECTS{ rptEvtPeriod,rptEvtValue,rptEvtVldty,rptEvtDateTime,rptEvtObjType,rptEvtParaLen,rptEvtPara }
        STATUS current
        DESCRIPTION
            "Bits per second received"
        ::= { optixTrapsPM 679 }

    -- 1.3.6.1.4.1.2011.2.25.3.40.40.20.680
    pmTXBPS NOTIFICATION-TYPE
        OBJECTS{ rptEvtPeriod,rptEvtValue,rptEvtVldty,rptEvtDateTime,rptEvtObjType,rptEvtParaLen,rptEvtPara }
        STATUS current
        DESCRIPTION
            "Bits per second transmitted"
        ::= { optixTrapsPM 680 }

    -- 1.3.6.1.4.1.2011.2.25.3.40.40.20.681
    pmRXPPS NOTIFICATION-TYPE
        OBJECTS{ rptEvtPeriod,rptEvtValue,rptEvtVldty,rptEvtDateTime,rptEvtObjType,rptEvtParaLen,rptEvtPara }
        STATUS current
        DESCRIPTION
            "Packets per second received"
        ::= { optixTrapsPM 681 }

    -- 1.3.6.1.4.1.2011.2.25.3.40.40.20.682
    pmTXPPS NOTIFICATION-TYPE
        OBJECTS{ rptEvtPeriod,rptEvtValue,rptEvtVldty,rptEvtDateTime,rptEvtObjType,rptEvtParaLen,rptEvtPara }
        STATUS current
        DESCRIPTION
            "Packets per second transmitted"
        ::= { optixTrapsPM 682 }

    -- 1.3.6.1.4.1.2011.2.25.3.40.40.20.683
    pmETHRXTHROUGHPUTMAX NOTIFICATION-TYPE
        OBJECTS{ rptEvtPeriod,rptEvtValue,rptEvtVldty,rptEvtDateTime,rptEvtObjType,rptEvtParaLen,rptEvtPara }
        STATUS current
        DESCRIPTION
            "Maximum rate of packets including framing bits (20 bytes) and FCS bytes received by the port."
        ::= { optixTrapsPM 683 }

    -- 1.3.6.1.4.1.2011.2.25.3.40.40.20.684
    pmETHRXTHROUGHPUTMIN NOTIFICATION-TYPE
        OBJECTS{ rptEvtPeriod,rptEvtValue,rptEvtVldty,rptEvtDateTime,rptEvtObjType,rptEvtParaLen,rptEvtPara }
        STATUS current
        DESCRIPTION
            "Minimum rate of packets including framing bits (20 bytes) and FCS bytes received by the port."
        ::= { optixTrapsPM 684 }

    -- 1.3.6.1.4.1.2011.2.25.3.40.40.20.685
    pmETHRXTHROUGHPUTAVG NOTIFICATION-TYPE
        OBJECTS{ rptEvtPeriod,rptEvtValue,rptEvtVldty,rptEvtDateTime,rptEvtObjType,rptEvtParaLen,rptEvtPara }
        STATUS current
        DESCRIPTION
            "Average rate of packets including framing bits (20 bytes) and FCS bytes received by the port."
        ::= { optixTrapsPM 685 }

    -- 1.3.6.1.4.1.2011.2.25.3.40.40.20.686
    pmETHTXTHROUGHPUTMAX NOTIFICATION-TYPE
        OBJECTS{ rptEvtPeriod,rptEvtValue,rptEvtVldty,rptEvtDateTime,rptEvtObjType,rptEvtParaLen,rptEvtPara }
        STATUS current
        DESCRIPTION
            "Maximum rate of packets including framing bits (20 bytes) and FCS bytes transmitted by the port."
        ::= { optixTrapsPM 686 }

    -- 1.3.6.1.4.1.2011.2.25.3.40.40.20.687
    pmETHTXTHROUGHPUTMIN NOTIFICATION-TYPE
        OBJECTS{ rptEvtPeriod,rptEvtValue,rptEvtVldty,rptEvtDateTime,rptEvtObjType,rptEvtParaLen,rptEvtPara }
        STATUS current
        DESCRIPTION
            "Minimum rate of packets including framing bits (20 bytes) and FCS bytes transmitted by the port."
        ::= { optixTrapsPM 687 }

    -- 1.3.6.1.4.1.2011.2.25.3.40.40.20.688
    pmETHTXTHROUGHPUTAVG NOTIFICATION-TYPE
        OBJECTS{ rptEvtPeriod,rptEvtValue,rptEvtVldty,rptEvtDateTime,rptEvtObjType,rptEvtParaLen,rptEvtPara }
        STATUS current
        DESCRIPTION
            "Average rate of packets including framing bits (20 bytes) and FCS bytes transmitted by the port."
        ::= { optixTrapsPM 688 }

    -- 1.3.6.1.4.1.2011.2.25.3.40.40.20.689
    pmVUNISNDDROPPKTS NOTIFICATION-TYPE
        OBJECTS{ rptEvtPeriod,rptEvtValue,rptEvtVldty,rptEvtDateTime,rptEvtObjType,rptEvtParaLen,rptEvtPara }
        STATUS current
        DESCRIPTION
            "Packets discarded on the VUNI in the Egress direction"
        ::= { optixTrapsPM 689 }

    -- 1.3.6.1.4.1.2011.2.25.3.40.40.20.690
    pmVUNISNDDROPBYTES NOTIFICATION-TYPE
        OBJECTS{ rptEvtPeriod,rptEvtValue,rptEvtVldty,rptEvtDateTime,rptEvtObjType,rptEvtParaLen,rptEvtPara }
        STATUS current
        DESCRIPTION
            "Bytes discarded on the VUNI in the Egress direction"
        ::= { optixTrapsPM 690 }

    -- 1.3.6.1.4.1.2011.2.25.3.40.40.20.691
    pmVUNISNDDROPRATIO NOTIFICATION-TYPE
        OBJECTS{ rptEvtPeriod,rptEvtValue,rptEvtVldty,rptEvtDateTime,rptEvtObjType,rptEvtParaLen,rptEvtPara }
        STATUS current
        DESCRIPTION
            "Ratio discarded on VUNI in the Ingress direction"
        ::= { optixTrapsPM 691 }

    -- 1.3.6.1.4.1.2011.2.25.3.40.40.20.692
    pmRXDROPRATIO NOTIFICATION-TYPE
        OBJECTS{ rptEvtPeriod,rptEvtValue,rptEvtVldty,rptEvtDateTime,rptEvtObjType,rptEvtParaLen,rptEvtPara }
        STATUS current
        DESCRIPTION
            "Packet loss ratio in the ingress direction"
        ::= { optixTrapsPM 692 }

    -- 1.3.6.1.4.1.2011.2.25.3.40.40.20.693
    pmTXDROPRATIO NOTIFICATION-TYPE
        OBJECTS{ rptEvtPeriod,rptEvtValue,rptEvtVldty,rptEvtDateTime,rptEvtObjType,rptEvtParaLen,rptEvtPara }
        STATUS current
        DESCRIPTION
            "Packet loss ratio in the egress direction"
        ::= { optixTrapsPM 693 }

    -- 1.3.6.1.4.1.2011.2.25.3.40.40.20.698
    pmTUNNELREVERSERXBPS NOTIFICATION-TYPE
        OBJECTS{ rptEvtPeriod,rptEvtValue,rptEvtVldty,rptEvtDateTime,rptEvtObjType,rptEvtParaLen,rptEvtPara }
        STATUS current
        DESCRIPTION
            "Bits per second of received on the reverse tunnel, that is, number of actually received bytes x 8/time unit."
        ::= { optixTrapsPM 698 }

    -- 1.3.6.1.4.1.2011.2.25.3.40.40.20.699
    pmTUNNELREVERSETXBPS NOTIFICATION-TYPE
        OBJECTS{ rptEvtPeriod,rptEvtValue,rptEvtVldty,rptEvtDateTime,rptEvtObjType,rptEvtParaLen,rptEvtPara }
        STATUS current
        DESCRIPTION
            "Bits per second of transmitted on the reverse tunnel, that is, number of actually received bytes x 8/time unit."
        ::= { optixTrapsPM 699 }

    -- 1.3.6.1.4.1.2011.2.25.3.40.40.20.700
    pmTUNNELREVERSERXPPS NOTIFICATION-TYPE
        OBJECTS{ rptEvtPeriod,rptEvtValue,rptEvtVldty,rptEvtDateTime,rptEvtObjType,rptEvtParaLen,rptEvtPara }
        STATUS current
        DESCRIPTION
            "Packets per second of received on the reverse tunnel, that is, number of actually received packets/time unit."
        ::= { optixTrapsPM 700 }

    -- 1.3.6.1.4.1.2011.2.25.3.40.40.20.701
    pmTUNNELREVERSETXPPS NOTIFICATION-TYPE
        OBJECTS{ rptEvtPeriod,rptEvtValue,rptEvtVldty,rptEvtDateTime,rptEvtObjType,rptEvtParaLen,rptEvtPara }
        STATUS current
        DESCRIPTION
            "Packets per second transmitted on the reverse tunnel"
        ::= { optixTrapsPM 701 }

    -- 1.3.6.1.4.1.2011.2.25.3.40.40.20.702
    pmTUNNELRXBPS NOTIFICATION-TYPE
        OBJECTS{ rptEvtPeriod,rptEvtValue,rptEvtVldty,rptEvtDateTime,rptEvtObjType,rptEvtParaLen,rptEvtPara }
        STATUS current
        DESCRIPTION
            "Bits per second received on tunnel"
        ::= { optixTrapsPM 702 }

    -- 1.3.6.1.4.1.2011.2.25.3.40.40.20.703
    pmTUNNELTXBPS NOTIFICATION-TYPE
        OBJECTS{ rptEvtPeriod,rptEvtValue,rptEvtVldty,rptEvtDateTime,rptEvtObjType,rptEvtParaLen,rptEvtPara }
        STATUS current
        DESCRIPTION
            "Bits per second transmitted on tunnel"
        ::= { optixTrapsPM 703 }

    -- 1.3.6.1.4.1.2011.2.25.3.40.40.20.704
    pmTUNNELRXPPS NOTIFICATION-TYPE
        OBJECTS{ rptEvtPeriod,rptEvtValue,rptEvtVldty,rptEvtDateTime,rptEvtObjType,rptEvtParaLen,rptEvtPara }
        STATUS current
        DESCRIPTION
            "Packets per second received on tunnel"
        ::= { optixTrapsPM 704 }

    -- 1.3.6.1.4.1.2011.2.25.3.40.40.20.705
    pmTUNNELTXPPS NOTIFICATION-TYPE
        OBJECTS{ rptEvtPeriod,rptEvtValue,rptEvtVldty,rptEvtDateTime,rptEvtObjType,rptEvtParaLen,rptEvtPara }
        STATUS current
        DESCRIPTION
            "Packets per second transmitted on tunnel"
        ::= { optixTrapsPM 705 }

    -- 1.3.6.1.4.1.2011.2.25.3.40.40.20.706
    pmPWRXBPS NOTIFICATION-TYPE
        OBJECTS{ rptEvtPeriod,rptEvtValue,rptEvtVldty,rptEvtDateTime,rptEvtObjType,rptEvtParaLen,rptEvtPara }
        STATUS current
        DESCRIPTION
            "Bits per second received on PW"
        ::= { optixTrapsPM 706 }

    -- 1.3.6.1.4.1.2011.2.25.3.40.40.20.707
    pmPWTXBPS NOTIFICATION-TYPE
        OBJECTS{ rptEvtPeriod,rptEvtValue,rptEvtVldty,rptEvtDateTime,rptEvtObjType,rptEvtParaLen,rptEvtPara }
        STATUS current
        DESCRIPTION
            "Bits per second transmitted on PW"
        ::= { optixTrapsPM 707 }

    -- 1.3.6.1.4.1.2011.2.25.3.40.40.20.708
    pmPWRXPPS NOTIFICATION-TYPE
        OBJECTS{ rptEvtPeriod,rptEvtValue,rptEvtVldty,rptEvtDateTime,rptEvtObjType,rptEvtParaLen,rptEvtPara }
        STATUS current
        DESCRIPTION
            "Packets per second received on PW"
        ::= { optixTrapsPM 708 }

    -- 1.3.6.1.4.1.2011.2.25.3.40.40.20.709
    pmPWTXPPS NOTIFICATION-TYPE
        OBJECTS{ rptEvtPeriod,rptEvtValue,rptEvtVldty,rptEvtDateTime,rptEvtObjType,rptEvtParaLen,rptEvtPara }
        STATUS current
        DESCRIPTION
            "Packets per second transmitted on PW"
        ::= { optixTrapsPM 709 }

    -- 1.3.6.1.4.1.2011.2.25.3.40.40.20.710
    pmVUNIRXBPS NOTIFICATION-TYPE
        OBJECTS{ rptEvtPeriod,rptEvtValue,rptEvtVldty,rptEvtDateTime,rptEvtObjType,rptEvtParaLen,rptEvtPara }
        STATUS current
        DESCRIPTION
            "Bits per second received at V-UNI."
        ::= { optixTrapsPM 710 }

    -- 1.3.6.1.4.1.2011.2.25.3.40.40.20.711
    pmVUNITXBPS NOTIFICATION-TYPE
        OBJECTS{ rptEvtPeriod,rptEvtValue,rptEvtVldty,rptEvtDateTime,rptEvtObjType,rptEvtParaLen,rptEvtPara }
        STATUS current
        DESCRIPTION
            "Bits per second transmitted at V-UNI."
        ::= { optixTrapsPM 711 }

    -- 1.3.6.1.4.1.2011.2.25.3.40.40.20.712
    pmVUNIRXPPS NOTIFICATION-TYPE
        OBJECTS{ rptEvtPeriod,rptEvtValue,rptEvtVldty,rptEvtDateTime,rptEvtObjType,rptEvtParaLen,rptEvtPara }
        STATUS current
        DESCRIPTION
            "Packets per second received at V-UNI."
        ::= { optixTrapsPM 712 }

    -- 1.3.6.1.4.1.2011.2.25.3.40.40.20.713
    pmVUNITXPPS NOTIFICATION-TYPE
        OBJECTS{ rptEvtPeriod,rptEvtValue,rptEvtVldty,rptEvtDateTime,rptEvtObjType,rptEvtParaLen,rptEvtPara }
        STATUS current
        DESCRIPTION
            "Packets per second transmitted at V-UNI."
        ::= { optixTrapsPM 713 }

    -- 1.3.6.1.4.1.2011.2.25.3.40.40.20.714
    pmVLANRXBPS NOTIFICATION-TYPE
        OBJECTS{ rptEvtPeriod,rptEvtValue,rptEvtVldty,rptEvtDateTime,rptEvtObjType,rptEvtParaLen,rptEvtPara }
        STATUS current
        DESCRIPTION
            "Bits per second received matching VLAN at V-UNI"
        ::= { optixTrapsPM 714 }

    -- 1.3.6.1.4.1.2011.2.25.3.40.40.20.715
    pmVLANTXBPS NOTIFICATION-TYPE
        OBJECTS{ rptEvtPeriod,rptEvtValue,rptEvtVldty,rptEvtDateTime,rptEvtObjType,rptEvtParaLen,rptEvtPara }
        STATUS current
        DESCRIPTION
            "Bits per second transmitted matching VLAN at V-UNI."
        ::= { optixTrapsPM 715 }

    -- 1.3.6.1.4.1.2011.2.25.3.40.40.20.716
    pmVLANRXPPS NOTIFICATION-TYPE
        OBJECTS{ rptEvtPeriod,rptEvtValue,rptEvtVldty,rptEvtDateTime,rptEvtObjType,rptEvtParaLen,rptEvtPara }
        STATUS current
        DESCRIPTION
            "Packets per second received matching VLAN at V-UNI"
        ::= { optixTrapsPM 716 }

    -- 1.3.6.1.4.1.2011.2.25.3.40.40.20.717
    pmVLANTXPPS NOTIFICATION-TYPE
        OBJECTS{ rptEvtPeriod,rptEvtValue,rptEvtVldty,rptEvtDateTime,rptEvtObjType,rptEvtParaLen,rptEvtPara }
        STATUS current
        DESCRIPTION
            "Packets per second transmitted matching VLAN at V-UNI."
        ::= { optixTrapsPM 717 }

    -- 1.3.6.1.4.1.2011.2.25.3.40.40.20.718
    pmQOSPORTSTRMRXBPS NOTIFICATION-TYPE
        OBJECTS{ rptEvtPeriod,rptEvtValue,rptEvtVldty,rptEvtDateTime,rptEvtObjType,rptEvtParaLen,rptEvtPara }
        STATUS current
        DESCRIPTION
            "Bits per second received matching port flow classification."
        ::= { optixTrapsPM 718 }

    -- 1.3.6.1.4.1.2011.2.25.3.40.40.20.719
    pmQOSPORTSTRMTXBPS NOTIFICATION-TYPE
        OBJECTS{ rptEvtPeriod,rptEvtValue,rptEvtVldty,rptEvtDateTime,rptEvtObjType,rptEvtParaLen,rptEvtPara }
        STATUS current
        DESCRIPTION
            "Bits per second transmitted matching port flow classification."
        ::= { optixTrapsPM 719 }

    -- 1.3.6.1.4.1.2011.2.25.3.40.40.20.720
    pmQOSPORTSTRMRXPPS NOTIFICATION-TYPE
        OBJECTS{ rptEvtPeriod,rptEvtValue,rptEvtVldty,rptEvtDateTime,rptEvtObjType,rptEvtParaLen,rptEvtPara }
        STATUS current
        DESCRIPTION
            "Packets per second received matching port flow classification"
        ::= { optixTrapsPM 720 }

    -- 1.3.6.1.4.1.2011.2.25.3.40.40.20.721
    pmQOSPORTSTRMTXPPS NOTIFICATION-TYPE
        OBJECTS{ rptEvtPeriod,rptEvtValue,rptEvtVldty,rptEvtDateTime,rptEvtObjType,rptEvtParaLen,rptEvtPara }
        STATUS current
        DESCRIPTION
            "Packets per second transmitted matching port flow classification"
        ::= { optixTrapsPM 721 }

    -- 1.3.6.1.4.1.2011.2.25.3.40.40.20.722
    pmPORTPRITXBPS NOTIFICATION-TYPE
        OBJECTS{ rptEvtPeriod,rptEvtValue,rptEvtVldty,rptEvtDateTime,rptEvtObjType,rptEvtParaLen,rptEvtPara }
        STATUS current
        DESCRIPTION
            "Bits per second transmitted matching PHB service class"
        ::= { optixTrapsPM 722 }

    -- 1.3.6.1.4.1.2011.2.25.3.40.40.20.723
    pmPORTPRITXPPS NOTIFICATION-TYPE
        OBJECTS{ rptEvtPeriod,rptEvtValue,rptEvtVldty,rptEvtDateTime,rptEvtObjType,rptEvtParaLen,rptEvtPara }
        STATUS current
        DESCRIPTION
            "Packets per second transmitted matching PHB service class"
        ::= { optixTrapsPM 723 }

    -- 1.3.6.1.4.1.2011.2.25.3.40.40.20.724
    pmPWQUEUETXBPS NOTIFICATION-TYPE
        OBJECTS{ rptEvtPeriod,rptEvtValue,rptEvtVldty,rptEvtDateTime,rptEvtObjType,rptEvtParaLen,rptEvtPara }
        STATUS current
        DESCRIPTION
            "Bits per second discarded on the PW in the Ingress direction."
        ::= { optixTrapsPM 724 }

    -- 1.3.6.1.4.1.2011.2.25.3.40.40.20.725
    pmPWQUEUETXPPS NOTIFICATION-TYPE
        OBJECTS{ rptEvtPeriod,rptEvtValue,rptEvtVldty,rptEvtDateTime,rptEvtObjType,rptEvtParaLen,rptEvtPara }
        STATUS current
        DESCRIPTION
            "Packets per second discarded on the PW in the Ingress direction."
        ::= { optixTrapsPM 725 }

    -- 1.3.6.1.4.1.2011.2.25.3.40.40.20.726
    pmETHCFMFLRPRI0 NOTIFICATION-TYPE
        OBJECTS{ rptEvtPeriod,rptEvtValue,rptEvtVldty,rptEvtDateTime,rptEvtObjType,rptEvtParaLen,rptEvtPara }
        STATUS current
        DESCRIPTION
            "E-Line service packet loss ratio for priority 0."
        ::= { optixTrapsPM 726 }

    -- 1.3.6.1.4.1.2011.2.25.3.40.40.20.727
    pmETHCFMFLPRI0 NOTIFICATION-TYPE
        OBJECTS{ rptEvtPeriod,rptEvtValue,rptEvtVldty,rptEvtDateTime,rptEvtObjType,rptEvtParaLen,rptEvtPara }
        STATUS current
        DESCRIPTION
            "E-Line service lost packets for priority 0."
        ::= { optixTrapsPM 727 }

    -- 1.3.6.1.4.1.2011.2.25.3.40.40.20.728
    pmETHCFMFDPRI0 NOTIFICATION-TYPE
        OBJECTS{ rptEvtPeriod,rptEvtValue,rptEvtVldty,rptEvtDateTime,rptEvtObjType,rptEvtParaLen,rptEvtPara }
        STATUS current
        DESCRIPTION
            "E-Line service delay for priority 0."
        ::= { optixTrapsPM 728 }

    -- 1.3.6.1.4.1.2011.2.25.3.40.40.20.729
    pmETHCFMFDVPRI0 NOTIFICATION-TYPE
        OBJECTS{ rptEvtPeriod,rptEvtValue,rptEvtVldty,rptEvtDateTime,rptEvtObjType,rptEvtParaLen,rptEvtPara }
        STATUS current
        DESCRIPTION
            "E-Line service delay variation for priority 0."
        ::= { optixTrapsPM 729 }

    -- 1.3.6.1.4.1.2011.2.25.3.40.40.20.730
    pmETHCFMFLRPRI1 NOTIFICATION-TYPE
        OBJECTS{ rptEvtPeriod,rptEvtValue,rptEvtVldty,rptEvtDateTime,rptEvtObjType,rptEvtParaLen,rptEvtPara }
        STATUS current
        DESCRIPTION
            "E-Line service packet loss ratio for priority 1."
        ::= { optixTrapsPM 730 }

    -- 1.3.6.1.4.1.2011.2.25.3.40.40.20.731
    pmETHCFMFLPRI1 NOTIFICATION-TYPE
        OBJECTS{ rptEvtPeriod,rptEvtValue,rptEvtVldty,rptEvtDateTime,rptEvtObjType,rptEvtParaLen,rptEvtPara }
        STATUS current
        DESCRIPTION
            "E-Line service lost packets for priority 1."
        ::= { optixTrapsPM 731 }

    -- 1.3.6.1.4.1.2011.2.25.3.40.40.20.732
    pmETHCFMFDPRI1 NOTIFICATION-TYPE
        OBJECTS{ rptEvtPeriod,rptEvtValue,rptEvtVldty,rptEvtDateTime,rptEvtObjType,rptEvtParaLen,rptEvtPara }
        STATUS current
        DESCRIPTION
            "E-Line service delay for priority 1."
        ::= { optixTrapsPM 732 }

    -- 1.3.6.1.4.1.2011.2.25.3.40.40.20.733
    pmETHCFMFDVPRI1 NOTIFICATION-TYPE
        OBJECTS{ rptEvtPeriod,rptEvtValue,rptEvtVldty,rptEvtDateTime,rptEvtObjType,rptEvtParaLen,rptEvtPara }
        STATUS current
        DESCRIPTION
            "E-Line service delay variation for priority 1."
        ::= { optixTrapsPM 733 }

    -- 1.3.6.1.4.1.2011.2.25.3.40.40.20.734
    pmETHCFMFLRPRI2 NOTIFICATION-TYPE
        OBJECTS{ rptEvtPeriod,rptEvtValue,rptEvtVldty,rptEvtDateTime,rptEvtObjType,rptEvtParaLen,rptEvtPara }
        STATUS current
        DESCRIPTION
            "E-Line service packet loss ratio for priority 2."
        ::= { optixTrapsPM 734 }

    -- 1.3.6.1.4.1.2011.2.25.3.40.40.20.735
    pmETHCFMFLPRI2 NOTIFICATION-TYPE
        OBJECTS{ rptEvtPeriod,rptEvtValue,rptEvtVldty,rptEvtDateTime,rptEvtObjType,rptEvtParaLen,rptEvtPara }
        STATUS current
        DESCRIPTION
            "E-Line service lost packets for priority 2."
        ::= { optixTrapsPM 735 }

    -- 1.3.6.1.4.1.2011.2.25.3.40.40.20.736
    pmETHCFMFDPRI2 NOTIFICATION-TYPE
        OBJECTS{ rptEvtPeriod,rptEvtValue,rptEvtVldty,rptEvtDateTime,rptEvtObjType,rptEvtParaLen,rptEvtPara }
        STATUS current
        DESCRIPTION
            "E-Line service delay for priority 2."
        ::= { optixTrapsPM 736 }

    -- 1.3.6.1.4.1.2011.2.25.3.40.40.20.737
    pmETHCFMFDVPRI2 NOTIFICATION-TYPE
        OBJECTS{ rptEvtPeriod,rptEvtValue,rptEvtVldty,rptEvtDateTime,rptEvtObjType,rptEvtParaLen,rptEvtPara }
        STATUS current
        DESCRIPTION
            "E-Line service delay variation for priority 2."
        ::= { optixTrapsPM 737 }

    -- 1.3.6.1.4.1.2011.2.25.3.40.40.20.738
    pmETHCFMFLRPRI3 NOTIFICATION-TYPE
        OBJECTS{ rptEvtPeriod,rptEvtValue,rptEvtVldty,rptEvtDateTime,rptEvtObjType,rptEvtParaLen,rptEvtPara }
        STATUS current
        DESCRIPTION
            "E-Line service packet loss ratio for priority 3."
        ::= { optixTrapsPM 738 }

    -- 1.3.6.1.4.1.2011.2.25.3.40.40.20.739
    pmETHCFMFLPRI3 NOTIFICATION-TYPE
        OBJECTS{ rptEvtPeriod,rptEvtValue,rptEvtVldty,rptEvtDateTime,rptEvtObjType,rptEvtParaLen,rptEvtPara }
        STATUS current
        DESCRIPTION
            "E-Line service lost packets for priority 3."
        ::= { optixTrapsPM 739 }

    -- 1.3.6.1.4.1.2011.2.25.3.40.40.20.740
    pmETHCFMFDPRI3 NOTIFICATION-TYPE
        OBJECTS{ rptEvtPeriod,rptEvtValue,rptEvtVldty,rptEvtDateTime,rptEvtObjType,rptEvtParaLen,rptEvtPara }
        STATUS current
        DESCRIPTION
            "E-Line service delay for priority 3."
        ::= { optixTrapsPM 740 }

    -- 1.3.6.1.4.1.2011.2.25.3.40.40.20.741
    pmETHCFMFDVPRI3 NOTIFICATION-TYPE
        OBJECTS{ rptEvtPeriod,rptEvtValue,rptEvtVldty,rptEvtDateTime,rptEvtObjType,rptEvtParaLen,rptEvtPara }
        STATUS current
        DESCRIPTION
            "E-Line service delay variation for priority 3."
        ::= { optixTrapsPM 741 }

    -- 1.3.6.1.4.1.2011.2.25.3.40.40.20.742
    pmETHCFMFLRPRI4 NOTIFICATION-TYPE
        OBJECTS{ rptEvtPeriod,rptEvtValue,rptEvtVldty,rptEvtDateTime,rptEvtObjType,rptEvtParaLen,rptEvtPara }
        STATUS current
        DESCRIPTION
            "E-Line service packet loss ratio for priority 4."
        ::= { optixTrapsPM 742 }

    -- 1.3.6.1.4.1.2011.2.25.3.40.40.20.743
    pmETHCFMFLPRI4 NOTIFICATION-TYPE
        OBJECTS{ rptEvtPeriod,rptEvtValue,rptEvtVldty,rptEvtDateTime,rptEvtObjType,rptEvtParaLen,rptEvtPara }
        STATUS current
        DESCRIPTION
            "E-Line service lost packets for priority 4."
        ::= { optixTrapsPM 743 }

    -- 1.3.6.1.4.1.2011.2.25.3.40.40.20.744
    pmETHCFMFDPRI4 NOTIFICATION-TYPE
        OBJECTS{ rptEvtPeriod,rptEvtValue,rptEvtVldty,rptEvtDateTime,rptEvtObjType,rptEvtParaLen,rptEvtPara }
        STATUS current
        DESCRIPTION
            "E-Line service delay for priority 4."
        ::= { optixTrapsPM 744 }

    -- 1.3.6.1.4.1.2011.2.25.3.40.40.20.745
    pmETHCFMFDVPRI4 NOTIFICATION-TYPE
        OBJECTS{ rptEvtPeriod,rptEvtValue,rptEvtVldty,rptEvtDateTime,rptEvtObjType,rptEvtParaLen,rptEvtPara }
        STATUS current
        DESCRIPTION
            "E-Line service delay variation for priority 4."
        ::= { optixTrapsPM 745 }

    -- 1.3.6.1.4.1.2011.2.25.3.40.40.20.746
    pmETHCFMFLRPRI5 NOTIFICATION-TYPE
        OBJECTS{ rptEvtPeriod,rptEvtValue,rptEvtVldty,rptEvtDateTime,rptEvtObjType,rptEvtParaLen,rptEvtPara }
        STATUS current
        DESCRIPTION
            "E-Line service packet loss ratio for priority 5."
        ::= { optixTrapsPM 746 }

    -- 1.3.6.1.4.1.2011.2.25.3.40.40.20.747
    pmETHCFMFLPRI5 NOTIFICATION-TYPE
        OBJECTS{ rptEvtPeriod,rptEvtValue,rptEvtVldty,rptEvtDateTime,rptEvtObjType,rptEvtParaLen,rptEvtPara }
        STATUS current
        DESCRIPTION
            "E-Line service lost packets for priority 5."
        ::= { optixTrapsPM 747 }

    -- 1.3.6.1.4.1.2011.2.25.3.40.40.20.748
    pmETHCFMFDPRI5 NOTIFICATION-TYPE
        OBJECTS{ rptEvtPeriod,rptEvtValue,rptEvtVldty,rptEvtDateTime,rptEvtObjType,rptEvtParaLen,rptEvtPara }
        STATUS current
        DESCRIPTION
            "E-Line service delay for priority 5."
        ::= { optixTrapsPM 748 }

    -- 1.3.6.1.4.1.2011.2.25.3.40.40.20.749
    pmETHCFMFDVPRI5 NOTIFICATION-TYPE
        OBJECTS{ rptEvtPeriod,rptEvtValue,rptEvtVldty,rptEvtDateTime,rptEvtObjType,rptEvtParaLen,rptEvtPara }
        STATUS current
        DESCRIPTION
            "E-Line service delay variation for priority 5."
        ::= { optixTrapsPM 749 }

    -- 1.3.6.1.4.1.2011.2.25.3.40.40.20.750
    pmETHCFMFLRPRI6 NOTIFICATION-TYPE
        OBJECTS{ rptEvtPeriod,rptEvtValue,rptEvtVldty,rptEvtDateTime,rptEvtObjType,rptEvtParaLen,rptEvtPara }
        STATUS current
        DESCRIPTION
            "E-Line service packet loss ratio for priority 6."
        ::= { optixTrapsPM 750 }

    -- 1.3.6.1.4.1.2011.2.25.3.40.40.20.751
    pmETHCFMFLPRI6 NOTIFICATION-TYPE
        OBJECTS{ rptEvtPeriod,rptEvtValue,rptEvtVldty,rptEvtDateTime,rptEvtObjType,rptEvtParaLen,rptEvtPara }
        STATUS current
        DESCRIPTION
            "E-Line service lost packets for priority 6."
        ::= { optixTrapsPM 751 }

    -- 1.3.6.1.4.1.2011.2.25.3.40.40.20.752
    pmETHCFMFDPRI6 NOTIFICATION-TYPE
        OBJECTS{ rptEvtPeriod,rptEvtValue,rptEvtVldty,rptEvtDateTime,rptEvtObjType,rptEvtParaLen,rptEvtPara }
        STATUS current
        DESCRIPTION
            "E-Line service delay for priority 6."
        ::= { optixTrapsPM 752 }

    -- 1.3.6.1.4.1.2011.2.25.3.40.40.20.753
    pmETHCFMFDVPRI6 NOTIFICATION-TYPE
        OBJECTS{ rptEvtPeriod,rptEvtValue,rptEvtVldty,rptEvtDateTime,rptEvtObjType,rptEvtParaLen,rptEvtPara }
        STATUS current
        DESCRIPTION
            "E-Line service delay variation for priority 6."
        ::= { optixTrapsPM 753 }

    -- 1.3.6.1.4.1.2011.2.25.3.40.40.20.754
    pmETHCFMFLRPRI7 NOTIFICATION-TYPE
        OBJECTS{ rptEvtPeriod,rptEvtValue,rptEvtVldty,rptEvtDateTime,rptEvtObjType,rptEvtParaLen,rptEvtPara }
        STATUS current
        DESCRIPTION
            "E-Line service packet loss ratio for priority 7."
        ::= { optixTrapsPM 754 }

    -- 1.3.6.1.4.1.2011.2.25.3.40.40.20.755
    pmETHCFMFLPRI7 NOTIFICATION-TYPE
        OBJECTS{ rptEvtPeriod,rptEvtValue,rptEvtVldty,rptEvtDateTime,rptEvtObjType,rptEvtParaLen,rptEvtPara }
        STATUS current
        DESCRIPTION
            "E-Line service lost packets for priority 7."
        ::= { optixTrapsPM 755 }

    -- 1.3.6.1.4.1.2011.2.25.3.40.40.20.756
    pmETHCFMFDPRI7 NOTIFICATION-TYPE
        OBJECTS{ rptEvtPeriod,rptEvtValue,rptEvtVldty,rptEvtDateTime,rptEvtObjType,rptEvtParaLen,rptEvtPara }
        STATUS current
        DESCRIPTION
            "E-Line service delay for priority 7."
        ::= { optixTrapsPM 756 }

    -- 1.3.6.1.4.1.2011.2.25.3.40.40.20.757
    pmETHCFMFDVPRI7 NOTIFICATION-TYPE
        OBJECTS{ rptEvtPeriod,rptEvtValue,rptEvtVldty,rptEvtDateTime,rptEvtObjType,rptEvtParaLen,rptEvtPara }
        STATUS current
        DESCRIPTION
            "E-Line service delay variation for priority 7."
        ::= { optixTrapsPM 757 }

    -- 1.3.6.1.4.1.2011.2.25.3.40.40.20.758
    pmETHCFMLANFLTX NOTIFICATION-TYPE
        OBJECTS{ rptEvtPeriod,rptEvtValue,rptEvtVldty,rptEvtDateTime,rptEvtObjType,rptEvtParaLen,rptEvtPara }
        STATUS current
        DESCRIPTION
            "E-LAN service far lost packets"
        ::= { optixTrapsPM 758 }

    -- 1.3.6.1.4.1.2011.2.25.3.40.40.20.759
    pmETHCFMLANFLRRX NOTIFICATION-TYPE
        OBJECTS{ rptEvtPeriod,rptEvtValue,rptEvtVldty,rptEvtDateTime,rptEvtObjType,rptEvtParaLen,rptEvtPara }
        STATUS current
        DESCRIPTION
            "E-LAN service near packet loss ratio"
        ::= { optixTrapsPM 759 }

    -- 1.3.6.1.4.1.2011.2.25.3.40.40.20.760
    pmETHCFMLANFLRX NOTIFICATION-TYPE
        OBJECTS{ rptEvtPeriod,rptEvtValue,rptEvtVldty,rptEvtDateTime,rptEvtObjType,rptEvtParaLen,rptEvtPara }
        STATUS current
        DESCRIPTION
            "E-LAN service near lost packets"
        ::= { optixTrapsPM 760 }

    -- 1.3.6.1.4.1.2011.2.25.3.40.40.20.761
    pmETHCFMLANFD NOTIFICATION-TYPE
        OBJECTS{ rptEvtPeriod,rptEvtValue,rptEvtVldty,rptEvtDateTime,rptEvtObjType,rptEvtParaLen,rptEvtPara }
        STATUS current
        DESCRIPTION
            "E-LAN service delay"
        ::= { optixTrapsPM 761 }

    -- 1.3.6.1.4.1.2011.2.25.3.40.40.20.762
    pmETHCFMLANFDV NOTIFICATION-TYPE
        OBJECTS{ rptEvtPeriod,rptEvtValue,rptEvtVldty,rptEvtDateTime,rptEvtObjType,rptEvtParaLen,rptEvtPara }
        STATUS current
        DESCRIPTION
            "E-LAN service delay variation"
        ::= { optixTrapsPM 762 }

    -- 1.3.6.1.4.1.2011.2.25.3.40.40.20.765
    pmETHCFMLANFPSTX NOTIFICATION-TYPE
        OBJECTS{ rptEvtPeriod,rptEvtValue,rptEvtVldty,rptEvtDateTime,rptEvtObjType,rptEvtParaLen,rptEvtPara }
        STATUS current
        DESCRIPTION
            "E-LAN service far packets transmitted"
        ::= { optixTrapsPM 765 }

    -- 1.3.6.1.4.1.2011.2.25.3.40.40.20.766
    pmETHCFMLANFBPSTX NOTIFICATION-TYPE
        OBJECTS{ rptEvtPeriod,rptEvtValue,rptEvtVldty,rptEvtDateTime,rptEvtObjType,rptEvtParaLen,rptEvtPara }
        STATUS current
        DESCRIPTION
            "E-LAN service far packet Bytes transmitted"
        ::= { optixTrapsPM 766 }

    -- 1.3.6.1.4.1.2011.2.25.3.40.40.20.767
    pmETHCFMLANFPSRX NOTIFICATION-TYPE
        OBJECTS{ rptEvtPeriod,rptEvtValue,rptEvtVldty,rptEvtDateTime,rptEvtObjType,rptEvtParaLen,rptEvtPara }
        STATUS current
        DESCRIPTION
            "E-LAN service near packets transmitted"
        ::= { optixTrapsPM 767 }

    -- 1.3.6.1.4.1.2011.2.25.3.40.40.20.768
    pmETHCFMLANFBPSRX NOTIFICATION-TYPE
        OBJECTS{ rptEvtPeriod,rptEvtValue,rptEvtVldty,rptEvtDateTime,rptEvtObjType,rptEvtParaLen,rptEvtPara }
        STATUS current
        DESCRIPTION
            "E-LAN service near packet Bytes transmitted"
        ::= { optixTrapsPM 768 }

    -- 1.3.6.1.4.1.2011.2.25.3.40.40.20.769
    pmETHCFMFLRTXMAX NOTIFICATION-TYPE
        OBJECTS{ rptEvtPeriod,rptEvtValue,rptEvtVldty,rptEvtDateTime,rptEvtObjType,rptEvtParaLen,rptEvtPara }
        STATUS current
        DESCRIPTION
            "Maximum ratio of E-LAN service far packet loss"
        ::= { optixTrapsPM 769 }

    -- 1.3.6.1.4.1.2011.2.25.3.40.40.20.770
    pmETHCFMFLRTXMIN NOTIFICATION-TYPE
        OBJECTS{ rptEvtPeriod,rptEvtValue,rptEvtVldty,rptEvtDateTime,rptEvtObjType,rptEvtParaLen,rptEvtPara }
        STATUS current
        DESCRIPTION
            "Minimum ratio of E-LAN service far packet loss"
        ::= { optixTrapsPM 770 }

    -- 1.3.6.1.4.1.2011.2.25.3.40.40.20.771
    pmETHCFMFLRTXAVG NOTIFICATION-TYPE
        OBJECTS{ rptEvtPeriod,rptEvtValue,rptEvtVldty,rptEvtDateTime,rptEvtObjType,rptEvtParaLen,rptEvtPara }
        STATUS current
        DESCRIPTION
            "Average ratio of E-LAN service far packet loss"
        ::= { optixTrapsPM 771 }

    -- 1.3.6.1.4.1.2011.2.25.3.40.40.20.772
    pmETHCFMFLRRXMAX NOTIFICATION-TYPE
        OBJECTS{ rptEvtPeriod,rptEvtValue,rptEvtVldty,rptEvtDateTime,rptEvtObjType,rptEvtParaLen,rptEvtPara }
        STATUS current
        DESCRIPTION
            "Maximum ratio of E-LAN service near packet loss"
        ::= { optixTrapsPM 772 }

    -- 1.3.6.1.4.1.2011.2.25.3.40.40.20.773
    pmETHCFMFLRRXMIN NOTIFICATION-TYPE
        OBJECTS{ rptEvtPeriod,rptEvtValue,rptEvtVldty,rptEvtDateTime,rptEvtObjType,rptEvtParaLen,rptEvtPara }
        STATUS current
        DESCRIPTION
            "Minimum ratio of E-LAN service near packet loss"
        ::= { optixTrapsPM 773 }

    -- 1.3.6.1.4.1.2011.2.25.3.40.40.20.774
    pmETHCFMFLRRXAVG NOTIFICATION-TYPE
        OBJECTS{ rptEvtPeriod,rptEvtValue,rptEvtVldty,rptEvtDateTime,rptEvtObjType,rptEvtParaLen,rptEvtPara }
        STATUS current
        DESCRIPTION
            "Average ratio of E-LAN service near packet loss"
        ::= { optixTrapsPM 774 }

    -- 1.3.6.1.4.1.2011.2.25.3.40.40.20.775
    pmETHCFMLANFPSTXMAX NOTIFICATION-TYPE
        OBJECTS{ rptEvtPeriod,rptEvtValue,rptEvtVldty,rptEvtDateTime,rptEvtObjType,rptEvtParaLen,rptEvtPara }
        STATUS current
        DESCRIPTION
            "Maximum ratio of E-LAN service far packets transmitted"
        ::= { optixTrapsPM 775 }

    -- 1.3.6.1.4.1.2011.2.25.3.40.40.20.776
    pmETHCFMLANFPSTXMIN NOTIFICATION-TYPE
        OBJECTS{ rptEvtPeriod,rptEvtValue,rptEvtVldty,rptEvtDateTime,rptEvtObjType,rptEvtParaLen,rptEvtPara }
        STATUS current
        DESCRIPTION
            "Minimum ratio of E-LAN service far packets transmitted"
        ::= { optixTrapsPM 776 }

    -- 1.3.6.1.4.1.2011.2.25.3.40.40.20.777
    pmETHCFMLANFPSTXAVG NOTIFICATION-TYPE
        OBJECTS{ rptEvtPeriod,rptEvtValue,rptEvtVldty,rptEvtDateTime,rptEvtObjType,rptEvtParaLen,rptEvtPara }
        STATUS current
        DESCRIPTION
            "Average ratio of E-LAN service far packets transmitted"
        ::= { optixTrapsPM 777 }

    -- 1.3.6.1.4.1.2011.2.25.3.40.40.20.778
    pmETHCFMLANFBPSTXMAX NOTIFICATION-TYPE
        OBJECTS{ rptEvtPeriod,rptEvtValue,rptEvtVldty,rptEvtDateTime,rptEvtObjType,rptEvtParaLen,rptEvtPara }
        STATUS current
        DESCRIPTION
            "Maximum ratio of E-LAN service far packet Bytes transmitted"
        ::= { optixTrapsPM 778 }

    -- 1.3.6.1.4.1.2011.2.25.3.40.40.20.779
    pmETHCFMLANFBPSTXMIN NOTIFICATION-TYPE
        OBJECTS{ rptEvtPeriod,rptEvtValue,rptEvtVldty,rptEvtDateTime,rptEvtObjType,rptEvtParaLen,rptEvtPara }
        STATUS current
        DESCRIPTION
            "Minimum ratio of E-LAN service far packet Bytes transmitted"
        ::= { optixTrapsPM 779 }

    -- 1.3.6.1.4.1.2011.2.25.3.40.40.20.780
    pmETHCFMLANFBPSTXAVG NOTIFICATION-TYPE
        OBJECTS{ rptEvtPeriod,rptEvtValue,rptEvtVldty,rptEvtDateTime,rptEvtObjType,rptEvtParaLen,rptEvtPara }
        STATUS current
        DESCRIPTION
            "Average ratio of E-LAN service far packet Bytes transmitted"
        ::= { optixTrapsPM 780 }

    -- 1.3.6.1.4.1.2011.2.25.3.40.40.20.781
    pmETHCFMLANFPSRXMAX NOTIFICATION-TYPE
        OBJECTS{ rptEvtPeriod,rptEvtValue,rptEvtVldty,rptEvtDateTime,rptEvtObjType,rptEvtParaLen,rptEvtPara }
        STATUS current
        DESCRIPTION
            "Maximum ratio of E-LAN service near packets transmitted"
        ::= { optixTrapsPM 781 }

    -- 1.3.6.1.4.1.2011.2.25.3.40.40.20.782
    pmETHCFMLANFPSRXMIN NOTIFICATION-TYPE
        OBJECTS{ rptEvtPeriod,rptEvtValue,rptEvtVldty,rptEvtDateTime,rptEvtObjType,rptEvtParaLen,rptEvtPara }
        STATUS current
        DESCRIPTION
            "Minimum ratio of E-LAN service near packets transmitted"
        ::= { optixTrapsPM 782 }

    -- 1.3.6.1.4.1.2011.2.25.3.40.40.20.783
    pmETHCFMLANFPSRXAVG NOTIFICATION-TYPE
        OBJECTS{ rptEvtPeriod,rptEvtValue,rptEvtVldty,rptEvtDateTime,rptEvtObjType,rptEvtParaLen,rptEvtPara }
        STATUS current
        DESCRIPTION
            "Average ratio of E-LAN service near packets transmitted"
        ::= { optixTrapsPM 783 }

    -- 1.3.6.1.4.1.2011.2.25.3.40.40.20.784
    pmETHCFMLANFBPSRXMAX NOTIFICATION-TYPE
        OBJECTS{ rptEvtPeriod,rptEvtValue,rptEvtVldty,rptEvtDateTime,rptEvtObjType,rptEvtParaLen,rptEvtPara }
        STATUS current
        DESCRIPTION
            "Maximum ratio of E-LAN service near packet Bytes transmitted"
        ::= { optixTrapsPM 784 }

    -- 1.3.6.1.4.1.2011.2.25.3.40.40.20.785
    pmETHCFMLANFBPSRXMIN NOTIFICATION-TYPE
        OBJECTS{ rptEvtPeriod,rptEvtValue,rptEvtVldty,rptEvtDateTime,rptEvtObjType,rptEvtParaLen,rptEvtPara }
        STATUS current
        DESCRIPTION
            "Minimum ratio of E-LAN service near packet Bytes transmitted"
        ::= { optixTrapsPM 785 }

    -- 1.3.6.1.4.1.2011.2.25.3.40.40.20.786
    pmETHCFMLANFBPSRXAVG NOTIFICATION-TYPE
        OBJECTS{ rptEvtPeriod,rptEvtValue,rptEvtVldty,rptEvtDateTime,rptEvtObjType,rptEvtParaLen,rptEvtPara }
        STATUS current
        DESCRIPTION
            "Average ratio of E-LAN service near packet Bytes transmitted"
        ::= { optixTrapsPM 786 }

    -- 1.3.6.1.4.1.2011.2.25.3.40.40.20.787
    pmETHCFMLANFDMAX NOTIFICATION-TYPE
        OBJECTS{ rptEvtPeriod,rptEvtValue,rptEvtVldty,rptEvtDateTime,rptEvtObjType,rptEvtParaLen,rptEvtPara }
        STATUS current
        DESCRIPTION
            "Maximum ratio of E-LAN service delay"
        ::= { optixTrapsPM 787 }

    -- 1.3.6.1.4.1.2011.2.25.3.40.40.20.788
    pmETHCFMLANFDMIN NOTIFICATION-TYPE
        OBJECTS{ rptEvtPeriod,rptEvtValue,rptEvtVldty,rptEvtDateTime,rptEvtObjType,rptEvtParaLen,rptEvtPara }
        STATUS current
        DESCRIPTION
            "Minimum ratio of E-LAN service delay"
        ::= { optixTrapsPM 788 }

    -- 1.3.6.1.4.1.2011.2.25.3.40.40.20.789
    pmETHCFMLANFDAVG NOTIFICATION-TYPE
        OBJECTS{ rptEvtPeriod,rptEvtValue,rptEvtVldty,rptEvtDateTime,rptEvtObjType,rptEvtParaLen,rptEvtPara }
        STATUS current
        DESCRIPTION
            "Average ratio of E-LAN service delay"
        ::= { optixTrapsPM 789 }

    -- 1.3.6.1.4.1.2011.2.25.3.40.40.20.790
    pmETHCFMLANFDVMAX NOTIFICATION-TYPE
        OBJECTS{ rptEvtPeriod,rptEvtValue,rptEvtVldty,rptEvtDateTime,rptEvtObjType,rptEvtParaLen,rptEvtPara }
        STATUS current
        DESCRIPTION
            "Maximum ratio of E-LAN service delay variation"
        ::= { optixTrapsPM 790 }

    -- 1.3.6.1.4.1.2011.2.25.3.40.40.20.791
    pmETHCFMLANFDVMIN NOTIFICATION-TYPE
        OBJECTS{ rptEvtPeriod,rptEvtValue,rptEvtVldty,rptEvtDateTime,rptEvtObjType,rptEvtParaLen,rptEvtPara }
        STATUS current
        DESCRIPTION
            "Minimum ratio of E-LAN service delay variation"
        ::= { optixTrapsPM 791 }

    -- 1.3.6.1.4.1.2011.2.25.3.40.40.20.792
    pmETHCFMLANFDVAVG NOTIFICATION-TYPE
        OBJECTS{ rptEvtPeriod,rptEvtValue,rptEvtVldty,rptEvtDateTime,rptEvtObjType,rptEvtParaLen,rptEvtPara }
        STATUS current
        DESCRIPTION
            "Average ratio of E-LAN service delay variation"
        ::= { optixTrapsPM 792 }

    -- 1.3.6.1.4.1.2011.2.25.3.40.40.20.799
    pmETHCFMLANFLRTX NOTIFICATION-TYPE
        OBJECTS{ rptEvtPeriod,rptEvtValue,rptEvtVldty,rptEvtDateTime,rptEvtObjType,rptEvtParaLen,rptEvtPara }
        STATUS current
        DESCRIPTION
            "E-LAN service far packet loss ratio"
        ::= { optixTrapsPM 799 }

    -- 1.3.6.1.4.1.2011.2.25.3.40.40.20.801
    pmMPLSPWFLN NOTIFICATION-TYPE
        OBJECTS{ rptEvtPeriod,rptEvtValue,rptEvtVldty,rptEvtDateTime,rptEvtObjType,rptEvtParaLen,rptEvtPara }
        STATUS current
        DESCRIPTION
            "Number of near-end lost PW packets"
        ::= { optixTrapsPM 801 }

    -- 1.3.6.1.4.1.2011.2.25.3.40.40.20.802
    pmMPLSPWFLRN NOTIFICATION-TYPE
        OBJECTS{ rptEvtPeriod,rptEvtValue,rptEvtVldty,rptEvtDateTime,rptEvtObjType,rptEvtParaLen,rptEvtPara }
        STATUS current
        DESCRIPTION
            "Near-end PW packet loss ratio"
        ::= { optixTrapsPM 802 }

    -- 1.3.6.1.4.1.2011.2.25.3.40.40.20.803
    pmMPLSTUNNELFLN NOTIFICATION-TYPE
        OBJECTS{ rptEvtPeriod,rptEvtValue,rptEvtVldty,rptEvtDateTime,rptEvtObjType,rptEvtParaLen,rptEvtPara }
        STATUS current
        DESCRIPTION
            "Near-end Tunnel lost packets"
        ::= { optixTrapsPM 803 }

    -- 1.3.6.1.4.1.2011.2.25.3.40.40.20.804
    pmMPLSTUNNELFLRN NOTIFICATION-TYPE
        OBJECTS{ rptEvtPeriod,rptEvtValue,rptEvtVldty,rptEvtDateTime,rptEvtObjType,rptEvtParaLen,rptEvtPara }
        STATUS current
        DESCRIPTION
            "Near-end Tunnel packet loss ratio"
        ::= { optixTrapsPM 804 }

    -- 1.3.6.1.4.1.2011.2.25.3.40.40.20.805
    pmETHCFMFLRN NOTIFICATION-TYPE
        OBJECTS{ rptEvtPeriod,rptEvtValue,rptEvtVldty,rptEvtDateTime,rptEvtObjType,rptEvtParaLen,rptEvtPara }
        STATUS current
        DESCRIPTION
            "E-Line service packet loss ratio on the near end."
        ::= { optixTrapsPM 805 }

    -- 1.3.6.1.4.1.2011.2.25.3.40.40.20.806
    pmETHCFMFLN NOTIFICATION-TYPE
        OBJECTS{ rptEvtPeriod,rptEvtValue,rptEvtVldty,rptEvtDateTime,rptEvtObjType,rptEvtParaLen,rptEvtPara }
        STATUS current
        DESCRIPTION
            "Number of E-Line service lost packets on the near end."
        ::= { optixTrapsPM 806 }

    -- 1.3.6.1.4.1.2011.2.25.3.40.40.20.839
    pmPORTRXBWUTILIZATIONMIN NOTIFICATION-TYPE
        OBJECTS{ rptEvtPeriod,rptEvtValue,rptEvtVldty,rptEvtDateTime,rptEvtObjType,rptEvtParaLen,rptEvtPara }
        STATUS current
        DESCRIPTION
            "Minimum bandwidth utilization of the receive port"
        ::= { optixTrapsPM 839 }

    -- 1.3.6.1.4.1.2011.2.25.3.40.40.20.840
    pmPORTRXBWUTILIZATIONAVG NOTIFICATION-TYPE
        OBJECTS{ rptEvtPeriod,rptEvtValue,rptEvtVldty,rptEvtDateTime,rptEvtObjType,rptEvtParaLen,rptEvtPara }
        STATUS current
        DESCRIPTION
            "Average bandwidth utilization of the receive port"
        ::= { optixTrapsPM 840 }

    -- 1.3.6.1.4.1.2011.2.25.3.40.40.20.841
    pmPORTRXBWUTILIZATIONMAX NOTIFICATION-TYPE
        OBJECTS{ rptEvtPeriod,rptEvtValue,rptEvtVldty,rptEvtDateTime,rptEvtObjType,rptEvtParaLen,rptEvtPara }
        STATUS current
        DESCRIPTION
            "Maximum bandwidth utilization of the receive port"
        ::= { optixTrapsPM 841 }

    -- 1.3.6.1.4.1.2011.2.25.3.40.40.20.842
    pmPORTTXBWUTILIZATIONMIN NOTIFICATION-TYPE
        OBJECTS{ rptEvtPeriod,rptEvtValue,rptEvtVldty,rptEvtDateTime,rptEvtObjType,rptEvtParaLen,rptEvtPara }
        STATUS current
        DESCRIPTION
            "Minimum bandwidth utilization of the transmit port"
        ::= { optixTrapsPM 842 }

    -- 1.3.6.1.4.1.2011.2.25.3.40.40.20.843
    pmPORTTXBWUTILIZATIONAVG NOTIFICATION-TYPE
        OBJECTS{ rptEvtPeriod,rptEvtValue,rptEvtVldty,rptEvtDateTime,rptEvtObjType,rptEvtParaLen,rptEvtPara }
        STATUS current
        DESCRIPTION
            "Average bandwidth utilization of the transmit port"
        ::= { optixTrapsPM 843 }

    -- 1.3.6.1.4.1.2011.2.25.3.40.40.20.844
    pmPORTTXBWUTILIZATIONMAX NOTIFICATION-TYPE
        OBJECTS{ rptEvtPeriod,rptEvtValue,rptEvtVldty,rptEvtDateTime,rptEvtObjType,rptEvtParaLen,rptEvtPara }
        STATUS current
        DESCRIPTION
            "Maximum bandwidth utilization of the transmit port"
        ::= { optixTrapsPM 844 }

    -- 1.3.6.1.4.1.2011.2.25.3.40.40.20.859
    pmTNLBWUTILISATIONMIN NOTIFICATION-TYPE
        OBJECTS{ rptEvtPeriod,rptEvtValue,rptEvtVldty,rptEvtDateTime,rptEvtObjType,rptEvtParaLen,rptEvtPara }
        STATUS current
        DESCRIPTION
            "Minimum bandwidth utilization of the tunnel, that is, number of actually transmitted bytes x 8/time unit/configured or actual bandwidth."
        ::= { optixTrapsPM 859 }

    -- 1.3.6.1.4.1.2011.2.25.3.40.40.20.860
    pmTNLBWUTILISATIONAVG NOTIFICATION-TYPE
        OBJECTS{ rptEvtPeriod,rptEvtValue,rptEvtVldty,rptEvtDateTime,rptEvtObjType,rptEvtParaLen,rptEvtPara }
        STATUS current
        DESCRIPTION
            "Average bandwidth utilization of the tunnel, that is, number of actually transmitted bytes x 8/time unit/configured or actual bandwidth."
        ::= { optixTrapsPM 860 }

    -- 1.3.6.1.4.1.2011.2.25.3.40.40.20.861
    pmTNLBWUTILISATIONMAX NOTIFICATION-TYPE
        OBJECTS{ rptEvtPeriod,rptEvtValue,rptEvtVldty,rptEvtDateTime,rptEvtObjType,rptEvtParaLen,rptEvtPara }
        STATUS current
        DESCRIPTION
            "Maximum bandwidth utilization of the tunnel, that is, number of actually transmitted bytes x 8/time unit/configured or actual bandwidth."
        ::= { optixTrapsPM 861 }

    -- 1.3.6.1.4.1.2011.2.25.3.40.40.20.862
    pmTNLREVERSEBWUTILISATIONMIN NOTIFICATION-TYPE
        OBJECTS{ rptEvtPeriod,rptEvtValue,rptEvtVldty,rptEvtDateTime,rptEvtObjType,rptEvtParaLen,rptEvtPara }
        STATUS current
        DESCRIPTION
            "Minimum bandwidth utilization on the reverse direction of specified bidirectional transit tunnel"
        ::= { optixTrapsPM 862 }

    -- 1.3.6.1.4.1.2011.2.25.3.40.40.20.863
    pmTNLREVERSEBWUTILISATIONAVG NOTIFICATION-TYPE
        OBJECTS{ rptEvtPeriod,rptEvtValue,rptEvtVldty,rptEvtDateTime,rptEvtObjType,rptEvtParaLen,rptEvtPara }
        STATUS current
        DESCRIPTION
            "Average bandwidth utilization on the reverse direction of specified bidirectional transit tunnel"
        ::= { optixTrapsPM 863 }

    -- 1.3.6.1.4.1.2011.2.25.3.40.40.20.864
    pmTNLREVERSEBWUTILISATIONMAX NOTIFICATION-TYPE
        OBJECTS{ rptEvtPeriod,rptEvtValue,rptEvtVldty,rptEvtDateTime,rptEvtObjType,rptEvtParaLen,rptEvtPara }
        STATUS current
        DESCRIPTION
            "Maximum bandwidth utilization on the reverse direction of specified bidirectional transit tunnel"
        ::= { optixTrapsPM 864 }

    -- 1.3.6.1.4.1.2011.2.25.3.40.40.20.865
    pmPWBANDWIDTHUTILISATIONMIN NOTIFICATION-TYPE
        OBJECTS{ rptEvtPeriod,rptEvtValue,rptEvtVldty,rptEvtDateTime,rptEvtObjType,rptEvtParaLen,rptEvtPara }
        STATUS current
        DESCRIPTION
            "Minimum bandwidth utilization of the specified PW, that is, number of actually transmitted bytes x 8/time unit/configured or actual bandwidth."
        ::= { optixTrapsPM 865 }

    -- 1.3.6.1.4.1.2011.2.25.3.40.40.20.866
    pmPWBANDWIDTHUTILISATIONAVG NOTIFICATION-TYPE
        OBJECTS{ rptEvtPeriod,rptEvtValue,rptEvtVldty,rptEvtDateTime,rptEvtObjType,rptEvtParaLen,rptEvtPara }
        STATUS current
        DESCRIPTION
            "Average bandwidth utilization of the specified PW, that is, number of actually transmitted bytes x 8/time unit/configured or actual bandwidth."
        ::= { optixTrapsPM 866 }

    -- 1.3.6.1.4.1.2011.2.25.3.40.40.20.867
    pmPWBANDWIDTHUTILISATIONMAX NOTIFICATION-TYPE
        OBJECTS{ rptEvtPeriod,rptEvtValue,rptEvtVldty,rptEvtDateTime,rptEvtObjType,rptEvtParaLen,rptEvtPara }
        STATUS current
        DESCRIPTION
            "Maximum bandwidth utilization of the specified PW, that is, number of actually transmitted bytes x 8/time unit/configured or actual bandwidth."
        ::= { optixTrapsPM 867 }

    -- 1.3.6.1.4.1.2011.2.25.3.40.40.20.868
    pmTXDROPPKTS NOTIFICATION-TYPE
        OBJECTS{ rptEvtPeriod,rptEvtValue,rptEvtVldty,rptEvtDateTime,rptEvtObjType,rptEvtParaLen,rptEvtPara }
        STATUS current
        DESCRIPTION
            "Number of discarded packets in the egress direction"
        ::= { optixTrapsPM 868 }

    -- 1.3.6.1.4.1.2011.2.25.3.40.40.20.869
    pmRXDROPPKTS NOTIFICATION-TYPE
        OBJECTS{ rptEvtPeriod,rptEvtValue,rptEvtVldty,rptEvtDateTime,rptEvtObjType,rptEvtParaLen,rptEvtPara }
        STATUS current
        DESCRIPTION
            "Number of discarded packets in the ingress direction."
        ::= { optixTrapsPM 869 }

    -- 1.3.6.1.4.1.2011.2.25.3.40.40.20.894
    pmTXBPSMIN NOTIFICATION-TYPE
        OBJECTS{ rptEvtPeriod,rptEvtValue,rptEvtVldty,rptEvtDateTime,rptEvtObjType,rptEvtParaLen,rptEvtPara }
        STATUS current
        DESCRIPTION
            "Minimum bits per second of the Ethernet port in the transmit direction,that is, number of actually transmitted bytes x 8/time unit."
        ::= { optixTrapsPM 894 }

    -- 1.3.6.1.4.1.2011.2.25.3.40.40.20.895
    pmTXBPSAVG NOTIFICATION-TYPE
        OBJECTS{ rptEvtPeriod,rptEvtValue,rptEvtVldty,rptEvtDateTime,rptEvtObjType,rptEvtParaLen,rptEvtPara }
        STATUS current
        DESCRIPTION
            "Average bits per second of the Ethernet port in the transmit direction,that is, number of actually transmitted bytes x 8/time unit"
        ::= { optixTrapsPM 895 }

    -- 1.3.6.1.4.1.2011.2.25.3.40.40.20.896
    pmTXBPSMAX NOTIFICATION-TYPE
        OBJECTS{ rptEvtPeriod,rptEvtValue,rptEvtVldty,rptEvtDateTime,rptEvtObjType,rptEvtParaLen,rptEvtPara }
        STATUS current
        DESCRIPTION
            "Maximum bits per second of the Ethernet port in the transmit direction,that is, number of actually transmitted bytes x 8/time unit"
        ::= { optixTrapsPM 896 }

    -- 1.3.6.1.4.1.2011.2.25.3.40.40.20.897
    pmRXBPSMIN NOTIFICATION-TYPE
        OBJECTS{ rptEvtPeriod,rptEvtValue,rptEvtVldty,rptEvtDateTime,rptEvtObjType,rptEvtParaLen,rptEvtPara }
        STATUS current
        DESCRIPTION
            "Minimum bits per second of the Ethernet port in the receive direction, that is, number of actually received bytes x 8/time unit."
        ::= { optixTrapsPM 897 }

    -- 1.3.6.1.4.1.2011.2.25.3.40.40.20.898
    pmRXBPSAVG NOTIFICATION-TYPE
        OBJECTS{ rptEvtPeriod,rptEvtValue,rptEvtVldty,rptEvtDateTime,rptEvtObjType,rptEvtParaLen,rptEvtPara }
        STATUS current
        DESCRIPTION
            "Average bits per second of the Ethernet port in the receive direction, that is, number of actually received bytes x 8/time unit."
        ::= { optixTrapsPM 898 }

    -- 1.3.6.1.4.1.2011.2.25.3.40.40.20.899
    pmRXBPSMAX NOTIFICATION-TYPE
        OBJECTS{ rptEvtPeriod,rptEvtValue,rptEvtVldty,rptEvtDateTime,rptEvtObjType,rptEvtParaLen,rptEvtPara }
        STATUS current
        DESCRIPTION
            "Maximum bits per second of the Ethernet port in the receive direction, that is, number of actually received bytes x 8/time unit."
        ::= { optixTrapsPM 899 }

    -- 1.3.6.1.4.1.2011.2.25.3.40.40.20.941
    pmECMPRSRATIO NOTIFICATION-TYPE
        OBJECTS{ rptEvtPeriod,rptEvtValue,rptEvtVldty,rptEvtDateTime,rptEvtObjType,rptEvtParaLen,rptEvtPara }
        STATUS current
        DESCRIPTION
            "Compression ratio of enhanced compression."
        ::= { optixTrapsPM 941 }

    -- 1.3.6.1.4.1.2011.2.25.3.40.40.20.956
    pmTXHSTRAFFBWRATIO NOTIFICATION-TYPE
        OBJECTS{ rptEvtPeriod,rptEvtValue,rptEvtVldty,rptEvtDateTime,rptEvtObjType,rptEvtParaLen,rptEvtPara }
        STATUS current
        DESCRIPTION
            "Ratio of traffic to bandwidth for high-priority services in the transmit direction"
        ::= { optixTrapsPM 956 }

    -- 1.3.6.1.4.1.2011.2.25.3.40.40.20.957
    pmRXBRDCASTRATIO NOTIFICATION-TYPE
        OBJECTS{ rptEvtPeriod,rptEvtValue,rptEvtVldty,rptEvtDateTime,rptEvtObjType,rptEvtParaLen,rptEvtPara }
        STATUS current
        DESCRIPTION
            "Ratio of broadcast and multicast packets to all packets in the receive direction."
        ::= { optixTrapsPM 957 }

    -- 1.3.6.1.4.1.2011.2.25.3.40.40.20.958
    pmTXBRDCASTRATIO NOTIFICATION-TYPE
        OBJECTS{ rptEvtPeriod,rptEvtValue,rptEvtVldty,rptEvtDateTime,rptEvtObjType,rptEvtParaLen,rptEvtPara }
        STATUS current
        DESCRIPTION
            "Ratio of broadcast and multicast packets to all packets in the transmit direction."
        ::= { optixTrapsPM 958 }

    -- 1.3.6.1.4.1.2011.2.25.3.40.40.20.505
    pmPortRxBytesAvailability NOTIFICATION-TYPE
        OBJECTS{ rptEvtPeriod,rptEvtValue,rptEvtVldty,rptEvtDateTime,rptEvtObjType,rptEvtParaLen,rptEvtPara }
        STATUS current
        DESCRIPTION
            "Port bandwidth availability"
        ::= { optixTrapsPM 505 }

    -- 1.3.6.1.4.1.2011.2.25.3.40.40.20.508
    pmPwBandwidthUtilisation NOTIFICATION-TYPE
        OBJECTS{ rptEvtPeriod,rptEvtValue,rptEvtVldty,rptEvtDateTime,rptEvtObjType,rptEvtParaLen,rptEvtPara }
        STATUS current
        DESCRIPTION
            "PW bandwidth utilization"
        ::= { optixTrapsPM 508 }

    -- 1.3.6.1.4.1.2011.2.25.3.40.40.20.509
    pmPwAvailability NOTIFICATION-TYPE
        OBJECTS{ rptEvtPeriod,rptEvtValue,rptEvtVldty,rptEvtDateTime,rptEvtObjType,rptEvtParaLen,rptEvtPara }
        STATUS current
        DESCRIPTION
            "PW availability"
        ::= { optixTrapsPM 509 }

    -- 1.3.6.1.4.1.2011.2.25.3.40.40.20.512
    pmQosPriBandwidthUtilisation NOTIFICATION-TYPE
        OBJECTS{ rptEvtPeriod,rptEvtValue,rptEvtVldty,rptEvtDateTime,rptEvtObjType,rptEvtParaLen,rptEvtPara }
        STATUS current
        DESCRIPTION
            "Bandwidth utilization of different service priorities"
        ::= { optixTrapsPM 512 }

    -- 1.3.6.1.4.1.2011.2.25.3.40.40.20.526
    pmAtmBoardDropcells NOTIFICATION-TYPE
        OBJECTS{ rptEvtPeriod,rptEvtValue,rptEvtVldty,rptEvtDateTime,rptEvtObjType,rptEvtParaLen,rptEvtPara }
        STATUS current
        DESCRIPTION
            "ATM cells discarded"
        ::= { optixTrapsPM 526 }

    -- 1.3.6.1.4.1.2011.2.25.3.40.40.20.533
    pmCesRxBytes NOTIFICATION-TYPE
        OBJECTS{ rptEvtPeriod,rptEvtValue,rptEvtVldty,rptEvtDateTime,rptEvtObjType,rptEvtParaLen,rptEvtPara }
        STATUS current
        DESCRIPTION
            "received bytes"
        ::= { optixTrapsPM 533 }

    -- 1.3.6.1.4.1.2011.2.25.3.40.40.20.560
    pmEthbadpkts NOTIFICATION-TYPE
        OBJECTS{ rptEvtPeriod,rptEvtValue,rptEvtVldty,rptEvtDateTime,rptEvtObjType,rptEvtParaLen,rptEvtPara }
        STATUS current
        DESCRIPTION
            "bad packets"
        ::= { optixTrapsPM 560 }

    -- 1.3.6.1.4.1.2011.2.25.3.40.40.20.569
    pmAtmpwBwUtilization NOTIFICATION-TYPE
        OBJECTS{ rptEvtPeriod,rptEvtValue,rptEvtVldty,rptEvtDateTime,rptEvtObjType,rptEvtParaLen,rptEvtPara }
        STATUS current
        DESCRIPTION
            "ATM PW bandwidth utilization"
        ::= { optixTrapsPM 569 }

    -- 1.3.6.1.4.1.2011.2.25.3.40.40.20.577
    pmTnlBwUtilisation NOTIFICATION-TYPE
        OBJECTS{ rptEvtPeriod,rptEvtValue,rptEvtVldty,rptEvtDateTime,rptEvtObjType,rptEvtParaLen,rptEvtPara }
        STATUS current
        DESCRIPTION
            "tunnel bandwidth utilization"
        ::= { optixTrapsPM 577 }

    -- 1.3.6.1.4.1.2011.2.25.3.40.40.20.600
    pmTnlReverseBwUtilisation NOTIFICATION-TYPE
        OBJECTS{ rptEvtPeriod,rptEvtValue,rptEvtVldty,rptEvtDateTime,rptEvtObjType,rptEvtParaLen,rptEvtPara }
        STATUS current
        DESCRIPTION
            "Bandwidth utilisation on reverse direction of  tunnel"
        ::= { optixTrapsPM 600 }

    -- 1.3.6.1.4.1.2011.2.25.3.40.40.20.656
    pmFlowTxUtilization NOTIFICATION-TYPE
        OBJECTS{ rptEvtPeriod,rptEvtValue,rptEvtVldty,rptEvtDateTime,rptEvtObjType,rptEvtParaLen,rptEvtPara }
        STATUS current
        DESCRIPTION
            "transmitted flow classifier bandwidth utilization"
        ::= { optixTrapsPM 656 }

    -- 1.3.6.1.4.1.2011.2.25.3.40.40.20.660
    pmVunigroupRcvpkts NOTIFICATION-TYPE
        OBJECTS{ rptEvtPeriod,rptEvtValue,rptEvtVldty,rptEvtDateTime,rptEvtObjType,rptEvtParaLen,rptEvtPara }
        STATUS current
        DESCRIPTION
            "Packets received matching VUNI GROUP"
        ::= { optixTrapsPM 660 }

    -- 1.3.6.1.4.1.2011.2.25.3.40.40.20.661
    pmVunigroupRcvbytes NOTIFICATION-TYPE
        OBJECTS{ rptEvtPeriod,rptEvtValue,rptEvtVldty,rptEvtDateTime,rptEvtObjType,rptEvtParaLen,rptEvtPara }
        STATUS current
        DESCRIPTION
            "Bytes received  matching VUNI GROUP"
        ::= { optixTrapsPM 661 }

    -- 1.3.6.1.4.1.2011.2.25.3.40.40.20.800
    pmVuniRxUtilization NOTIFICATION-TYPE
        OBJECTS{ rptEvtPeriod,rptEvtValue,rptEvtVldty,rptEvtDateTime,rptEvtObjType,rptEvtParaLen,rptEvtPara }
        STATUS current
        DESCRIPTION
            "Bandwidth utilization in the VUNI receive direction"
        ::= { optixTrapsPM 800 }

    -- 1.3.6.1.4.1.2011.2.25.3.40.40.20.807
    pmEthCfmFlrPri1N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 1 on the near end"
        ::= { optixTrapsPM 807 }

    -- 1.3.6.1.4.1.2011.2.25.3.40.40.20.808
    pmEthCfmFlrPri0N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 0 on the near end"
        ::= { optixTrapsPM 808 }

    -- 1.3.6.1.4.1.2011.2.25.3.40.40.20.809
    pmEthCfmFlrPri2N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 2 on the near end"
        ::= { optixTrapsPM 809 }

    -- 1.3.6.1.4.1.2011.2.25.3.40.40.20.810
    pmEthCfmFlrPri3N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 3 on the near end"
        ::= { optixTrapsPM 810 }

    -- 1.3.6.1.4.1.2011.2.25.3.40.40.20.811
    pmEthCfmFlrPri4N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 4 on the near end"
        ::= { optixTrapsPM 811 }

    -- 1.3.6.1.4.1.2011.2.25.3.40.40.20.812
    pmEthCfmFlrPri5N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 5 on the near end"
        ::= { optixTrapsPM 812 }

    -- 1.3.6.1.4.1.2011.2.25.3.40.40.20.813
    pmEthCfmFlrPri6N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 6 on the near end"
        ::= { optixTrapsPM 813 }

    -- 1.3.6.1.4.1.2011.2.25.3.40.40.20.814
    pmEthCfmFlrPri7N NOTIFICATION-TYPE
        OBJECTS{ rptEvtPeriod,rptEvtValue,rptEvtVldty,rptEvtDateTime,rptEvtObjType,rptEvtParaLen,rptEvtPara }
        STATUS current
        DESCRIPTION
            "Packet loss ratio of the E-Line service with priority 7 on the near end"
        ::= { optixTrapsPM 814 }

    -- 1.3.6.1.4.1.2011.2.25.3.40.40.20.815
    pmEthCfmFlPri0N NOTIFICATION-TYPE
        OBJECTS{ rptEvtPeriod,rptEvtValue,rptEvtVldty,rptEvtDateTime,rptEvtObjType,rptEvtParaLen,rptEvtPara }
        STATUS current
        DESCRIPTION
            "Number of E-Line service lost packets with priority 0 on the near end"
        ::= { optixTrapsPM 815 }

    -- 1.3.6.1.4.1.2011.2.25.3.40.40.20.816
    pmEthCfmFlPri1N NOTIFICATION-TYPE
        OBJECTS{ rptEvtPeriod,rptEvtValue,rptEvtVldty,rptEvtDateTime,rptEvtObjType,rptEvtParaLen,rptEvtPara }
        STATUS current
        DESCRIPTION
            "Number of E-Line service lost packets with priority 1 on the near end"
        ::= { optixTrapsPM 816 }

    -- 1.3.6.1.4.1.2011.2.25.3.40.40.20.817
    pmEthCfmFlPri2N NOTIFICATION-TYPE
        OBJECTS{ rptEvtPeriod,rptEvtValue,rptEvtVldty,rptEvtDateTime,rptEvtObjType,rptEvtParaLen,rptEvtPara }
        STATUS current
        DESCRIPTION
            "Number of E-Line service lost packets with priority 2 on the near end"
        ::= { optixTrapsPM 817 }

    -- 1.3.6.1.4.1.2011.2.25.3.40.40.20.818
    pmEthCfmFlPri3N NOTIFICATION-TYPE
        OBJECTS{ rptEvtPeriod,rptEvtValue,rptEvtVldty,rptEvtDateTime,rptEvtObjType,rptEvtParaLen,rptEvtPara }
        STATUS current
        DESCRIPTION
            "Number of E-Line service lost packets with priority 3 on the near end"
        ::= { optixTrapsPM 818 }

    -- 1.3.6.1.4.1.2011.2.25.3.40.40.20.819
    pmEthCfmFlPri4N NOTIFICATION-TYPE
        OBJECTS{ rptEvtPeriod,rptEvtValue,rptEvtVldty,rptEvtDateTime,rptEvtObjType,rptEvtParaLen,rptEvtPara }
        STATUS current
        DESCRIPTION
            "Number of E-Line service lost packets with priority 4 on the near end"
        ::= { optixTrapsPM 819 }

    -- 1.3.6.1.4.1.2011.2.25.3.40.40.20.820
    pmEthCfmFlPri5N NOTIFICATION-TYPE
        OBJECTS{ rptEvtPeriod,rptEvtValue,rptEvtVldty,rptEvtDateTime,rptEvtObjType,rptEvtParaLen,rptEvtPara }
        STATUS current
        DESCRIPTION
            "Number of E-Line service lost packets with priority 5 on the near end"
        ::= { optixTrapsPM 820 }

    -- 1.3.6.1.4.1.2011.2.25.3.40.40.20.821
    pmEthCfmFlPri6N NOTIFICATION-TYPE
        OBJECTS{ rptEvtPeriod,rptEvtValue,rptEvtVldty,rptEvtDateTime,rptEvtObjType,rptEvtParaLen,rptEvtPara }
        STATUS current
        DESCRIPTION
            "Number of E-Line service lost packets with priority 6 on the near end"
        ::= { optixTrapsPM 821 }

    -- 1.3.6.1.4.1.2011.2.25.3.40.40.20.822
    pmEthCfmFlPri7N NOTIFICATION-TYPE
        OBJECTS{ rptEvtPeriod,rptEvtValue,rptEvtVldty,rptEvtDateTime,rptEvtObjType,rptEvtParaLen,rptEvtPara }
        STATUS current
        DESCRIPTION
            "Number of E-Line service lost packets with priority 7 on the near end"
        ::= { optixTrapsPM 822 }

    -- 1.3.6.1.4.1.2011.2.25.3.40.40.20.906
    pmCesTxPkts NOTIFICATION-TYPE
        OBJECTS{ rptEvtPeriod,rptEvtValue,rptEvtVldty,rptEvtDateTime,rptEvtObjType,rptEvtParaLen,rptEvtPara }
        STATUS current
        DESCRIPTION
            "Number of transmitted packets"
        ::= { optixTrapsPM 906 }

    -- 1.3.6.1.4.1.2011.2.25.3.40.40.20.954
    pmVlanRxUtilization NOTIFICATION-TYPE
        OBJECTS{ rptEvtPeriod,rptEvtValue,rptEvtVldty,rptEvtDateTime,rptEvtObjType,rptEvtParaLen,rptEvtPara }
        STATUS current
        DESCRIPTION
            "Bandwidth utilization in the VUNI VLAN receive direction."
        ::= { optixTrapsPM 954 }

    -- 1.3.6.1.4.1.2011.2.25.3.40.40.20.955
    pmVlanTxUtilization NOTIFICATION-TYPE
        OBJECTS{ rptEvtPeriod,rptEvtValue,rptEvtVldty,rptEvtDateTime,rptEvtObjType,rptEvtParaLen,rptEvtPara }
        STATUS current
        DESCRIPTION
            "Bandwidth utilization in the VUNI VLAN transmit direction."
        ::= { optixTrapsPM 955 }

    -- 1.3.6.1.4.1.2011.2.25.3.40.40.20.966
    pmRxMaxBwUtilizationCapacity NOTIFICATION-TYPE
        OBJECTS{ rptEvtPeriod,rptEvtValue,rptEvtVldty,rptEvtDateTime,rptEvtObjType,rptEvtParaLen,rptEvtPara }
        STATUS current
        DESCRIPTION
            "Total air interface bandwidth mapping to the maximum bandwidth utilization of the receive port."
        ::= { optixTrapsPM 966 }

    -- 1.3.6.1.4.1.2011.2.25.3.40.40.20.967
    pmTxMaxBwUtilizationCapacity NOTIFICATION-TYPE
        OBJECTS{ rptEvtPeriod,rptEvtValue,rptEvtVldty,rptEvtDateTime,rptEvtObjType,rptEvtParaLen,rptEvtPara }
        STATUS current
        DESCRIPTION
            "Total air interface bandwidth mapping to the maximum bandwidth utilization of the transmit  port."
        ::= { optixTrapsPM 967 }

    -- 1.3.6.1.4.1.2011.2.25.3.40.40.200
    optixRtnPmTrapConformance OBJECT IDENTIFIER ::= { optixGlobalTrap 200 }

    -- 1.3.6.1.4.1.2011.2.25.3.40.40.200.1
    optixRtnPmTrapGroups OBJECT IDENTIFIER ::= { optixRtnPmTrapConformance 1 }

    -- 1.3.6.1.4.1.2011.2.25.3.40.40.200.1.1
    optixRtnPmTrapObjectGroup OBJECT-GROUP
        OBJECTS { pmRXPKT64,pmRXPKT65,pmRXPKT128,pmRXPKT256,pmRXPKT512,pmRXPKT1024,pmTXPKT64,pmTXPKT65,pmTXPKT128,pmTXPKT256,pmTXPKT512,pmTXPKT1024,pmRXUNICAST,pmRXMULCAST,pmRXBRDCAST,pmTXUNICAST,pmTXMULCAST,pmTXBRDCAST,pmRXPAUSE,pmTXPAUSE,pmETHDROP,pmETHUNDER,pmETHOVER,pmETHFRG,pmETHJAB,pmRXBGOOD,pmTXBGOOD,pmRXBBAD,pmTXBBAD,pmETHCOL,pmETHALI,pmETHFCS,pmETHUNICOL,pmETHMULCOL,pmETHCARERR,pmETHLATECOL,pmETHLATECOL,pmTXDEFFRM,pmRXPKT1519,pmTXPKT1519,pmPKT64,pmPKT65,pmPKT128,pmPKT256,pmPKT512,pmPKT1024,pmPKT1519,pmRXGOODFULLFRAMESPEED,pmTXGOODFULLFRAMESPEED,pmRXFULLBGOOD,pmTXFULLBGOOD,pmRXCTLPKTS,pmTXCTLPKTS,pmTXETHDROP,pmTXETHOVER,pmETHUTILIZ,pmTXPKTS,pmTXOCTETS,pmRXOCTETS,pmRXPKTS,pmETHCRCALI,pmVCGRXOCTETS,pmVCGTXOCTETS,pmVCGRXPACKETS,pmVCGTXPACKETS,pmVCGRXGOODPACKETS,pmVCGTXGOODPACKETS,pmVCGRXSPEED,pmVCGTXSPEED,pmCESLOSPKTS,pmCESMISORDERPKTS,pmCESSTRAYPKTS,pmCESMALPKTS,pmCESJTRUDR,pmCESJTROVR,pmVUNIRCVPKTS,pmVUNIRCVBYTES,pmVUNISNDPKTS,pmVUNISNDBYTES,pmVLANSNDPKTS,pmVLANSNDBYTES,pmTUNNELRCVPKTS,
pmTUNNELRCVBYTES,pmTUNNELSNDPKTS,pmTUNNELSNDBYTES,pmPWRCVPKTS,pmPWRCVBYTES,pmPWSNDPKTS,pmPWSNDBYTES,pmETHCFMFLR,pmETHCFMFL,pmETHCFMFD,pmETHCFMFDV,pmATMPWSNDCELLS,pmATMPWRCVCELLS,pmATMPWUNKNOWNCELLS,pmATMUNI1INCELLS,pmATMUNI1OUTCELLS,pmATMCORRECTED_HCSERR,pmATMUNCORRECTEDHCSERR,pmATMRCVCELLS,pmATMRCVIDLECELLS,pmATMSNDCELLS,pmPWDROPPKTS,pmPWDROPBYTES,pmQOSPRIDROPPKTS,pmQOSPRIDROPBYTES,pmATMIFINRATE_MAX,pmATMIFINRATE_MIN,pmQOSSTRMMATCHPKTS,pmQOSSTRMMATCHBYTES,pmQOSCARGRNPKTS,pmQOSCARGRNBYTES,pmQOSCARYLWPKTS,pmQOSCARYLWBYTES,pmQOSCARREDPKTS,pmQOSCARREDBYTES,pmATMIFINRATE_AVG,pmATMIFOUTRATE_MAX,pmATMIFOUTRATE_MIN,pmATMIFOUTRATE_AVG,pmATMCELLAVAILABILITY,pmATMUNI1INRATEMAX,pmATMUNI1INRATEMIN,pmATMUNI1INRATEAVG,pmATMUNI1OUTRATEMAX,pmATMUNI1OUTRATEMIN,pmATMUNI1OUTRATEAVG,pmCESRXPKTS,pmPORTRXBWUTILIZATION,pmPORTTXBWUTILIZATION,pmATMUNI2INCELLS,pmATMUNI2OUTCELLS,pmATMUNI2INRATEMAX,pmATMUNI2INRATEMIN,pmATMUNI2INRATEAVG,pmATMUNI2OUTRATEMAX,pmATMUNI2OUTRATEMIN,pmATMUNI2OUTRATEAVG,pmTUNNELREVERSESNDPKTS,
pmTUNNELREVERSESNDBYTES,pmTUNNELREVERSERCVPKTS,pmTUNNELREVERSERCVBYTES,pmQOSPORTSTRMRCVMATCHPKTS,pmQOSPORTSTRMRCVMATCHBYTES,pmQOSPORTSTRMSNDMATCHPKTS,pmQOSPORTSTRMSNDMATCHBYTES,pmQOSPORTCARMarkedRedPKTS,pmQOSPORTCARMarkedYellowPKTS,pmQOSPORTCARMarkedGreenPKTS,pmDSCVLANPRIPKTS,pmDSCVLANPRIBYTES,pmDSSVLANPRIPKTS,pmDSSVLANPRIBYTES,pmDSDSCPPKTS,pmDSDSCPBYTES,pmVLANRCVPKTS,pmVLANRCVBYTES,pmPORTPRISNDPKTS,pmPORTPRISNDBYTES,pmPORTSTRMSHAPINGDROPPKTS,pmPORTSTRMSHAPINGDROPRATIO,pmQOSPORTCARMarkedRedRATIO,pmQOSPORTQUEUEDROPRATIO,pmRXBPS,pmTXBPS,pmRXPPS,pmTXPPS,pmFLOWRXUTILIZATION,pmVUNITXUTILIZATION,pmVUNIGROUPSNDPKTS,pmVUNIGROUPSNDBYTES,pmVGROUPTXUTILIZATION,pmVUNIQUEUESNDDROPPKTS,pmVUNIQUEUESNDDROPBYTES,pmVUNIQUEUESNDDROPRATIO,pmVUNIGROUPSNDDROPPKTS,pmVUNIGROUPSNDDROPBYTES,pmVUNIGROUPSNDDROPRATIO,pmPWQUEUESNDDROPPKTS,pmPWQUEUESNDDROPBYTES,pmPWQUEUESNDDROPRATIO,pmTNLSNDDROPPKTS,pmTNLSNDDROPBYTES,pmTNLSNDDROPRATIO,pmQOSCARREDRATIO,pmTNLREVERSESNDDROPPKTS,pmTNLREVERSESNDDROPBYTES,pmTNLREVERSESNDDROPRATIO,
pmVUNISNDDROPPKTS,pmVUNISNDDROPBYTES,pmVUNISNDDROPRATIO,pmTUNNELREVERSETXBPS,pmTUNNELREVERSETXPPS,pmTUNNELTXBPS,pmTUNNELTXPPS,pmPWTXBPS,pmPWTXPPS,pmVUNIRXBPS,pmVUNITXBPS,pmVUNIRXPPS,pmVUNITXPPS,pmVLANTXBPS,pmVLANTXPPS,pmQOSPORTSTRMRXBPS,pmMPLSTUNNEL1WFD,pmMPLSTUNNEL1WFDV,pmMPLSPW1WFD,pmMPLSPW1WFDV,  pmMPLSTUNNELFLR,pmMPLSTUNNELFL,pmMPLSTUNNELFD,pmMPLSTUNNELFDV,pmRXDROPRATIO,pmTXDROPRATIO,pmPPPTXPKTS,pmPPPTXBYTES,pmPPPRXPKTS,pmPPPRXBYTES,pmPPPRXFCSPKTS,pmPPPTXLOSPKTS,pmPPPRXLOSPKTS,pmPPPRXBWUTILIZATION,pmPPPTXBWUTILIZATION,pmMPTXPKTS,pmMPTXBYTES,pmMPRXPKTS,pmMPRXBYTES,pmMPRXERRPKTS,pmMPTXTOTALPKTS,pmMPRXTOTALPKTS,pmMPRXBWUTILIZATION,pmMPTXBWUTILIZATION,pmMPLSPWFLR,pmMPLSPWFL,pmMPLSPWFD,pmMPLSPWFDV,pmETHRXTHROUGHPUTMAX,pmETHRXTHROUGHPUTMIN,pmETHRXTHROUGHPUTAVG,pmTUNNELREVERSERXBPS,pmTUNNELREVERSERXPPS,pmTUNNELRXBPS,pmTUNNELRXPPS,pmPWRXBPS,pmPWRXPPS,pmVLANRXBPS,pmVLANRXPPS,pmQOSPORTSTRMRXPPS,pmQOSPORTSTRMTXPPS,pmPORTPRITXBPS,pmPORTPRITXPPS,pmPWQUEUETXBPS,pmPWQUEUETXPPS,pmETHCFMFLRPRI0,pmETHCFMFLPRI0,
pmETHCFMFDPRI0,pmETHCFMFDVPRI0,pmETHCFMFLRPRI1,pmETHCFMFLPRI1,pmETHCFMFDPRI1,pmETHCFMFDVPRI1,pmETHCFMFLRPRI2,pmETHCFMFLPRI2,pmETHCFMFDPRI2,pmETHCFMFDVPRI2,pmETHCFMFLRPRI3,pmETHCFMFLPRI3,pmETHCFMFDPRI3,pmETHCFMFDVPRI3,pmETHCFMFLRPRI4,pmETHCFMFLPRI4,pmETHCFMFDPRI4,pmETHCFMFDVPRI4,pmETHCFMFLRPRI5,pmETHCFMFLPRI5,pmETHCFMFDPRI5,pmETHCFMFDVPRI5,pmETHCFMFLRPRI6,pmETHCFMFLPRI6,pmETHCFMFDPRI6,pmETHCFMFDVPRI6,pmETHCFMFLRPRI7,pmETHCFMFLPRI7,pmETHCFMFDPRI7,pmETHCFMFDVPRI7,pmETHCFMLANFLTX,pmETHCFMLANFLRRX,pmETHCFMLANFLRX,pmETHCFMLANFD,pmETHCFMLANFDV,pmETHCFMLANFPSTX,pmETHCFMLANFBPSTX,pmETHCFMLANFPSRX,pmETHCFMLANFBPSRX,pmETHCFMFLRTXMAX,pmETHCFMFLRTXMIN,pmETHCFMFLRTXAVG,pmETHCFMFLRRXMAX,pmETHCFMFLRRXMIN,pmETHCFMFLRRXAVG,pmETHCFMLANFPSTXMAX,pmETHCFMLANFPSTXMIN,pmETHCFMLANFPSTXAVG,pmETHCFMLANFBPSTXMAX,pmETHCFMLANFBPSTXMIN,pmETHCFMLANFBPSTXAVG,pmETHCFMLANFPSRXMAX,pmETHCFMLANFPSRXMIN,pmETHCFMLANFPSRXAVG,pmETHCFMLANFBPSRXMAX,pmETHCFMLANFBPSRXMIN,pmETHCFMLANFBPSRXAVG,pmETHCFMLANFDMAX,pmETHCFMLANFDMIN,pmETHCFMLANFDAVG,
pmETHCFMLANFDVMAX,pmETHCFMLANFDVMIN,pmETHCFMLANFDVAVG,pmETHCFMLANFLRTX,pmMPLSPWFLN,pmMPLSPWFLRN,pmMPLSTUNNELFLN,pmMPLSTUNNELFLRN,pmETHCFMFLRN,pmETHCFMFLN, pmPORTRXBWUTILIZATIONMIN,pmPORTRXBWUTILIZATIONAVG,pmPORTRXBWUTILIZATIONMAX,pmPORTTXBWUTILIZATIONMIN,pmPORTTXBWUTILIZATIONAVG,pmPORTTXBWUTILIZATIONMAX,pmTNLBWUTILISATIONMIN,pmTNLBWUTILISATIONAVG,pmTNLBWUTILISATIONMAX,pmTNLREVERSEBWUTILISATIONMIN,pmTNLREVERSEBWUTILISATIONAVG,pmTNLREVERSEBWUTILISATIONMAX,pmPWBANDWIDTHUTILISATIONMIN,pmPWBANDWIDTHUTILISATIONAVG,pmPWBANDWIDTHUTILISATIONMAX,pmTXDROPPKTS,pmRXDROPPKTS,pmTXBPSMIN,pmTXBPSAVG,pmTXBPSMAX,pmRXBPSMIN,pmRXBPSAVG,pmRXBPSMAX,pmECMPRSRATIO,pmAtmpwLospkts,pmAtmpwMisorderpkts,pmPortRxBytesAvailability,pmPwBandwidthUtilisation,pmPwAvailability,pmQosPriBandwidthUtilisation,pmAtmBoardDropcells,pmCesRxBytes,pmEthbadpkts,pmAtmpwBwUtilization,pmTnlBwUtilisation,pmTnlReverseBwUtilisation,pmFlowTxUtilization,pmVunigroupRcvpkts,pmVunigroupRcvbytes,pmVuniRxUtilization,pmEthCfmFlrPri1N,pmEthCfmFlrPri0N,pmEthCfmFlrPri2N,
pmEthCfmFlrPri3N,pmEthCfmFlrPri4N,pmEthCfmFlrPri5N,pmEthCfmFlrPri6N,pmEthCfmFlrPri7N,pmEthCfmFlPri0N,pmEthCfmFlPri1N,pmEthCfmFlPri2N,pmEthCfmFlPri3N,pmEthCfmFlPri4N,pmEthCfmFlPri5N,pmEthCfmFlPri6N,pmEthCfmFlPri7N,pmCesTxPkts,pmVlanRxUtilization,pmRXBPS,pmRXPPS,
pmVlanTxUtilization,pmRxMaxBwUtilizationCapacity,pmTxMaxBwUtilizationCapacity }
        STATUS current
        DESCRIPTION
            "Enter the description of the created OBJECT-GROUP."
        ::= { optixRtnPmTrapGroups 1 }

    -- 1.3.6.1.4.1.2011.2.25.3.40.40.200.2
    optixRtnPmTrapCompliances OBJECT IDENTIFIER ::= { optixRtnPmTrapConformance 2 }

    -- 1.3.6.1.4.1.2011.2.25.3.40.40.200.2.1
    optixRtnPmTrapbasicCompliance MODULE-COMPLIANCE
        STATUS current
        DESCRIPTION
            "Enter the description of the created MODULE-COMPLIANCE."
        MODULE -- this module
	    MANDATORY-GROUPS { optixRtnPmTrapObjectGroup }                                 
        ::= { optixRtnPmTrapCompliances 1 }

END
