-- OPTIX-L2VPN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-L2VPN-MIB DEFINITIONS ::= BEGIN
    IMPORTS
        OBJECT-GROUP,MODULE-COMPLIANCE
            FROM SNMPv2-CONF
        MODULE-IDENTITY,OBJECT-TYPE,Unsigned32,Integer32,IpAddress,Counter64,NOTIFICATION-TYPE
            FROM SNMPv2-SMI
        RowStatus,MacAddress,DateAndTime
            FROM SNMPv2-TC
        optixProvisionPtn
            FROM OPTIX-OID-MIB
        ;

    optixEthSrvMod MODULE-IDENTITY
        LAST-UPDATED "201204120000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage ETH services, including the private line, private network,aggregate services and related attributes. The ETH private line service is shown in the point-to-point mode in the topology and used to transmit ETH services in the point-to-point mode. According to thetransmission mode, theETH private line services can be classified as follows: UNI-UNI UNI-NNI (QINQ or PW) NNI (QINQ)-NNI (QINQ) UNI-NNI (QINQ or PW) NNI (QINQ)-NNI (QINQ) The ETH private network service is shown in the muti-point to multi-point mode in the topology. Through the ETH private network,devices transmit ETH services in multi-point to multi-pointmode by self-learning MAC addresses to connect multiple UNIs and NNIs. In topology, an E-AGGR service is a multipoint-to-point service.Devices aggregate services input from multiple UNIs to one UNI or NNI carried by ports or PWs, or aggregate services input from multiple NNIs carried by PWs or ports to one UNI."
        REVISION "201204120000Z"
        DESCRIPTION
            "Initial version of this MIB module"
        ::={ optixProvisionPtn 3 }

    -- 1.3.6.1.4.1.2011.2.25.4.50.3.1
    optixEthSrvObject OBJECT IDENTIFIER ::= { optixEthSrvMod 1 }

    -- 1.3.6.1.4.1.2011.2.25.4.50.3.1.1
    optixUnitoUniElineTable OBJECT-TYPE
        SYNTAX SEQUENCE OF OptixUnitoUniElineEntry
        MAX-ACCESS not-accessible
        STATUS current
        DESCRIPTION
            "The ETH private line service is shown in the point-to-point mode in the topology. This table is used to transmit UNI-to-UNI ETH private line service in the point-to-point mode."
        ::= { optixEthSrvObject 1 }

    -- 1.3.6.1.4.1.2011.2.25.4.50.3.1.1.1
    optixUnitoUniElineEntry OBJECT-TYPE
        SYNTAX OptixUnitoUniElineEntry
        MAX-ACCESS not-accessible
        STATUS current
        DESCRIPTION
            "This entry indicates the UNI-to-UNI ETH private line service in the point-to-point mode."
        INDEX{ optixUnitoUniElineIndex,optixUnitoUniElineFirstUniId,optixUnitoUniElineSecondUniId }
        ::= { optixUnitoUniElineTable 1 }

    OptixUnitoUniElineEntry ::=
        SEQUENCE {
            optixUnitoUniElineIndex
                Unsigned32,
            optixUnitoUniElineFirstUniId
                Unsigned32,
            optixUnitoUniElineSecondUniId
                Unsigned32,
            optixUnitoUniElineId
                Unsigned32,
            optixUnitoUniElineName
                OCTET STRING,
            optixUnitoUniElinePrtlthrough
                INTEGER,
            optixUnitoUniElineMtu
                Unsigned32,
            optixUnitoUniElineTagrole
                INTEGER,
            optixUnitoUniElineFirstUniBid
                Unsigned32,
            optixUnitoUniElineFirstUniSubBid
                Unsigned32,
            optixUnitoUniElineFirstUniPortId
                Unsigned32,
            optixUnitoUniFirstUniVlanNum
                Unsigned32,
            optixUnitoUniFirstUniVlanlist
                OCTET STRING,
            optixUnitoUniElineSecondUniBid
                Unsigned32,
            optixUnitoUniElineSecondUniSubBid
                Unsigned32,
            optixUnitoUniElineSecondUniPortId
                Unsigned32,
            optixUnitoUniSecondUniVlanNum
                Unsigned32,
            optixUnitoUniSecondUniVlanlist
                OCTET STRING,
            optixUnitoUniElineRowStatus
                RowStatus
        }

    -- 1.3.6.1.4.1.2011.2.25.4.50.3.1.1.1.1
    optixUnitoUniElineIndex OBJECT-TYPE
        SYNTAX Unsigned32
        MAX-ACCESS not-accessible
        STATUS current
        DESCRIPTION
            "This object indicates the service index."
        ::= { optixUnitoUniElineEntry 1 }

    -- 1.3.6.1.4.1.2011.2.25.4.50.3.1.1.1.2
    optixUnitoUniElineFirstUniId OBJECT-TYPE
        SYNTAX Unsigned32(1..65535)
        MAX-ACCESS not-accessible
        STATUS current
        DESCRIPTION
            "This object indicates the first V-UNI ID of the service. Value range: 1 to 65535."
        ::= { optixUnitoUniElineEntry 2 }

    -- 1.3.6.1.4.1.2011.2.25.4.50.3.1.1.1.3
    optixUnitoUniElineSecondUniId OBJECT-TYPE
        SYNTAX Unsigned32(1..65535)
        MAX-ACCESS not-accessible
        STATUS current
        DESCRIPTION
            "This object indicates the second V-UNI ID of the service. Value range: 1 to 65535."
        ::= { optixUnitoUniElineEntry 3 }

    -- 1.3.6.1.4.1.2011.2.25.4.50.3.1.1.1.4
    optixUnitoUniElineId OBJECT-TYPE
        SYNTAX Unsigned32
        MAX-ACCESS read-create
        STATUS current
        DESCRIPTION
            "This object indicates the service ID."
        ::= { optixUnitoUniElineEntry 4 }

    -- 1.3.6.1.4.1.2011.2.25.4.50.3.1.1.1.5
    optixUnitoUniElineName OBJECT-TYPE
        SYNTAX OCTET STRING(SIZE(0..64))
        MAX-ACCESS read-create
        STATUS current
        DESCRIPTION
            "This object indicates the service name, which is a character string in 64 bytes."
        ::= { optixUnitoUniElineEntry 5 }

    -- 1.3.6.1.4.1.2011.2.25.4.50.3.1.1.1.6
    optixUnitoUniElinePrtlthrough OBJECT-TYPE
        SYNTAX INTEGER
        {
            disable(0),
            bpdu(1),
            lacp(2)
        }
        MAX-ACCESS read-create
        STATUS current
        DESCRIPTION
            "This object indicates the flag of transparently transmitting Layer 2 protocol packets. 0: disable 1: bpdu (transparently transmitting BPDU protocol packets) 2: lacp (transparently transmitting LACP protocol packets)"
        DEFVAL{ 0 }
        ::= { optixUnitoUniElineEntry 6 }

    -- 1.3.6.1.4.1.2011.2.25.4.50.3.1.1.1.7
    optixUnitoUniElineMtu OBJECT-TYPE
        SYNTAX Unsigned32
        MAX-ACCESS read-create
        STATUS current
        DESCRIPTION
            "This object indicates the packet length."
        DEFVAL{ 1500 }
        ::= { optixUnitoUniElineEntry 7 }

    -- 1.3.6.1.4.1.2011.2.25.4.50.3.1.1.1.8
    optixUnitoUniElineTagrole OBJECT-TYPE
        SYNTAX INTEGER
        {
            user(1),
            service(2)
        }
        MAX-ACCESS read-create
        STATUS current
        DESCRIPTION
            "This object indicates the tag role attribute. 1: user 2: service"
        DEFVAL{ 1 }
        ::= { optixUnitoUniElineEntry 8 }

    -- 1.3.6.1.4.1.2011.2.25.4.50.3.1.1.1.9
    optixUnitoUniElineFirstUniBid OBJECT-TYPE
        SYNTAX Unsigned32(1..65535)
        MAX-ACCESS read-create
        STATUS current
        DESCRIPTION
            "This object indicates the first V-UNI slot ID of the service. Value range: 1 to 65535."
        ::= { optixUnitoUniElineEntry 9 }

    -- 1.3.6.1.4.1.2011.2.25.4.50.3.1.1.1.10
    optixUnitoUniElineFirstUniSubBid OBJECT-TYPE
        SYNTAX Unsigned32(1..255)
        MAX-ACCESS read-create
        STATUS current
        DESCRIPTION
            "This object indicates the first V-UNI subboard ID of the service. Value range: 1 to 255."
        ::= { optixUnitoUniElineEntry 10 }

    -- 1.3.6.1.4.1.2011.2.25.4.50.3.1.1.1.11
    optixUnitoUniElineFirstUniPortId OBJECT-TYPE
        SYNTAX Unsigned32(1..65535)
        MAX-ACCESS read-create
        STATUS current
        DESCRIPTION
            "This object indicates the first V-UNI port number of the service. Value range: 1 to 65535."
        ::= { optixUnitoUniElineEntry 11 }

    -- 1.3.6.1.4.1.2011.2.25.4.50.3.1.1.1.12
    optixUnitoUniFirstUniVlanNum OBJECT-TYPE
        SYNTAX Unsigned32(0..4094)
        MAX-ACCESS read-create
        STATUS current
        DESCRIPTION
            "This object indicates the number of VLANs of the first V-UNI (0: VLAN number of the port). Value range: 0 to 4094."
        ::= { optixUnitoUniElineEntry 12 }

    -- 1.3.6.1.4.1.2011.2.25.4.50.3.1.1.1.13
    optixUnitoUniFirstUniVlanlist OBJECT-TYPE
        SYNTAX OCTET STRING(SIZE(0..512))
        MAX-ACCESS read-create
        STATUS current
        DESCRIPTION
            "This object indicates the list of VLANs of the first V-UNI. The number of each bit indicates whether the corresponding VLAN exists. For example, The number of the third bit is 1,indicating that the VLAN ID of the PW is 3."
        ::= { optixUnitoUniElineEntry 13 }

    -- 1.3.6.1.4.1.2011.2.25.4.50.3.1.1.1.14
    optixUnitoUniElineSecondUniBid OBJECT-TYPE
        SYNTAX Unsigned32(1..65535)
        MAX-ACCESS read-create
        STATUS current
        DESCRIPTION
            "This object indicates the second V-UNI slot ID of the service. Value range: 1 to 65535."
        ::= { optixUnitoUniElineEntry 14 }

    -- 1.3.6.1.4.1.2011.2.25.4.50.3.1.1.1.15
    optixUnitoUniElineSecondUniSubBid OBJECT-TYPE
        SYNTAX Unsigned32(1..255)
        MAX-ACCESS read-create
        STATUS current
        DESCRIPTION
            "This object indicates the second V-UNI subboard ID of the service. Value range: 1 to 255."
        ::= { optixUnitoUniElineEntry 15 }

    -- 1.3.6.1.4.1.2011.2.25.4.50.3.1.1.1.16
    optixUnitoUniElineSecondUniPortId OBJECT-TYPE
        SYNTAX Unsigned32(1..65535)
        MAX-ACCESS read-create
        STATUS current
        DESCRIPTION
            "This object indicates the second V-UNI port number of the service. Value range: 1 to 65535."
        ::= { optixUnitoUniElineEntry 16 }

    -- 1.3.6.1.4.1.2011.2.25.4.50.3.1.1.1.17
    optixUnitoUniSecondUniVlanNum OBJECT-TYPE
        SYNTAX Unsigned32(0..4094)
        MAX-ACCESS read-create
        STATUS current
        DESCRIPTION
            "This object indicates the number of VLANs of thesecond V-UNI (0: VLAN number of the port). Value range: 0 to 4094."
        ::= { optixUnitoUniElineEntry 17 }

    -- 1.3.6.1.4.1.2011.2.25.4.50.3.1.1.1.18
    optixUnitoUniSecondUniVlanlist OBJECT-TYPE
        SYNTAX OCTET STRING(SIZE(0..512))
        MAX-ACCESS read-create
        STATUS current
        DESCRIPTION
            "This object indicates the list of VLANs of thesecond V-UNI. The number of each bit indicates whether the corresponding VLAN exists. For example, The number of the third bit is 1, indicating that the VLAN ID of the PW is 3."
        ::= { optixUnitoUniElineEntry 18 }

    -- 1.3.6.1.4.1.2011.2.25.4.50.3.1.1.1.255
    optixUnitoUniElineRowStatus OBJECT-TYPE
        SYNTAX RowStatus
        MAX-ACCESS read-create
        STATUS current
        DESCRIPTION
            "This object indicates the row status. 1: active,4: createAndGo,6: destroy"
        ::= { optixUnitoUniElineEntry 255 }

    -- 1.3.6.1.4.1.2011.2.25.4.50.3.1.2
    optixUnitoNniElineTable OBJECT-TYPE
        SYNTAX SEQUENCE OF OptixUnitoNniElineEntry
        MAX-ACCESS not-accessible
        STATUS current
        DESCRIPTION
            "The ETH private line service is shown in the point-to-point mode in the topology. This table is used to transmit UNI-to-NNI ETH private line service in the point-to-point mode."
        ::= { optixEthSrvObject 2 }

    -- 1.3.6.1.4.1.2011.2.25.4.50.3.1.2.1
    optixUnitoNniElineEntry OBJECT-TYPE
        SYNTAX OptixUnitoNniElineEntry
        MAX-ACCESS not-accessible
        STATUS current
        DESCRIPTION
            "This entry indicates the UNI-to-NNI ETH private line service in the point-to-point mode."
        INDEX{ optixUnitoNniElineIndex,optixUnitoNniElineUniId,optixUnitoNniElineNniId }
        ::= { optixUnitoNniElineTable 1 }

    OptixUnitoNniElineEntry ::=
        SEQUENCE {
            optixUnitoNniElineIndex
                Unsigned32,
            optixUnitoNniElineUniId
                Unsigned32,
            optixUnitoNniElineNniId
                Unsigned32,
            optixUnitoNniElineId
                Unsigned32,
            optixUnitoNniElineName
                OCTET STRING,
            optixUnitoNniElinePrtlthrough
                INTEGER,
            optixUnitoNniElineMtu
                Unsigned32,
            optixUnitoNniElineTagrole
                INTEGER,
            optixUnitoNniElineUniBid
                Unsigned32,
            optixUnitoNniElineUniSubBid
                Unsigned32,
            optixUnitoNniElineUniPortId
                Unsigned32,
            optixUnitoNniElineUniVlanNum
                Unsigned32,
            optixUnitoNniElineUniVlanlist
                OCTET STRING,
            optixUnitoNniElineNniType
                INTEGER,
            optixUnitoNniElineNniParaOne
                Unsigned32,
            optixUnitoNniElineNniParaTwo
                Unsigned32,
            optixUnitoNniElineNniParaThree
                Unsigned32,
            optixUnitoNniArpSendSwitchEnable
                INTEGER,
            optixUnitoNniElineRowStatus
                RowStatus
        }

    -- 1.3.6.1.4.1.2011.2.25.4.50.3.1.2.1.1
    optixUnitoNniElineIndex OBJECT-TYPE
        SYNTAX Unsigned32
        MAX-ACCESS not-accessible
        STATUS current
        DESCRIPTION
            "This object indicates the service index."
        ::= { optixUnitoNniElineEntry 1 }

    -- 1.3.6.1.4.1.2011.2.25.4.50.3.1.2.1.2
    optixUnitoNniElineUniId OBJECT-TYPE
        SYNTAX Unsigned32(1..65535)
        MAX-ACCESS not-accessible
        STATUS current
        DESCRIPTION
            "This object indicates the service V-UNI ID. Value range: 1 to 65535."
        ::= { optixUnitoNniElineEntry 2 }

    -- 1.3.6.1.4.1.2011.2.25.4.50.3.1.2.1.3
    optixUnitoNniElineNniId OBJECT-TYPE
        SYNTAX Unsigned32(1..65535)
        MAX-ACCESS not-accessible
        STATUS current
        DESCRIPTION
            "This object indicates the service V-NNI ID. Value range: 1 to 65535."
        ::= { optixUnitoNniElineEntry 3 }

    -- 1.3.6.1.4.1.2011.2.25.4.50.3.1.2.1.4
    optixUnitoNniElineId OBJECT-TYPE
        SYNTAX Unsigned32
        MAX-ACCESS read-create
        STATUS current
        DESCRIPTION
            "This object indicates the service ID."
        ::= { optixUnitoNniElineEntry 4 }

    -- 1.3.6.1.4.1.2011.2.25.4.50.3.1.2.1.5
    optixUnitoNniElineName OBJECT-TYPE
        SYNTAX OCTET STRING(SIZE(0..64))
        MAX-ACCESS read-create
        STATUS current
        DESCRIPTION
            "This object indicates the service name, which is a character string in 64 bytes."
        ::= { optixUnitoNniElineEntry 5 }

    -- 1.3.6.1.4.1.2011.2.25.4.50.3.1.2.1.6
    optixUnitoNniElinePrtlthrough OBJECT-TYPE
        SYNTAX INTEGER
        {
            disable(0),
            bpdu(1),
            lacp(2)
        }
        MAX-ACCESS read-create
        STATUS current
        DESCRIPTION
            "This object indicates the flag of transparently transmitting Layer 2 protocol packets. 0: disable 1: bpdu (transparently transmitting BPDU protocol packets) 2: lacp (transparently transmitting LACP protocol packets)"
        DEFVAL{ 0 }
        ::= { optixUnitoNniElineEntry 6 }

    -- 1.3.6.1.4.1.2011.2.25.4.50.3.1.2.1.7
    optixUnitoNniElineMtu OBJECT-TYPE
        SYNTAX Unsigned32
        MAX-ACCESS read-create
        STATUS current
        DESCRIPTION
            "This object indicates the packet length."
        DEFVAL{ 1500 }
        ::= { optixUnitoNniElineEntry 7 }

    -- 1.3.6.1.4.1.2011.2.25.4.50.3.1.2.1.8
    optixUnitoNniElineTagrole OBJECT-TYPE
        SYNTAX INTEGER
        {
            user(1),
            service(2)
        }
        MAX-ACCESS read-create
        STATUS current
        DESCRIPTION
            "This object indicates the tag role attribute. 1: user 2: service"
        DEFVAL{ 1 }
        ::= { optixUnitoNniElineEntry 8 }

    -- 1.3.6.1.4.1.2011.2.25.4.50.3.1.2.1.9
    optixUnitoNniElineUniBid OBJECT-TYPE
        SYNTAX Unsigned32(1..65535)
        MAX-ACCESS read-create
        STATUS current
        DESCRIPTION
            "This object indicates the slot ID of the service V-UNI. Value range: 1 to 65535."
        ::= { optixUnitoNniElineEntry 9 }

    -- 1.3.6.1.4.1.2011.2.25.4.50.3.1.2.1.10
    optixUnitoNniElineUniSubBid OBJECT-TYPE
        SYNTAX Unsigned32(1..255)
        MAX-ACCESS read-create
        STATUS current
        DESCRIPTION
            "This object indicates the subboard ID of the service V-UNI. Value range: 1 to 255."
        ::= { optixUnitoNniElineEntry 10 }

    -- 1.3.6.1.4.1.2011.2.25.4.50.3.1.2.1.11
    optixUnitoNniElineUniPortId OBJECT-TYPE
        SYNTAX Unsigned32(1..65535)
        MAX-ACCESS read-create
        STATUS current
        DESCRIPTION
            "This object indicates the port number of the service V-UNI. Value range: 1 to 65535."
        ::= { optixUnitoNniElineEntry 11 }

    -- 1.3.6.1.4.1.2011.2.25.4.50.3.1.2.1.12
    optixUnitoNniElineUniVlanNum OBJECT-TYPE
        SYNTAX Unsigned32(0..4094)
        MAX-ACCESS read-create
        STATUS current
        DESCRIPTION
            "This object indicates the number of VLANs of the V-UNI (0: VLAN number of the port). Value range: 0 to 4094."
        ::= { optixUnitoNniElineEntry 12 }

    -- 1.3.6.1.4.1.2011.2.25.4.50.3.1.2.1.13
    optixUnitoNniElineUniVlanlist OBJECT-TYPE
        SYNTAX OCTET STRING(SIZE(0..512))
        MAX-ACCESS read-create
        STATUS current
        DESCRIPTION
            "This object indicates the list of VLANs of the V-UNI. The number of each bit indicates whether the corresponding VLAN exists. For example, The number of the third bit is 1, indicating that the VLAN ID of the PW is 3."
        ::= { optixUnitoNniElineEntry 13 }

    -- 1.3.6.1.4.1.2011.2.25.4.50.3.1.2.1.14
    optixUnitoNniElineNniType OBJECT-TYPE
        SYNTAX INTEGER
        {
            pw(1),
            phyport(3),
            qinq(4)
        }
        MAX-ACCESS read-create
        STATUS current
        DESCRIPTION
            "This object indicates the NNI carrier type. 1: pw 3: phyport 4: qinq"
        ::= { optixUnitoNniElineEntry 14 }

    -- 1.3.6.1.4.1.2011.2.25.4.50.3.1.2.1.15
    optixUnitoNniElineNniParaOne OBJECT-TYPE
        SYNTAX Unsigned32
        MAX-ACCESS read-create
        STATUS current
        DESCRIPTION
            "This object indicates the first parameter of the carrier ID. When the carrier type is pw, this paramter is invalid and the parameter value is 0xffffffff. When the carrier type is phy port, this parameter indicates the slot ID. When the carrier type is qinq link, this paramter is invalid and the parameter value is 0xffffffff."
        ::= { optixUnitoNniElineEntry 15 }

    -- 1.3.6.1.4.1.2011.2.25.4.50.3.1.2.1.16
    optixUnitoNniElineNniParaTwo OBJECT-TYPE
        SYNTAX Unsigned32
        MAX-ACCESS read-create
        STATUS current
        DESCRIPTION
            "This object indicates thesecond parameter of the carrier ID. When the carrier type is pw, this paramter is invalid and the parameter value is 0xffffffff. When the carrier type is phy port, this parameter indicates thesubboard ID. When the carrier type is qinq link, this paramter is invalid and the parameter value is 0xffffffff."
        ::= { optixUnitoNniElineEntry 16 }

    -- 1.3.6.1.4.1.2011.2.25.4.50.3.1.2.1.17
    optixUnitoNniElineNniParaThree OBJECT-TYPE
        SYNTAX Unsigned32
        MAX-ACCESS read-create
        STATUS current
        DESCRIPTION
            "This object indicates the third parameter of the carrier ID. When the carrier type is PW, this parameter indicates the PW index. When the carrier type is phy port, this parameter indicates the port number. When the carrier type is Qinq Link, this parameter indicates the Qinq link index."
        ::= { optixUnitoNniElineEntry 17 }

    -- 1.3.6.1.4.1.2011.2.25.4.50.3.1.2.1.18
    optixUnitoNniArpSendSwitchEnable OBJECT-TYPE
        SYNTAX INTEGER
        {
            disable(0),
            enable(1)
        }
        MAX-ACCESS read-create
        STATUS current
        DESCRIPTION
            "This object indicates the state of the ARP both send switch."
        DEFVAL{ 0 }
        ::= { optixUnitoNniElineEntry 18 }

    -- 1.3.6.1.4.1.2011.2.25.4.50.3.1.2.1.255
    optixUnitoNniElineRowStatus OBJECT-TYPE
        SYNTAX RowStatus
        MAX-ACCESS read-create
        STATUS current
        DESCRIPTION
            "This object indicates the row status. 1: active,4: createAndGo,6: destroy"
        ::= { optixUnitoNniElineEntry 255 }

    -- 1.3.6.1.4.1.2011.2.25.4.50.3.1.3
    optixNnitoNniElineTable OBJECT-TYPE
        SYNTAX SEQUENCE OF OptixNnitoNniElineEntry
        MAX-ACCESS not-accessible
        STATUS current
        DESCRIPTION
            "The ETH private line service is shown in the point-to-point mode in the topology. This table is used to transmit NNI-to-NNI ETH private line service in the point-to-point mode."
        ::= { optixEthSrvObject 3 }

    -- 1.3.6.1.4.1.2011.2.25.4.50.3.1.3.1
    optixNnitoNniElineEntry OBJECT-TYPE
        SYNTAX OptixNnitoNniElineEntry
        MAX-ACCESS not-accessible
        STATUS current
        DESCRIPTION
            "This entry indicates the NNI-to-NNI ETH private line service in the point-to-point mode."
        INDEX{ optixNnitoNniElineIndex,optixNnitoNniFirstNniId,optixNnitoNniSecondNniId }
        ::= { optixNnitoNniElineTable 1 }

    OptixNnitoNniElineEntry ::=
        SEQUENCE {
            optixNnitoNniElineIndex
                Unsigned32,
            optixNnitoNniFirstNniId
                Unsigned32,
            optixNnitoNniSecondNniId
                Unsigned32,
            optixNnitoNniElineId
                Unsigned32,
            optixNnitoNniElineName
                OCTET STRING,
            optixNnitoNniElinePrtlthrough
                INTEGER,
            optixNnitoNniElineMtu
                Unsigned32,
            optixNnitoNniElineTagrole
                INTEGER,
            optixNnitoNniFirstNniType
                INTEGER,
            optixNnitoNniFirstNniParaOne
                Unsigned32,
            optixNnitoNniFirstNniParaTwo
                Unsigned32,
            optixNnitoNniFirstNniParaThree
                Unsigned32,
            optixNnitoNniSecondNniType
                INTEGER,
            optixNnitoNniSecondNniParaOne
                Unsigned32,
            optixNnitoNniSecondNniParaTwo
                Unsigned32,
            optixNnitoNniSecondNniParaThree
                Unsigned32,
            optixNnitoNniElineRowStatus
                RowStatus
        }

    -- 1.3.6.1.4.1.2011.2.25.4.50.3.1.3.1.1
    optixNnitoNniElineIndex OBJECT-TYPE
        SYNTAX Unsigned32
        MAX-ACCESS not-accessible
        STATUS current
        DESCRIPTION
            "This object indicates the service index."
        ::= { optixNnitoNniElineEntry 1 }

    -- 1.3.6.1.4.1.2011.2.25.4.50.3.1.3.1.2
    optixNnitoNniFirstNniId OBJECT-TYPE
        SYNTAX Unsigned32(1..65535)
        MAX-ACCESS not-accessible
        STATUS current
        DESCRIPTION
            "This object indicates the first V-NNI ID of the service. Value range: 1 to 65535."
        ::= { optixNnitoNniElineEntry 2 }

    -- 1.3.6.1.4.1.2011.2.25.4.50.3.1.3.1.3
    optixNnitoNniSecondNniId OBJECT-TYPE
        SYNTAX Unsigned32(1..65535)
        MAX-ACCESS not-accessible
        STATUS current
        DESCRIPTION
            "This object indicates thesecond V-NNI ID of the service. Value range: 1 to 65535."
        ::= { optixNnitoNniElineEntry 3 }

    -- 1.3.6.1.4.1.2011.2.25.4.50.3.1.3.1.4
    optixNnitoNniElineId OBJECT-TYPE
        SYNTAX Unsigned32
        MAX-ACCESS read-create
        STATUS current
        DESCRIPTION
            "This object indicates the service ID."
        ::= { optixNnitoNniElineEntry 4 }

    -- 1.3.6.1.4.1.2011.2.25.4.50.3.1.3.1.5
    optixNnitoNniElineName OBJECT-TYPE
        SYNTAX OCTET STRING(SIZE(0..64))
        MAX-ACCESS read-create
        STATUS current
        DESCRIPTION
            "This object indicates the service name, which is a character string in 64 bytes."
        ::= { optixNnitoNniElineEntry 5 }

    -- 1.3.6.1.4.1.2011.2.25.4.50.3.1.3.1.6
    optixNnitoNniElinePrtlthrough OBJECT-TYPE
        SYNTAX INTEGER
        {
            disable(0),
            bpdu(1),
            lacp(2)
        }
        MAX-ACCESS read-create
        STATUS current
        DESCRIPTION
            "This object indicates the flag of transparently transmitting Layer 2 protocol packets. 0: disable 1: bpdu (transparently transmitting BPDU protocol packets) 2: lacp (transparently transmitting LACP protocol packets)"
        DEFVAL{ 0 }
        ::= { optixNnitoNniElineEntry 6 }

    -- 1.3.6.1.4.1.2011.2.25.4.50.3.1.3.1.7
    optixNnitoNniElineMtu OBJECT-TYPE
        SYNTAX Unsigned32
        MAX-ACCESS read-create
        STATUS current
        DESCRIPTION
            "This object indicates the packet length."
        DEFVAL{ 1500 }
        ::= { optixNnitoNniElineEntry 7 }

    -- 1.3.6.1.4.1.2011.2.25.4.50.3.1.3.1.8
    optixNnitoNniElineTagrole OBJECT-TYPE
        SYNTAX INTEGER
        {
            user(1)
        }
        MAX-ACCESS read-create
        STATUS current
        DESCRIPTION
            "This object indicates the tag role attribute. 1: user 2: service"
        DEFVAL{ 1 }
        ::= { optixNnitoNniElineEntry 8 }

    -- 1.3.6.1.4.1.2011.2.25.4.50.3.1.3.1.9
    optixNnitoNniFirstNniType OBJECT-TYPE
        SYNTAX INTEGER
        {
            pw(1),
            phyport(3),
            qinq(4)
        }
        MAX-ACCESS read-create
        STATUS current
        DESCRIPTION
            "This object indicates the carrier type of the first NNI. 1: pw 3: phyport 4: qinq"
        ::= { optixNnitoNniElineEntry 9 }

    -- 1.3.6.1.4.1.2011.2.25.4.50.3.1.3.1.10
    optixNnitoNniFirstNniParaOne OBJECT-TYPE
        SYNTAX Unsigned32
        MAX-ACCESS read-create
        STATUS current
        DESCRIPTION
            "This object indicates the first parameter of the first NNI carrier ID. When the carrier type is pw, this paramter is invalid and the parameter value is 0xffffffff. When the carrier type is phy port, this parameter indicates the slot ID. When the carrier type is qinq link, this paramter is invalid and the parameter value is 0xffffffff."
        ::= { optixNnitoNniElineEntry 10 }

    -- 1.3.6.1.4.1.2011.2.25.4.50.3.1.3.1.11
    optixNnitoNniFirstNniParaTwo OBJECT-TYPE
        SYNTAX Unsigned32
        MAX-ACCESS read-create
        STATUS current
        DESCRIPTION
            "This object indicates the second parameter of the first NNI carrier ID. When the carrier type is pw, this paramter is invalid and the parameter value is 0xffffffff. When the carrier type is phy port, this parameter indicates the subboard ID. When the carrier type is qinq link, this paramter is invalid and the parameter value is 0xffffffff."
        ::= { optixNnitoNniElineEntry 11 }

    -- 1.3.6.1.4.1.2011.2.25.4.50.3.1.3.1.12
    optixNnitoNniFirstNniParaThree OBJECT-TYPE
        SYNTAX Unsigned32
        MAX-ACCESS read-create
        STATUS current
        DESCRIPTION
            "This object indicates the third parameter of the first NNI carrier ID. When the carrier type is pw, this parameter indicates the PW index. When the carrier type is phy port, this parameter indicates the port number. When the carrier type is Qinq link, this parameter indicates the QinQ link index."
        ::= { optixNnitoNniElineEntry 12 }

    -- 1.3.6.1.4.1.2011.2.25.4.50.3.1.3.1.13
    optixNnitoNniSecondNniType OBJECT-TYPE
        SYNTAX INTEGER
        {
            pw(1),
            phyport(3),
            qinq(4)
        }
        MAX-ACCESS read-create
        STATUS current
        DESCRIPTION
            "This object indicates the carrier type of the second NNI. 1: pw, 3: phyport, 4: qinq"
        ::= { optixNnitoNniElineEntry 13 }

    -- 1.3.6.1.4.1.2011.2.25.4.50.3.1.3.1.14
    optixNnitoNniSecondNniParaOne OBJECT-TYPE
        SYNTAX Unsigned32
        MAX-ACCESS read-create
        STATUS current
        DESCRIPTION
            "This object indicates the first parameter of thesecond NNI carrier ID. When the carrier type is pw, this paramter is invalid and the parameter value is 0xffffffff. When the carrier type is phy port, this parameter indicates the slot ID. When the carrier type is qinq link, this paramter is invalid and the parameter value is 0xffffffff."
        ::= { optixNnitoNniElineEntry 14 }

    -- 1.3.6.1.4.1.2011.2.25.4.50.3.1.3.1.15
    optixNnitoNniSecondNniParaTwo OBJECT-TYPE
        SYNTAX Unsigned32
        MAX-ACCESS read-create
        STATUS current
        DESCRIPTION
            "This object indicates the second parameter of the second NNI carrier ID. When the carrier type is pw, this paramter is invalid and the parameter value is 0xffffffff. When the carrier type is phy port, this parameter indicates the subboard ID. When the carrier type is qinq link, this paramter is invalid and the parameter value is 0xffffffff."
        ::= { optixNnitoNniElineEntry 15 }

    -- 1.3.6.1.4.1.2011.2.25.4.50.3.1.3.1.16
    optixNnitoNniSecondNniParaThree OBJECT-TYPE
        SYNTAX Unsigned32
        MAX-ACCESS read-create
        STATUS current
        DESCRIPTION
            "This object indicates thethird parameter of the second NNI carrier ID. When the carrier type is pw, this parameter indicates the PW index. When the carrier type is phy port, this parameter indicates the port number. When the carrier type is qinq link, this parameter indicates the QinQ link index."
        ::= { optixNnitoNniElineEntry 16 }

    -- 1.3.6.1.4.1.2011.2.25.4.50.3.1.3.1.255
    optixNnitoNniElineRowStatus OBJECT-TYPE
        SYNTAX RowStatus
        MAX-ACCESS read-create
        STATUS current
        DESCRIPTION
            "This object indicates the row status. 1: active,4: createAndGo,6: destroy"
        ::= { optixNnitoNniElineEntry 255 }

    -- 1.3.6.1.4.1.2011.2.25.4.50.3.1.4
    optixElanTable OBJECT-TYPE
        SYNTAX SEQUENCE OF OptixElanEntry
        MAX-ACCESS not-accessible
        STATUS current
        DESCRIPTION
            "This table implements the configurations of ETH private network services. The ETH private network service is shown in the muti-point to multi-point mode in the topology. Devices transmit ETH services in the multi-point to multi-point mode through the ETH private network."
        ::= { optixEthSrvObject 4 }

    -- 1.3.6.1.4.1.2011.2.25.4.50.3.1.4.1
    optixElanEntry OBJECT-TYPE
        SYNTAX OptixElanEntry
        MAX-ACCESS not-accessible
        STATUS current
        DESCRIPTION
            "This entry indicates the configuration table of the ETH private network service."
        INDEX{ optixElanIndex }
        ::= { optixElanTable 1 }

    OptixElanEntry ::=
        SEQUENCE {
            optixElanIndex
                Unsigned32,
            optixElanId
                Unsigned32,
            optixElanName
                OCTET STRING,
            optixElanPrtlthrough
                INTEGER,
            optixElanMtu
                Unsigned32,
            optixElanTagrole
                INTEGER,
            optixElanTagMode
                INTEGER,
            optixElanMacLearnEnable
                INTEGER,
            optixElanMacLearnMode
                INTEGER,
            optixElanMacAgingEnable
                INTEGER,
            optixElanMacAgingTime
                Unsigned32,
            optixElanMacSize
                Unsigned32,
            optixElanMacAlmUpperLimit
                Unsigned32,
            optixElanMacAlmLowerLimit
                Unsigned32,
            optixElanUnicastDispose
                INTEGER,
            optixElanMulticastDispose
                INTEGER,
            optixElanSportRole
                INTEGER,
            optixElanRowStatus
                RowStatus
        }

    -- 1.3.6.1.4.1.2011.2.25.4.50.3.1.4.1.1
    optixElanIndex OBJECT-TYPE
        SYNTAX Unsigned32
        MAX-ACCESS not-accessible
        STATUS current
        DESCRIPTION
            "This object indicates the service index."
        ::= { optixElanEntry 1 }

    -- 1.3.6.1.4.1.2011.2.25.4.50.3.1.4.1.2
    optixElanId OBJECT-TYPE
        SYNTAX Unsigned32
        MAX-ACCESS read-create
        STATUS current
        DESCRIPTION
            "This object indicates the service ID."
        ::= { optixElanEntry 2 }

    -- 1.3.6.1.4.1.2011.2.25.4.50.3.1.4.1.3
    optixElanName OBJECT-TYPE
        SYNTAX OCTET STRING(SIZE(0..64))
        MAX-ACCESS read-create
        STATUS current
        DESCRIPTION
            "This object indicates the service name, which is a character string in 64 bytes."
        ::= { optixElanEntry 3 }

    -- 1.3.6.1.4.1.2011.2.25.4.50.3.1.4.1.4
    optixElanPrtlthrough OBJECT-TYPE
        SYNTAX INTEGER
        {
            disable(0),
            bpdu(1),
            lacp(2)
        }
        MAX-ACCESS read-create
        STATUS current
        DESCRIPTION
            "This object indicates the flag of transparently transmitting Layer 2 protocol packets. 0: disable 1: bpdu (transparently transmitting BPDU protocol packets) 2: lacp (transparently transmitting LACP protocol packets)"
        DEFVAL{ 0 }
        ::= { optixElanEntry 4 }

    -- 1.3.6.1.4.1.2011.2.25.4.50.3.1.4.1.5
    optixElanMtu OBJECT-TYPE
        SYNTAX Unsigned32
        MAX-ACCESS read-create
        STATUS current
        DESCRIPTION
            "This object indicates the packet length."
        DEFVAL{ 1500 }
        ::= { optixElanEntry 5 }

    -- 1.3.6.1.4.1.2011.2.25.4.50.3.1.4.1.6
    optixElanTagrole OBJECT-TYPE
        SYNTAX INTEGER
        {
            user(1)
        }
        MAX-ACCESS read-create
        STATUS current
        DESCRIPTION
            "This object indicates the tag role attribute. 1: user 2: service"
        DEFVAL{ 1 }
        ::= { optixElanEntry 6 }

    -- 1.3.6.1.4.1.2011.2.25.4.50.3.1.4.1.7
    optixElanTagMode OBJECT-TYPE
        SYNTAX INTEGER
        {
            tawared(0),
            cawared(1),
            sawared(2)
        }
        MAX-ACCESS read-create
        STATUS current
        DESCRIPTION
            "This object indicates the tag type of the private network service. 0: t-awared 1: c-awared 2: s-awared"
        DEFVAL{ 1 }
        ::= { optixElanEntry 7 }

    -- 1.3.6.1.4.1.2011.2.25.4.50.3.1.4.1.8
    optixElanMacLearnEnable OBJECT-TYPE
        SYNTAX INTEGER
        {
            disable(0),
            enable(1)
        }
        MAX-ACCESS read-create
        STATUS current
        DESCRIPTION
            "This object indicates the capability of self-learning MAC addresses. 0: disable 1: enable"
        DEFVAL{ 1 }
        ::= { optixElanEntry 8 }

    -- 1.3.6.1.4.1.2011.2.25.4.50.3.1.4.1.9
    optixElanMacLearnMode OBJECT-TYPE
        SYNTAX INTEGER
        {
            svl(1),
            ivl(2)
        }
        MAX-ACCESS read-create
        STATUS current
        DESCRIPTION
            "This object indicates the MAC address learning mode. 1: svl 2: ivl"
        DEFVAL{ 2 }
        ::= { optixElanEntry 9 }

    -- 1.3.6.1.4.1.2011.2.25.4.50.3.1.4.1.10
    optixElanMacAgingEnable OBJECT-TYPE
        SYNTAX INTEGER
        {
            disable(0),
            enable(1)
        }
        MAX-ACCESS read-create
        STATUS current
        DESCRIPTION
            "This object indicates the capability of aging MAC addresses. 0: disable 1: enable"
        DEFVAL{ 1 }
        ::= { optixElanEntry 10 }

    -- 1.3.6.1.4.1.2011.2.25.4.50.3.1.4.1.11
    optixElanMacAgingTime OBJECT-TYPE
        SYNTAX Unsigned32(1..640)
        MAX-ACCESS read-create
        STATUS current
        DESCRIPTION
            "This object indicates the MAC address aging time. Valid values: 1-640 minutes."
        DEFVAL{ 5 }
        ::= { optixElanEntry 11 }

    -- 1.3.6.1.4.1.2011.2.25.4.50.3.1.4.1.12
    optixElanMacSize OBJECT-TYPE
        SYNTAX Unsigned32
        MAX-ACCESS read-create
        STATUS current
        DESCRIPTION
            "This object indicates the size of the MAC address table."
        DEFVAL{ 512 }
        ::= { optixElanEntry 12 }

    -- 1.3.6.1.4.1.2011.2.25.4.50.3.1.4.1.13
    optixElanMacAlmUpperLimit OBJECT-TYPE
        SYNTAX Unsigned32(80..100)
        MAX-ACCESS read-create
        STATUS current
        DESCRIPTION
            "This object indicates the upper threshold of the MAC address detection. Valid values: 80-100."
        DEFVAL{ 95 }
        ::= { optixElanEntry 13 }

    -- 1.3.6.1.4.1.2011.2.25.4.50.3.1.4.1.14
    optixElanMacAlmLowerLimit OBJECT-TYPE
        SYNTAX Unsigned32(60..100)
        MAX-ACCESS read-create
        STATUS current
        DESCRIPTION
            "This object indicates the lower threshold of the MAC address detection. Valid values: 60-100."
        DEFVAL{ 90 }
        ::= { optixElanEntry 14 }

    -- 1.3.6.1.4.1.2011.2.25.4.50.3.1.4.1.15
    optixElanUnicastDispose OBJECT-TYPE
        SYNTAX INTEGER
        {
            discard(1),
            flood(2)
        }
        MAX-ACCESS read-create
        STATUS current
        DESCRIPTION
            "This object indicates the processing mode of unknown unicast frames. 1: discard 2: flood"
        DEFVAL{ 2 }
        ::= { optixElanEntry 15 }

    -- 1.3.6.1.4.1.2011.2.25.4.50.3.1.4.1.16
    optixElanMulticastDispose OBJECT-TYPE
        SYNTAX INTEGER
        {
            discard(1),
            flood(2)
        }
        MAX-ACCESS read-create
        STATUS current
        DESCRIPTION
            "This object indicates the processing mode of unknown multicast frames. 1: discard 2: flood"
        DEFVAL{ 2 }
        ::= { optixElanEntry 16 }

    -- 1.3.6.1.4.1.2011.2.25.4.50.3.1.4.1.17
    optixElanSportRole OBJECT-TYPE
        SYNTAX INTEGER
        {
            auto(0),
            pbnni(1),
            vuni(2)
        }
        MAX-ACCESS read-create
        STATUS current
        DESCRIPTION
            "This object indicates the role of port S in the E-LAN service."
        ::= { optixElanEntry 17 }

    -- 1.3.6.1.4.1.2011.2.25.4.50.3.1.4.1.255
    optixElanRowStatus OBJECT-TYPE
        SYNTAX RowStatus
        MAX-ACCESS read-create
        STATUS current
        DESCRIPTION
            "This object indicates the row status. 1: active,4: createAndGo,6: destroy"
        ::= { optixElanEntry 255 }

    -- 1.3.6.1.4.1.2011.2.25.4.50.3.1.5
    optixElanUniTable OBJECT-TYPE
        SYNTAX SEQUENCE OF OptixElanUniEntry
        MAX-ACCESS not-accessible
        STATUS current
        DESCRIPTION
            "The UNI refers to the ETH port oriented to the user devices, which is used to carry UNI services. This table implements the configurations of the ETH UNI services. These configurations include the slot ID, subboard ID, port number, and VLAN list."
        ::= { optixEthSrvObject 5 }

    -- 1.3.6.1.4.1.2011.2.25.4.50.3.1.5.1
    optixElanUniEntry OBJECT-TYPE
        SYNTAX OptixElanUniEntry
        MAX-ACCESS not-accessible
        STATUS current
        DESCRIPTION
            "This entry indicates the configuration table of the logical UNIs for the ETH private network ."
        INDEX{ optixElanIndex,optixElanUniId }
        ::= { optixElanUniTable 1 }

    OptixElanUniEntry ::=
        SEQUENCE {
            optixElanUniId
                Unsigned32,
            optixElanUniBid
                Unsigned32,
            optixElanUniSubBid
                Unsigned32,
            optixElanUniPortId
                Unsigned32,
            optixElanUniVlanNum
                Unsigned32,
            optixElanUniVlanlist
                OCTET STRING,
            optixElanUniRowStatus
                RowStatus
        }

    -- 1.3.6.1.4.1.2011.2.25.4.50.3.1.5.1.1
    optixElanUniId OBJECT-TYPE
        SYNTAX Unsigned32(1..65535)
        MAX-ACCESS not-accessible
        STATUS current
        DESCRIPTION
            "This object indicates the service V-UNI ID. Value range: 1 to 65535."
        ::= { optixElanUniEntry 1 }

    -- 1.3.6.1.4.1.2011.2.25.4.50.3.1.5.1.2
    optixElanUniBid OBJECT-TYPE
        SYNTAX Unsigned32(1..65535)
        MAX-ACCESS read-create
        STATUS current
        DESCRIPTION
            "This object indicates the slot ID of the service V-UNI. Value range: 1 to 65535."
        ::= { optixElanUniEntry 2 }

    -- 1.3.6.1.4.1.2011.2.25.4.50.3.1.5.1.3
    optixElanUniSubBid OBJECT-TYPE
        SYNTAX Unsigned32(1..255)
        MAX-ACCESS read-create
        STATUS current
        DESCRIPTION
            "This object indicates the subboard ID of the service V-UNI. Value range: 1 to 255."
        ::= { optixElanUniEntry 3 }

    -- 1.3.6.1.4.1.2011.2.25.4.50.3.1.5.1.4
    optixElanUniPortId OBJECT-TYPE
        SYNTAX Unsigned32(1..65535)
        MAX-ACCESS read-create
        STATUS current
        DESCRIPTION
            "This object indicates the port number of the service V-UNI. Value range: 1 to 65535."
        ::= { optixElanUniEntry 4 }

    -- 1.3.6.1.4.1.2011.2.25.4.50.3.1.5.1.5
    optixElanUniVlanNum OBJECT-TYPE
        SYNTAX Unsigned32(0..4094)
        MAX-ACCESS read-create
        STATUS current
        DESCRIPTION
            "This object indicates the number of VLANs of the V-UNI (0: VLAN number of the port). Value range: 0 to 4094."
        ::= { optixElanUniEntry 5 }

    -- 1.3.6.1.4.1.2011.2.25.4.50.3.1.5.1.6
    optixElanUniVlanlist OBJECT-TYPE
        SYNTAX OCTET STRING(SIZE(0..512))
        MAX-ACCESS read-create
        STATUS current
        DESCRIPTION
            "This object indicates the list of VLANs of the V-UNI. The number of each bit indicates whether the corresponding VLAN exists. For example, The number of the third bit is 1, indicating that the VLAN ID of the PW is 3."
        ::= { optixElanUniEntry 6 }

    -- 1.3.6.1.4.1.2011.2.25.4.50.3.1.5.1.255
    optixElanUniRowStatus OBJECT-TYPE
        SYNTAX RowStatus
        MAX-ACCESS read-create
        STATUS current
        DESCRIPTION
            "This object indicates the row status. 1: active,4: createAndGo,6: destroy"
        ::= { optixElanUniEntry 255 }

    -- 1.3.6.1.4.1.2011.2.25.4.50.3.1.6
    optixElanPbUniTable OBJECT-TYPE
        SYNTAX SEQUENCE OF OptixElanPbUniEntry
        MAX-ACCESS not-accessible
        STATUS current
        DESCRIPTION
            "The PB UNI is used to add an SVLAN label to the UNI service after the service is connected to the Provide Bridge network. This table implements the configurations of the logical UNIs of the Provide Bridge private network. These configurations include the slot ID, subboard ID, port number, VLAN list, and SVLAN ID added to the UNI service."
        ::= { optixEthSrvObject 6 }

    -- 1.3.6.1.4.1.2011.2.25.4.50.3.1.6.1
    optixElanPbUniEntry OBJECT-TYPE
        SYNTAX OptixElanPbUniEntry
        MAX-ACCESS not-accessible
        STATUS current
        DESCRIPTION
            "This entry indicates the configuration table of the logical UNIs for the Provide Bridge ETH private network."
        INDEX{ optixElanIndex,optixElanPbUniId }
        ::= { optixElanPbUniTable 1 }

    OptixElanPbUniEntry ::=
        SEQUENCE {
            optixElanPbUniId
                Unsigned32,
            optixElanPbUniBid
                Unsigned32,
            optixElanPbUniSubBid
                Unsigned32,
            optixElanPbUniPortId
                Unsigned32,
            optixElanPbUniVlanNum
                Unsigned32,
            optixElanPbUniVlanlist
                OCTET STRING,
            optixElanPbUniSVlanId
                Unsigned32,
            optixElanPbUniRowStatus
                RowStatus
        }

    -- 1.3.6.1.4.1.2011.2.25.4.50.3.1.6.1.1
    optixElanPbUniId OBJECT-TYPE
        SYNTAX Unsigned32(1..65535)
        MAX-ACCESS not-accessible
        STATUS current
        DESCRIPTION
            "This object indicates the service V-UNI ID. Value range: 1 to 65535."
        ::= { optixElanPbUniEntry 1 }

    -- 1.3.6.1.4.1.2011.2.25.4.50.3.1.6.1.2
    optixElanPbUniBid OBJECT-TYPE
        SYNTAX Unsigned32(1..65535)
        MAX-ACCESS read-create
        STATUS current
        DESCRIPTION
            "This object indicates the slot ID of the service V-UNI. Value range: 1 to 65535."
        ::= { optixElanPbUniEntry 2 }

    -- 1.3.6.1.4.1.2011.2.25.4.50.3.1.6.1.3
    optixElanPbUniSubBid OBJECT-TYPE
        SYNTAX Unsigned32(1..255)
        MAX-ACCESS read-create
        STATUS current
        DESCRIPTION
            "This object indicates the subboard ID of the service V-UNI. Value range: 1 to 255."
        ::= { optixElanPbUniEntry 3 }

    -- 1.3.6.1.4.1.2011.2.25.4.50.3.1.6.1.4
    optixElanPbUniPortId OBJECT-TYPE
        SYNTAX Unsigned32(1..65535)
        MAX-ACCESS read-create
        STATUS current
        DESCRIPTION
            "This object indicates the port number of the service V-UNI. Value range: 1 to 65535."
        ::= { optixElanPbUniEntry 4 }

    -- 1.3.6.1.4.1.2011.2.25.4.50.3.1.6.1.5
    optixElanPbUniVlanNum OBJECT-TYPE
        SYNTAX Unsigned32(0..4094)
        MAX-ACCESS read-create
        STATUS current
        DESCRIPTION
            "This object indicates the number of VLANs of the V-UNI (0: VLAN number of the port). Value range: 0 to 4094."
        ::= { optixElanPbUniEntry 5 }

    -- 1.3.6.1.4.1.2011.2.25.4.50.3.1.6.1.6
    optixElanPbUniVlanlist OBJECT-TYPE
        SYNTAX OCTET STRING(SIZE(0..512))
        MAX-ACCESS read-create
        STATUS current
        DESCRIPTION
            "This object indicates the list of VLANs of the V-UNI. The number of each bit indicates whether the corresponding VLAN exists. For example, The number of the third bit is 1, indicating that the VLAN ID of the PW is 3."
        ::= { optixElanPbUniEntry 6 }

    -- 1.3.6.1.4.1.2011.2.25.4.50.3.1.6.1.7
    optixElanPbUniSVlanId OBJECT-TYPE
        SYNTAX Unsigned32(1..4094)
        MAX-ACCESS read-create
        STATUS current
        DESCRIPTION
            "This object indicates the added SVLAN ID. Value range: 1 to 4094."
        ::= { optixElanPbUniEntry 7 }

    -- 1.3.6.1.4.1.2011.2.25.4.50.3.1.6.1.255
    optixElanPbUniRowStatus OBJECT-TYPE
        SYNTAX RowStatus
        MAX-ACCESS read-create
        STATUS current
        DESCRIPTION
            "This object indicates the row status. 1: active4: createAndGo6: destroy"
        ::= { optixElanPbUniEntry 255 }

    -- 1.3.6.1.4.1.2011.2.25.4.50.3.1.7
    optixElanNniTable OBJECT-TYPE
        SYNTAX SEQUENCE OF OptixElanNniEntry
        MAX-ACCESS not-accessible
        STATUS current
        DESCRIPTION
            "This table implements the configurations of the logical ETH NNIs. The NNI refers to the ETH port oriented to the packet transport network, which is used to configure ETH NNI services. According to the service carrying mode, the NNIs can be classified to: carried by port,caried by PW,carried by QinQ link"
        ::= { optixEthSrvObject 7 }

    -- 1.3.6.1.4.1.2011.2.25.4.50.3.1.7.1
    optixElanNniEntry OBJECT-TYPE
        SYNTAX OptixElanNniEntry
        MAX-ACCESS not-accessible
        STATUS current
        DESCRIPTION
            "This entry indicates the configuration table of the logical NNIs for the ETH private network ."
        INDEX{ optixElanIndex,optixElanNniId }
        ::= { optixElanNniTable 1 }

    OptixElanNniEntry ::=
        SEQUENCE {
            optixElanNniId
                Unsigned32,
            optixElanNniType
                INTEGER,
            optixElanNniParaOne
                Unsigned32,
            optixElanNniParaTwo
                Unsigned32,
            optixElanNniParaThree
                Unsigned32,
            optixElanNniRowStatus
                RowStatus
        }

    -- 1.3.6.1.4.1.2011.2.25.4.50.3.1.7.1.1
    optixElanNniId OBJECT-TYPE
        SYNTAX Unsigned32
        MAX-ACCESS not-accessible
        STATUS current
        DESCRIPTION
            "This object indicates the service V-NNI ID."
        ::= { optixElanNniEntry 1 }

    -- 1.3.6.1.4.1.2011.2.25.4.50.3.1.7.1.2
    optixElanNniType OBJECT-TYPE
        SYNTAX INTEGER
        {
            pw(1),
            phyport(3),
            qinq(4)
        }
        MAX-ACCESS read-create
        STATUS current
        DESCRIPTION
            "This object indicates the NNI carrier type. 1: pw 3: phyport 4: qinq"
        ::= { optixElanNniEntry 2 }

    -- 1.3.6.1.4.1.2011.2.25.4.50.3.1.7.1.3
    optixElanNniParaOne OBJECT-TYPE
        SYNTAX Unsigned32
        MAX-ACCESS read-create
        STATUS current
        DESCRIPTION
            "This object indicates the first parameter of the carrier ID. When the carrier type is pw, this paramter is invalid and the parameter value is 0xffffffff. When the carrier type is phy port, this parameter indicates the slot ID. When the carrier type is qinq link, this paramter is invalid and the parameter value is 0xffffffff."
        ::= { optixElanNniEntry 3 }

    -- 1.3.6.1.4.1.2011.2.25.4.50.3.1.7.1.4
    optixElanNniParaTwo OBJECT-TYPE
        SYNTAX Unsigned32
        MAX-ACCESS read-create
        STATUS current
        DESCRIPTION
            "This object indicates the second parameter of the carrier ID. When the carrier type is pw, this paramter is invalid and the parameter value is 0xffffffff. When the carrier type is phy port, this parameter indicates the subboard ID. When the carrier type is qinq link, this paramter is invalid and the parameter value is 0xffffffff."
        ::= { optixElanNniEntry 4 }

    -- 1.3.6.1.4.1.2011.2.25.4.50.3.1.7.1.5
    optixElanNniParaThree OBJECT-TYPE
        SYNTAX Unsigned32
        MAX-ACCESS read-create
        STATUS current
        DESCRIPTION
            "This object indicates the third parameter of the carrier ID. When the carrier type is pw, this parameter indicates the PW index. When the carrier type is phy port, this parameter indicates the port number. When the carrier type is Qinq Link, this parameter indicates the QinQ link index."
        ::= { optixElanNniEntry 5 }

    -- 1.3.6.1.4.1.2011.2.25.4.50.3.1.7.1.255
    optixElanNniRowStatus OBJECT-TYPE
        SYNTAX RowStatus
        MAX-ACCESS read-create
        STATUS current
        DESCRIPTION
            "This object indicates the row status. 1: active,4: createAndGo,6: destroy"
        ::= { optixElanNniEntry 255 }

    -- 1.3.6.1.4.1.2011.2.25.4.50.3.1.8
    optixElanSplithrigrpTable OBJECT-TYPE
        SYNTAX SEQUENCE OF OptixElanSplithrigrpEntry
        MAX-ACCESS not-accessible
        STATUS current
        DESCRIPTION
            "This table implements the configurations of the spit horizon group for an ETH private network. Packets cannot be forwarded between ports in a split horizon group to prevent broadcast storm due to packet loopbacks."
        ::= { optixEthSrvObject 8 }

    -- 1.3.6.1.4.1.2011.2.25.4.50.3.1.8.1
    optixElanSplithrigrpEntry OBJECT-TYPE
        SYNTAX OptixElanSplithrigrpEntry
        MAX-ACCESS not-accessible
        STATUS current
        DESCRIPTION
            "This entry indicates the configuration table of the ETH private network horizon split group."
        INDEX{ optixElanIndex,optixElanSplithrigrpId }
        ::= { optixElanSplithrigrpTable 1 }

    OptixElanSplithrigrpEntry ::=
        SEQUENCE {
            optixElanSplithrigrpId
                Unsigned32,
            optixElanSplithrigrpPortNum
                Unsigned32,
            optixElanSplithrigrpPortTypeList
                OCTET STRING,
            optixElanSplithrigrpPortIdList
                OCTET STRING,
            optixElanSplithrigrpRowStatus
                RowStatus
        }

    -- 1.3.6.1.4.1.2011.2.25.4.50.3.1.8.1.1
    optixElanSplithrigrpId OBJECT-TYPE
        SYNTAX Unsigned32(1..65535)
        MAX-ACCESS not-accessible
        STATUS current
        DESCRIPTION
            "This object indicates the horizon split group ID."
        ::= { optixElanSplithrigrpEntry 1 }

    -- 1.3.6.1.4.1.2011.2.25.4.50.3.1.8.1.2
    optixElanSplithrigrpPortNum OBJECT-TYPE
        SYNTAX Unsigned32(1..65535)
        MAX-ACCESS read-create
        STATUS current
        DESCRIPTION
            "This object indicates the number of logical interfaces."
        ::= { optixElanSplithrigrpEntry 2 }

    -- 1.3.6.1.4.1.2011.2.25.4.50.3.1.8.1.3
    optixElanSplithrigrpPortTypeList OBJECT-TYPE
        SYNTAX OCTET STRING(SIZE(0..1024))
        MAX-ACCESS read-create
        STATUS current
        DESCRIPTION
            "This object indicates the type list of logical interfaces. 1: vuni 2: vnni Each byte indicates the type of the interface."
        ::= { optixElanSplithrigrpEntry 3 }

    -- 1.3.6.1.4.1.2011.2.25.4.50.3.1.8.1.4
    optixElanSplithrigrpPortIdList OBJECT-TYPE
        SYNTAX OCTET STRING(SIZE(0..2048))
        MAX-ACCESS read-create
        STATUS current
        DESCRIPTION
            "This object indicates thelist of logical interface IDs. Each two bytes indicates the port number."
        ::= { optixElanSplithrigrpEntry 4 }

    -- 1.3.6.1.4.1.2011.2.25.4.50.3.1.8.1.255
    optixElanSplithrigrpRowStatus OBJECT-TYPE
        SYNTAX RowStatus
        MAX-ACCESS read-create
        STATUS current
        DESCRIPTION
            "This object indicates the row status. 1: active,4: createAndGo,6: destroy"
        ::= { optixElanSplithrigrpEntry 255 }

    -- 1.3.6.1.4.1.2011.2.25.4.50.3.1.9
    optixElanMacBlackListTable OBJECT-TYPE
        SYNTAX SEQUENCE OF OptixElanMacBlackListEntry
        MAX-ACCESS not-accessible
        STATUS current
        DESCRIPTION
            "This table implements the configurations of the MAC blacklist for an ETH private network to filter packets that are not allowed to forward MAC addresses."
        ::= { optixEthSrvObject 9 }

    -- 1.3.6.1.4.1.2011.2.25.4.50.3.1.9.1
    optixElanMacBlackListEntry OBJECT-TYPE
        SYNTAX OptixElanMacBlackListEntry
        MAX-ACCESS not-accessible
        STATUS current
        DESCRIPTION
            "This entry indicates the configuration table of the black list of the ETH private network MAC addresses."
        INDEX{ optixElanIndex,optixElanMacBlackListVlanId,optixElanMacBlackListMacAddr }
        ::= { optixElanMacBlackListTable 1 }

    OptixElanMacBlackListEntry ::=
        SEQUENCE {
            optixElanMacBlackListVlanId
                Unsigned32,
            optixElanMacBlackListMacAddr
                MacAddress,
            optixElanMacBlackListRowStatus
                RowStatus
        }

    -- 1.3.6.1.4.1.2011.2.25.4.50.3.1.9.1.1
    optixElanMacBlackListVlanId OBJECT-TYPE
        SYNTAX Unsigned32(1..4094|65534)
        MAX-ACCESS not-accessible
        STATUS current
        DESCRIPTION
            "This object indicates the VLAN ID. Valid values: 1-4094. 0xfffe: svl mode."
        ::= { optixElanMacBlackListEntry 1 }

    -- 1.3.6.1.4.1.2011.2.25.4.50.3.1.9.1.2
    optixElanMacBlackListMacAddr OBJECT-TYPE
        SYNTAX MacAddress
        MAX-ACCESS not-accessible
        STATUS current
        DESCRIPTION
            "This object indicates the MAC addresses in the black list."
        ::= { optixElanMacBlackListEntry 2 }

    -- 1.3.6.1.4.1.2011.2.25.4.50.3.1.9.1.255
    optixElanMacBlackListRowStatus OBJECT-TYPE
        SYNTAX RowStatus
        MAX-ACCESS read-create
        STATUS current
        DESCRIPTION
            "This object indicates the row status. 1: active,4: createAndGo,6: destroy"
        ::= { optixElanMacBlackListEntry 255 }

    -- 1.3.6.1.4.1.2011.2.25.4.50.3.1.10
    optixElanStaticMacFdbTable OBJECT-TYPE
        SYNTAX SEQUENCE OF OptixElanStaticMacFdbEntry
        MAX-ACCESS not-accessible
        STATUS current
        DESCRIPTION
            "This table implements the configurations of the static MAC forwarding table for an ETH private network. Static MAC addresses will not be aged."
        ::= { optixEthSrvObject 10 }

    -- 1.3.6.1.4.1.2011.2.25.4.50.3.1.10.1
    optixElanStaticMacFdbEntry OBJECT-TYPE
        SYNTAX OptixElanStaticMacFdbEntry
        MAX-ACCESS not-accessible
        STATUS current
        DESCRIPTION
            "This entry indicates the forwarding table of the ETH private network static MAC addresses."
        INDEX{ optixElanIndex,optixElanStaticMacFdbVlanId,optixElanStaticMacFdbMacAddr }
        ::= { optixElanStaticMacFdbTable 1 }

    OptixElanStaticMacFdbEntry ::=
        SEQUENCE {
            optixElanStaticMacFdbVlanId
                Unsigned32,
            optixElanStaticMacFdbMacAddr
                MacAddress,
            optixElanStaticMacFdbOutPortType
                INTEGER,
            optixElanStaticMacFdbOutPortId
                Unsigned32,
            optixElanStaticMacFdbRowStatus
                RowStatus
        }

    -- 1.3.6.1.4.1.2011.2.25.4.50.3.1.10.1.1
    optixElanStaticMacFdbVlanId OBJECT-TYPE
        SYNTAX Unsigned32(1..4094|65534)
        MAX-ACCESS not-accessible
        STATUS current
        DESCRIPTION
            "This object indicates the VLAN ID. Valid values: 1-4094. 0xfffe: svl mode."
        ::= { optixElanStaticMacFdbEntry 1 }

    -- 1.3.6.1.4.1.2011.2.25.4.50.3.1.10.1.2
    optixElanStaticMacFdbMacAddr OBJECT-TYPE
        SYNTAX MacAddress
        MAX-ACCESS not-accessible
        STATUS current
        DESCRIPTION
            "This object indicates the MAC address, which is an unicast address."
        ::= { optixElanStaticMacFdbEntry 2 }

    -- 1.3.6.1.4.1.2011.2.25.4.50.3.1.10.1.3
    optixElanStaticMacFdbOutPortType OBJECT-TYPE
        SYNTAX INTEGER
        {
            vuni(1),
            vnni(2)
        }
        MAX-ACCESS read-create
        STATUS current
        DESCRIPTION
            "This object indicates the type of the logical destination interface of the MAC address. 1: vuni 2: vnni"
        ::= { optixElanStaticMacFdbEntry 3 }

    -- 1.3.6.1.4.1.2011.2.25.4.50.3.1.10.1.4
    optixElanStaticMacFdbOutPortId OBJECT-TYPE
        SYNTAX Unsigned32
        MAX-ACCESS read-create
        STATUS current
        DESCRIPTION
            "This object indicates the logical destination interface ID of the MAC address."
        ::= { optixElanStaticMacFdbEntry 4 }

    -- 1.3.6.1.4.1.2011.2.25.4.50.3.1.10.1.255
    optixElanStaticMacFdbRowStatus OBJECT-TYPE
        SYNTAX RowStatus
        MAX-ACCESS read-create
        STATUS current
        DESCRIPTION
            "This object indicates the row status. 1: active,4: createAndGo,6: destroy"
        ::= { optixElanStaticMacFdbEntry 255 }

    -- 1.3.6.1.4.1.2011.2.25.4.50.3.1.11
    optixElanMacQueryTable OBJECT-TYPE
        SYNTAX SEQUENCE OF OptixElanMacQueryEntry
        MAX-ACCESS not-accessible
        STATUS current
        DESCRIPTION
            "This table implements the query of the actual static MAC forwarding table for an ETH private network."
        ::= { optixEthSrvObject 11 }

    -- 1.3.6.1.4.1.2011.2.25.4.50.3.1.11.1
    optixElanMacQueryEntry OBJECT-TYPE
        SYNTAX OptixElanMacQueryEntry
        MAX-ACCESS not-accessible
        STATUS current
        DESCRIPTION
            "This entry is used to query the forwarding table of the private network static MAC addresses."
        INDEX{ optixElanIndex,optixElanMacQueryVlanId,optixElanMacQueryMacAddr }
        ::= { optixElanMacQueryTable 1 }

    OptixElanMacQueryEntry ::=
        SEQUENCE {
            optixElanMacQueryVlanId
                Unsigned32,
            optixElanMacQueryMacAddr
                MacAddress,
            optixElanMacQueryMacType
                INTEGER,
            optixElanMacQueryOutPortType
                INTEGER,
            optixElanMacQueryPortParaOne
                Unsigned32,
            optixElanMacQueryPortParaTwo
                Unsigned32,
            optixElanMacQueryPortParaThree
                Unsigned32
        }

    -- 1.3.6.1.4.1.2011.2.25.4.50.3.1.11.1.1
    optixElanMacQueryVlanId OBJECT-TYPE
        SYNTAX Unsigned32(1..4094|65534)
        MAX-ACCESS not-accessible
        STATUS current
        DESCRIPTION
            "This object indicates the VLAN ID. Valid values: 1-4094. 0xfffe: svl mode."
        ::= { optixElanMacQueryEntry 1 }

    -- 1.3.6.1.4.1.2011.2.25.4.50.3.1.11.1.2
    optixElanMacQueryMacAddr OBJECT-TYPE
        SYNTAX MacAddress
        MAX-ACCESS not-accessible
        STATUS current
        DESCRIPTION
            "This object indicates the MAC address, which is an unicast address."
        ::= { optixElanMacQueryEntry 2 }

    -- 1.3.6.1.4.1.2011.2.25.4.50.3.1.11.1.3
    optixElanMacQueryMacType OBJECT-TYPE
        SYNTAX INTEGER
        {
            static(1),
            dynamic(2)
        }
        MAX-ACCESS read-only
        STATUS current
        DESCRIPTION
            "This object indicates the MAC address type. 1: static 2: dynamic"
        ::= { optixElanMacQueryEntry 3 }

    -- 1.3.6.1.4.1.2011.2.25.4.50.3.1.11.1.4
    optixElanMacQueryOutPortType OBJECT-TYPE
        SYNTAX INTEGER
        {
            phyport(1),
            pw(2),
            qinq(3),
            unkown(4)
        }
        MAX-ACCESS read-only
        STATUS current
        DESCRIPTION
            "This object indicates the destination interface type of the MAC address. 1: physical interfaces (including UNIs and NNIs in the phyport type) 2: PW 3: QinQ"
        ::= { optixElanMacQueryEntry 4 }

    -- 1.3.6.1.4.1.2011.2.25.4.50.3.1.11.1.5
    optixElanMacQueryPortParaOne OBJECT-TYPE
        SYNTAX Unsigned32
        MAX-ACCESS read-only
        STATUS current
        DESCRIPTION
            "This object indicates the first parameter of the destination interface ID. When the carrier type is pw, this paramter is invalid and the parameter value is 0xffffffff. When the carrier type is phy port, this parameter indicates the slot ID. When the carrier type is qinq link, this paramter is invalid and the parameter value is 0xffffffff."
        ::= { optixElanMacQueryEntry 5 }

    -- 1.3.6.1.4.1.2011.2.25.4.50.3.1.11.1.6
    optixElanMacQueryPortParaTwo OBJECT-TYPE
        SYNTAX Unsigned32
        MAX-ACCESS read-only
        STATUS current
        DESCRIPTION
            "This object indicates the second parameter of the carrier ID. When the carrier type is pw, this paramter is invalid and the parameter value is 0xffffffff. When the carrier type is phy port, this parameter indicates the subboard ID. When the carrier type is qinq link, this paramter is invalid and the parameter value is 0xffffffff."
        ::= { optixElanMacQueryEntry 6 }

    -- 1.3.6.1.4.1.2011.2.25.4.50.3.1.11.1.7
    optixElanMacQueryPortParaThree OBJECT-TYPE
        SYNTAX Unsigned32
        MAX-ACCESS read-only
        STATUS current
        DESCRIPTION
            "This object indicates the third parameter of the carrier ID. When the carrier type is pw, this parameter indicates the PW index. When the carrier type is phy port, this parameter indicates the port number. When the carrier type is Qinq Link, this parameter indicates the QinQ link index."
        ::= { optixElanMacQueryEntry 7 }

    -- 1.3.6.1.4.1.2011.2.25.4.50.3.1.12
    optixEthAggregateTable OBJECT-TYPE
        SYNTAX SEQUENCE OF OptixEthAggregateEntry
        MAX-ACCESS not-accessible
        STATUS current
        DESCRIPTION
            "This table implements the configurations of an E-AGGR service, which is shown in themulti-point to point mode in the topology. Devices aggregate services input from multiple UNIs to one UNI or NNI carried by ports or PWs, or aggregate services input from multiple NNIs carried by PWs or ports to one UNI."
        ::= { optixEthSrvObject 12 }

    -- 1.3.6.1.4.1.2011.2.25.4.50.3.1.12.1
    optixEthAggregateEntry OBJECT-TYPE
        SYNTAX OptixEthAggregateEntry
        MAX-ACCESS not-accessible
        STATUS current
        DESCRIPTION
            "This entry indicates the configuration table of the E-AGGR service."
        INDEX{ optixEthAggregateIndex }
        ::= { optixEthAggregateTable 1 }

    OptixEthAggregateEntry ::=
        SEQUENCE {
            optixEthAggregateIndex
                Unsigned32,
            optixEthAggregateId
                Unsigned32,
            optixEthAggregateName
                OCTET STRING,
            optixEthAggregateMtu
                Unsigned32,
            optixEthAggregateTagrole
                INTEGER,
            optixEthAggregateRowStatus
                RowStatus
        }

    -- 1.3.6.1.4.1.2011.2.25.4.50.3.1.12.1.1
    optixEthAggregateIndex OBJECT-TYPE
        SYNTAX Unsigned32
        MAX-ACCESS not-accessible
        STATUS current
        DESCRIPTION
            "This object indicates the service index."
        ::= { optixEthAggregateEntry 1 }

    -- 1.3.6.1.4.1.2011.2.25.4.50.3.1.12.1.2
    optixEthAggregateId OBJECT-TYPE
        SYNTAX Unsigned32
        MAX-ACCESS read-create
        STATUS current
        DESCRIPTION
            "This object indicates the service ID."
        ::= { optixEthAggregateEntry 2 }

    -- 1.3.6.1.4.1.2011.2.25.4.50.3.1.12.1.3
    optixEthAggregateName OBJECT-TYPE
        SYNTAX OCTET STRING(SIZE(0..64))
        MAX-ACCESS read-create
        STATUS current
        DESCRIPTION
            "This object indicates the service name, which is a character string in 64 bytes."
        ::= { optixEthAggregateEntry 3 }

    -- 1.3.6.1.4.1.2011.2.25.4.50.3.1.12.1.4
    optixEthAggregateMtu OBJECT-TYPE
        SYNTAX Unsigned32
        MAX-ACCESS read-create
        STATUS current
        DESCRIPTION
            "This object indicates the packet length."
        DEFVAL{ 1500 }
        ::= { optixEthAggregateEntry 4 }

    -- 1.3.6.1.4.1.2011.2.25.4.50.3.1.12.1.5
    optixEthAggregateTagrole OBJECT-TYPE
        SYNTAX INTEGER
        {
            user(0),
            service(1)
        }
        MAX-ACCESS read-create
        STATUS current
        DESCRIPTION
            "This object indicates the tag role attribute. 1: user 2: service"
        DEFVAL{ 1 }
        ::= { optixEthAggregateEntry 5 }

    -- 1.3.6.1.4.1.2011.2.25.4.50.3.1.12.1.255
    optixEthAggregateRowStatus OBJECT-TYPE
        SYNTAX RowStatus
        MAX-ACCESS read-create
        STATUS current
        DESCRIPTION
            "This object indicates the row status. 1: active,4: createAndGo,6: destroy"
        ::= { optixEthAggregateEntry 255 }

    -- 1.3.6.1.4.1.2011.2.25.4.50.3.1.13
    optixEthAggregateUniTable OBJECT-TYPE
        SYNTAX SEQUENCE OF OptixEthAggregateUniEntry
        MAX-ACCESS not-accessible
        STATUS current
        DESCRIPTION
            "This table implements the configurations of the logical UNI for an E-AGGR service. The UNI refers to the ETH port oriented to the user devices tocarry UNI services. These configurations include the slot ID, subboard ID, port number, and VLAN list."
        ::= { optixEthSrvObject 13 }

    -- 1.3.6.1.4.1.2011.2.25.4.50.3.1.13.1
    optixEthAggregateUniEntry OBJECT-TYPE
        SYNTAX OptixEthAggregateUniEntry
        MAX-ACCESS not-accessible
        STATUS current
        DESCRIPTION
            "This entry indicates the configuration table of the logical UNIs of the E-AGGR service."
        INDEX{ optixEthAggregateIndex,optixEthAggregateUniId }
        ::= { optixEthAggregateUniTable 1 }

    OptixEthAggregateUniEntry ::=
        SEQUENCE {
            optixEthAggregateUniId
                Unsigned32,
            optixEthAggregateUniRole
                INTEGER,
            optixEthAggregateUniBid
                Unsigned32,
            optixEthAggregateUniSubBid
                Unsigned32,
            optixEthAggregateUniPortId
                Unsigned32,
            optixEthAggregateUniVlanNum
                Unsigned32,
            optixEthAggregateUniVlanlist
                OCTET STRING,
            optixEthAggregateUniRowStatus
                RowStatus
        }

    -- 1.3.6.1.4.1.2011.2.25.4.50.3.1.13.1.1
    optixEthAggregateUniId OBJECT-TYPE
        SYNTAX Unsigned32(1..65535)
        MAX-ACCESS not-accessible
        STATUS current
        DESCRIPTION
            "This object indicates the service V-UNI ID. Value range: 1 to 65535."
        ::= { optixEthAggregateUniEntry 1 }

    -- 1.3.6.1.4.1.2011.2.25.4.50.3.1.13.1.2
    optixEthAggregateUniRole OBJECT-TYPE
        SYNTAX INTEGER
        {
            root(1),
            leaf(2)
        }
        MAX-ACCESS read-create
        STATUS current
        DESCRIPTION
            "This object indicates the role of the logical interface. 1: root 2: leaf"
        ::= { optixEthAggregateUniEntry 2 }

    -- 1.3.6.1.4.1.2011.2.25.4.50.3.1.13.1.3
    optixEthAggregateUniBid OBJECT-TYPE
        SYNTAX Unsigned32(1..65535)
        MAX-ACCESS read-create
        STATUS current
        DESCRIPTION
            "This object indicates the slot ID of the service V-UNI. Value range: 1 to 65535."
        ::= { optixEthAggregateUniEntry 3 }

    -- 1.3.6.1.4.1.2011.2.25.4.50.3.1.13.1.4
    optixEthAggregateUniSubBid OBJECT-TYPE
        SYNTAX Unsigned32(1..255)
        MAX-ACCESS read-create
        STATUS current
        DESCRIPTION
            "This object indicates the subboard ID of the service V-UNI. Value range: 1 to 255."
        ::= { optixEthAggregateUniEntry 4 }

    -- 1.3.6.1.4.1.2011.2.25.4.50.3.1.13.1.5
    optixEthAggregateUniPortId OBJECT-TYPE
        SYNTAX Unsigned32(1..65535)
        MAX-ACCESS read-create
        STATUS current
        DESCRIPTION
            "This object indicates the port number of the service V-UNI. Value range: 1 to 65535."
        ::= { optixEthAggregateUniEntry 5 }

    -- 1.3.6.1.4.1.2011.2.25.4.50.3.1.13.1.6
    optixEthAggregateUniVlanNum OBJECT-TYPE
        SYNTAX Unsigned32(0..4094)
        MAX-ACCESS read-create
        STATUS current
        DESCRIPTION
            "This object indicates the number of VLANs of the V-UNI (0: VLAN number of the port). Value range: 0 to 4094."
        ::= { optixEthAggregateUniEntry 6 }

    -- 1.3.6.1.4.1.2011.2.25.4.50.3.1.13.1.7
    optixEthAggregateUniVlanlist OBJECT-TYPE
        SYNTAX OCTET STRING(SIZE(0..512))
        MAX-ACCESS read-create
        STATUS current
        DESCRIPTION
            "This object indicates the list of VLANs of the V-UNI. The number of each bit indicates whether the corresponding VLAN exists. For example, The number of the third bit is 1, indicating that the VLAN ID of the PW is 3."
        ::= { optixEthAggregateUniEntry 7 }

    -- 1.3.6.1.4.1.2011.2.25.4.50.3.1.13.1.255
    optixEthAggregateUniRowStatus OBJECT-TYPE
        SYNTAX RowStatus
        MAX-ACCESS read-create
        STATUS current
        DESCRIPTION
            "This object indicates the row status. 1: active,4: createAndGo,6: destroy"
        ::= { optixEthAggregateUniEntry 255 }

    -- 1.3.6.1.4.1.2011.2.25.4.50.3.1.14
    optixEthAggregateNniTable OBJECT-TYPE
        SYNTAX SEQUENCE OF OptixEthAggregateNniEntry
        MAX-ACCESS not-accessible
        STATUS current
        DESCRIPTION
            "This table implements the configurations of the logical ETH NNIs for an E-AGGR service. The NNI refers to the ETH port oriented to the packet transport network, which is used to configure ETH NNI services. According to the service carrying mode, the NNIs can be classified to: carried by port,caried by PW,carried by QinQ link"
        ::= { optixEthSrvObject 14 }

    -- 1.3.6.1.4.1.2011.2.25.4.50.3.1.14.1
    optixEthAggregateNniEntry OBJECT-TYPE
        SYNTAX OptixEthAggregateNniEntry
        MAX-ACCESS not-accessible
        STATUS current
        DESCRIPTION
            "This entry indicates the configuration table for the NNIs of the E-AGGR service."
        INDEX{ optixEthAggregateIndex,optixEthAggregateNniId }
        ::= { optixEthAggregateNniTable 1 }

    OptixEthAggregateNniEntry ::=
        SEQUENCE {
            optixEthAggregateNniId
                Unsigned32,
            optixEthAggregateNniRole
                INTEGER,
            optixEthAggregateNniType
                INTEGER,
            optixEthAggregateNniParaOne
                Unsigned32,
            optixEthAggregateNniParaTwo
                Unsigned32,
            optixEthAggregateNniParaThree
                Unsigned32,
            optixEthAggregateNniRowStatus
                RowStatus
        }

    -- 1.3.6.1.4.1.2011.2.25.4.50.3.1.14.1.1
    optixEthAggregateNniId OBJECT-TYPE
        SYNTAX Unsigned32
        MAX-ACCESS not-accessible
        STATUS current
        DESCRIPTION
            "This object indicates the service V-NNI ID."
        ::= { optixEthAggregateNniEntry 1 }

    -- 1.3.6.1.4.1.2011.2.25.4.50.3.1.14.1.2
    optixEthAggregateNniRole OBJECT-TYPE
        SYNTAX INTEGER
        {
            root(1),
            leaf(2)
        }
        MAX-ACCESS read-create
        STATUS current
        DESCRIPTION
            "This object indicates the role of the logical interface. 1: root 2: leaf"
        ::= { optixEthAggregateNniEntry 2 }

    -- 1.3.6.1.4.1.2011.2.25.4.50.3.1.14.1.3
    optixEthAggregateNniType OBJECT-TYPE
        SYNTAX INTEGER
        {
            pw(1),
            phyport(3),
            qinq(4)
        }
        MAX-ACCESS read-create
        STATUS current
        DESCRIPTION
            "This object indicates the NNI carrier type. 1: pw 3: phyport 4: qinq"
        ::= { optixEthAggregateNniEntry 3 }

    -- 1.3.6.1.4.1.2011.2.25.4.50.3.1.14.1.4
    optixEthAggregateNniParaOne OBJECT-TYPE
        SYNTAX Unsigned32
        MAX-ACCESS read-create
        STATUS current
        DESCRIPTION
            "This object indicates the first parameter of the carrier ID. When the carrier type is pw, this paramter is invalid and the parameter value is 0xffffffff. When the carrier type is phy port, this parameter indicates the slot ID. When the carrier type is qinq link, this paramter is invalid and the parameter value is 0xffffffff."
        ::= { optixEthAggregateNniEntry 4 }

    -- 1.3.6.1.4.1.2011.2.25.4.50.3.1.14.1.5
    optixEthAggregateNniParaTwo OBJECT-TYPE
        SYNTAX Unsigned32
        MAX-ACCESS read-create
        STATUS current
        DESCRIPTION
            "This object indicates the second parameter of the carrier ID. When the carrier type is pw, this paramter is invalid and the parameter value is 0xffffffff. When the carrier type is phy port, this parameter indicates the subboard ID. When the carrier type is qinq link, this paramter is invalid and the parameter value is 0xffffffff."
        ::= { optixEthAggregateNniEntry 5 }

    -- 1.3.6.1.4.1.2011.2.25.4.50.3.1.14.1.6
    optixEthAggregateNniParaThree OBJECT-TYPE
        SYNTAX Unsigned32
        MAX-ACCESS read-create
        STATUS current
        DESCRIPTION
            "This object indicates the third parameter of the carrier ID. When the carrier type is pw, this parameter indicates the PW index. When the carrier type is phy port, this parameter indicates the port number. When the carrier type is Qinq Link, this parameter indicates the QinQ link index."
        ::= { optixEthAggregateNniEntry 6 }

    -- 1.3.6.1.4.1.2011.2.25.4.50.3.1.14.1.255
    optixEthAggregateNniRowStatus OBJECT-TYPE
        SYNTAX RowStatus
        MAX-ACCESS read-create
        STATUS current
        DESCRIPTION
            "This object indicates the row status. 1: active,4: createAndGo,6: destroy"
        ::= { optixEthAggregateNniEntry 255 }

    -- 1.3.6.1.4.1.2011.2.25.4.50.3.1.15
    optixEthSrvVlanFdbTable OBJECT-TYPE
        SYNTAX SEQUENCE OF OptixEthSrvVlanFdbEntry
        MAX-ACCESS not-accessible
        STATUS current
        DESCRIPTION
            "Thistable implements the VLAN interaction function for a private line or E-AGGR service and the exchange of VLAN labelsfrom both ends of the service."
        ::= { optixEthSrvObject 15 }

    -- 1.3.6.1.4.1.2011.2.25.4.50.3.1.15.1
    optixEthSrvVlanFdbEntry OBJECT-TYPE
        SYNTAX OptixEthSrvVlanFdbEntry
        MAX-ACCESS not-accessible
        STATUS current
        DESCRIPTION
            "This entry is used to configure the VLAN interaction function for ETH private line and E-AGGR services."
        INDEX{ optixEthSrvIndex,optixEthSrvVlanFdbId }
        ::= { optixEthSrvVlanFdbTable 1 }

    OptixEthSrvVlanFdbEntry ::=
        SEQUENCE {
            optixEthSrvIndex
                Unsigned32,
            optixEthSrvVlanFdbId
                Unsigned32,
            optixEthSrvVlanFdbInPortId
                Unsigned32,
            optixEthSrvVlanFdbInPortType
                INTEGER,
            optixEthSrvVlanFdbInVlanId
                Unsigned32,
            optixEthSrvVlanFdbOutPortId
                Unsigned32,
            optixEthSrvVlanFdbOutPortType
                INTEGER,
            optixEthSrvVlanFdbOutVlanId
                Unsigned32,
            optixEthSrvVlanFdbRowStatus
                RowStatus
        }

    -- 1.3.6.1.4.1.2011.2.25.4.50.3.1.15.1.1
    optixEthSrvIndex OBJECT-TYPE
        SYNTAX Unsigned32
        MAX-ACCESS not-accessible
        STATUS current
        DESCRIPTION
            "This object indicates the index to an ETH private line or AGGR service."
        ::= { optixEthSrvVlanFdbEntry 1 }

    -- 1.3.6.1.4.1.2011.2.25.4.50.3.1.15.1.2
    optixEthSrvVlanFdbId OBJECT-TYPE
        SYNTAX Unsigned32(1..65535)
        MAX-ACCESS not-accessible
        STATUS current
        DESCRIPTION
            "This object indicates the VLAN forwarding table ID. Value range: 1 to 65535."
        ::= { optixEthSrvVlanFdbEntry 2 }

    -- 1.3.6.1.4.1.2011.2.25.4.50.3.1.15.1.3
    optixEthSrvVlanFdbInPortId OBJECT-TYPE
        SYNTAX Unsigned32
        MAX-ACCESS read-create
        STATUS current
        DESCRIPTION
            "This object indicates the logical input interface ID of the VLANforwarding table."
        ::= { optixEthSrvVlanFdbEntry 3 }

    -- 1.3.6.1.4.1.2011.2.25.4.50.3.1.15.1.4
    optixEthSrvVlanFdbInPortType OBJECT-TYPE
        SYNTAX INTEGER
        {
            vuni(1),
            vnni(2)
        }
        MAX-ACCESS read-create
        STATUS current
        DESCRIPTION
            "This object indicates the logical input interfacetype of the VLAN forwarding table. 1: vuni 2: vnni"
        ::= { optixEthSrvVlanFdbEntry 4 }

    -- 1.3.6.1.4.1.2011.2.25.4.50.3.1.15.1.5
    optixEthSrvVlanFdbInVlanId OBJECT-TYPE
        SYNTAX Unsigned32(1..4094)
        MAX-ACCESS read-create
        STATUS current
        DESCRIPTION
            "This object indicates the input VLAN ID of the VLAN forwarding table. Value range: 1 to 4094."
        ::= { optixEthSrvVlanFdbEntry 5 }

    -- 1.3.6.1.4.1.2011.2.25.4.50.3.1.15.1.6
    optixEthSrvVlanFdbOutPortId OBJECT-TYPE
        SYNTAX Unsigned32
        MAX-ACCESS read-create
        STATUS current
        DESCRIPTION
            "This object indicates the logical output interface ID of the VLAN forwarding table."
        ::= { optixEthSrvVlanFdbEntry 6 }

    -- 1.3.6.1.4.1.2011.2.25.4.50.3.1.15.1.7
    optixEthSrvVlanFdbOutPortType OBJECT-TYPE
        SYNTAX INTEGER
        {
            vuni(1),
            vnni(2)
        }
        MAX-ACCESS read-create
        STATUS current
        DESCRIPTION
            "This object indicates the logical output interface type of the VLAN forwarding table. 1: vuni 2: vnni"
        ::= { optixEthSrvVlanFdbEntry 7 }

    -- 1.3.6.1.4.1.2011.2.25.4.50.3.1.15.1.8
    optixEthSrvVlanFdbOutVlanId OBJECT-TYPE
        SYNTAX Unsigned32(1..4094)
        MAX-ACCESS read-create
        STATUS current
        DESCRIPTION
            "This object indicates the output VLAN ID of the VLAN forwarding table. Value range: 1 to 4094."
        ::= { optixEthSrvVlanFdbEntry 8 }

    -- 1.3.6.1.4.1.2011.2.25.4.50.3.1.15.1.255
    optixEthSrvVlanFdbRowStatus OBJECT-TYPE
        SYNTAX RowStatus
        MAX-ACCESS read-create
        STATUS current
        DESCRIPTION
            "This object indicates the row status. 1: active,4: createAndGo,6: destroy"
        ::= { optixEthSrvVlanFdbEntry 255 }

    -- 1.3.6.1.4.1.2011.2.25.4.50.3.1.16
    optixElanVlanFilterTable OBJECT-TYPE
        SYNTAX SEQUENCE OF OptixElanVlanFilterEntry
        MAX-ACCESS not-accessible
        STATUS current
        DESCRIPTION
            "This MIB implements the configurations of the UNI VLAN filtering table for an ETH private network service. This UNI receives VLANs according to the configurations of the filtering table."
        ::= { optixEthSrvObject 16 }

    -- 1.3.6.1.4.1.2011.2.25.4.50.3.1.16.1
    optixElanVlanFilterEntry OBJECT-TYPE
        SYNTAX OptixElanVlanFilterEntry
        MAX-ACCESS not-accessible
        STATUS current
        DESCRIPTION
            "This entry indicates the configuration table of the VLAN filtering table for ETH private network UNIs."
        INDEX{ optixElanIndex,optixElanVlanFilterUniId }
        ::= { optixElanVlanFilterTable 1 }

    OptixElanVlanFilterEntry ::=
        SEQUENCE {
            optixElanVlanFilterUniId
                Unsigned32,
            optixElanVlanFilterVlanNum
                Unsigned32,
            optixElanVlanFilterVlanlist
                OCTET STRING,
            optixElanVlanFilterRowStatus
                RowStatus
        }

    -- 1.3.6.1.4.1.2011.2.25.4.50.3.1.16.1.1
    optixElanVlanFilterUniId OBJECT-TYPE
        SYNTAX Unsigned32(1..65535)
        MAX-ACCESS not-accessible
        STATUS current
        DESCRIPTION
            "This object indicates the V-UNI ID of theprivate network service. Value range: 1 to 65535."
        ::= { optixElanVlanFilterEntry 1 }

    -- 1.3.6.1.4.1.2011.2.25.4.50.3.1.16.1.2
    optixElanVlanFilterVlanNum OBJECT-TYPE
        SYNTAX Unsigned32(0..4094)
        MAX-ACCESS read-create
        STATUS current
        DESCRIPTION
            "This object indicates the VLAN number of the VLAN filtering table for the service V-UNI. Value range: 0 to 4094."
        ::= { optixElanVlanFilterEntry 2 }

    -- 1.3.6.1.4.1.2011.2.25.4.50.3.1.16.1.3
    optixElanVlanFilterVlanlist OBJECT-TYPE
        SYNTAX OCTET STRING(SIZE(0..512))
        MAX-ACCESS read-create
        STATUS current
        DESCRIPTION
            "This object indicates the list of VLANs of the V-UNI. The number of each bit indicates whether the corresponding VLAN exists. For example, The number of the third bit is 1, indicating that the VLAN ID of the PW is 3."
        ::= { optixElanVlanFilterEntry 3 }

    -- 1.3.6.1.4.1.2011.2.25.4.50.3.1.16.1.255
    optixElanVlanFilterRowStatus OBJECT-TYPE
        SYNTAX RowStatus
        MAX-ACCESS read-create
        STATUS current
        DESCRIPTION
            "This object indicates the row status. 1: active,4: createAndGo,6: destroy"
        ::= { optixElanVlanFilterEntry 255 }

    -- 1.3.6.1.4.1.2011.2.25.4.50.3.1.17
    optixVplsVlanNum OBJECT-TYPE
        SYNTAX Unsigned32 (1..4096)
        MAX-ACCESS read-only
        STATUS current
        DESCRIPTION
            "This object is usd to configure the number of VLAN supported by the VPLS service (NE attribute) and the usage of VPLS services for RTN products. Value range: 1 to 4096."
        ::= { optixEthSrvObject 17 }

    -- 1.3.6.1.4.1.2011.2.25.4.50.3.1.18
    optixVplsSVlanTpid OBJECT-TYPE
        SYNTAX Unsigned32 (1536..65535)
        MAX-ACCESS read-write
        STATUS current
        DESCRIPTION
            "This object is usd to configure the TP ID of Service VLAN supported by the VPLS service's PW(NE attribute) and the usage of VPLS services for RTN products. Value range: 1536 to 65535."
        DEFVAL{ 34984 }
        ::= { optixEthSrvObject 18 }

    -- 1.3.6.1.4.1.2011.2.25.4.50.3.1.19
    optixEthForWardMode OBJECT-TYPE
        SYNTAX INTEGER
        {
            center(1),
            local(2)
        }
        MAX-ACCESS read-write
        STATUS current
        DESCRIPTION
            "This object is used to configure the Ethernet forwarding mode."
        ::= { optixEthSrvObject 19 }

    -- 1.3.6.1.4.1.2011.2.25.4.50.3.1.20
    optixElanSrvTrapMember OBJECT IDENTIFIER ::= { optixEthSrvObject 20 }

    -- 1.3.6.1.4.1.2011.2.25.4.50.3.1.20.1
    optixElanSrvTrapServerIndex OBJECT-TYPE
        SYNTAX Unsigned32
        MAX-ACCESS accessible-for-notify
        STATUS current
        DESCRIPTION
            "This parameter indicates the service index of the reported event."
        ::= { optixElanSrvTrapMember 1 }

    -- 1.3.6.1.4.1.2011.2.25.4.50.3.1.20.2
    optixElanSrvTrapFrameSize OBJECT-TYPE
        SYNTAX Unsigned32
        MAX-ACCESS accessible-for-notify
        STATUS current
        DESCRIPTION
            "This parameter indicates the frame size of the reported event."
        ::= { optixElanSrvTrapMember 2 }

    -- 1.3.6.1.4.1.2011.2.25.4.50.3.1.20.3
    optixElanSrvTrapTrafficRatio OBJECT-TYPE
        SYNTAX Unsigned32 (1..100)
        MAX-ACCESS accessible-for-notify
        STATUS current
        DESCRIPTION
            "This parameter indicates the throughput ratio of the reported event. Range: 1-100; unit: %"
        ::= { optixElanSrvTrapMember 3 }

    -- 1.3.6.1.4.1.2011.2.25.4.50.3.1.20.4
    optixElanSrvTrapSendPktNum OBJECT-TYPE
        SYNTAX OCTET STRING
        MAX-ACCESS accessible-for-notify
        STATUS current
        DESCRIPTION
            "This parameter indicates the number of sent packets in the reported event."
        ::= { optixElanSrvTrapMember 4 }

    -- 1.3.6.1.4.1.2011.2.25.4.50.3.1.20.5
    optixElanSrvTrapRecPktNum OBJECT-TYPE
        SYNTAX OCTET STRING
        MAX-ACCESS accessible-for-notify
        STATUS current
        DESCRIPTION
            "This parameter indicates the number of received packets in the reported event."
        ::= { optixElanSrvTrapMember 5 }

    -- 1.3.6.1.4.1.2011.2.25.4.50.3.1.20.6
    optixElanSrvTrapLossRatio OBJECT-TYPE
        SYNTAX Unsigned32 (0..10000)
        MAX-ACCESS accessible-for-notify
        STATUS current
        DESCRIPTION
            "This parameter indicates the packet loss ratio in the reported event.Range: 1-10000; unit:0.01%"
        ::= { optixElanSrvTrapMember 6 }

    -- 1.3.6.1.4.1.2011.2.25.4.50.3.1.20.7
    optixElanSrvTrapProgress OBJECT-TYPE
        SYNTAX Unsigned32 (1..100)
        MAX-ACCESS accessible-for-notify
        STATUS current
        DESCRIPTION
            "This parameter indicates the task progress.Range: 1-100; unit:%"
        ::= { optixElanSrvTrapMember 7 }

    -- 1.3.6.1.4.1.2011.2.25.4.50.3.1.20.8
    optixElanSrvTrapTraffic OBJECT-TYPE
        SYNTAX Unsigned32
        MAX-ACCESS accessible-for-notify
        STATUS current
        DESCRIPTION
            "This parameter indicates the throughput of the reported event.Unit: kbit/s"
        ::= { optixElanSrvTrapMember 8 }

    -- 1.3.6.1.4.1.2011.2.25.4.50.3.1.20.9
    optixElanSrvTrapDelay OBJECT-TYPE
        SYNTAX Unsigned32
        MAX-ACCESS accessible-for-notify
        STATUS current
        DESCRIPTION
            "This parameter indicates the delay of the reported event. Unit: us"
        ::= { optixElanSrvTrapMember 9 }

    -- 1.3.6.1.4.1.2011.2.25.4.50.3.1.20.10
    optixElanSrvTrapResult OBJECT-TYPE
        SYNTAX Unsigned32
        MAX-ACCESS accessible-for-notify
        STATUS current
        DESCRIPTION
            "This parameter indicates the test ending status. 
0: The test is ended normally. 
Others: The test is ended abnormally (with an error code)."
        ::= { optixElanSrvTrapMember 10 }

    -- 1.3.6.1.4.1.2011.2.25.4.50.3.1.21
    optixElanSrvTrapEvent OBJECT IDENTIFIER ::= { optixEthSrvObject 21 }

    -- 1.3.6.1.4.1.2011.2.25.4.50.3.1.21.1
    optixElanSrvTrapLTLossRatioTrap NOTIFICATION-TYPE
        OBJECTS{ optixElanSrvTrapServerIndex,optixElanSrvTrapFrameSize,optixElanSrvTrapTrafficRatio,optixElanSrvTrapSendPktNum,optixElanSrvTrapRecPktNum,optixElanSrvTrapLossRatio }
        STATUS current
        DESCRIPTION
            "This parameter indicates that the long-term packet loss test result event is reported."
        ::= { optixElanSrvTrapEvent 1 }

    -- 1.3.6.1.4.1.2011.2.25.4.50.3.1.21.2
    optixElanSrvTrapLossRatioTrap NOTIFICATION-TYPE
        OBJECTS{ optixElanSrvTrapServerIndex,optixElanSrvTrapFrameSize,optixElanSrvTrapTrafficRatio,optixElanSrvTrapLossRatio,optixElanSrvTrapProgress }
        STATUS current
        DESCRIPTION
            "This parameter indicates that the packet loss result event is reported."
        ::= { optixElanSrvTrapEvent 2 }

    -- 1.3.6.1.4.1.2011.2.25.4.50.3.1.21.3
    optixElanSrvThroughputTrap NOTIFICATION-TYPE
        OBJECTS{ optixElanSrvTrapServerIndex,optixElanSrvTrapFrameSize,optixElanSrvTrapTraffic,optixElanSrvTrapProgress }
        STATUS current
        DESCRIPTION
            "This parameter indicates that the througput result event is reported."
        ::= { optixElanSrvTrapEvent 3 }

    -- 1.3.6.1.4.1.2011.2.25.4.50.3.1.21.4
    optixElanSrvTrapRspLatencyTrap NOTIFICATION-TYPE
        OBJECTS{ optixElanSrvTrapServerIndex,optixElanSrvTrapFrameSize,optixElanSrvTrapTrafficRatio,optixElanSrvTrapDelay,optixElanSrvTrapProgress }
        STATUS current
        DESCRIPTION
            "This parameter indicates that the delay result event is reported."
        ::= { optixElanSrvTrapEvent 4 }

    -- 1.3.6.1.4.1.2011.2.25.4.50.3.1.21.5
    optixElanSrvTrapAutoTestEndTrap NOTIFICATION-TYPE
        OBJECTS{ optixElanSrvTrapServerIndex,optixElanSrvTrapResult }
        STATUS current
        DESCRIPTION
            "This parameter indicates the throughput, packet loss, and delay test ending events are reported."
        ::= { optixElanSrvTrapEvent 5 }

    -- 1.3.6.1.4.1.2011.2.25.4.50.3.1.21.6
    optixElanSrvTrapNeEndPktLossTrap NOTIFICATION-TYPE
        OBJECTS{ optixElanSrvTrapServerIndex,optixElanSrvTrapFrameSize,optixElanSrvTrapTrafficRatio,optixElanSrvTrapLossRatio,optixElanSrvTrapProgress }
        STATUS current
        DESCRIPTION
            "This parameter indicates that the near-end packet loss event is reported."
        ::= { optixElanSrvTrapEvent 6 }

    -- 1.3.6.1.4.1.2011.2.25.4.50.3.1.22
    optixEthAutoTestTable OBJECT-TYPE
        SYNTAX SEQUENCE OF OptixEthAutoTestEntry
        MAX-ACCESS not-accessible
        STATUS current
        DESCRIPTION
            "This table implements the auto-test function."
        ::= { optixEthSrvObject 22 }

    -- 1.3.6.1.4.1.2011.2.25.4.50.3.1.22.1
    optixEthAutoTestEntry OBJECT-TYPE
        SYNTAX OptixEthAutoTestEntry
        MAX-ACCESS not-accessible
        STATUS current
        DESCRIPTION
            "This entry implements the auto-test function."
        INDEX{ optixEthSrvIndex }
        ::= { optixEthAutoTestTable 1 }

    OptixEthAutoTestEntry ::=
        SEQUENCE {
            optixEthAutoTestvuni
                Unsigned32,
            optixEthAutoTestBID
                Unsigned32,
            optixEthAutoTestSubBID
                Unsigned32,
            optixEthAutoTestPID
                Unsigned32,
            optixEthAutoTestState
                INTEGER,
            optixEthAutoTestPort
                INTEGER,
            optixEthAutoTestName
                OCTET STRING,
            optixEthAutoTestAction
                INTEGER,
            optixEthAutoTestLongtermFrameSize
                Unsigned32,
            optixEthAutoTestLongtermTrafficRadio
                Unsigned32,
            optixEthAutoTestLongtermAction
                INTEGER,
            optixEthAutoTestFrameLen
                Unsigned32
        }

    -- 1.3.6.1.4.1.2011.2.25.4.50.3.1.22.1.1
    optixEthAutoTestvuni OBJECT-TYPE
        SYNTAX Unsigned32
        MAX-ACCESS read-write
        STATUS current
        DESCRIPTION
            "This object indicates the service V-UNI ID used in the auto-test."
        ::= { optixEthAutoTestEntry 1 }

    -- 1.3.6.1.4.1.2011.2.25.4.50.3.1.22.1.2
    optixEthAutoTestBID OBJECT-TYPE
        SYNTAX Unsigned32
        MAX-ACCESS read-only
        STATUS current
        DESCRIPTION
            "This entry implements the board ID used in the auto-test."
        ::= { optixEthAutoTestEntry 2 }

    -- 1.3.6.1.4.1.2011.2.25.4.50.3.1.22.1.3
    optixEthAutoTestSubBID OBJECT-TYPE
        SYNTAX Unsigned32
        MAX-ACCESS read-only
        STATUS current
        DESCRIPTION
            "This entry implements the subboard ID used in the auto-test."
        ::= { optixEthAutoTestEntry 3 }

    -- 1.3.6.1.4.1.2011.2.25.4.50.3.1.22.1.4
    optixEthAutoTestPID OBJECT-TYPE
        SYNTAX Unsigned32
        MAX-ACCESS read-only
        STATUS current
        DESCRIPTION
            "This entry implements the port ID used in the auto-test."
        ::= { optixEthAutoTestEntry 4 }

    -- 1.3.6.1.4.1.2011.2.25.4.50.3.1.22.1.5
    optixEthAutoTestState OBJECT-TYPE
        SYNTAX INTEGER
        {
            disable(0),
            enable(1)
        }
        MAX-ACCESS read-write
        STATUS current
        DESCRIPTION
            "This object indicates the auto-test enable status."
        ::= { optixEthAutoTestEntry 5 }

    -- 1.3.6.1.4.1.2011.2.25.4.50.3.1.22.1.6
    optixEthAutoTestPort OBJECT-TYPE
        SYNTAX INTEGER
        {
            source(0),
            dest(1)
        }
        MAX-ACCESS read-write
        STATUS current
        DESCRIPTION
            "This object indicates the port information used in the auto-test."
        ::= { optixEthAutoTestEntry 6 }

    -- 1.3.6.1.4.1.2011.2.25.4.50.3.1.22.1.7
    optixEthAutoTestName OBJECT-TYPE
        SYNTAX OCTET STRING (SIZE(0..64))
        MAX-ACCESS read-write
        STATUS current
        DESCRIPTION
            "This object indicates the auto-test name."
        ::= { optixEthAutoTestEntry 7 }

    -- 1.3.6.1.4.1.2011.2.25.4.50.3.1.22.1.8
    optixEthAutoTestAction OBJECT-TYPE
        SYNTAX INTEGER
        {
            stop(0),
            start(1)
        }
        MAX-ACCESS read-write
        STATUS current
        DESCRIPTION
            "This object indicates the start or end of the auto-test."
        ::= { optixEthAutoTestEntry 8 }

    -- 1.3.6.1.4.1.2011.2.25.4.50.3.1.22.1.9
    optixEthAutoTestLongtermFrameSize OBJECT-TYPE
        SYNTAX Unsigned32
        MAX-ACCESS read-write
        STATUS current
        DESCRIPTION
            "This object indicates the frame size used in the long-term auto-test."
        ::= { optixEthAutoTestEntry 9 }

    -- 1.3.6.1.4.1.2011.2.25.4.50.3.1.22.1.10
    optixEthAutoTestLongtermTrafficRadio OBJECT-TYPE
        SYNTAX Unsigned32
        MAX-ACCESS read-write
        STATUS current
        DESCRIPTION
            "This object indicates the throughput percentage used in the long-term auto-test."
        ::= { optixEthAutoTestEntry 10 }

    -- 1.3.6.1.4.1.2011.2.25.4.50.3.1.22.1.11
    optixEthAutoTestLongtermAction OBJECT-TYPE
        SYNTAX INTEGER
        {
            stop(0),
            start(1)
        }
        MAX-ACCESS read-write
        STATUS current
        DESCRIPTION
            "This object indicates the start or end of the long-term auto-test."
        ::= { optixEthAutoTestEntry 11 }

    -- 1.3.6.1.4.1.2011.2.25.4.50.3.1.22.1.12
    optixEthAutoTestFrameLen OBJECT-TYPE
        SYNTAX Unsigned32
        MAX-ACCESS read-write
        STATUS current
        DESCRIPTION
            "This object indicates the frame length used in the auto-test."
        ::= { optixEthAutoTestEntry 12 }

    -- 1.3.6.1.4.1.2011.2.25.4.50.3.1.23
    optixEthAutoTestReportTable OBJECT-TYPE
        SYNTAX SEQUENCE OF OptixEthAutoTestReportEntry
        MAX-ACCESS not-accessible
        STATUS current
        DESCRIPTION
            "This table implements the auto-test report."
        ::= { optixEthSrvObject 23 }

    -- 1.3.6.1.4.1.2011.2.25.4.50.3.1.23.1
    optixEthAutoTestReportEntry OBJECT-TYPE
        SYNTAX OptixEthAutoTestReportEntry
        MAX-ACCESS not-accessible
        STATUS current
        DESCRIPTION
            "This entry implements the auto-test report."
        INDEX{ optixEthSrvIndex,optixEthAutoTestReportNo }
        ::= { optixEthAutoTestReportTable 1 }

    OptixEthAutoTestReportEntry ::=
        SEQUENCE {
            optixEthAutoTestReportNo
                Unsigned32,
            optixEthAutoTestReportResultType
                Unsigned32,
            optixEthAutoTestReportProgress
                Unsigned32,
            optixEthAutoTestReportFrameSize
                Unsigned32,
            optixEthAutoTestReportTraffic
                Unsigned32,
            optixEthAutoTestReportSendPkt
                Counter64,
            optixEthAutoTestReportRecPkt
                Counter64,
            optixEthAutoTestReportLR80
                Unsigned32,
            optixEthAutoTestReportLR90
                Unsigned32,
            optixEthAutoTestReportLR100
                Unsigned32,
            optixEthAutoTestReportDelay80
                Unsigned32,
            optixEthAutoTestReportDelay90
                Unsigned32,
            optixEthAutoTestReportDelay100
                Unsigned32,
            optixEthAutoTestReportBeginTime
                DateAndTime,
            optixEthAutoTestReportEndTime
                DateAndTime
        }

    -- 1.3.6.1.4.1.2011.2.25.4.50.3.1.23.1.1
    optixEthAutoTestReportNo OBJECT-TYPE
        SYNTAX Unsigned32
        MAX-ACCESS not-accessible
        STATUS current
        DESCRIPTION
            "This object indicates the sequence number of the auto test result."
        ::= { optixEthAutoTestReportEntry 1 }

    -- 1.3.6.1.4.1.2011.2.25.4.50.3.1.23.1.2
    optixEthAutoTestReportResultType OBJECT-TYPE
        SYNTAX Unsigned32
        MAX-ACCESS read-only
        STATUS current
        DESCRIPTION
            "This object indicates the auto-test type."
        ::= { optixEthAutoTestReportEntry 2 }

    -- 1.3.6.1.4.1.2011.2.25.4.50.3.1.23.1.3
    optixEthAutoTestReportProgress OBJECT-TYPE
        SYNTAX Unsigned32
        MAX-ACCESS read-only
        STATUS current
        DESCRIPTION
            "This object indicates the auto-test progress."
        ::= { optixEthAutoTestReportEntry 3 }

    -- 1.3.6.1.4.1.2011.2.25.4.50.3.1.23.1.4
    optixEthAutoTestReportFrameSize OBJECT-TYPE
        SYNTAX Unsigned32
        MAX-ACCESS read-only
        STATUS current
        DESCRIPTION
            "This object indicates the frame size in the auto-test result."
        ::= { optixEthAutoTestReportEntry 4 }

    -- 1.3.6.1.4.1.2011.2.25.4.50.3.1.23.1.5
    optixEthAutoTestReportTraffic OBJECT-TYPE
        SYNTAX Unsigned32
        MAX-ACCESS read-only
        STATUS current
        DESCRIPTION
            "This object indicates the throughput in the auto-test result."
        ::= { optixEthAutoTestReportEntry 5 }

    -- 1.3.6.1.4.1.2011.2.25.4.50.3.1.23.1.6
    optixEthAutoTestReportSendPkt OBJECT-TYPE
        SYNTAX Counter64
        MAX-ACCESS read-only
        STATUS current
        DESCRIPTION
            "This object indicates the number of sent packages in the auto-test result."
        ::= { optixEthAutoTestReportEntry 6 }

    -- 1.3.6.1.4.1.2011.2.25.4.50.3.1.23.1.7
    optixEthAutoTestReportRecPkt OBJECT-TYPE
        SYNTAX Counter64
        MAX-ACCESS read-only
        STATUS current
        DESCRIPTION
            "This object indicates the number of received packages in the auto-test result."
        ::= { optixEthAutoTestReportEntry 7 }

    -- 1.3.6.1.4.1.2011.2.25.4.50.3.1.23.1.8
    optixEthAutoTestReportLR80 OBJECT-TYPE
        SYNTAX Unsigned32
        MAX-ACCESS read-only
        STATUS current
        DESCRIPTION
            "This object indicates the packet loss rate in case of 80% throughput in the auto-test result."
        ::= { optixEthAutoTestReportEntry 8 }

    -- 1.3.6.1.4.1.2011.2.25.4.50.3.1.23.1.9
    optixEthAutoTestReportLR90 OBJECT-TYPE
        SYNTAX Unsigned32
        MAX-ACCESS read-only
        STATUS current
        DESCRIPTION
            "This object indicates the packet loss rate in case of 90% throughput in the auto-test result."
        ::= { optixEthAutoTestReportEntry 9 }

    -- 1.3.6.1.4.1.2011.2.25.4.50.3.1.23.1.10
    optixEthAutoTestReportLR100 OBJECT-TYPE
        SYNTAX Unsigned32
        MAX-ACCESS read-only
        STATUS current
        DESCRIPTION
            "This object indicates the packet loss rate in case of 100% throughput in the auto-test result."
        ::= { optixEthAutoTestReportEntry 10 }

    -- 1.3.6.1.4.1.2011.2.25.4.50.3.1.23.1.11
    optixEthAutoTestReportDelay80 OBJECT-TYPE
        SYNTAX Unsigned32
        MAX-ACCESS read-only
        STATUS current
        DESCRIPTION
            "This object indicates the delay in case of 80% throughput in the auto-test result."
        ::= { optixEthAutoTestReportEntry 11 }

    -- 1.3.6.1.4.1.2011.2.25.4.50.3.1.23.1.12
    optixEthAutoTestReportDelay90 OBJECT-TYPE
        SYNTAX Unsigned32
        MAX-ACCESS read-only
        STATUS current
        DESCRIPTION
            "This object indicates the delay in case of 90% throughput in the auto-test result."
        ::= { optixEthAutoTestReportEntry 12 }

    -- 1.3.6.1.4.1.2011.2.25.4.50.3.1.23.1.13
    optixEthAutoTestReportDelay100 OBJECT-TYPE
        SYNTAX Unsigned32
        MAX-ACCESS read-only
        STATUS current
        DESCRIPTION
            "This object indicates the delay in case of 100% throughput in the auto-test result."
        ::= { optixEthAutoTestReportEntry 13 }

    -- 1.3.6.1.4.1.2011.2.25.4.50.3.1.23.1.14
    optixEthAutoTestReportBeginTime OBJECT-TYPE
        SYNTAX DateAndTime
        MAX-ACCESS read-only
        STATUS current
        DESCRIPTION
            "This object indicates the auto-test start time."
        ::= { optixEthAutoTestReportEntry 14 }

    -- 1.3.6.1.4.1.2011.2.25.4.50.3.1.23.1.15
    optixEthAutoTestReportEndTime OBJECT-TYPE
        SYNTAX DateAndTime
        MAX-ACCESS read-only
        STATUS current
        DESCRIPTION
            "This object indicates the auto-test end time."
        ::= { optixEthAutoTestReportEntry 15 }

    -- 1.3.6.1.4.1.2011.2.25.4.50.3.1.24
    optixSrvMacTable OBJECT-TYPE
        SYNTAX SEQUENCE OF OptixSrvMacEntry
        MAX-ACCESS not-accessible
        STATUS current
        DESCRIPTION
            "This table implements the query of the current MAC address quantity."
        ::= { optixEthSrvObject 24 }

    -- 1.3.6.1.4.1.2011.2.25.4.50.3.1.24.1
    optixSrvMacEntry OBJECT-TYPE
        SYNTAX OptixSrvMacEntry
        MAX-ACCESS not-accessible
        STATUS current
        DESCRIPTION
            "This entry is used to query the MAC address quantity."
        INDEX{ optixSrvMacSrvIndex,optixSrvMacBoardID,optixSrvMacTypeFlag }
        ::= { optixSrvMacTable 1 }

    OptixSrvMacEntry ::=
        SEQUENCE {
            optixSrvMacSrvIndex
                Unsigned32,
            optixSrvMacBoardID
                Unsigned32,
            optixSrvMacTypeFlag
                INTEGER,
            optixSrvMacNum
                Unsigned32
        }

    -- 1.3.6.1.4.1.2011.2.25.4.50.3.1.24.1.1
    optixSrvMacSrvIndex OBJECT-TYPE
        SYNTAX Unsigned32
        MAX-ACCESS not-accessible
        STATUS current
        DESCRIPTION
            "This object indicates the service index."
        ::= { optixSrvMacEntry 1 }

    -- 1.3.6.1.4.1.2011.2.25.4.50.3.1.24.1.2
    optixSrvMacBoardID OBJECT-TYPE
        SYNTAX Unsigned32
        MAX-ACCESS not-accessible
        STATUS current
        DESCRIPTION
            "This object indicates the board ID."
        ::= { optixSrvMacEntry 2 }

    -- 1.3.6.1.4.1.2011.2.25.4.50.3.1.24.1.3
    optixSrvMacTypeFlag OBJECT-TYPE
        SYNTAX INTEGER
        {
            staticmac(0),
            dynamicmac(1),
            blackmac(2)
        }
        MAX-ACCESS not-accessible
        STATUS current
        DESCRIPTION
            "This object indicates the MAC address type flag."
        ::= { optixSrvMacEntry 3 }

    -- 1.3.6.1.4.1.2011.2.25.4.50.3.1.24.1.4
    optixSrvMacNum OBJECT-TYPE
        SYNTAX Unsigned32
        MAX-ACCESS read-only
        STATUS current
        DESCRIPTION
            "This object indicates the number of MAC addresses."
        ::= { optixSrvMacEntry 4 }

    -- 1.3.6.1.4.1.2011.2.25.4.50.3.1.25
    optixSrvRefCaseTable OBJECT-TYPE
        SYNTAX SEQUENCE OF OptixSrvRefCaseEntry
        MAX-ACCESS not-accessible
        STATUS current
        DESCRIPTION
            "This table describes the reflector-related configurations in the RFC2544 meter-free test."
        ::= { optixEthSrvObject 25 }

    -- 1.3.6.1.4.1.2011.2.25.4.50.3.1.25.1
    optixSrvRefCaseEntry OBJECT-TYPE
        SYNTAX OptixSrvRefCaseEntry
        MAX-ACCESS not-accessible
        STATUS current
        DESCRIPTION
            "This entry describes the reflector-related configurations in the RFC2544 meter-free test."
        INDEX{ optixSrvRefCaseID }
        ::= { optixSrvRefCaseTable 1 }

    OptixSrvRefCaseEntry ::=
        SEQUENCE {
            optixSrvRefCaseID
                Unsigned32,
            optixSrvRefCaseFlag
                INTEGER,
            optixSrvRefCaseSrvIndex
                Unsigned32,
            optixSrvRefCaseVuniType
                INTEGER,
            optixSrvRefCaseVuniID
                Unsigned32,
            optixSrvRefCaseFstVlan
                Unsigned32,
            optixSrvRefCaseSecVlan
                Unsigned32,
            optixSrvRefCaseDMac
                OCTET STRING,
            optixSrvRefCaseTimeOut
                Unsigned32,
            optixSrvRefCaseIP
                IpAddress,
            optixSrvRefCaseSrcPort
                Unsigned32,
            optixSrvRefCaseDestPort
                Unsigned32,
            optixSrvRefCaseState
                INTEGER,
            optixSrvRefCaseName
                OCTET STRING,
            optixSrvRefCaseRowStatus
                RowStatus
        }

    -- 1.3.6.1.4.1.2011.2.25.4.50.3.1.25.1.1
    optixSrvRefCaseID OBJECT-TYPE
        SYNTAX Unsigned32
        MAX-ACCESS not-accessible
        STATUS current
        DESCRIPTION
            "This parameter indicates the reflector ID in the RFC2544 meter-free test. Value range: 1 to 0xffffffff"
        ::= { optixSrvRefCaseEntry 1 }

    -- 1.3.6.1.4.1.2011.2.25.4.50.3.1.25.1.2
    optixSrvRefCaseFlag OBJECT-TYPE
        SYNTAX INTEGER
        {
            l2(1),
            l3(2)
        }
        MAX-ACCESS read-create
        STATUS current
        DESCRIPTION
            "This parameter indicates the scene flag of the reflector in the RFC2544 meter-free test. Values: L2(1) and L3(2)"
        ::= { optixSrvRefCaseEntry 2 }

    -- 1.3.6.1.4.1.2011.2.25.4.50.3.1.25.1.3
    optixSrvRefCaseSrvIndex OBJECT-TYPE
        SYNTAX Unsigned32
        MAX-ACCESS read-create
        STATUS current
        DESCRIPTION
            "This parameter indicates the service index of the reflector in the RFC2544 meter-free test. Value range: 1 to 0xffffffff"
        ::= { optixSrvRefCaseEntry 3 }

    -- 1.3.6.1.4.1.2011.2.25.4.50.3.1.25.1.4
    optixSrvRefCaseVuniType OBJECT-TYPE
        SYNTAX INTEGER
        {
            vuni(1),
            vnni(2)
        }
        MAX-ACCESS read-create
        STATUS current
        DESCRIPTION
            "This parameter indicates the logical subinterface type for the service of the reflector in the RFC2544 meter-free test. Values: vuni(1) and vnni(2)"
        ::= { optixSrvRefCaseEntry 4 }

    -- 1.3.6.1.4.1.2011.2.25.4.50.3.1.25.1.5
    optixSrvRefCaseVuniID OBJECT-TYPE
        SYNTAX Unsigned32
        MAX-ACCESS read-create
        STATUS current
        DESCRIPTION
            "This parameter indicates the logical subinterface ID for the service of the reflector in the RFC2544 meter-free test. Value range: 1 to 65535"
        ::= { optixSrvRefCaseEntry 5 }

    -- 1.3.6.1.4.1.2011.2.25.4.50.3.1.25.1.6
    optixSrvRefCaseFstVlan OBJECT-TYPE
        SYNTAX Unsigned32
        MAX-ACCESS read-create
        STATUS current
        DESCRIPTION
            "This parameter indicates the layer-1 VLAN of the reflector in the RFC2544 meter-free test. Values: 1 to 4094"
        ::= { optixSrvRefCaseEntry 6 }

    -- 1.3.6.1.4.1.2011.2.25.4.50.3.1.25.1.7
    optixSrvRefCaseSecVlan OBJECT-TYPE
        SYNTAX Unsigned32
        MAX-ACCESS read-create
        STATUS current
        DESCRIPTION
            "This parameter indicates the layer-2 VLAN of the reflector in the RFC2544 meter-free test. Values: 1 to 4094, 0xffff"
        ::= { optixSrvRefCaseEntry 7 }

    -- 1.3.6.1.4.1.2011.2.25.4.50.3.1.25.1.8
    optixSrvRefCaseDMac OBJECT-TYPE
        SYNTAX OCTET STRING
        MAX-ACCESS read-create
        STATUS current
        DESCRIPTION
            "This parameter indicates the MAC address of the reflector in the RFC2544 meter-free test."
        ::= { optixSrvRefCaseEntry 8 }

    -- 1.3.6.1.4.1.2011.2.25.4.50.3.1.25.1.9
    optixSrvRefCaseTimeOut OBJECT-TYPE
        SYNTAX Unsigned32
        MAX-ACCESS read-create
        STATUS current
        DESCRIPTION
            "This parameter indicates the timeout interval of the reflector in the RFC2544 meter-free test. Values: 10 to 173400, 0; default value: 14400; unit: second"
        ::= { optixSrvRefCaseEntry 9 }

    -- 1.3.6.1.4.1.2011.2.25.4.50.3.1.25.1.10
    optixSrvRefCaseIP OBJECT-TYPE
        SYNTAX IpAddress
        MAX-ACCESS read-create
        STATUS current
        DESCRIPTION
            "This parameter indicates the simulated IP address of the reflector in the RFC2544 meter-free test."
        ::= { optixSrvRefCaseEntry 10 }

    -- 1.3.6.1.4.1.2011.2.25.4.50.3.1.25.1.11
    optixSrvRefCaseSrcPort OBJECT-TYPE
        SYNTAX Unsigned32
        MAX-ACCESS read-create
        STATUS current
        DESCRIPTION
            "This parameter indicates the UDP source port of the reflector in the RFC2544 meter-free test."
        DEFVAL{ 49184 }
        ::= { optixSrvRefCaseEntry 11 }

    -- 1.3.6.1.4.1.2011.2.25.4.50.3.1.25.1.12
    optixSrvRefCaseDestPort OBJECT-TYPE
        SYNTAX Unsigned32
        MAX-ACCESS read-create
        STATUS current
        DESCRIPTION
            "This parameter indicates the UDP destination port of the reflector in the RFC2544 meter-free test."
        DEFVAL{ 7 }
        ::= { optixSrvRefCaseEntry 12 }

    -- 1.3.6.1.4.1.2011.2.25.4.50.3.1.25.1.13
    optixSrvRefCaseState OBJECT-TYPE
        SYNTAX INTEGER
        {
            running(0),
            finished(1),
            ipconflict(2)
        }
        MAX-ACCESS read-only
        STATUS current
        DESCRIPTION
            "This parameter indicates the reflector status in the RFC2544 meter-free test. Values: running(0), finished(1), and ipconflict(2)"
        ::= { optixSrvRefCaseEntry 13 }

    -- 1.3.6.1.4.1.2011.2.25.4.50.3.1.25.1.14
    optixSrvRefCaseName OBJECT-TYPE
        SYNTAX OCTET STRING (SIZE(0..64))
        MAX-ACCESS read-create
        STATUS current
        DESCRIPTION
            "This parameter indicates the reflector name in the RFC2544 meter-free test."
        ::= { optixSrvRefCaseEntry 14 }

    -- 1.3.6.1.4.1.2011.2.25.4.50.3.1.25.1.255
    optixSrvRefCaseRowStatus OBJECT-TYPE
        SYNTAX RowStatus
        MAX-ACCESS read-create
        STATUS current
        DESCRIPTION
            "This parameter indicates the row status of the table."
        ::= { optixSrvRefCaseEntry 255 }

    -- 1.3.6.1.4.1.2011.2.25.4.50.3.1.26
    optixSrvLauCaseTable OBJECT-TYPE
        SYNTAX SEQUENCE OF OptixSrvLauCaseEntry
        MAX-ACCESS not-accessible
        STATUS current
        DESCRIPTION
            "This table describes the initiator-related configurations in the RFC2544 meter-free test."
        ::= { optixEthSrvObject 26 }

    -- 1.3.6.1.4.1.2011.2.25.4.50.3.1.26.1
    optixSrvLauCaseEntry OBJECT-TYPE
        SYNTAX OptixSrvLauCaseEntry
        MAX-ACCESS not-accessible
        STATUS current
        DESCRIPTION
            "This entry describes the initiator-related configurations in the RFC2544 meter-free test."
        INDEX{ optixSrvLauCaseID }
        ::= { optixSrvLauCaseTable 1 }

    OptixSrvLauCaseEntry ::=
        SEQUENCE {
            optixSrvLauCaseID
                Unsigned32,
            optixSrvLauCaseSrvIndex
                Unsigned32,
            optixSrvLauCaseVuniType
                INTEGER,
            optixSrvLauCaseVuniID
                Unsigned32,
            optixSrvLauCaseFstVlan
                Unsigned32,
            optixSrvLauCaseSecSVlan
                Unsigned32,
            optixSrvLauCaseDMac
                OCTET STRING,
            optixSrvLauCaseType
                INTEGER,
            optixSrvLauCaseLoss
                Unsigned32,
            optixSrvLauCasePrecision
                Unsigned32,
            optixSrvLauCaseRateMax
                Unsigned32,
            optixSrvLauCaseRateMin
                Unsigned32,
            optixSrvLauCaseSendRate
                Unsigned32,
            optixSrvLauCaseIntervarTime
                Unsigned32,
            optixSrvLauCaseFstVlanpri
                Unsigned32,
            optixSrvLauCaseSecVlanpri
                Unsigned32,
            optixSrvLauCaseTestTime
                Unsigned32,
            optixSrvLauCaseState
                INTEGER,
            optixSrvLauCaseName
                OCTET STRING,
            optixSrvLauCaseNum
                Unsigned32,
            optixSrvLauCasePkt
                OCTET STRING,
            optixSrvLauCaseAction
                INTEGER,
            optixSrvLauCaseDei
                Unsigned32,
            optixSrvLauCaseRowStatus
                RowStatus
        }

    -- 1.3.6.1.4.1.2011.2.25.4.50.3.1.26.1.1
    optixSrvLauCaseID OBJECT-TYPE
        SYNTAX Unsigned32
        MAX-ACCESS not-accessible
        STATUS current
        DESCRIPTION
            "This parameter indicates the initiator ID in the RFC2544 meter-free test. Value range: 1 to 0xffffffff"
        ::= { optixSrvLauCaseEntry 1 }

    -- 1.3.6.1.4.1.2011.2.25.4.50.3.1.26.1.2
    optixSrvLauCaseSrvIndex OBJECT-TYPE
        SYNTAX Unsigned32
        MAX-ACCESS read-create
        STATUS current
        DESCRIPTION
            "This parameter indicates the service index of the initiator in the RFC2544 meter-free test. Value range: 1 to 0xffffffff"
        ::= { optixSrvLauCaseEntry 2 }

    -- 1.3.6.1.4.1.2011.2.25.4.50.3.1.26.1.3
    optixSrvLauCaseVuniType OBJECT-TYPE
        SYNTAX INTEGER
        {
            vuni(1),
            vnni(2)
        }
        MAX-ACCESS read-create
        STATUS current
        DESCRIPTION
            "This parameter indicates the logical subinterface type for the service of the initiator in the RFC2544 meter-free test. Values: vuni(1) and vnni(2)"
        ::= { optixSrvLauCaseEntry 3 }

    -- 1.3.6.1.4.1.2011.2.25.4.50.3.1.26.1.4
    optixSrvLauCaseVuniID OBJECT-TYPE
        SYNTAX Unsigned32
        MAX-ACCESS read-create
        STATUS current
        DESCRIPTION
            "This parameter indicates the logical subinterface ID for the service of the initiator in the RFC2544 meter-free test. Value range: 1 to 65535"
        ::= { optixSrvLauCaseEntry 4 }

    -- 1.3.6.1.4.1.2011.2.25.4.50.3.1.26.1.5
    optixSrvLauCaseFstVlan OBJECT-TYPE
        SYNTAX Unsigned32
        MAX-ACCESS read-create
        STATUS current
        DESCRIPTION
            "This parameter indicates the layer-1 VLAN of the initiator in the RFC2544 meter-free test. Values: 1 to 4094,0xffff"
        ::= { optixSrvLauCaseEntry 5 }

    -- 1.3.6.1.4.1.2011.2.25.4.50.3.1.26.1.6
    optixSrvLauCaseSecSVlan OBJECT-TYPE
        SYNTAX Unsigned32
        MAX-ACCESS read-create
        STATUS current
        DESCRIPTION
            "This parameter indicates the layer-2 VLAN of the initiator in the RFC2544 meter-free test. Values: 1 to 4094, 0xffff"
        ::= { optixSrvLauCaseEntry 6 }

    -- 1.3.6.1.4.1.2011.2.25.4.50.3.1.26.1.7
    optixSrvLauCaseDMac OBJECT-TYPE
        SYNTAX OCTET STRING
        MAX-ACCESS read-create
        STATUS current
        DESCRIPTION
            "This parameter indicates the destination MAC address of the initiator in the RFC2544 meter-free test."
        ::= { optixSrvLauCaseEntry 7 }

    -- 1.3.6.1.4.1.2011.2.25.4.50.3.1.26.1.8
    optixSrvLauCaseType OBJECT-TYPE
        SYNTAX INTEGER
        {
            delay(1),
            packetloss(2),
            throughput(3)
        }
        MAX-ACCESS read-create
        STATUS current
        DESCRIPTION
            "This parameter indicates the test type of the initiator in the RFC2544 meter-free test. Values: throughput(1), packetloss(2), and delay(3)"
        ::= { optixSrvLauCaseEntry 8 }

    -- 1.3.6.1.4.1.2011.2.25.4.50.3.1.26.1.9
    optixSrvLauCaseLoss OBJECT-TYPE
        SYNTAX Unsigned32
        MAX-ACCESS read-create
        STATUS current
        DESCRIPTION
            "This parameter indicates the packet loss ratio of the throughput test for the initiator in the RFC2544 meter-free test. Value range: 0 to 100; default value: 0; unit: 1/10000"
        ::= { optixSrvLauCaseEntry 9 }

    -- 1.3.6.1.4.1.2011.2.25.4.50.3.1.26.1.10
    optixSrvLauCasePrecision OBJECT-TYPE
        SYNTAX Unsigned32
        MAX-ACCESS read-create
        STATUS current
        DESCRIPTION
            "This parameter indicates the throughput test precision for the initiator in the RFC2544 meter-free test. Value range: 1 to 10000; default value: 1000; unit: kbit/s"
        ::= { optixSrvLauCaseEntry 10 }

    -- 1.3.6.1.4.1.2011.2.25.4.50.3.1.26.1.11
    optixSrvLauCaseRateMax OBJECT-TYPE
        SYNTAX Unsigned32
        MAX-ACCESS read-create
        STATUS current
        DESCRIPTION
            "This parameter indicates the upper rate threshold of the throughput test for the initiator in the RFC2544 meter-free test. Value range: 1 to port bandwidth; unit: kbit/s (The upper threshold must be equal to or larger than the lower threshold.)"
        ::= { optixSrvLauCaseEntry 11 }

    -- 1.3.6.1.4.1.2011.2.25.4.50.3.1.26.1.12
    optixSrvLauCaseRateMin OBJECT-TYPE
        SYNTAX Unsigned32
        MAX-ACCESS read-create
        STATUS current
        DESCRIPTION
            "This parameter indicates the lower rate threshold of the throughput test for the initiator in the RFC2544 meter-free test. Value range: 1 to port bandwidth; unit: kbit/s (The upper threshold must be equal to or larger than the lower threshold.)"
        ::= { optixSrvLauCaseEntry 12 }

    -- 1.3.6.1.4.1.2011.2.25.4.50.3.1.26.1.13
    optixSrvLauCaseSendRate OBJECT-TYPE
        SYNTAX Unsigned32
        MAX-ACCESS read-create
        STATUS current
        DESCRIPTION
            "This parameter indicates the transmit rate of the initiator in the RFC2544 meter-free test. Value range: 1 to port bandwidth; unit: kbit/s"
        ::= { optixSrvLauCaseEntry 13 }

    -- 1.3.6.1.4.1.2011.2.25.4.50.3.1.26.1.14
    optixSrvLauCaseIntervarTime OBJECT-TYPE
        SYNTAX Unsigned32
        MAX-ACCESS read-create
        STATUS current
        DESCRIPTION
            "This parameter indicates the interval for the initiator in the RFC2544 meter-free test. Value range: 1 to 60; default value: 4; unit: second"
        ::= { optixSrvLauCaseEntry 14 }

    -- 1.3.6.1.4.1.2011.2.25.4.50.3.1.26.1.15
    optixSrvLauCaseFstVlanpri OBJECT-TYPE
        SYNTAX Unsigned32
        MAX-ACCESS read-create
        STATUS current
        DESCRIPTION
            "This parameter indicates the layer-1 VLAN priority of the initiator in the RFC2544 meter-free test. Value range: 0 to 7; default value: 0"
        ::= { optixSrvLauCaseEntry 15 }

    -- 1.3.6.1.4.1.2011.2.25.4.50.3.1.26.1.16
    optixSrvLauCaseSecVlanpri OBJECT-TYPE
        SYNTAX Unsigned32
        MAX-ACCESS read-create
        STATUS current
        DESCRIPTION
            "This parameter indicates the layer-2 VLAN priority of the initiator in the RFC2544 meter-free test. Value range: 0 to 7; default value: 0"
        ::= { optixSrvLauCaseEntry 16 }

    -- 1.3.6.1.4.1.2011.2.25.4.50.3.1.26.1.17
    optixSrvLauCaseTestTime OBJECT-TYPE
        SYNTAX Unsigned32
        MAX-ACCESS read-create
        STATUS current
        DESCRIPTION
            "This parameter indicates the test time for a single packet of the initiator in the RFC2544 meter-free test. Value range: 10 to 172800; default value: 60; unit: second"
        ::= { optixSrvLauCaseEntry 17 }

    -- 1.3.6.1.4.1.2011.2.25.4.50.3.1.26.1.18
    optixSrvLauCaseState OBJECT-TYPE
        SYNTAX INTEGER
        {
            running(0),
            finished(1)
        }
        MAX-ACCESS read-only
        STATUS current
        DESCRIPTION
            "This parameter indicates the initiator status in the RFC2544 meter-free test. Values: running(0) and finished(1)"
        ::= { optixSrvLauCaseEntry 18 }

    -- 1.3.6.1.4.1.2011.2.25.4.50.3.1.26.1.19
    optixSrvLauCaseName OBJECT-TYPE
        SYNTAX OCTET STRING (SIZE(0..64))
        MAX-ACCESS read-create
        STATUS current
        DESCRIPTION
            "This parameter indicates the initiator name in the RFC2544 meter-free test."
        ::= { optixSrvLauCaseEntry 19 }

    -- 1.3.6.1.4.1.2011.2.25.4.50.3.1.26.1.20
    optixSrvLauCaseNum OBJECT-TYPE
        SYNTAX Unsigned32
        MAX-ACCESS read-create
        STATUS current
        DESCRIPTION
            "This parameter indicates the number of packets sent from the initiator in the RFC2544 meter-free test. Value range: 1 to 7"
        ::= { optixSrvLauCaseEntry 20 }

    -- 1.3.6.1.4.1.2011.2.25.4.50.3.1.26.1.21
    optixSrvLauCasePkt OBJECT-TYPE
        SYNTAX OCTET STRING
        MAX-ACCESS read-create
        STATUS current
        DESCRIPTION
            "This parameter indicates the length of packets sent from the initiator in the RFC2544 meter-free test. Value range: 64 to 65535"
        ::= { optixSrvLauCaseEntry 21 }

    -- 1.3.6.1.4.1.2011.2.25.4.50.3.1.26.1.22
    optixSrvLauCaseAction OBJECT-TYPE
        SYNTAX INTEGER
        {
            stop(0),
            start(1)
        }
        MAX-ACCESS read-create
        STATUS current
        DESCRIPTION
            "This parameter indicates whether to start or stop the RFC2544 meter-free test. Values: stop(0) and start(1)"
        ::= { optixSrvLauCaseEntry 22 }

    -- 1.3.6.1.4.1.2011.2.25.4.50.3.1.26.1.23
    optixSrvLauCaseDei OBJECT-TYPE
        SYNTAX Unsigned32
        MAX-ACCESS read-create
        STATUS current
        DESCRIPTION
            "This parameter indicates the DEI of the initiator in the RFC2544-based meter-free throughput test. Values: 0, 1"
        ::= { optixSrvLauCaseEntry 23 }

    -- 1.3.6.1.4.1.2011.2.25.4.50.3.1.26.1.255
    optixSrvLauCaseRowStatus OBJECT-TYPE
        SYNTAX RowStatus
        MAX-ACCESS read-create
        STATUS current
        DESCRIPTION
            "This parameter indicates the row status of the table."
        ::= { optixSrvLauCaseEntry 255 }

    -- 1.3.6.1.4.1.2011.2.25.4.50.3.1.27
    optixSrvCaseResultTable OBJECT-TYPE
        SYNTAX SEQUENCE OF OptixSrvCaseResultEntry
        MAX-ACCESS not-accessible
        STATUS current
        DESCRIPTION
            "This table describes the query-related configurations in the RFC2544 meter-free test."
        ::= { optixEthSrvObject 27 }

    -- 1.3.6.1.4.1.2011.2.25.4.50.3.1.27.1
    optixSrvCaseResultEntry OBJECT-TYPE
        SYNTAX OptixSrvCaseResultEntry
        MAX-ACCESS not-accessible
        STATUS current
        DESCRIPTION
            "This entry describes the query-related configurations in the RFC2544 meter-free test."
        INDEX{ optixSrvLauCaseID,optixSrvCaseSize }
        ::= { optixSrvCaseResultTable 1 }

    OptixSrvCaseResultEntry ::=
        SEQUENCE {
            optixSrvCaseSize
                Unsigned32,
            optixSrvCaseThroughput
                Unsigned32,
            optixSrvCasePrecision
                Unsigned32,
            optixSrvCaseThrougLoss
                Unsigned32,
            optixSrvCaseThroughComletion
                INTEGER,
            optixSrvCaseTxRate
                Unsigned32,
            optixSrvCaseRxRate
                Unsigned32,
            optixSrvCaseTxCount
                Unsigned32,
            optixSrvCaseRxCount
                Unsigned32,
            optixSrvCaseLoss
                Unsigned32,
            optixSrvCaseLossComletion
                INTEGER,
            optixSrvCaseMinRtt
                Unsigned32,
            optixSrvCaseMaxRtt
                Unsigned32,
            optixSrvCaseAvgRtt
                Unsigned32,
            optixSrvCaseMinJitter
                Unsigned32,
            optixSrvCaseMaxJitter
                Unsigned32,
            optixSrvCaseAvgJitter
                Unsigned32,
            optixSrvCaseDelayComletion
                INTEGER,
            optixSrvCaseThroughDetail
                INTEGER,
            optixSrvCaseLossDetail
                INTEGER,
            optixSrvCaseDelayDetail
                INTEGER
        }

    -- 1.3.6.1.4.1.2011.2.25.4.50.3.1.27.1.1
    optixSrvCaseSize OBJECT-TYPE
        SYNTAX Unsigned32
        MAX-ACCESS not-accessible
        STATUS current
        DESCRIPTION
            "This parameter indicates the packet length of the initiator in the RFC2544 meter-free test."
        ::= { optixSrvCaseResultEntry 1 }

    -- 1.3.6.1.4.1.2011.2.25.4.50.3.1.27.1.2
    optixSrvCaseThroughput OBJECT-TYPE
        SYNTAX Unsigned32
        MAX-ACCESS read-only
        STATUS current
        DESCRIPTION
            "This parameter indicates the throughput of the RFC2544 meter-free throughput test."
        ::= { optixSrvCaseResultEntry 2 }

    -- 1.3.6.1.4.1.2011.2.25.4.50.3.1.27.1.3
    optixSrvCasePrecision OBJECT-TYPE
        SYNTAX Unsigned32
        MAX-ACCESS read-only
        STATUS current
        DESCRIPTION
            "This parameter indicates the precision of the RFC2544 meter-free throughput test."
        ::= { optixSrvCaseResultEntry 3 }

    -- 1.3.6.1.4.1.2011.2.25.4.50.3.1.27.1.4
    optixSrvCaseThrougLoss OBJECT-TYPE
        SYNTAX Unsigned32
        MAX-ACCESS read-only
        STATUS current
        DESCRIPTION
            "This parameter indicates the packet loss ratio in the RFC2544 meter-free throughput test."
        ::= { optixSrvCaseResultEntry 4 }

    -- 1.3.6.1.4.1.2011.2.25.4.50.3.1.27.1.5
    optixSrvCaseThroughComletion OBJECT-TYPE
        SYNTAX INTEGER
        {
            noResult(0),
            success(1),
            failed(2),
            finished(3)
        }
        MAX-ACCESS read-only
        STATUS current
        DESCRIPTION
            "This parameter indicates the end status of the RFC2544 meter-free throughput test.Values: noResult(0), success(1), failed(2), finished(3)"
        ::= { optixSrvCaseResultEntry 5 }

    -- 1.3.6.1.4.1.2011.2.25.4.50.3.1.27.1.6
    optixSrvCaseTxRate OBJECT-TYPE
        SYNTAX Unsigned32
        MAX-ACCESS read-only
        STATUS current
        DESCRIPTION
            "This parameter indicates the transmit rate in the RFC2544 meter-free packet loss test."
        ::= { optixSrvCaseResultEntry 6 }

    -- 1.3.6.1.4.1.2011.2.25.4.50.3.1.27.1.7
    optixSrvCaseRxRate OBJECT-TYPE
        SYNTAX Unsigned32
        MAX-ACCESS read-only
        STATUS current
        DESCRIPTION
            "This parameter indicates the receive rate in the RFC2544 meter-free packet loss test."
        ::= { optixSrvCaseResultEntry 7 }

    -- 1.3.6.1.4.1.2011.2.25.4.50.3.1.27.1.8
    optixSrvCaseTxCount OBJECT-TYPE
        SYNTAX Unsigned32
        MAX-ACCESS read-only
        STATUS current
        DESCRIPTION
            "This parameter indicates the number of transmitted packets in the RFC2544 meter-free packet loss test."
        ::= { optixSrvCaseResultEntry 8 }

    -- 1.3.6.1.4.1.2011.2.25.4.50.3.1.27.1.9
    optixSrvCaseRxCount OBJECT-TYPE
        SYNTAX Unsigned32
        MAX-ACCESS read-only
        STATUS current
        DESCRIPTION
            "This parameter indicates the number of received packets in the RFC2544 meter-free packet loss test."
        ::= { optixSrvCaseResultEntry 9 }

    -- 1.3.6.1.4.1.2011.2.25.4.50.3.1.27.1.10
    optixSrvCaseLoss OBJECT-TYPE
        SYNTAX Unsigned32
        MAX-ACCESS read-only
        STATUS current
        DESCRIPTION
            "This parameter indicates the packet loss ratio in the RFC2544 meter-free packet loss test."
        ::= { optixSrvCaseResultEntry 10 }

    -- 1.3.6.1.4.1.2011.2.25.4.50.3.1.27.1.11
    optixSrvCaseLossComletion OBJECT-TYPE
        SYNTAX INTEGER
        {
            noResult(0),
            success(1),
            failed(2),
            finished(3)
        }
        MAX-ACCESS read-only
        STATUS current
        DESCRIPTION
            "This parameter indicates the end status of the RFC2544 meter-free packet loss test.Values: noResult(0), success(1), failed(2), finished(3)"
        ::= { optixSrvCaseResultEntry 11 }

    -- 1.3.6.1.4.1.2011.2.25.4.50.3.1.27.1.12
    optixSrvCaseMinRtt OBJECT-TYPE
        SYNTAX Unsigned32
        MAX-ACCESS read-only
        STATUS current
        DESCRIPTION
            "This parameter indicates the minimum RTT in the RFC2544 meter-free delay test."
        ::= { optixSrvCaseResultEntry 12 }

    -- 1.3.6.1.4.1.2011.2.25.4.50.3.1.27.1.13
    optixSrvCaseMaxRtt OBJECT-TYPE
        SYNTAX Unsigned32
        MAX-ACCESS read-only
        STATUS current
        DESCRIPTION
            "This parameter indicates the maximum RTT in the RFC2544 meter-free delay test."
        ::= { optixSrvCaseResultEntry 13 }

    -- 1.3.6.1.4.1.2011.2.25.4.50.3.1.27.1.14
    optixSrvCaseAvgRtt OBJECT-TYPE
        SYNTAX Unsigned32
        MAX-ACCESS read-only
        STATUS current
        DESCRIPTION
            "This parameter indicates the average RTT in the RFC2544 meter-free delay test."
        ::= { optixSrvCaseResultEntry 14 }

    -- 1.3.6.1.4.1.2011.2.25.4.50.3.1.27.1.15
    optixSrvCaseMinJitter OBJECT-TYPE
        SYNTAX Unsigned32
        MAX-ACCESS read-only
        STATUS current
        DESCRIPTION
            "This parameter indicates the minimum delay in the RFC2544 meter-free delay test."
        ::= { optixSrvCaseResultEntry 15 }

    -- 1.3.6.1.4.1.2011.2.25.4.50.3.1.27.1.16
    optixSrvCaseMaxJitter OBJECT-TYPE
        SYNTAX Unsigned32
        MAX-ACCESS read-only
        STATUS current
        DESCRIPTION
            "This parameter indicates the maximum delay in the RFC2544 meter-free delay test."
        ::= { optixSrvCaseResultEntry 16 }

    -- 1.3.6.1.4.1.2011.2.25.4.50.3.1.27.1.17
    optixSrvCaseAvgJitter OBJECT-TYPE
        SYNTAX Unsigned32
        MAX-ACCESS read-only
        STATUS current
        DESCRIPTION
            "This parameter indicates the average delay in the RFC2544 meter-free delay test."
        ::= { optixSrvCaseResultEntry 17 }

    -- 1.3.6.1.4.1.2011.2.25.4.50.3.1.27.1.18
    optixSrvCaseDelayComletion OBJECT-TYPE
        SYNTAX INTEGER
        {
            noResult(0),
            success(1),
            failed(2),
            finished(3)
        }
        MAX-ACCESS read-only
        STATUS current
        DESCRIPTION
            "This parameter indicates the end status of the RFC2544 meter-free delay test. Values: noResult(0), success(1), failed(2), finished(3)"
        ::= { optixSrvCaseResultEntry 18 }

    -- 1.3.6.1.4.1.2011.2.25.4.50.3.1.27.1.19
    optixSrvCaseThroughDetail OBJECT-TYPE
        SYNTAX INTEGER
        {
            success(0),
            lrTooLarge(1),
            hrTooSmall(2),
            timeout(3),
            pingFailed(4),
            testFailed(5),
            sendFailed(6)
        }
        MAX-ACCESS read-only
        STATUS current
        DESCRIPTION
            "This parameter indicates the end cause of the RFC2544-based meter-free throughput test. Values: success(0), lrTooLarge(1), hrTooSmall(2), timeout(3), pingFailed(4), testFailed(5), sendFailed(6)"
        ::= { optixSrvCaseResultEntry 19 }

    -- 1.3.6.1.4.1.2011.2.25.4.50.3.1.27.1.20
    optixSrvCaseLossDetail OBJECT-TYPE
        SYNTAX INTEGER
        {
            success(0),
            lrTooLarge(1),
            hrTooSmall(2),
            timeout(3),
            pingFailed(4),
            testFailed(5),
            sendFailed(6)
        }
        MAX-ACCESS read-only
        STATUS current
        DESCRIPTION
            "This parameter indicates the end cause of the RFC2544-based meter-free packet loss test. Values: success(0), lrTooLarge(1), hrTooSmall(2), timeout(3), pingFailed(4), testFailed(5), sendFailed(6)"
        ::= { optixSrvCaseResultEntry 20 }

    -- 1.3.6.1.4.1.2011.2.25.4.50.3.1.27.1.21
    optixSrvCaseDelayDetail OBJECT-TYPE
        SYNTAX INTEGER
        {
            success(0),
            lrTooLarge(1),
            hrTooSmall(2),
            timeout(3),
            pingFailed(4),
            testFailed(5),
            sendFailed(6)
        }
        MAX-ACCESS read-only
        STATUS current
        DESCRIPTION
            "This parameter indicates the end cause of the RFC2544-based meter-free delay test. Values: success(0), lrTooLarge(1), hrTooSmall(2), timeout(3), pingFailed(4), testFailed(5), sendFailed(6)"
        ::= { optixSrvCaseResultEntry 21 }

    -- 1.3.6.1.4.1.2011.2.25.4.50.3.1.28
    optixSrvCaseTrapMember OBJECT IDENTIFIER ::= { optixEthSrvObject 28 }

    -- 1.3.6.1.4.1.2011.2.25.4.50.3.1.28.1
    optixSrvCaseTrapID OBJECT-TYPE
        SYNTAX Unsigned32
        MAX-ACCESS accessible-for-notify
        STATUS current
        DESCRIPTION
            "This parameter indicates the ID of the initiator or reflector that reports the event."
        ::= { optixSrvCaseTrapMember 1 }

    -- 1.3.6.1.4.1.2011.2.25.4.50.3.1.28.2
    optixSrvCaseTrapState OBJECT-TYPE
        SYNTAX INTEGER
        {
            running(0),
            finished(1),
            ipconflict(2)
        }
        MAX-ACCESS accessible-for-notify
        STATUS current
        DESCRIPTION
            "This parameter indicates the status of the event. Values: running(0) ,finished(1), ipconflict(2)"
        ::= { optixSrvCaseTrapMember 2 }

    -- 1.3.6.1.4.1.2011.2.25.4.50.3.1.28.3
    optixSrvCaseTrapReason OBJECT-TYPE
        SYNTAX INTEGER
        {
            success(0),
            lrTooLarge(1),
            hrTooSmall(2),
            timeout(3),
            pingFailed(4),
            testFailed(5),
            sendFailed(6)
        }
        MAX-ACCESS accessible-for-notify
        STATUS current
        DESCRIPTION
            "This parameter indicates the termination reason for the initiator that reports the event. Values: success(0), lrTooLarge(1), hrTooSmall(2), timeout(3), pingFailed(4), testFailed(5), sendFailed(6)"
        ::= { optixSrvCaseTrapMember 3 }

    -- 1.3.6.1.4.1.2011.2.25.4.50.3.1.29
    optixSrvCaseEvent OBJECT IDENTIFIER ::= { optixEthSrvObject 29 }

    -- 1.3.6.1.4.1.2011.2.25.4.50.3.1.29.1
    optixSrvLauCaseEnd NOTIFICATION-TYPE
        OBJECTS{ optixSrvCaseTrapID,optixSrvCaseTrapState }
        STATUS current
        DESCRIPTION
            "This object is used to report the initiator termination event in the RFC2544 test."
        ::= { optixSrvCaseEvent 1 }

    -- 1.3.6.1.4.1.2011.2.25.4.50.3.1.29.2
    optixSrvRefCaseChange NOTIFICATION-TYPE
        OBJECTS{ optixSrvCaseTrapID,optixSrvCaseTrapReason }
        STATUS current
        DESCRIPTION
            "This object is used to report the reflector status change event in the RFC2544 test."
        ::= { optixSrvCaseEvent 2 }

    -- 1.3.6.1.4.1.2011.2.25.4.50.3.1.30
    optixSrvCreateLauCaseTable OBJECT-TYPE
        SYNTAX SEQUENCE OF OptixSrvCreateLauCaseEntry
        MAX-ACCESS not-accessible
        STATUS current
        DESCRIPTION
            "This table describes the initiator-related configurations for creating the RFC2544-based meter-free test."
        ::= { optixEthSrvObject 30 }

    -- 1.3.6.1.4.1.2011.2.25.4.50.3.1.30.1
    optixSrvCreateLauCaseEntry OBJECT-TYPE
        SYNTAX OptixSrvCreateLauCaseEntry
        MAX-ACCESS not-accessible
        STATUS current
        DESCRIPTION
            "This entry describes the initiator-related configurations for creating the RFC2544-based meter-free test."
        INDEX{ optixSrvLauCaseID }
        ::= { optixSrvCreateLauCaseTable 1 }

    OptixSrvCreateLauCaseEntry ::=
        SEQUENCE {
            optixSrvCreateLauCaseSrvIndex
                Unsigned32,
            optixSrvCreateLauCaseVuniType
                INTEGER,
            optixSrvCreateLauCaseVuniID
                Unsigned32,
            optixSrCreatevLauCaseFstVlan
                Unsigned32,
            optixSrvCreateLauCaseSecSVlan
                Unsigned32,
            optixSrvCreateLauCaseDMac
                OCTET STRING,
            optixSrvCreateLauCaseName
                OCTET STRING,
            optixSrvCreateLauCaseRowStatus
                RowStatus
        }

    -- 1.3.6.1.4.1.2011.2.25.4.50.3.1.30.1.1
    optixSrvCreateLauCaseSrvIndex OBJECT-TYPE
        SYNTAX Unsigned32
        MAX-ACCESS read-create
        STATUS current
        DESCRIPTION
            "This parameter indicates the service index of the initiator for creating the RFC2544-based meter-free test. Value range: 1 to 0xffffffff"
        ::= { optixSrvCreateLauCaseEntry 1 }

    -- 1.3.6.1.4.1.2011.2.25.4.50.3.1.30.1.2
    optixSrvCreateLauCaseVuniType OBJECT-TYPE
        SYNTAX INTEGER
        {
            vuni(1),
            vnni(2),
            snmp0xff(255)
        }
        MAX-ACCESS read-create
        STATUS current
        DESCRIPTION
            "This parameter indicates the service logical subinterface type of the initiator for creating the RFC2544-based meter-free test. Values: vuni(1), vnni(2), and snmp0xff(255)"
        ::= { optixSrvCreateLauCaseEntry 2 }

    -- 1.3.6.1.4.1.2011.2.25.4.50.3.1.30.1.3
    optixSrvCreateLauCaseVuniID OBJECT-TYPE
        SYNTAX Unsigned32
        MAX-ACCESS read-create
        STATUS current
        DESCRIPTION
            "This parameter indicates the service logical subinterface ID of the initiator for creating the RFC2544-based meter-free test. Value range: 1 to 65535"
        ::= { optixSrvCreateLauCaseEntry 3 }

    -- 1.3.6.1.4.1.2011.2.25.4.50.3.1.30.1.4
    optixSrCreatevLauCaseFstVlan OBJECT-TYPE
        SYNTAX Unsigned32
        MAX-ACCESS read-create
        STATUS current
        DESCRIPTION
            "This parameter indicates the layer-1 VLAN of the initiator for creating the RFC2544-based meter-free test. Values: 1 to 4094, 0xffff"
        ::= { optixSrvCreateLauCaseEntry 4 }

    -- 1.3.6.1.4.1.2011.2.25.4.50.3.1.30.1.5
    optixSrvCreateLauCaseSecSVlan OBJECT-TYPE
        SYNTAX Unsigned32
        MAX-ACCESS read-create
        STATUS current
        DESCRIPTION
            "This parameter indicates the layer-2 VLAN of the initiator for creating the RFC2544-based meter-free test. Values: 1 to 4094, 0xffff"
        ::= { optixSrvCreateLauCaseEntry 5 }

    -- 1.3.6.1.4.1.2011.2.25.4.50.3.1.30.1.6
    optixSrvCreateLauCaseDMac OBJECT-TYPE
        SYNTAX OCTET STRING
        MAX-ACCESS read-create
        STATUS current
        DESCRIPTION
            "This parameter indicates the destination MAC address of the initiator for creating the RFC2544-based meter-free test."
        ::= { optixSrvCreateLauCaseEntry 6 }

    -- 1.3.6.1.4.1.2011.2.25.4.50.3.1.30.1.7
    optixSrvCreateLauCaseName OBJECT-TYPE
        SYNTAX OCTET STRING (SIZE(0..64))
        MAX-ACCESS read-create
        STATUS current
        DESCRIPTION
            "This parameter indicates the initiator name for creating the RFC2544-based meter-free test."
        ::= { optixSrvCreateLauCaseEntry 7 }

    -- 1.3.6.1.4.1.2011.2.25.4.50.3.1.30.1.255
    optixSrvCreateLauCaseRowStatus OBJECT-TYPE
        SYNTAX RowStatus
        MAX-ACCESS read-create
        STATUS current
        DESCRIPTION
            "This parameter indicates the row status of the table."
        ::= { optixSrvCreateLauCaseEntry 255 }

    -- 1.3.6.1.4.1.2011.2.25.4.50.3.1.31
    optixEthAutoLDTable OBJECT-TYPE
        SYNTAX SEQUENCE OF OptixEthAutoLDEntry
        MAX-ACCESS not-accessible
        STATUS current
        DESCRIPTION
            "This table indicates the configuration information of the automatic ring breaking enable status."
        ::= { optixEthSrvObject 31 }

    -- 1.3.6.1.4.1.2011.2.25.4.50.3.1.31.1
    optixEthAutoLDEntry OBJECT-TYPE
        SYNTAX OptixEthAutoLDEntry
        MAX-ACCESS not-accessible
        STATUS current
        DESCRIPTION
            "This entry indicates the configuration information of the automatic ring breaking enable status."
        INDEX{ optixEthAutoLDType }
        ::= { optixEthAutoLDTable 1 }

    OptixEthAutoLDEntry ::=
        SEQUENCE {
            optixEthAutoLDType
                INTEGER,
            optixEthAutoLDstate
                INTEGER
        }

    -- 1.3.6.1.4.1.2011.2.25.4.50.3.1.31.1.1
    optixEthAutoLDType OBJECT-TYPE
        SYNTAX INTEGER
        {
            port(0),
            srv(1)
        }
        MAX-ACCESS not-accessible
        STATUS current
        DESCRIPTION
            "This parameter indicates the automatic ring breaking type.0:port,1:srv"
        ::= { optixEthAutoLDEntry 1 }

    -- 1.3.6.1.4.1.2011.2.25.4.50.3.1.31.1.2
    optixEthAutoLDstate OBJECT-TYPE
        SYNTAX INTEGER
        {
            disable(0),
            enable(1)
        }
        MAX-ACCESS read-write
        STATUS current
        DESCRIPTION
            "This parameter indicates the automatic ring breaking enable status."
        ::= { optixEthAutoLDEntry 2 }

    -- 1.3.6.1.4.1.2011.2.25.4.50.3.1.32
    optixCrtDelPktDropTable OBJECT-TYPE
        SYNTAX SEQUENCE OF OptixCrtDelPktDropEntry
        MAX-ACCESS not-accessible
        STATUS current
        DESCRIPTION
            "This table is used to create and delete packet coloring instances."
        ::= { optixEthSrvObject 32 }

    -- 1.3.6.1.4.1.2011.2.25.4.50.3.1.32.1
    optixCrtDelPktDropEntry OBJECT-TYPE
        SYNTAX OptixCrtDelPktDropEntry
        MAX-ACCESS not-accessible
        STATUS current
        DESCRIPTION
            "This entry is used to create and delete packet coloring instances."
        INDEX{ optixCrtDelPktDropTestID }
        ::= { optixCrtDelPktDropTable 1 }

    OptixCrtDelPktDropEntry ::=
        SEQUENCE {
            optixCrtDelPktDropTestID
                Unsigned32,
            optixCrtDelPktDropTestName
                OCTET STRING,
            optixCrtDelPktDropTestRole
                INTEGER,
            optixCrtDelPktDropTestAction
                INTEGER,
            optixCrtDelPktDropTestTime
                Unsigned32,
            optixCrtDelPktDropTestRowStatus
                RowStatus
        }

    -- 1.3.6.1.4.1.2011.2.25.4.50.3.1.32.1.1
    optixCrtDelPktDropTestID OBJECT-TYPE
        SYNTAX Unsigned32
        MAX-ACCESS not-accessible
        STATUS current
        DESCRIPTION
            "This parameter indicates the packet coloring instance ID."
        ::= { optixCrtDelPktDropEntry 1 }

    -- 1.3.6.1.4.1.2011.2.25.4.50.3.1.32.1.2
    optixCrtDelPktDropTestName OBJECT-TYPE
        SYNTAX OCTET STRING
        MAX-ACCESS read-create
        STATUS current
        DESCRIPTION
            "This parameter indicates the packet coloring instance name."
        ::= { optixCrtDelPktDropEntry 2 }

    -- 1.3.6.1.4.1.2011.2.25.4.50.3.1.32.1.3
    optixCrtDelPktDropTestRole OBJECT-TYPE
        SYNTAX INTEGER
        {
            up(0),
            mid(1),
            down(2)
        }
        MAX-ACCESS read-create
        STATUS current
        DESCRIPTION
            "This parameter indicates the packet coloring test role."
        ::= { optixCrtDelPktDropEntry 3 }

    -- 1.3.6.1.4.1.2011.2.25.4.50.3.1.32.1.4
    optixCrtDelPktDropTestAction OBJECT-TYPE
        SYNTAX INTEGER
        {
            cnt(0),
            colcnt(1),
            reccnt(2)
        }
        MAX-ACCESS read-create
        STATUS current
        DESCRIPTION
            "This parameter indicates the packet coloring test action."
        ::= { optixCrtDelPktDropEntry 4 }

    -- 1.3.6.1.4.1.2011.2.25.4.50.3.1.32.1.5
    optixCrtDelPktDropTestTime OBJECT-TYPE
        SYNTAX Unsigned32
        MAX-ACCESS read-create
        STATUS current
        DESCRIPTION
            "This parameter indicates the packet coloring time."
        ::= { optixCrtDelPktDropEntry 5 }

    -- 1.3.6.1.4.1.2011.2.25.4.50.3.1.32.1.255
    optixCrtDelPktDropTestRowStatus OBJECT-TYPE
        SYNTAX RowStatus
        MAX-ACCESS read-create
        STATUS current
        DESCRIPTION
            "This parameter indicates the row status of the table."
        ::= { optixCrtDelPktDropEntry 255 }

    -- 1.3.6.1.4.1.2011.2.25.4.50.3.1.33
    optixPktDropTable OBJECT-TYPE
        SYNTAX SEQUENCE OF OptixPktDropEntry
        MAX-ACCESS not-accessible
        STATUS current
        DESCRIPTION
            "This table describes configurations about packet coloring instances."
        ::= { optixEthSrvObject 33 }

    -- 1.3.6.1.4.1.2011.2.25.4.50.3.1.33.1
    optixPktDropEntry OBJECT-TYPE
        SYNTAX OptixPktDropEntry
        MAX-ACCESS not-accessible
        STATUS current
        DESCRIPTION
            "This entry describes configurations about packet coloring instances."
        INDEX{ optixPktDropTestID }
        ::= { optixPktDropTable 1 }

    OptixPktDropEntry ::=
        SEQUENCE {
            optixPktDropTestID
                Unsigned32,
            optixPktDropTestName
                OCTET STRING,
            optixPktDropTestRole
                INTEGER,
            optixPktDropTestAction
                INTEGER,
            optixPktDropTestTime
                Unsigned32,
            optixPktDropTestOperate
                INTEGER,
            optixPktDropTestState
                INTEGER,
            optixPktDropTestPktNum
                Counter64,
            optixPktDropTestPktByte
                Counter64,
            optixPktDropTestUnPktNum
                Counter64,
            optixPktDropTestUnPktByte
                Counter64
        }

    -- 1.3.6.1.4.1.2011.2.25.4.50.3.1.33.1.1
    optixPktDropTestID OBJECT-TYPE
        SYNTAX Unsigned32
        MAX-ACCESS not-accessible
        STATUS current
        DESCRIPTION
            "This parameter indicates the packet coloring instance ID."
        ::= { optixPktDropEntry 1 }

    -- 1.3.6.1.4.1.2011.2.25.4.50.3.1.33.1.2
    optixPktDropTestName OBJECT-TYPE
        SYNTAX OCTET STRING
        MAX-ACCESS read-write
        STATUS current
        DESCRIPTION
            "This parameter indicates the packet coloring instance name."
        ::= { optixPktDropEntry 2 }

    -- 1.3.6.1.4.1.2011.2.25.4.50.3.1.33.1.3
    optixPktDropTestRole OBJECT-TYPE
        SYNTAX INTEGER
        {
            up(0),
            mid(1),
            down(2)
        }
        MAX-ACCESS read-write
        STATUS current
        DESCRIPTION
            "This parameter indicates the packet coloring test role."
        ::= { optixPktDropEntry 3 }

    -- 1.3.6.1.4.1.2011.2.25.4.50.3.1.33.1.4
    optixPktDropTestAction OBJECT-TYPE
        SYNTAX INTEGER
        {
            cnt(0),
            colCnt(1),
            recCnt(2)
        }
        MAX-ACCESS read-write
        STATUS current
        DESCRIPTION
            "This parameter indicates the packet coloring test action."
        ::= { optixPktDropEntry 4 }

    -- 1.3.6.1.4.1.2011.2.25.4.50.3.1.33.1.5
    optixPktDropTestTime OBJECT-TYPE
        SYNTAX Unsigned32
        MAX-ACCESS read-write
        STATUS current
        DESCRIPTION
            "This parameter indicates the packet coloring time."
        ::= { optixPktDropEntry 5 }

    -- 1.3.6.1.4.1.2011.2.25.4.50.3.1.33.1.6
    optixPktDropTestOperate OBJECT-TYPE
        SYNTAX INTEGER
        {
            start(0),
            stop(1)
        }
        MAX-ACCESS read-write
        STATUS current
        DESCRIPTION
            "This parameter indicates whether to enable/disable packet coloring."
        ::= { optixPktDropEntry 6 }

    -- 1.3.6.1.4.1.2011.2.25.4.50.3.1.33.1.7
    optixPktDropTestState OBJECT-TYPE
        SYNTAX INTEGER
        {
            inprogress(0),
            stop(1)
        }
        MAX-ACCESS read-only
        STATUS current
        DESCRIPTION
            "This parameter indicates the packet coloring status."
        ::= { optixPktDropEntry 7 }

    -- 1.3.6.1.4.1.2011.2.25.4.50.3.1.33.1.8
    optixPktDropTestPktNum OBJECT-TYPE
        SYNTAX Counter64
        MAX-ACCESS read-only
        STATUS current
        DESCRIPTION
            "This parameter indicates the number of colored packets."
        ::= { optixPktDropEntry 8 }

    -- 1.3.6.1.4.1.2011.2.25.4.50.3.1.33.1.9
    optixPktDropTestPktByte OBJECT-TYPE
        SYNTAX Counter64
        MAX-ACCESS read-only
        STATUS current
        DESCRIPTION
            "This parameter indicates the number of bytes of the colored packets."
        ::= { optixPktDropEntry 9 }

    -- 1.3.6.1.4.1.2011.2.25.4.50.3.1.33.1.10
    optixPktDropTestUnPktNum OBJECT-TYPE
        SYNTAX Counter64
        MAX-ACCESS read-only
        STATUS current
        DESCRIPTION
            "This parameter indicates the number of uncolored packets."
        ::= { optixPktDropEntry 10 }

    -- 1.3.6.1.4.1.2011.2.25.4.50.3.1.33.1.11
    optixPktDropTestUnPktByte OBJECT-TYPE
        SYNTAX Counter64
        MAX-ACCESS read-only
        STATUS current
        DESCRIPTION
            "This parameter indicates the number of bytes of the uncolored packets."
        ::= { optixPktDropEntry 11 }

    -- 1.3.6.1.4.1.2011.2.25.4.50.3.1.34
    optixPktDropPointTable OBJECT-TYPE
        SYNTAX SEQUENCE OF OptixPktDropPointEntry
        MAX-ACCESS not-accessible
        STATUS current
        DESCRIPTION
            "This table describes configurations about packet coloring test points."
        ::= { optixEthSrvObject 34 }

    -- 1.3.6.1.4.1.2011.2.25.4.50.3.1.34.1
    optixPktDropPointEntry OBJECT-TYPE
        SYNTAX OptixPktDropPointEntry
        MAX-ACCESS not-accessible
        STATUS current
        DESCRIPTION
            "This entry describes configurations about packet coloring test points."
        INDEX{ optixPktDropTestID }
        ::= { optixPktDropPointTable 1 }

    OptixPktDropPointEntry ::=
        SEQUENCE {
            optixPktDropTestPointType
                INTEGER,
            optixPktDropTestDir
                INTEGER,
            optixPktDropTestSrvIndex
                Unsigned32,
            optixPktDropTestIFType
                INTEGER,
            optixPktDropTestIFID
                Unsigned32,
            optixPktDropVlanNum
                Unsigned32,
            optixPktDropVlanList
                OCTET STRING,
            optixPktDropCarrierPara1
                Unsigned32,
            optixPktDropCarrierPara2
                Unsigned32,
            optixPktDropCarrierPara3
                Unsigned32,
            optixPktDropTunnelDir
                INTEGER,
            optixPktDropTunnelIndex
                Unsigned32,
            optixPktDropBoardID
                Unsigned32,
            optixPktDropSubID
                Unsigned32,
            optixPktDropPortID
                Unsigned32,
            optixPktDropPwLabel
                Unsigned32,
            optixPktDropTagRole
                INTEGER,
            optixPktDropPwEthType
                INTEGER,
            optixPktDropVlanTpID
                Unsigned32,
            optixPktDropPwCw
                INTEGER,
            optixPktDropUniTag
                Unsigned32,
            optixPktDropUniTpID
                Unsigned32,
            optixPktDropSrvType
                INTEGER,
            optixPktDropStagTpID
                Unsigned32,
            optixPktDropVlanPriNum
                Unsigned32,
            optixPktDropVlanPriList
                OCTET STRING,
            optixPktDropTunnelID
                Unsigned32
        }

    -- 1.3.6.1.4.1.2011.2.25.4.50.3.1.34.1.1
    optixPktDropTestPointType OBJECT-TYPE
        SYNTAX INTEGER
        {
            vuni(0),
            qinq(1),
            tunnel(2),
            phyport(3),
            null(255)
        }
        MAX-ACCESS read-write
        STATUS current
        DESCRIPTION
            "This parameter indicates the type of the packet coloring test point."
        ::= { optixPktDropPointEntry 1 }

    -- 1.3.6.1.4.1.2011.2.25.4.50.3.1.34.1.2
    optixPktDropTestDir OBJECT-TYPE
        SYNTAX INTEGER
        {
            tx(0),
            rx(1)
        }
        MAX-ACCESS read-write
        STATUS current
        DESCRIPTION
            "This parameter indicates the direction where packets are colored."
        ::= { optixPktDropPointEntry 2 }

    -- 1.3.6.1.4.1.2011.2.25.4.50.3.1.34.1.3
    optixPktDropTestSrvIndex OBJECT-TYPE
        SYNTAX Unsigned32
        MAX-ACCESS read-write
        STATUS current
        DESCRIPTION
            "This parameter indicates the service index for packer coloring."
        ::= { optixPktDropPointEntry 3 }

    -- 1.3.6.1.4.1.2011.2.25.4.50.3.1.34.1.4
    optixPktDropTestIFType OBJECT-TYPE
        SYNTAX INTEGER
        {
            vuni(1),
            vnni(2)
        }
        MAX-ACCESS read-write
        STATUS current
        DESCRIPTION
            "This parameter indicates the type of the logical subinterface for packet coloring."
        ::= { optixPktDropPointEntry 4 }

    -- 1.3.6.1.4.1.2011.2.25.4.50.3.1.34.1.5
    optixPktDropTestIFID OBJECT-TYPE
        SYNTAX Unsigned32
        MAX-ACCESS read-write
        STATUS current
        DESCRIPTION
            "This parameter indicates the ID of the logical subinterface for packet coloring."
        ::= { optixPktDropPointEntry 5 }

    -- 1.3.6.1.4.1.2011.2.25.4.50.3.1.34.1.6
    optixPktDropVlanNum OBJECT-TYPE
        SYNTAX Unsigned32
        MAX-ACCESS read-write
        STATUS current
        DESCRIPTION
            "This parameter indicates the number of VLANs for packet coloring."
        ::= { optixPktDropPointEntry 6 }

    -- 1.3.6.1.4.1.2011.2.25.4.50.3.1.34.1.7
    optixPktDropVlanList OBJECT-TYPE
        SYNTAX OCTET STRING
        MAX-ACCESS read-write
        STATUS current
        DESCRIPTION
            "This parameter indicates the list of VLANs for packet coloring."
        ::= { optixPktDropPointEntry 7 }

    -- 1.3.6.1.4.1.2011.2.25.4.50.3.1.34.1.8
    optixPktDropCarrierPara1 OBJECT-TYPE
        SYNTAX Unsigned32
        MAX-ACCESS read-only
        STATUS current
        DESCRIPTION
            "This parameter indicates Parameter 1 about service bearing for packet coloring."
        ::= { optixPktDropPointEntry 8 }

    -- 1.3.6.1.4.1.2011.2.25.4.50.3.1.34.1.9
    optixPktDropCarrierPara2 OBJECT-TYPE
        SYNTAX Unsigned32
        MAX-ACCESS read-only
        STATUS current
        DESCRIPTION
            "This parameter indicates Parameter 2 about service bearing for packet coloring."
        ::= { optixPktDropPointEntry 9 }

    -- 1.3.6.1.4.1.2011.2.25.4.50.3.1.34.1.10
    optixPktDropCarrierPara3 OBJECT-TYPE
        SYNTAX Unsigned32
        MAX-ACCESS read-only
        STATUS current
        DESCRIPTION
            "This parameter indicates Parameter 3 about service bearing for packet coloring."
        ::= { optixPktDropPointEntry 10 }

    -- 1.3.6.1.4.1.2011.2.25.4.50.3.1.34.1.11
    optixPktDropTunnelDir OBJECT-TYPE
        SYNTAX INTEGER
        {
            tx(0),
            rx(1)
        }
        MAX-ACCESS read-write
        STATUS current
        DESCRIPTION
            "This parameter indicates the direction of the tunnel test point for packet coloring."
        ::= { optixPktDropPointEntry 11 }

    -- 1.3.6.1.4.1.2011.2.25.4.50.3.1.34.1.12
    optixPktDropTunnelIndex OBJECT-TYPE
        SYNTAX Unsigned32
        MAX-ACCESS read-write
        STATUS current
        DESCRIPTION
            "This parameter indicates the tunnel index for packet coloring."
        ::= { optixPktDropPointEntry 12 }

    -- 1.3.6.1.4.1.2011.2.25.4.50.3.1.34.1.13
    optixPktDropBoardID OBJECT-TYPE
        SYNTAX Unsigned32
        MAX-ACCESS read-write
        STATUS current
        DESCRIPTION
            "This parameter indicates the slot ID of the tunnel test point for packet coloring."
        ::= { optixPktDropPointEntry 13 }

    -- 1.3.6.1.4.1.2011.2.25.4.50.3.1.34.1.14
    optixPktDropSubID OBJECT-TYPE
        SYNTAX Unsigned32
        MAX-ACCESS read-write
        STATUS current
        DESCRIPTION
            "This parameter indicates the subboard ID of the tunnel test point for packet coloring."
        ::= { optixPktDropPointEntry 14 }

    -- 1.3.6.1.4.1.2011.2.25.4.50.3.1.34.1.15
    optixPktDropPortID OBJECT-TYPE
        SYNTAX Unsigned32
        MAX-ACCESS read-write
        STATUS current
        DESCRIPTION
            "This parameter indicates the port ID of the tunnel test point for packet coloring."
        ::= { optixPktDropPointEntry 15 }

    -- 1.3.6.1.4.1.2011.2.25.4.50.3.1.34.1.16
    optixPktDropPwLabel OBJECT-TYPE
        SYNTAX Unsigned32
        MAX-ACCESS read-write
        STATUS current
        DESCRIPTION
            "This parameter indicates the PW label of the tunnel test point for packet coloring."
        ::= { optixPktDropPointEntry 16 }

    -- 1.3.6.1.4.1.2011.2.25.4.50.3.1.34.1.17
    optixPktDropTagRole OBJECT-TYPE
        SYNTAX INTEGER
        {
            user(0),
            service(1)
        }
        MAX-ACCESS read-write
        STATUS current
        DESCRIPTION
            "This parameter indicates the service tag role of the tunnel test point for packet coloring."
        ::= { optixPktDropPointEntry 17 }

    -- 1.3.6.1.4.1.2011.2.25.4.50.3.1.34.1.18
    optixPktDropPwEthType OBJECT-TYPE
        SYNTAX INTEGER
        {
            ethRaw(0),
            ethTag(1)
        }
        MAX-ACCESS read-write
        STATUS current
        DESCRIPTION
            "This parameter indicates the PW Ethernet type of the tunnel test point for packet coloring."
        ::= { optixPktDropPointEntry 18 }

    -- 1.3.6.1.4.1.2011.2.25.4.50.3.1.34.1.19
    optixPktDropVlanTpID OBJECT-TYPE
        SYNTAX Unsigned32
        MAX-ACCESS read-write
        STATUS current
        DESCRIPTION
            "This parameter indicates the VLAN TPID of the tunnel test point for packet coloring."
        ::= { optixPktDropPointEntry 19 }

    -- 1.3.6.1.4.1.2011.2.25.4.50.3.1.34.1.20
    optixPktDropPwCw OBJECT-TYPE
        SYNTAX INTEGER
        {
            notuse(0),
            fstuse(1),
            mstuse(2)
        }
        MAX-ACCESS read-write
        STATUS current
        DESCRIPTION
            "This parameter indicates the PW control word of the tunnel test point for packet coloring."
        ::= { optixPktDropPointEntry 20 }

    -- 1.3.6.1.4.1.2011.2.25.4.50.3.1.34.1.21
    optixPktDropUniTag OBJECT-TYPE
        SYNTAX Unsigned32
        MAX-ACCESS read-write
        STATUS current
        DESCRIPTION
            "This parameter indicates the UNI encapsulation of the tunnel test point for packet coloring."
        ::= { optixPktDropPointEntry 21 }

    -- 1.3.6.1.4.1.2011.2.25.4.50.3.1.34.1.22
    optixPktDropUniTpID OBJECT-TYPE
        SYNTAX Unsigned32
        MAX-ACCESS read-write
        STATUS current
        DESCRIPTION
            "This parameter indicates the UNI TPID of the tunnel test point for packet coloring."
        ::= { optixPktDropPointEntry 22 }

    -- 1.3.6.1.4.1.2011.2.25.4.50.3.1.34.1.23
    optixPktDropSrvType OBJECT-TYPE
        SYNTAX INTEGER
        {
            eLine(0),
            eLan(1),
            eAggr(2)
        }
        MAX-ACCESS read-write
        STATUS current
        DESCRIPTION
            "This parameter indicates the service type of the tunnel test point for packet coloring."
        ::= { optixPktDropPointEntry 23 }

    -- 1.3.6.1.4.1.2011.2.25.4.50.3.1.34.1.24
    optixPktDropStagTpID OBJECT-TYPE
        SYNTAX Unsigned32
        MAX-ACCESS read-write
        STATUS current
        DESCRIPTION
            "This parameter indicates the Stag TPID of the tunnel test point for packet coloring."
        ::= { optixPktDropPointEntry 24 }

    -- 1.3.6.1.4.1.2011.2.25.4.50.3.1.34.1.25
    optixPktDropVlanPriNum OBJECT-TYPE
        SYNTAX Unsigned32
        MAX-ACCESS read-write
        STATUS current
        DESCRIPTION
            "This parameter indicates the number of VLAN prioritys for packet coloring."
        ::= { optixPktDropPointEntry 25 }

    -- 1.3.6.1.4.1.2011.2.25.4.50.3.1.34.1.26
    optixPktDropVlanPriList OBJECT-TYPE
        SYNTAX OCTET STRING
        MAX-ACCESS read-write
        STATUS current
        DESCRIPTION
            "This parameter indicates the list of VLAN prioritys for packet coloring."
        ::= { optixPktDropPointEntry 26 }

    -- 1.3.6.1.4.1.2011.2.25.4.50.3.1.34.1.27
    optixPktDropTunnelID OBJECT-TYPE
        SYNTAX Unsigned32
        MAX-ACCESS read-only
        STATUS current
        DESCRIPTION
            "This parameter indicates the tunnel ID for packet coloring."
        ::= { optixPktDropPointEntry 27 }

    -- 1.3.6.1.4.1.2011.2.25.4.50.3.1.35
    optixPktDropRuleTable OBJECT-TYPE
        SYNTAX SEQUENCE OF OptixPktDropRuleEntry
        MAX-ACCESS not-accessible
        STATUS current
        DESCRIPTION
            "This table describes configurations about packet coloring rules."
        ::= { optixEthSrvObject 35 }

    -- 1.3.6.1.4.1.2011.2.25.4.50.3.1.35.1
    optixPktDropRuleEntry OBJECT-TYPE
        SYNTAX OptixPktDropRuleEntry
        MAX-ACCESS not-accessible
        STATUS current
        DESCRIPTION
            "This entry describes configurations about packet coloring rules."
        INDEX{ optixPktDropTestID }
        ::= { optixPktDropRuleTable 1 }

    OptixPktDropRuleEntry ::=
        SEQUENCE {
            optixPktDropOutVlan
                Unsigned32,
            optixPktDropOutVlanMask
                Unsigned32,
            optixPktDropInVlan
                Unsigned32,
            optixPktDropInVlanMask
                Unsigned32,
            optixPktDropOutVlanPri
                Unsigned32,
            optixPktDropOutVlanPriMask
                Unsigned32,
            optixPktDropInVlanPri
                Unsigned32,
            optixPktDropInVlanPriMask
                Unsigned32,
            optixPktDropStag
                Unsigned32,
            optixPktDropStagMask
                Unsigned32,
            optixPktDropDscp
                Unsigned32,
            optixPktDropDscpMask
                Unsigned32,
            optixPktDropDMac
                OCTET STRING,
            optixPktDropDMacMask
                OCTET STRING,
            optixPktDropSMac
                OCTET STRING,
            optixPktDropSMacMask
                OCTET STRING,
            optixPktDropPtl
                Unsigned32,
            optixPktDropPtlMask
                Unsigned32,
            optixPktDropDIp
                IpAddress,
            optixPktDropDIpMask
                IpAddress,
            optixPktDropSIp
                IpAddress,
            optixPktDropSIpMask
                IpAddress,
            optixPktDropDPort
                Unsigned32,
            optixPktDropDPortMask
                Unsigned32,
            optixPktDropSPort
                Unsigned32,
            optixPktDropSPortMask
                Unsigned32,
            optixPktDropCtag
                Unsigned32,
            optixPktDropCtagMask
                Unsigned32,
            optixPktDropEthType
                Unsigned32,
            optixPktDropEthTypeMask
                Unsigned32,
            optixPktDropIcmp
                Unsigned32,
            optixPktDropIcmpMask
                Unsigned32
        }

    -- 1.3.6.1.4.1.2011.2.25.4.50.3.1.35.1.1
    optixPktDropOutVlan OBJECT-TYPE
        SYNTAX Unsigned32
        MAX-ACCESS read-write
        STATUS current
        DESCRIPTION
            "This parameter indicates the outer VLAN ID for packet coloring."
        ::= { optixPktDropRuleEntry 1 }

    -- 1.3.6.1.4.1.2011.2.25.4.50.3.1.35.1.2
    optixPktDropOutVlanMask OBJECT-TYPE
        SYNTAX Unsigned32
        MAX-ACCESS read-write
        STATUS current
        DESCRIPTION
            "This parameter indicates the wildcard of the outer VLAN ID for packet coloring."
        ::= { optixPktDropRuleEntry 2 }

    -- 1.3.6.1.4.1.2011.2.25.4.50.3.1.35.1.3
    optixPktDropInVlan OBJECT-TYPE
        SYNTAX Unsigned32
        MAX-ACCESS read-write
        STATUS current
        DESCRIPTION
            "This parameter indicates the inner VLAN ID for packet coloring."
        ::= { optixPktDropRuleEntry 3 }

    -- 1.3.6.1.4.1.2011.2.25.4.50.3.1.35.1.4
    optixPktDropInVlanMask OBJECT-TYPE
        SYNTAX Unsigned32
        MAX-ACCESS read-write
        STATUS current
        DESCRIPTION
            "This parameter indicates the wildcard of the inner VLAN ID for packet coloring."
        ::= { optixPktDropRuleEntry 4 }

    -- 1.3.6.1.4.1.2011.2.25.4.50.3.1.35.1.5
    optixPktDropOutVlanPri OBJECT-TYPE
        SYNTAX Unsigned32
        MAX-ACCESS read-write
        STATUS current
        DESCRIPTION
            "This parameter indicates the outer VLAN priority for packet coloring."
        ::= { optixPktDropRuleEntry 5 }

    -- 1.3.6.1.4.1.2011.2.25.4.50.3.1.35.1.6
    optixPktDropOutVlanPriMask OBJECT-TYPE
        SYNTAX Unsigned32
        MAX-ACCESS read-write
        STATUS current
        DESCRIPTION
            "This parameter indicates the wildcard of the outer VLAN priority for packet coloring."
        ::= { optixPktDropRuleEntry 6 }

    -- 1.3.6.1.4.1.2011.2.25.4.50.3.1.35.1.7
    optixPktDropInVlanPri OBJECT-TYPE
        SYNTAX Unsigned32
        MAX-ACCESS read-write
        STATUS current
        DESCRIPTION
            "This parameter indicates the inner VLAN priority for packet coloring."
        ::= { optixPktDropRuleEntry 7 }

    -- 1.3.6.1.4.1.2011.2.25.4.50.3.1.35.1.8
    optixPktDropInVlanPriMask OBJECT-TYPE
        SYNTAX Unsigned32
        MAX-ACCESS read-write
        STATUS current
        DESCRIPTION
            "This parameter indicates the wildcard of the inner VLAN priority for packet coloring."
        ::= { optixPktDropRuleEntry 8 }

    -- 1.3.6.1.4.1.2011.2.25.4.50.3.1.35.1.9
    optixPktDropStag OBJECT-TYPE
        SYNTAX Unsigned32
        MAX-ACCESS read-write
        STATUS current
        DESCRIPTION
            "This parameter indicates the outer VLAN DP for packet coloring."
        ::= { optixPktDropRuleEntry 9 }

    -- 1.3.6.1.4.1.2011.2.25.4.50.3.1.35.1.10
    optixPktDropStagMask OBJECT-TYPE
        SYNTAX Unsigned32
        MAX-ACCESS read-write
        STATUS current
        DESCRIPTION
            "This parameter indicates the wildcard of the outer VLAN DP for packet coloring."
        ::= { optixPktDropRuleEntry 10 }

    -- 1.3.6.1.4.1.2011.2.25.4.50.3.1.35.1.11
    optixPktDropDscp OBJECT-TYPE
        SYNTAX Unsigned32
        MAX-ACCESS read-write
        STATUS current
        DESCRIPTION
            "This parameter indicates the DSCP for packet coloring."
        ::= { optixPktDropRuleEntry 11 }

    -- 1.3.6.1.4.1.2011.2.25.4.50.3.1.35.1.12
    optixPktDropDscpMask OBJECT-TYPE
        SYNTAX Unsigned32
        MAX-ACCESS read-write
        STATUS current
        DESCRIPTION
            "This parameter indicates the DSCP wildcard for packet coloring."
        ::= { optixPktDropRuleEntry 12 }

    -- 1.3.6.1.4.1.2011.2.25.4.50.3.1.35.1.13
    optixPktDropDMac OBJECT-TYPE
        SYNTAX OCTET STRING
        MAX-ACCESS read-write
        STATUS current
        DESCRIPTION
            "This parameter indicates the destination MAC address for packet coloring."
        ::= { optixPktDropRuleEntry 13 }

    -- 1.3.6.1.4.1.2011.2.25.4.50.3.1.35.1.14
    optixPktDropDMacMask OBJECT-TYPE
        SYNTAX OCTET STRING
        MAX-ACCESS read-write
        STATUS current
        DESCRIPTION
            "This parameter indicates the wildcard of the destination MAC address for packet coloring."
        ::= { optixPktDropRuleEntry 14 }

    -- 1.3.6.1.4.1.2011.2.25.4.50.3.1.35.1.15
    optixPktDropSMac OBJECT-TYPE
        SYNTAX OCTET STRING
        MAX-ACCESS read-write
        STATUS current
        DESCRIPTION
            "This parameter indicates the source MAC address for packet coloring."
        ::= { optixPktDropRuleEntry 15 }

    -- 1.3.6.1.4.1.2011.2.25.4.50.3.1.35.1.16
    optixPktDropSMacMask OBJECT-TYPE
        SYNTAX OCTET STRING
        MAX-ACCESS read-write
        STATUS current
        DESCRIPTION
            "This parameter indicates the wildcard of the source MAC address for packet coloring."
        ::= { optixPktDropRuleEntry 16 }

    -- 1.3.6.1.4.1.2011.2.25.4.50.3.1.35.1.17
    optixPktDropPtl OBJECT-TYPE
        SYNTAX Unsigned32
        MAX-ACCESS read-write
        STATUS current
        DESCRIPTION
            "This parameter indicates protocol type matching for packet coloring."
        ::= { optixPktDropRuleEntry 17 }

    -- 1.3.6.1.4.1.2011.2.25.4.50.3.1.35.1.18
    optixPktDropPtlMask OBJECT-TYPE
        SYNTAX Unsigned32
        MAX-ACCESS read-write
        STATUS current
        DESCRIPTION
            "This parameter indicates the wildcard of protocol type matching for packet coloring."
        ::= { optixPktDropRuleEntry 18 }

    -- 1.3.6.1.4.1.2011.2.25.4.50.3.1.35.1.19
    optixPktDropDIp OBJECT-TYPE
        SYNTAX IpAddress
        MAX-ACCESS read-write
        STATUS current
        DESCRIPTION
            "This parameter indicates the destination IP address for packet coloring."
        ::= { optixPktDropRuleEntry 19 }

    -- 1.3.6.1.4.1.2011.2.25.4.50.3.1.35.1.20
    optixPktDropDIpMask OBJECT-TYPE
        SYNTAX IpAddress
        MAX-ACCESS read-write
        STATUS current
        DESCRIPTION
            "This parameter indicates the wildcard of the destination IP address for packet coloring."
        ::= { optixPktDropRuleEntry 20 }

    -- 1.3.6.1.4.1.2011.2.25.4.50.3.1.35.1.21
    optixPktDropSIp OBJECT-TYPE
        SYNTAX IpAddress
        MAX-ACCESS read-write
        STATUS current
        DESCRIPTION
            "This parameter indicates the source IP address for packet coloring."
        ::= { optixPktDropRuleEntry 21 }

    -- 1.3.6.1.4.1.2011.2.25.4.50.3.1.35.1.22
    optixPktDropSIpMask OBJECT-TYPE
        SYNTAX IpAddress
        MAX-ACCESS read-write
        STATUS current
        DESCRIPTION
            "This parameter indicates the wildcard of the source IP address for packet coloring."
        ::= { optixPktDropRuleEntry 22 }

    -- 1.3.6.1.4.1.2011.2.25.4.50.3.1.35.1.23
    optixPktDropDPort OBJECT-TYPE
        SYNTAX Unsigned32
        MAX-ACCESS read-write
        STATUS current
        DESCRIPTION
            "This parameter indicates the destination port ID for packet coloring."
        ::= { optixPktDropRuleEntry 23 }

    -- 1.3.6.1.4.1.2011.2.25.4.50.3.1.35.1.24
    optixPktDropDPortMask OBJECT-TYPE
        SYNTAX Unsigned32
        MAX-ACCESS read-write
        STATUS current
        DESCRIPTION
            "This parameter indicates the wildcard of the destination port ID for packet coloring."
        ::= { optixPktDropRuleEntry 24 }

    -- 1.3.6.1.4.1.2011.2.25.4.50.3.1.35.1.25
    optixPktDropSPort OBJECT-TYPE
        SYNTAX Unsigned32
        MAX-ACCESS read-write
        STATUS current
        DESCRIPTION
            "This parameter indicates the source port ID for packet coloring."
        ::= { optixPktDropRuleEntry 25 }

    -- 1.3.6.1.4.1.2011.2.25.4.50.3.1.35.1.26
    optixPktDropSPortMask OBJECT-TYPE
        SYNTAX Unsigned32
        MAX-ACCESS read-write
        STATUS current
        DESCRIPTION
            "This parameter indicates the wildcard of the source port ID for packet coloring."
        ::= { optixPktDropRuleEntry 26 }

    -- 1.3.6.1.4.1.2011.2.25.4.50.3.1.35.1.27
    optixPktDropCtag OBJECT-TYPE
        SYNTAX Unsigned32
        MAX-ACCESS read-write
        STATUS current
        DESCRIPTION
            "This parameter indicates the inner VLAN DP for packet coloring."
        ::= { optixPktDropRuleEntry 27 }

    -- 1.3.6.1.4.1.2011.2.25.4.50.3.1.35.1.28
    optixPktDropCtagMask OBJECT-TYPE
        SYNTAX Unsigned32
        MAX-ACCESS read-write
        STATUS current
        DESCRIPTION
            "This parameter indicates the wildcard of the inner VLAN DP for packet coloring."
        ::= { optixPktDropRuleEntry 28 }

    -- 1.3.6.1.4.1.2011.2.25.4.50.3.1.35.1.29
    optixPktDropEthType OBJECT-TYPE
        SYNTAX Unsigned32
        MAX-ACCESS read-write
        STATUS current
        DESCRIPTION
            "This parameter indicates the Ethernet type for packet coloring."
        ::= { optixPktDropRuleEntry 29 }

    -- 1.3.6.1.4.1.2011.2.25.4.50.3.1.35.1.30
    optixPktDropEthTypeMask OBJECT-TYPE
        SYNTAX Unsigned32
        MAX-ACCESS read-write
        STATUS current
        DESCRIPTION
            "This parameter indicates the wildcard of the Ethernet type for packet coloring."
        ::= { optixPktDropRuleEntry 30 }

    -- 1.3.6.1.4.1.2011.2.25.4.50.3.1.35.1.31
    optixPktDropIcmp OBJECT-TYPE
        SYNTAX Unsigned32
        MAX-ACCESS read-write
        STATUS current
        DESCRIPTION
            "This parameter indicates the ICMP for packet coloring."
        ::= { optixPktDropRuleEntry 31 }

    -- 1.3.6.1.4.1.2011.2.25.4.50.3.1.35.1.32
    optixPktDropIcmpMask OBJECT-TYPE
        SYNTAX Unsigned32
        MAX-ACCESS read-write
        STATUS current
        DESCRIPTION
            "This parameter indicates the ICMP wildcard for packet coloring."
        ::= { optixPktDropRuleEntry 32 }

    -- 1.3.6.1.4.1.2011.2.25.4.50.3.1.36
    optixEthSrvPointTypeTable OBJECT-TYPE
        SYNTAX SEQUENCE OF OptixEthSrvPointTypeEntry
        MAX-ACCESS not-accessible
        STATUS current
        DESCRIPTION
            "This table is used to query service configurations based on packet coloring test points."
        ::= { optixEthSrvObject 36 }

    -- 1.3.6.1.4.1.2011.2.25.4.50.3.1.36.1
    optixEthSrvPointTypeEntry OBJECT-TYPE
        SYNTAX OptixEthSrvPointTypeEntry
        MAX-ACCESS not-accessible
        STATUS current
        DESCRIPTION
            "This entry is used to query service configurations based on packet coloring test points."
        INDEX{ optixPktDropTestPointType,optixEthSrvIndex }
        ::= { optixEthSrvPointTypeTable 1 }

    OptixEthSrvPointTypeEntry ::=
        SEQUENCE {
            optixEthSrvID
                Unsigned32,
            optixEthSrvName
                OCTET STRING
        }

    -- 1.3.6.1.4.1.2011.2.25.4.50.3.1.36.1.1
    optixEthSrvID OBJECT-TYPE
        SYNTAX Unsigned32
        MAX-ACCESS read-only
        STATUS current
        DESCRIPTION
            "This parameter indicates the service ID."
        ::= { optixEthSrvPointTypeEntry 1 }

    -- 1.3.6.1.4.1.2011.2.25.4.50.3.1.36.1.2
    optixEthSrvName OBJECT-TYPE
        SYNTAX OCTET STRING
        MAX-ACCESS read-only
        STATUS current
        DESCRIPTION
            "This parameter indicates the service name."
        ::= { optixEthSrvPointTypeEntry 2 }

    -- 1.3.6.1.4.1.2011.2.25.4.50.3.1.37
    optixPktDropEthSrvTable OBJECT-TYPE
        SYNTAX SEQUENCE OF OptixPktDropEthSrvEntry
        MAX-ACCESS not-accessible
        STATUS current
        DESCRIPTION
            "This table is used to query service configurations about packet coloring."
        ::= { optixEthSrvObject 37 }

    -- 1.3.6.1.4.1.2011.2.25.4.50.3.1.37.1
    optixPktDropEthSrvEntry OBJECT-TYPE
        SYNTAX OptixPktDropEthSrvEntry
        MAX-ACCESS not-accessible
        STATUS current
        DESCRIPTION
            "This entry is used to query service configurations about packet coloring."
        INDEX{ optixPktDropTestPointType,optixEthSrvIndex,optixElanSrvIfType,optixElanSrvIfID }
        ::= { optixPktDropEthSrvTable 1 }

    OptixPktDropEthSrvEntry ::=
        SEQUENCE {
            optixEthSrvBoardID
                Unsigned32,
            optixEthSrvSubID
                Unsigned32,
            optixEthSrvPortID
                Unsigned32,
            optixEthSrvQinqID
                Unsigned32,
            optixEthSrvQinqSvlan
                Unsigned32,
            optixEthSrvTagNum
                Unsigned32,
            optixEthSrvTagList
                OCTET STRING,
            optixEthSrvIfType
                INTEGER
        }

    -- 1.3.6.1.4.1.2011.2.25.4.50.3.1.37.1.1
    optixEthSrvBoardID OBJECT-TYPE
        SYNTAX Unsigned32
        MAX-ACCESS read-only
        STATUS current
        DESCRIPTION
            "This parameter indicates the slot ID for service bearing."
        ::= { optixPktDropEthSrvEntry 1 }

    -- 1.3.6.1.4.1.2011.2.25.4.50.3.1.37.1.2
    optixEthSrvSubID OBJECT-TYPE
        SYNTAX Unsigned32
        MAX-ACCESS read-only
        STATUS current
        DESCRIPTION
            "This parameter indicates the subboard ID for service bearing."
        ::= { optixPktDropEthSrvEntry 2 }

    -- 1.3.6.1.4.1.2011.2.25.4.50.3.1.37.1.3
    optixEthSrvPortID OBJECT-TYPE
        SYNTAX Unsigned32
        MAX-ACCESS read-only
        STATUS current
        DESCRIPTION
            "This parameter indicates the port ID for service bearing."
        ::= { optixPktDropEthSrvEntry 3 }

    -- 1.3.6.1.4.1.2011.2.25.4.50.3.1.37.1.4
    optixEthSrvQinqID OBJECT-TYPE
        SYNTAX Unsigned32
        MAX-ACCESS read-only
        STATUS current
        DESCRIPTION
            "This parameter indicates the QinQ port ID for service bearing."
        ::= { optixPktDropEthSrvEntry 4 }

    -- 1.3.6.1.4.1.2011.2.25.4.50.3.1.37.1.5
    optixEthSrvQinqSvlan OBJECT-TYPE
        SYNTAX Unsigned32
        MAX-ACCESS read-only
        STATUS current
        DESCRIPTION
            "This parameter indicates the S-VLAN corresponding to the QinQ port for service bearing."
        ::= { optixPktDropEthSrvEntry 5 }

    -- 1.3.6.1.4.1.2011.2.25.4.50.3.1.37.1.6
    optixEthSrvTagNum OBJECT-TYPE
        SYNTAX Unsigned32
        MAX-ACCESS read-only
        STATUS current
        DESCRIPTION
            "This parameter indicates the number of tags of the V-UNI for service bearing."
        ::= { optixPktDropEthSrvEntry 6 }

    -- 1.3.6.1.4.1.2011.2.25.4.50.3.1.37.1.7
    optixEthSrvTagList OBJECT-TYPE
        SYNTAX OCTET STRING
        MAX-ACCESS read-only
        STATUS current
        DESCRIPTION
            "This parameter indicates the tag list of the V-UNI for service bearing."
        ::= { optixPktDropEthSrvEntry 7 }

    -- 1.3.6.1.4.1.2011.2.25.4.50.3.1.37.1.8
    optixEthSrvIfType OBJECT-TYPE
        SYNTAX INTEGER
        {
            vuni(1),
            vnni(2),
            pbvuni(3),
            vuniext(4)
        }
        MAX-ACCESS read-only
        STATUS current
        DESCRIPTION
            "This parameter indicates the type of the logical subinterface for packet coloring."
        ::= { optixPktDropEthSrvEntry 8 }

    -- 1.3.6.1.4.1.2011.2.25.4.50.3.1.38
    optixPktDropStcUcTnlTable OBJECT-TYPE
        SYNTAX SEQUENCE OF OptixPktDropStcUcTnlEntry
        MAX-ACCESS not-accessible
        STATUS current
        DESCRIPTION
            "This table describes tunnel configurations about packet coloring."
        ::= { optixEthSrvObject 38 }

    -- 1.3.6.1.4.1.2011.2.25.4.50.3.1.38.1
    optixPktDropStcUcTnlEntry OBJECT-TYPE
        SYNTAX OptixPktDropStcUcTnlEntry
        MAX-ACCESS not-accessible
        STATUS current
        DESCRIPTION
            "This entry describes tunnel configurations about packet coloring."
        INDEX{ optixPktDropStcUcTnlIndex }
        ::= { optixPktDropStcUcTnlTable 1 }

    OptixPktDropStcUcTnlEntry ::=
        SEQUENCE {
            optixPktDropStcUcTnlIndex
                Unsigned32,
            optixPktDropStcUcTnlID
                Unsigned32,
            optixPktDropStcUcTnlInBid
                Unsigned32,
            optixPktDropStcUcTnlInSubBid
                Unsigned32,
            optixPktDropStcUcTnlInPortid
                Unsigned32,
            optixPktDropStcUcTnlOutBid
                Unsigned32,
            optixPktDropStcUcTnlOutSubBid
                Unsigned32,
            optixPktDropStcUcTnlOutPortId
                Unsigned32,
            optixPktDropStcUcTnlName
                OCTET STRING
        }

    -- 1.3.6.1.4.1.2011.2.25.4.50.3.1.38.1.1
    optixPktDropStcUcTnlIndex OBJECT-TYPE
        SYNTAX Unsigned32 (1..16777215)
        MAX-ACCESS not-accessible
        STATUS current
        DESCRIPTION
            "This parameter indicates the tunnel index. The value ranges from 1 to 0x00ffffff."
        ::= { optixPktDropStcUcTnlEntry 1 }

    -- 1.3.6.1.4.1.2011.2.25.4.50.3.1.38.1.2
    optixPktDropStcUcTnlID OBJECT-TYPE
        SYNTAX Unsigned32 (1..65535)
        MAX-ACCESS read-only
        STATUS current
        DESCRIPTION
            "This parameter indicates the tunnel ID. The value ranges from 1 to 0xffff."
        ::= { optixPktDropStcUcTnlEntry 2 }

    -- 1.3.6.1.4.1.2011.2.25.4.50.3.1.38.1.3
    optixPktDropStcUcTnlInBid OBJECT-TYPE
        SYNTAX Unsigned32 (1..65535)
        MAX-ACCESS read-only
        STATUS current
        DESCRIPTION
            "This parameter indicates the slot ID of the board where the ingress port is located."
        ::= { optixPktDropStcUcTnlEntry 3 }

    -- 1.3.6.1.4.1.2011.2.25.4.50.3.1.38.1.4
    optixPktDropStcUcTnlInSubBid OBJECT-TYPE
        SYNTAX Unsigned32 (1..255)
        MAX-ACCESS read-only
        STATUS current
        DESCRIPTION
            "This parameter indicates the ID of the subboard where the ingress port is located. The value is 255 if no subboard is supported."
        ::= { optixPktDropStcUcTnlEntry 4 }

    -- 1.3.6.1.4.1.2011.2.25.4.50.3.1.38.1.5
    optixPktDropStcUcTnlInPortid OBJECT-TYPE
        SYNTAX Unsigned32 (1..65535)
        MAX-ACCESS read-only
        STATUS current
        DESCRIPTION
            "This parameter indicates the ingress port ID."
        ::= { optixPktDropStcUcTnlEntry 5 }

    -- 1.3.6.1.4.1.2011.2.25.4.50.3.1.38.1.6
    optixPktDropStcUcTnlOutBid OBJECT-TYPE
        SYNTAX Unsigned32 (1..65535)
        MAX-ACCESS read-only
        STATUS current
        DESCRIPTION
            "This parameter indicates the slot ID of the board where the egress port is located."
        ::= { optixPktDropStcUcTnlEntry 6 }

    -- 1.3.6.1.4.1.2011.2.25.4.50.3.1.38.1.7
    optixPktDropStcUcTnlOutSubBid OBJECT-TYPE
        SYNTAX Unsigned32 (1..255)
        MAX-ACCESS read-only
        STATUS current
        DESCRIPTION
            "This parameter indicates the ID of the subboard where the egress port is located. The value is 255 if no subboard is supported."
        ::= { optixPktDropStcUcTnlEntry 7 }

    -- 1.3.6.1.4.1.2011.2.25.4.50.3.1.38.1.8
    optixPktDropStcUcTnlOutPortId OBJECT-TYPE
        SYNTAX Unsigned32 (1..65535)
        MAX-ACCESS read-only
        STATUS current
        DESCRIPTION
            "This parameter indicates the egress port ID."
        ::= { optixPktDropStcUcTnlEntry 8 }

    -- 1.3.6.1.4.1.2011.2.25.4.50.3.1.38.1.9
    optixPktDropStcUcTnlName OBJECT-TYPE
        SYNTAX OCTET STRING (SIZE(0..64))
        MAX-ACCESS read-only
        STATUS current
        DESCRIPTION
            "This parameter indicates the tunnel name. The value can be left blank or contain blank spaces and Chinese characters. The maximum length is 64 bytes."
        ::= { optixPktDropStcUcTnlEntry 9 }

    -- 1.3.6.1.4.1.2011.2.25.4.50.3.1.39
    optixPktDropTrapMember OBJECT IDENTIFIER ::= { optixEthSrvObject 39 }

    -- 1.3.6.1.4.1.2011.2.25.4.50.3.1.39.1
    optixPktDropTrapTestID OBJECT-TYPE
        SYNTAX Unsigned32
        MAX-ACCESS accessible-for-notify
        STATUS current
        DESCRIPTION
            "This parameter indicates the index of the packet coloring instance in the reported event."
        ::= { optixPktDropTrapMember 1 }

    -- 1.3.6.1.4.1.2011.2.25.4.50.3.1.39.2
    optixPktDropTrapPktNum OBJECT-TYPE
        SYNTAX Counter64
        MAX-ACCESS accessible-for-notify
        STATUS current
        DESCRIPTION
            "This parameter indicates the number of colored packets in the reported event."
        ::= { optixPktDropTrapMember 2 }

    -- 1.3.6.1.4.1.2011.2.25.4.50.3.1.39.3
    optixPktDropTrapPktByte OBJECT-TYPE
        SYNTAX Counter64
        MAX-ACCESS accessible-for-notify
        STATUS current
        DESCRIPTION
            "This parameter indicates the number of bytes of the colored packets in the reported event."
        ::= { optixPktDropTrapMember 3 }

    -- 1.3.6.1.4.1.2011.2.25.4.50.3.1.39.4
    optixPktDropTrapUnPktNum OBJECT-TYPE
        SYNTAX Counter64
        MAX-ACCESS accessible-for-notify
        STATUS current
        DESCRIPTION
            "This parameter indicates the number of uncolored packets in the reported event."
        ::= { optixPktDropTrapMember 4 }

    -- 1.3.6.1.4.1.2011.2.25.4.50.3.1.39.5
    optixPktDropTrapUnPktByte OBJECT-TYPE
        SYNTAX Counter64
        MAX-ACCESS accessible-for-notify
        STATUS current
        DESCRIPTION
            "This parameter indicates the number of bytes of the uncolored packets in the reported event."
        ::= { optixPktDropTrapMember 5 }

    -- 1.3.6.1.4.1.2011.2.25.4.50.3.1.40
    optixPktDropTrapEvent OBJECT IDENTIFIER ::= { optixEthSrvObject 40 }

    -- 1.3.6.1.4.1.2011.2.25.4.50.3.1.40.1
    optixPktDropEndTrap NOTIFICATION-TYPE
        OBJECTS{ optixPktDropTrapTestID,optixPktDropTrapPktNum,optixPktDropTrapPktByte,optixPktDropTrapUnPktNum,optixPktDropTrapUnPktByte }
        STATUS current
        DESCRIPTION
            "This parameter is used to report an event about the end of packet coloring."
        ::= { optixPktDropTrapEvent 1 }

    -- 1.3.6.1.4.1.2011.2.25.4.50.3.1.41
    optixElanSrvMacFlapTable OBJECT-TYPE
        SYNTAX SEQUENCE OF OptixElanSrvMacFlapEntry
        MAX-ACCESS not-accessible
        STATUS current
        DESCRIPTION
            "This table describes configuration information about automatic disabling of E-LAN services upon MAC address flapping."
        ::= { optixEthSrvObject 41 }

    -- 1.3.6.1.4.1.2011.2.25.4.50.3.1.41.1
    optixElanSrvMacFlapEntry OBJECT-TYPE
        SYNTAX OptixElanSrvMacFlapEntry
        MAX-ACCESS not-accessible
        STATUS current
        DESCRIPTION
            "This entry describes configuration information about automatic disabling of E-LAN services upon MAC address flapping."
        INDEX{ optixElanIndex,optixElanSrvIfType,optixElanSrvIfID }
        ::= { optixElanSrvMacFlapTable 1 }

    OptixElanSrvMacFlapEntry ::=
        SEQUENCE {
            optixElanSrvIfPortPri
                Unsigned32,
            optixElanSrvAutoCloseEnable
                INTEGER,
            optixElanSrvHoldOffTime
                Unsigned32,
            optixElanSrvCheckFreq
                Unsigned32
        }

    -- 1.3.6.1.4.1.2011.2.25.4.50.3.1.41.1.1
    optixElanSrvIfPortPri OBJECT-TYPE
        SYNTAX Unsigned32
        MAX-ACCESS read-write
        STATUS current
        DESCRIPTION
            "This parameter indicates IF port priority. Value range: 1~ to 4; default value : 1"
        ::= { optixElanSrvMacFlapEntry 1 }

    -- 1.3.6.1.4.1.2011.2.25.4.50.3.1.41.1.2
    optixElanSrvAutoCloseEnable OBJECT-TYPE
        SYNTAX INTEGER
        {
            enable(1),
            disable(0)
        }
        MAX-ACCESS read-write
        STATUS current
        DESCRIPTION
            "This object indicates whether automatic service disabling upon MAC address flapping is enabled.{enable(1),disable(0)}, default:disable"
        ::= { optixElanSrvMacFlapEntry 2 }

    -- 1.3.6.1.4.1.2011.2.25.4.50.3.1.41.1.3
    optixElanSrvHoldOffTime OBJECT-TYPE
        SYNTAX Unsigned32
        MAX-ACCESS read-write
        STATUS current
        DESCRIPTION
            "This object indicates the hold-off time for automatic service disabling upon MAC address flapping .range:1 to 30(minutes), default:0"
        ::= { optixElanSrvMacFlapEntry 3 }

    -- 1.3.6.1.4.1.2011.2.25.4.50.3.1.41.1.4
    optixElanSrvCheckFreq OBJECT-TYPE
        SYNTAX Unsigned32
        MAX-ACCESS read-write
        STATUS current
        DESCRIPTION
            "This object indicates the check frequency for automatic service disabling upon MAC address flapping.range:1~1800(second), default:60"
        ::= { optixElanSrvMacFlapEntry 4 }

    -- 1.3.6.1.4.1.2011.2.25.4.50.3.1.44
    optixQueryMACTableTable OBJECT-TYPE
        SYNTAX SEQUENCE OF OptixQueryMACTableEntry
        MAX-ACCESS not-accessible
        STATUS current
        DESCRIPTION
            "This table is used to query objects in the MAC address learning result."
        ::= { optixEthSrvObject 44 }

    -- 1.3.6.1.4.1.2011.2.25.4.50.3.1.44.1
    optixQueryMACTableEntry OBJECT-TYPE
        SYNTAX OptixQueryMACTableEntry
        MAX-ACCESS not-accessible
        STATUS current
        DESCRIPTION
            "This entry is used to query objects in the MAC address learning result."
        INDEX{ optixQueryMACTableMACAddr,optixQueryMACTableMACNumIndex,optixQueryMACTableMACFlag }
        ::= { optixQueryMACTableTable 1 }

    OptixQueryMACTableEntry ::=
        SEQUENCE {
            optixQueryMACTableMACAddr
                MacAddress,
            optixQueryMACTableMACNumIndex
                Unsigned32,
            optixQueryMACTableMACTotalNum
                Unsigned32,
            optixQueryMACTableSrvIndex
                Unsigned32,
            optixQueryMACTableVlanID
                Unsigned32,
            optixQueryMACTableBDID
                Unsigned32,
            optixQueryMACTableSBID
                Unsigned32,
            optixQueryMACTablePORTID
                Unsigned32,
            optixQueryMACTableSaveTime
                OCTET STRING,
            optixQueryMACTableStcDynState
                INTEGER,
            optixQueryMACTableQuerySate
                INTEGER,
            optixQueryMACTableMACFlag
                Unsigned32,
            optixQueryMACTablePortType
                INTEGER
        }

    -- 1.3.6.1.4.1.2011.2.25.4.50.3.1.44.1.1
    optixQueryMACTableMACAddr OBJECT-TYPE
        SYNTAX MacAddress
        MAX-ACCESS not-accessible
        STATUS current
        DESCRIPTION
            "This object indicates the MAC address."
        ::= { optixQueryMACTableEntry 1 }

    -- 1.3.6.1.4.1.2011.2.25.4.50.3.1.44.1.2
    optixQueryMACTableMACNumIndex OBJECT-TYPE
        SYNTAX Unsigned32
        MAX-ACCESS not-accessible
        STATUS current
        DESCRIPTION
            "This object indicates the MAC address learning result index."
        ::= { optixQueryMACTableEntry 2 }

    -- 1.3.6.1.4.1.2011.2.25.4.50.3.1.44.1.3
    optixQueryMACTableMACTotalNum OBJECT-TYPE
        SYNTAX Unsigned32
        MAX-ACCESS read-only
        STATUS current
        DESCRIPTION
            "This object indicates the total number of MAC addresses."
        ::= { optixQueryMACTableEntry 3 }

    -- 1.3.6.1.4.1.2011.2.25.4.50.3.1.44.1.4
    optixQueryMACTableSrvIndex OBJECT-TYPE
        SYNTAX Unsigned32
        MAX-ACCESS read-only
        STATUS current
        DESCRIPTION
            "This object indicates the service index."
        ::= { optixQueryMACTableEntry 4 }

    -- 1.3.6.1.4.1.2011.2.25.4.50.3.1.44.1.5
    optixQueryMACTableVlanID OBJECT-TYPE
        SYNTAX Unsigned32
        MAX-ACCESS read-only
        STATUS current
        DESCRIPTION
            "This object indicates the VLAN ID."
        ::= { optixQueryMACTableEntry 5 }

    -- 1.3.6.1.4.1.2011.2.25.4.50.3.1.44.1.6
    optixQueryMACTableBDID OBJECT-TYPE
        SYNTAX Unsigned32
        MAX-ACCESS read-only
        STATUS current
        DESCRIPTION
            "This object indicates the board ID."
        ::= { optixQueryMACTableEntry 6 }

    -- 1.3.6.1.4.1.2011.2.25.4.50.3.1.44.1.7
    optixQueryMACTableSBID OBJECT-TYPE
        SYNTAX Unsigned32
        MAX-ACCESS read-only
        STATUS current
        DESCRIPTION
            "This object indicates the subboard ID."
        ::= { optixQueryMACTableEntry 7 }

    -- 1.3.6.1.4.1.2011.2.25.4.50.3.1.44.1.8
    optixQueryMACTablePORTID OBJECT-TYPE
        SYNTAX Unsigned32
        MAX-ACCESS read-only
        STATUS current
        DESCRIPTION
            "This object indicates the port ID."
        ::= { optixQueryMACTableEntry 8 }

    -- 1.3.6.1.4.1.2011.2.25.4.50.3.1.44.1.9
    optixQueryMACTableSaveTime OBJECT-TYPE
        SYNTAX OCTET STRING
        MAX-ACCESS read-only
        STATUS current
        DESCRIPTION
            "thisThis object indicates the time needed to store the MAC address learning result."
        ::= { optixQueryMACTableEntry 9 }

    -- 1.3.6.1.4.1.2011.2.25.4.50.3.1.44.1.10
    optixQueryMACTableStcDynState OBJECT-TYPE
        SYNTAX INTEGER
        {
            static(0),
            dynamic(1)
        }
        MAX-ACCESS read-only
        STATUS current
        DESCRIPTION
            "This object indicates whether the MAC address learning result is dynamic or static. 0: static, 1: dynamic"
        ::= { optixQueryMACTableEntry 10 }

    -- 1.3.6.1.4.1.2011.2.25.4.50.3.1.44.1.11
    optixQueryMACTableQuerySate OBJECT-TYPE
        SYNTAX INTEGER
        {
            end(1),
            continue(2)
        }
        MAX-ACCESS read-only
        STATUS current
        DESCRIPTION
            "This object indicates the query status of the MAC address learning result. 1: end, 2: continue"
        ::= { optixQueryMACTableEntry 11 }

    -- 1.3.6.1.4.1.2011.2.25.4.50.3.1.44.1.12
    optixQueryMACTableMACFlag OBJECT-TYPE
        SYNTAX Unsigned32 (1..2)
        MAX-ACCESS not-accessible
        STATUS current
        DESCRIPTION
            "This object indicates the flag of querying the MAC address learning result.1:begin,2:continue"
        ::= { optixQueryMACTableEntry 12 }

    -- 1.3.6.1.4.1.2011.2.25.4.50.3.1.44.1.13
    optixQueryMACTablePortType OBJECT-TYPE
        SYNTAX INTEGER
        {
            phyport(1),
            pw(2),
            qinq(3),
            invalid(10)
        }
        MAX-ACCESS read-only
        STATUS current
        DESCRIPTION
            "This object indicates the type of querying the port result.1:phyport,2:pw,3:qinq,10:invalid"
        ::= { optixQueryMACTableEntry 13 }

    -- 1.3.6.1.4.1.2011.2.25.4.50.3.1.50
    optixElanUniNum OBJECT-TYPE
        SYNTAX Unsigned32(1..65535)
        MAX-ACCESS read-write
        STATUS current
        DESCRIPTION
            "This object is usd to configure the number of V-UNIs supported by the private network service (NE attribute) and the usage of VPLS services for RTN products. Value range: 1 to 65535."
        DEFVAL{ 32 }
        ::= { optixEthSrvObject 50 }

    -- 1.3.6.1.4.1.2011.2.25.4.50.3.1.51
    optixElanTestResultTable OBJECT-TYPE
        SYNTAX SEQUENCE OF OptixElanTestResultEntry
        MAX-ACCESS not-accessible
        STATUS current
        DESCRIPTION
            "This table uses to query the traffic,delay time,far-end lose packet ratio,near-end lose packet ratio and long test resluts"
        ::= { optixEthSrvObject 51 }

    -- 1.3.6.1.4.1.2011.2.25.4.50.3.1.51.1
    optixElanTestResultEntry OBJECT-TYPE
        SYNTAX OptixElanTestResultEntry
        MAX-ACCESS not-accessible
        STATUS current
        DESCRIPTION
            "This entry indicates query the traffic,delay time,far-end lose packet ratio,near-end lose packet ratio and long test resluts"
        INDEX{ optixEthIndex,optixElanTestResultBeginYear,optixElanTestResultBeginMonth,optixElanTestResultBeginData,optixElanTestResultBeginHour,optixElanTestResultBeginMinute,optixElanTestResultBeginSec,optixElanTestResultEndYear,optixElanTestResultEndMonth,optixElanTestResultEndData,optixElanTestResultEndHour,optixElanTestResultEndMinute,optixElanTestResultEndSec }
        ::= { optixElanTestResultTable 1 }

    OptixElanTestResultEntry ::=
        SEQUENCE {
            optixEthIndex
                Unsigned32,
            optixElanTestResultBeginYear
                Unsigned32,
            optixElanTestResultBeginMonth
                Unsigned32,
            optixElanTestResultBeginData
                Unsigned32,
            optixElanTestResultBeginHour
                Unsigned32,
            optixElanTestResultBeginMinute
                Unsigned32,
            optixElanTestResultBeginSec
                Unsigned32,
            optixElanTestResultEndYear
                Unsigned32,
            optixElanTestResultEndMonth
                Unsigned32,
            optixElanTestResultEndData
                Unsigned32,
            optixElanTestResultEndHour
                Unsigned32,
            optixElanTestResultEndMinute
                Unsigned32,
            optixElanTestResultEndSec
                Unsigned32,
            optixElanTestResultResultType
                INTEGER,
            optixElanTestResultProgress
                Unsigned32,
            optixElanTestResultFrameSize
                Unsigned32,
            optixElanTestResultTraffic
                Unsigned32,
            optixElanTestResultSendPkt
                Unsigned32,
            optixElanTestResultRecPkt
                Unsigned32,
            optixElanTestResultLFR80
                Unsigned32,
            optixElanTestResultLFR90
                Unsigned32,
            optixElanTestResultLFR100
                Unsigned32,
            optixElanTestResultLNR80
                Unsigned32,
            optixElanTestResultLNR90
                Unsigned32,
            optixElanTestResultLNR100
                Unsigned32,
            optixElanTestResultDelay80
                Unsigned32,
            optixElanTestResultDelay90
                Unsigned32,
            optixElanTestResultDelay100
                Unsigned32
        }

    -- 1.3.6.1.4.1.2011.2.25.4.50.3.1.51.1.1
    optixEthIndex OBJECT-TYPE
        SYNTAX Unsigned32
        MAX-ACCESS not-accessible
        STATUS current
        DESCRIPTION
            "This object describes the index of service"
        ::= { optixElanTestResultEntry 1 }

    -- 1.3.6.1.4.1.2011.2.25.4.50.3.1.51.1.2
    optixElanTestResultBeginYear OBJECT-TYPE
        SYNTAX Unsigned32
        MAX-ACCESS not-accessible
        STATUS current
        DESCRIPTION
            "This object describes the begin time of year"
        ::= { optixElanTestResultEntry 2 }

    -- 1.3.6.1.4.1.2011.2.25.4.50.3.1.51.1.3
    optixElanTestResultBeginMonth OBJECT-TYPE
        SYNTAX Unsigned32
        MAX-ACCESS not-accessible
        STATUS current
        DESCRIPTION
            "This object describes the begin time of month"
        ::= { optixElanTestResultEntry 3 }

    -- 1.3.6.1.4.1.2011.2.25.4.50.3.1.51.1.4
    optixElanTestResultBeginData OBJECT-TYPE
        SYNTAX Unsigned32
        MAX-ACCESS not-accessible
        STATUS current
        DESCRIPTION
            "This object describes the begin time of day"
        ::= { optixElanTestResultEntry 4 }

    -- 1.3.6.1.4.1.2011.2.25.4.50.3.1.51.1.5
    optixElanTestResultBeginHour OBJECT-TYPE
        SYNTAX Unsigned32
        MAX-ACCESS not-accessible
        STATUS current
        DESCRIPTION
            "This object describes the begin time of hour"
        ::= { optixElanTestResultEntry 5 }

    -- 1.3.6.1.4.1.2011.2.25.4.50.3.1.51.1.6
    optixElanTestResultBeginMinute OBJECT-TYPE
        SYNTAX Unsigned32
        MAX-ACCESS not-accessible
        STATUS current
        DESCRIPTION
            "This object describes the begin time of minute"
        ::= { optixElanTestResultEntry 6 }

    -- 1.3.6.1.4.1.2011.2.25.4.50.3.1.51.1.7
    optixElanTestResultBeginSec OBJECT-TYPE
        SYNTAX Unsigned32
        MAX-ACCESS not-accessible
        STATUS current
        DESCRIPTION
            "This object describes the begin time of second"
        ::= { optixElanTestResultEntry 7 }

    -- 1.3.6.1.4.1.2011.2.25.4.50.3.1.51.1.8
    optixElanTestResultEndYear OBJECT-TYPE
        SYNTAX Unsigned32
        MAX-ACCESS not-accessible
        STATUS current
        DESCRIPTION
            "This object describes the end time of year"
        ::= { optixElanTestResultEntry 8 }

    -- 1.3.6.1.4.1.2011.2.25.4.50.3.1.51.1.9
    optixElanTestResultEndMonth OBJECT-TYPE
        SYNTAX Unsigned32
        MAX-ACCESS not-accessible
        STATUS current
        DESCRIPTION
            "This object describes the end time of month"
        ::= { optixElanTestResultEntry 9 }

    -- 1.3.6.1.4.1.2011.2.25.4.50.3.1.51.1.10
    optixElanTestResultEndData OBJECT-TYPE
        SYNTAX Unsigned32
        MAX-ACCESS not-accessible
        STATUS current
        DESCRIPTION
            "This object describes the end time of day"
        ::= { optixElanTestResultEntry 10 }

    -- 1.3.6.1.4.1.2011.2.25.4.50.3.1.51.1.11
    optixElanTestResultEndHour OBJECT-TYPE
        SYNTAX Unsigned32
        MAX-ACCESS not-accessible
        STATUS current
        DESCRIPTION
            "This object describes the end time of hour"
        ::= { optixElanTestResultEntry 11 }

    -- 1.3.6.1.4.1.2011.2.25.4.50.3.1.51.1.12
    optixElanTestResultEndMinute OBJECT-TYPE
        SYNTAX Unsigned32
        MAX-ACCESS not-accessible
        STATUS current
        DESCRIPTION
            "This object describes the end time of minute"
        ::= { optixElanTestResultEntry 12 }

    -- 1.3.6.1.4.1.2011.2.25.4.50.3.1.51.1.13
    optixElanTestResultEndSec OBJECT-TYPE
        SYNTAX Unsigned32
        MAX-ACCESS not-accessible
        STATUS current
        DESCRIPTION
            "This object describes the end time of second"
        ::= { optixElanTestResultEntry 13 }

    -- 1.3.6.1.4.1.2011.2.25.4.50.3.1.51.1.14
    optixElanTestResultResultType OBJECT-TYPE
        SYNTAX INTEGER
        {
            shortTest(0),
            longTest(1)
        }
        MAX-ACCESS read-only
        STATUS current
        DESCRIPTION
            "This object describes the test-type:0 means traffic,delay time,lose ratio test;1 means lose ratio test for much hours."
        ::= { optixElanTestResultEntry 14 }

    -- 1.3.6.1.4.1.2011.2.25.4.50.3.1.51.1.15
    optixElanTestResultProgress OBJECT-TYPE
        SYNTAX Unsigned32
        MAX-ACCESS read-only
        STATUS current
        DESCRIPTION
            "This object describes the progess of test,only effect for traffic,delay time,lose packet test;the value must be 0(testing) or 100(test end) for lose packt ratio for much hours."
        ::= { optixElanTestResultEntry 15 }

    -- 1.3.6.1.4.1.2011.2.25.4.50.3.1.51.1.16
    optixElanTestResultFrameSize OBJECT-TYPE
        SYNTAX Unsigned32
        MAX-ACCESS read-only
        STATUS current
        DESCRIPTION
            "This object describes the length of packet"
        ::= { optixElanTestResultEntry 16 }

    -- 1.3.6.1.4.1.2011.2.25.4.50.3.1.51.1.17
    optixElanTestResultTraffic OBJECT-TYPE
        SYNTAX Unsigned32
        MAX-ACCESS read-only
        STATUS current
        DESCRIPTION
            "This object describes the value of traffic,unit:kbit/s"
        ::= { optixElanTestResultEntry 17 }

    -- 1.3.6.1.4.1.2011.2.25.4.50.3.1.51.1.18
    optixElanTestResultSendPkt OBJECT-TYPE
        SYNTAX Unsigned32
        MAX-ACCESS read-only
        STATUS current
        DESCRIPTION
            "This object describes the amount of send-packets"
        ::= { optixElanTestResultEntry 18 }

    -- 1.3.6.1.4.1.2011.2.25.4.50.3.1.51.1.19
    optixElanTestResultRecPkt OBJECT-TYPE
        SYNTAX Unsigned32
        MAX-ACCESS read-only
        STATUS current
        DESCRIPTION
            "This object describes the amount of receive-packets"
        ::= { optixElanTestResultEntry 19 }

    -- 1.3.6.1.4.1.2011.2.25.4.50.3.1.51.1.20
    optixElanTestResultLFR80 OBJECT-TYPE
        SYNTAX Unsigned32
        MAX-ACCESS read-only
        STATUS current
        DESCRIPTION
            "This object describes the far-end lose packet ration when 80% traffic,range:0~10000,unit:0.01%"
        ::= { optixElanTestResultEntry 20 }

    -- 1.3.6.1.4.1.2011.2.25.4.50.3.1.51.1.21
    optixElanTestResultLFR90 OBJECT-TYPE
        SYNTAX Unsigned32
        MAX-ACCESS read-only
        STATUS current
        DESCRIPTION
            "This object describes the far-end lose packet ration when 90% traffic,range:0~10000,unit:0.01%"
        ::= { optixElanTestResultEntry 21 }

    -- 1.3.6.1.4.1.2011.2.25.4.50.3.1.51.1.22
    optixElanTestResultLFR100 OBJECT-TYPE
        SYNTAX Unsigned32
        MAX-ACCESS read-only
        STATUS current
        DESCRIPTION
            "This object describes the far-end lose packet ration when 100% traffic,range:0~10000,unit:0.01%"
        ::= { optixElanTestResultEntry 22 }

    -- 1.3.6.1.4.1.2011.2.25.4.50.3.1.51.1.23
    optixElanTestResultLNR80 OBJECT-TYPE
        SYNTAX Unsigned32
        MAX-ACCESS read-only
        STATUS current
        DESCRIPTION
            "This object describes the far-end lose packet ration when 80% traffic,range:0~10000,unit:0.01%"
        ::= { optixElanTestResultEntry 23 }

    -- 1.3.6.1.4.1.2011.2.25.4.50.3.1.51.1.24
    optixElanTestResultLNR90 OBJECT-TYPE
        SYNTAX Unsigned32
        MAX-ACCESS read-only
        STATUS current
        DESCRIPTION
            "This object describes the far-end lose packet ration when 90% traffic,range:0~10000,unit:0.01%"
        ::= { optixElanTestResultEntry 24 }

    -- 1.3.6.1.4.1.2011.2.25.4.50.3.1.51.1.25
    optixElanTestResultLNR100 OBJECT-TYPE
        SYNTAX Unsigned32
        MAX-ACCESS read-only
        STATUS current
        DESCRIPTION
            "This object describes the far-end lose packet ration when 100% traffic,range:0~10000,unit:0.01%"
        ::= { optixElanTestResultEntry 25 }

    -- 1.3.6.1.4.1.2011.2.25.4.50.3.1.51.1.26
    optixElanTestResultDelay80 OBJECT-TYPE
        SYNTAX Unsigned32
        MAX-ACCESS read-only
        STATUS current
        DESCRIPTION
            "This object describes the delay-time when 80% traffic,unit:us"
        ::= { optixElanTestResultEntry 26 }

    -- 1.3.6.1.4.1.2011.2.25.4.50.3.1.51.1.27
    optixElanTestResultDelay90 OBJECT-TYPE
        SYNTAX Unsigned32
        MAX-ACCESS read-only
        STATUS current
        DESCRIPTION
            "This object describes the delay-time when 90% traffic,unit:us"
        ::= { optixElanTestResultEntry 27 }

    -- 1.3.6.1.4.1.2011.2.25.4.50.3.1.51.1.28
    optixElanTestResultDelay100 OBJECT-TYPE
        SYNTAX Unsigned32
        MAX-ACCESS read-only
        STATUS current
        DESCRIPTION
            "This object describes the delay-time when 100% traffic,unit:us"
        ::= { optixElanTestResultEntry 28 }

    -- 1.3.6.1.4.1.2011.2.25.4.50.3.1.52
    optixElanSrvPacketlossEventMember OBJECT IDENTIFIER ::= { optixEthSrvObject 52 }

    -- 1.3.6.1.4.1.2011.2.25.4.50.3.1.52.1
    optixElanEvtIndex OBJECT-TYPE
        SYNTAX Unsigned32
        MAX-ACCESS accessible-for-notify
        STATUS current
        DESCRIPTION
            "This object describes the index of ethservice"
        ::= { optixElanSrvPacketlossEventMember 1 }

    -- 1.3.6.1.4.1.2011.2.25.4.50.3.1.52.2
    optixElanEvtFrameSize OBJECT-TYPE
        SYNTAX Unsigned32
        MAX-ACCESS accessible-for-notify
        STATUS current
        DESCRIPTION
            "This object describes the frame size of packet"
        ::= { optixElanSrvPacketlossEventMember 2 }

    -- 1.3.6.1.4.1.2011.2.25.4.50.3.1.52.3
    optixElanEvtTrafficRatio OBJECT-TYPE
        SYNTAX Unsigned32
        MAX-ACCESS accessible-for-notify
        STATUS current
        DESCRIPTION
            "This object describes the percent of traffic.range:0~100,unit:%"
        ::= { optixElanSrvPacketlossEventMember 3 }

    -- 1.3.6.1.4.1.2011.2.25.4.50.3.1.52.4
    optixElanEvtLossRatio OBJECT-TYPE
        SYNTAX Unsigned32
        MAX-ACCESS accessible-for-notify
        STATUS current
        DESCRIPTION
            "This object describes the lose packet ration ,range:0~10000,unit:0.01%"
        ::= { optixElanSrvPacketlossEventMember 4 }

    -- 1.3.6.1.4.1.2011.2.25.4.50.3.1.52.5
    optixElanEvtProgress OBJECT-TYPE
        SYNTAX Unsigned32
        MAX-ACCESS accessible-for-notify
        STATUS current
        DESCRIPTION
            "This object describes the progress of task,range:1~100,unit:%"
        ::= { optixElanSrvPacketlossEventMember 5 }

    -- 1.3.6.1.4.1.2011.2.25.4.50.3.1.53
    optixElanSrvPacketlossEvent OBJECT IDENTIFIER ::= { optixEthSrvObject 53 }

    -- 1.3.6.1.4.1.2011.2.25.4.50.3.1.53.1
    optixElanSrvPacketloss NOTIFICATION-TYPE
        OBJECTS{ optixElanEvtIndex,optixElanEvtFrameSize,optixElanEvtTrafficRatio,optixElanEvtLossRatio,optixElanEvtProgress }
        STATUS current
        DESCRIPTION
            "This object describes the event of lose pacet ratio"
        ::= { optixElanSrvPacketlossEvent 1 }

    -- 1.3.6.1.4.1.2011.2.25.4.50.3.1.54
    optixElanSrvStateTable OBJECT-TYPE
        SYNTAX SEQUENCE OF OptixElanSrvStateEntry
        MAX-ACCESS not-accessible
        STATUS current
        DESCRIPTION
            "The table indicates the state of the elan ethserv configuration information."
        ::= { optixEthSrvObject 54 }

    -- 1.3.6.1.4.1.2011.2.25.4.50.3.1.54.1
    optixElanSrvStateEntry OBJECT-TYPE
        SYNTAX OptixElanSrvStateEntry
        MAX-ACCESS not-accessible
        STATUS current
        DESCRIPTION
            "This entry indicates the auto-loop detect of the elan ethserv configurations information."
        INDEX{ optixElanIndex,optixElanSrvIfType,optixElanSrvIfID,optixElanSrvVlanNum,optixElanSrvVlanID }
        ::= { optixElanSrvStateTable 1 }

    OptixElanSrvStateEntry ::=
        SEQUENCE {
            optixElanSrvIfType
                INTEGER,
            optixElanSrvIfID
                Unsigned32,
            optixElanSrvVlanNum
                Unsigned32,
            optixElanSrvVlanID
                Unsigned32,
            optixElanSrvCloseState
                INTEGER
        }

    -- 1.3.6.1.4.1.2011.2.25.4.50.3.1.54.1.1
    optixElanSrvIfType OBJECT-TYPE
        SYNTAX INTEGER
        {
            vuni(1),
            vnni(2)
        }
        MAX-ACCESS not-accessible
        STATUS current
        DESCRIPTION
            "This parameter indicates the logical interface type. 1: vuni 2: vnni"
        ::= { optixElanSrvStateEntry 1 }

    -- 1.3.6.1.4.1.2011.2.25.4.50.3.1.54.1.2
    optixElanSrvIfID OBJECT-TYPE
        SYNTAX Unsigned32
        MAX-ACCESS not-accessible
        STATUS current
        DESCRIPTION
            "This parameter indicates the logical interface ID."
        ::= { optixElanSrvStateEntry 2 }

    -- 1.3.6.1.4.1.2011.2.25.4.50.3.1.54.1.3
    optixElanSrvVlanNum OBJECT-TYPE
        SYNTAX Unsigned32
        MAX-ACCESS not-accessible
        STATUS current
        DESCRIPTION
            "This parameter indicates the number of VLANs."
        ::= { optixElanSrvStateEntry 3 }

    -- 1.3.6.1.4.1.2011.2.25.4.50.3.1.54.1.4
    optixElanSrvVlanID OBJECT-TYPE
        SYNTAX Unsigned32
        MAX-ACCESS not-accessible
        STATUS current
        DESCRIPTION
            "This parameter indicates the VLAN ID."
        ::= { optixElanSrvStateEntry 4 }

    -- 1.3.6.1.4.1.2011.2.25.4.50.3.1.54.1.5
    optixElanSrvCloseState OBJECT-TYPE
        SYNTAX INTEGER
        {
            close(0),
            open(1)
        }
        MAX-ACCESS read-write
        STATUS current
        DESCRIPTION
            "This parameter indicates the Ethernet service is disabled."
        ::= { optixElanSrvStateEntry 5 }

    -- 1.3.6.1.4.1.2011.2.25.4.50.3.1.55
    optixElanSrvLDTable OBJECT-TYPE
        SYNTAX SEQUENCE OF OptixElanSrvLDEntry
        MAX-ACCESS not-accessible
        STATUS current
        DESCRIPTION
            "This table indicates the auto-loop detect of the elan ethserv configurations information."
        ::= { optixEthSrvObject 55 }

    -- 1.3.6.1.4.1.2011.2.25.4.50.3.1.55.1
    optixElanSrvLDEntry OBJECT-TYPE
        SYNTAX OptixElanSrvLDEntry
        MAX-ACCESS not-accessible
        STATUS current
        DESCRIPTION
            "This entry indicates the auto-loop detect of the elan ethserv configurations information."
        INDEX{ optixElanIndex,optixElanSrvIfType,optixElanSrvIfID }
        ::= { optixElanSrvLDTable 1 }

    OptixElanSrvLDEntry ::=
        SEQUENCE {
            optixElanSrvLDPackLen
                Unsigned32,
            optixElanSrvLDSndInt
                Unsigned32,
            optixElanSrvLDHoldTime
                Unsigned32,
            optixElanSrvLDAutoClose
                Unsigned32,
            optixElanSrvLDVlanNum
                Unsigned32,
            optixElanSrvLDVlanList
                OCTET STRING,
            optixElanSrvLDStartFlag
                INTEGER
        }

    -- 1.3.6.1.4.1.2011.2.25.4.50.3.1.55.1.1
    optixElanSrvLDPackLen OBJECT-TYPE
        SYNTAX Unsigned32
        MAX-ACCESS read-write
        STATUS current
        DESCRIPTION
            "This parameter indicates the length of the packet. The value cannot be changed and the default value is 64."
        ::= { optixElanSrvLDEntry 1 }

    -- 1.3.6.1.4.1.2011.2.25.4.50.3.1.55.1.2
    optixElanSrvLDSndInt OBJECT-TYPE
        SYNTAX Unsigned32
        MAX-ACCESS read-write
        STATUS current
        DESCRIPTION
            "This parameter indicates the interval of sending detection packets between different VLAN services. The unit is ms. The value cannot be changed and the default value is 200 ms."
        ::= { optixElanSrvLDEntry 2 }

    -- 1.3.6.1.4.1.2011.2.25.4.50.3.1.55.1.3
    optixElanSrvLDHoldTime OBJECT-TYPE
        SYNTAX Unsigned32
        MAX-ACCESS read-write
        STATUS current
        DESCRIPTION
            "This parameter indicates the expire time of the packet. The unit is s. The value range is from 3s to 10s and the default value is 3s."
        ::= { optixElanSrvLDEntry 3 }

    -- 1.3.6.1.4.1.2011.2.25.4.50.3.1.55.1.4
    optixElanSrvLDAutoClose OBJECT-TYPE
        SYNTAX Unsigned32
        MAX-ACCESS read-write
        STATUS current
        DESCRIPTION
            "This parameter indicates whether loopback services are closed automatically. The value 0 is the default value and it indicates that loop services are not closed automatically. The value 1 indicates that loop services are closed automatically."
        ::= { optixElanSrvLDEntry 4 }

    -- 1.3.6.1.4.1.2011.2.25.4.50.3.1.55.1.5
    optixElanSrvLDVlanNum OBJECT-TYPE
        SYNTAX Unsigned32
        MAX-ACCESS read-write
        STATUS current
        DESCRIPTION
            "This parameter indicates the number of VLANs. The value range is from 0 to 20. The value 0 indicates that the detection packet does not have a VLAN ID."
        ::= { optixElanSrvLDEntry 5 }

    -- 1.3.6.1.4.1.2011.2.25.4.50.3.1.55.1.6
    optixElanSrvLDVlanList OBJECT-TYPE
        SYNTAX OCTET STRING
        MAX-ACCESS read-write
        STATUS current
        DESCRIPTION
            "This parameter indicates the VLAN LIST. The value range is from 1 to 4094. The value 0xfffe indicates all the VLANs. If the value of VLAN LIST is 0xfffe, the value of VLAN NUM can be only 1."
        ::= { optixElanSrvLDEntry 6 }

    -- 1.3.6.1.4.1.2011.2.25.4.50.3.1.55.1.7
    optixElanSrvLDStartFlag OBJECT-TYPE
        SYNTAX INTEGER
        {
            start(0),
            stop(1)
        }
        MAX-ACCESS read-write
        STATUS current
        DESCRIPTION
            "This parameter indicates whether the auto-loopback detection function of private network services is enabled or disabled."
        ::= { optixElanSrvLDEntry 7 }

    -- 1.3.6.1.4.1.2011.2.25.4.50.3.1.56
    optixElanSrvCycLDTable OBJECT-TYPE
        SYNTAX SEQUENCE OF OptixElanSrvCycLDEntry
        MAX-ACCESS not-accessible
        STATUS current
        DESCRIPTION
            "This table indicates the auto-loop cycle detect of the elan ethserv configurations information."
        ::= { optixEthSrvObject 56 }

    -- 1.3.6.1.4.1.2011.2.25.4.50.3.1.56.1
    optixElanSrvCycLDEntry OBJECT-TYPE
        SYNTAX OptixElanSrvCycLDEntry
        MAX-ACCESS not-accessible
        STATUS current
        DESCRIPTION
            "This entry indicates the auto-loop cycle detect of the elan ethserv configurations information."
        INDEX{ optixElanIndex,optixElanSrvIfType,optixElanSrvIfID }
        ::= { optixElanSrvCycLDTable 1 }

    OptixElanSrvCycLDEntry ::=
        SEQUENCE {
            optixElanSrvCycLDPackLen
                Unsigned32,
            optixElanSrvCycLDStartFlag
                INTEGER,
            optixElanSrvCycLDSVlanList
                OCTET STRING,
            optixElanSrvCycLDSndInt
                Unsigned32,
            optixElanSrvCycLDHoldTime
                Unsigned32,
            optixElanSrvCycLDAutoClose
                INTEGER,
            optixElanSrvCycLDCyCtime
                Unsigned32,
            optixElanSrvCycLDCVlanNum
                Unsigned32,
            optixElanSrvCycLDCVlanList
                OCTET STRING,
            optixElanSrvCycLDSVlanNum
                OCTET STRING,
            optixElanSrvCycLDRowStatus
                RowStatus
        }

    -- 1.3.6.1.4.1.2011.2.25.4.50.3.1.56.1.1
    optixElanSrvCycLDPackLen OBJECT-TYPE
        SYNTAX Unsigned32
        MAX-ACCESS read-create
        STATUS current
        DESCRIPTION
            "This parameter indicates the length of the packet. The value cannot be changed and the default value is 64."
        ::= { optixElanSrvCycLDEntry 1 }

    -- 1.3.6.1.4.1.2011.2.25.4.50.3.1.56.1.2
    optixElanSrvCycLDStartFlag OBJECT-TYPE
        SYNTAX INTEGER
        {
            start(0),
            stop(1)
        }
        MAX-ACCESS read-create
        STATUS current
        DESCRIPTION
            "This parameter indicates whether the periodic loopback detection function of private network services is enabled or disabled."
        ::= { optixElanSrvCycLDEntry 2 }

    -- 1.3.6.1.4.1.2011.2.25.4.50.3.1.56.1.3
    optixElanSrvCycLDSVlanList OBJECT-TYPE
        SYNTAX OCTET STRING
        MAX-ACCESS read-create
        STATUS current
        DESCRIPTION
            "This parameter indicates the SVLAN LIST. The value range is from 1 to 4094."
        ::= { optixElanSrvCycLDEntry 3 }

    -- 1.3.6.1.4.1.2011.2.25.4.50.3.1.56.1.4
    optixElanSrvCycLDSndInt OBJECT-TYPE
        SYNTAX Unsigned32
        MAX-ACCESS read-create
        STATUS current
        DESCRIPTION
            "This parameter indicates the interval of sending detection packets between different VLAN services. The unit is ms. The value cannot be changed and the default value is 200 ms."
        ::= { optixElanSrvCycLDEntry 4 }

    -- 1.3.6.1.4.1.2011.2.25.4.50.3.1.56.1.5
    optixElanSrvCycLDHoldTime OBJECT-TYPE
        SYNTAX Unsigned32
        MAX-ACCESS read-create
        STATUS current
        DESCRIPTION
            "This parameter indicates the expire time of the packet. The unit is s. The value cannot be changed and the default value is 10s."
        ::= { optixElanSrvCycLDEntry 5 }

    -- 1.3.6.1.4.1.2011.2.25.4.50.3.1.56.1.6
    optixElanSrvCycLDAutoClose OBJECT-TYPE
        SYNTAX INTEGER
        {
            enable(0),
            autoclose(1)
        }
        MAX-ACCESS read-create
        STATUS current
        DESCRIPTION
            "This parameter indicates whether loopback services are closed automatically. enable: indicates that loop services are not closed automatically. (default value) autoclose: indicates that loop services are closed automatically."
        ::= { optixElanSrvCycLDEntry 6 }

    -- 1.3.6.1.4.1.2011.2.25.4.50.3.1.56.1.7
    optixElanSrvCycLDCyCtime OBJECT-TYPE
        SYNTAX Unsigned32
        MAX-ACCESS read-create
        STATUS current
        DESCRIPTION
            "This parameter indicates the cyclic detection time. The value range is from 1s to 30 minutes and the default value is 60s."
        ::= { optixElanSrvCycLDEntry 7 }

    -- 1.3.6.1.4.1.2011.2.25.4.50.3.1.56.1.8
    optixElanSrvCycLDCVlanNum OBJECT-TYPE
        SYNTAX Unsigned32
        MAX-ACCESS read-create
        STATUS current
        DESCRIPTION
            "This parameter indicates the number of CVLANs. The value range is from 0 to 20. The value 0 indicates that the detection packet does not have a VLAN ID."
        ::= { optixElanSrvCycLDEntry 8 }

    -- 1.3.6.1.4.1.2011.2.25.4.50.3.1.56.1.9
    optixElanSrvCycLDCVlanList OBJECT-TYPE
        SYNTAX OCTET STRING
        MAX-ACCESS read-create
        STATUS current
        DESCRIPTION
            "This parameter indicates CVLAN LIST. The value range is from 1 to 4094."
        ::= { optixElanSrvCycLDEntry 9 }

    -- 1.3.6.1.4.1.2011.2.25.4.50.3.1.56.1.10
    optixElanSrvCycLDSVlanNum OBJECT-TYPE
        SYNTAX OCTET STRING
        MAX-ACCESS read-create
        STATUS current
        DESCRIPTION
            "This parameter indicates the number of SVLANs. The value range is from 0 to 20. The value 0 indicates that the detection packet does not have a VLAN ID."
        ::= { optixElanSrvCycLDEntry 10 }

    -- 1.3.6.1.4.1.2011.2.25.4.50.3.1.56.1.255
    optixElanSrvCycLDRowStatus OBJECT-TYPE
        SYNTAX RowStatus
        MAX-ACCESS read-create
        STATUS current
        DESCRIPTION
            "This parameter indicates the status of the periodic loopback detection of private network services."
        ::= { optixElanSrvCycLDEntry 255 }

    -- 1.3.6.1.4.1.2011.2.25.4.50.3.1.57
    optixElanSrvCycLDRetTable OBJECT-TYPE
        SYNTAX SEQUENCE OF OptixElanSrvCycLDRetEntry
        MAX-ACCESS not-accessible
        STATUS current
        DESCRIPTION
            "This table indicates the detected result of the auto-loop detect of the elan ethserv configurations information."
        ::= { optixEthSrvObject 57 }

    -- 1.3.6.1.4.1.2011.2.25.4.50.3.1.57.1
    optixElanSrvCycLDRetEntry OBJECT-TYPE
        SYNTAX OptixElanSrvCycLDRetEntry
        MAX-ACCESS not-accessible
        STATUS current
        DESCRIPTION
            "This table entry the detected result of the auto-loop detect of the elan ethserv configurations information."
        INDEX{ optixElanIndex,optixElanSrvCycLDSndIfType,optixElanSrvCycLDSndIfID,optixElanSrvCycLDVlanID,optixElanSrvCycLDTime }
        ::= { optixElanSrvCycLDRetTable 1 }

    OptixElanSrvCycLDRetEntry ::=
        SEQUENCE {
            optixElanSrvCycLDSndIfType
                INTEGER,
            optixElanSrvCycLDSndIfID
                Unsigned32,
            optixElanSrvCycLDVlanID
                Unsigned32,
            optixElanSrvCycLDTime
                DateAndTime,
            optixElanSrvCycLDDetResult
                Unsigned32,
            optixElanSrvCycLDRcvIfType
                INTEGER,
            optixElanSrvCycLDRcvIfID
                Unsigned32,
            optixElanSrvCycLDCloseState
                INTEGER
        }

    -- 1.3.6.1.4.1.2011.2.25.4.50.3.1.57.1.1
    optixElanSrvCycLDSndIfType OBJECT-TYPE
        SYNTAX INTEGER
        {
            vuni(1),
            vnni(2)
        }
        MAX-ACCESS not-accessible
        STATUS current
        DESCRIPTION
            "This parameter indicates the type of the logical interface that sends detection packets."
        ::= { optixElanSrvCycLDRetEntry 1 }

    -- 1.3.6.1.4.1.2011.2.25.4.50.3.1.57.1.2
    optixElanSrvCycLDSndIfID OBJECT-TYPE
        SYNTAX Unsigned32
        MAX-ACCESS not-accessible
        STATUS current
        DESCRIPTION
            "This parameter indicates the type of the logical interface that sends detection packets."
        ::= { optixElanSrvCycLDRetEntry 2 }

    -- 1.3.6.1.4.1.2011.2.25.4.50.3.1.57.1.3
    optixElanSrvCycLDVlanID OBJECT-TYPE
        SYNTAX Unsigned32
        MAX-ACCESS not-accessible
        STATUS current
        DESCRIPTION
            "This parameter indicates the VLAN ID."
        ::= { optixElanSrvCycLDRetEntry 3 }

    -- 1.3.6.1.4.1.2011.2.25.4.50.3.1.57.1.4
    optixElanSrvCycLDTime OBJECT-TYPE
        SYNTAX DateAndTime
        MAX-ACCESS not-accessible
        STATUS current
        DESCRIPTION
            "This parameter indicates the time when the change is detected."
        ::= { optixElanSrvCycLDRetEntry 4 }

    -- 1.3.6.1.4.1.2011.2.25.4.50.3.1.57.1.5
    optixElanSrvCycLDDetResult OBJECT-TYPE
        SYNTAX Unsigned32
        MAX-ACCESS read-only
        STATUS current
        DESCRIPTION
            "This parameter indicates the detection result."
        ::= { optixElanSrvCycLDRetEntry 5 }

    -- 1.3.6.1.4.1.2011.2.25.4.50.3.1.57.1.6
    optixElanSrvCycLDRcvIfType OBJECT-TYPE
        SYNTAX INTEGER
        {
            vuni(1),
            vnni(2)
        }
        MAX-ACCESS read-only
        STATUS current
        DESCRIPTION
            "This parameter indicates the type of the logical interface that receives detection packets."
        ::= { optixElanSrvCycLDRetEntry 6 }

    -- 1.3.6.1.4.1.2011.2.25.4.50.3.1.57.1.7
    optixElanSrvCycLDRcvIfID OBJECT-TYPE
        SYNTAX Unsigned32
        MAX-ACCESS read-only
        STATUS current
        DESCRIPTION
            "This parameter indicates the type of the logical interface that receives detection packets."
        ::= { optixElanSrvCycLDRetEntry 7 }

    -- 1.3.6.1.4.1.2011.2.25.4.50.3.1.57.1.8
    optixElanSrvCycLDCloseState OBJECT-TYPE
        SYNTAX INTEGER
        {
            close(0),
            open(1)
        }
        MAX-ACCESS read-only
        STATUS current
        DESCRIPTION
            "This parameter indicates the open/close status of the service."
        ::= { optixElanSrvCycLDRetEntry 8 }

    -- 1.3.6.1.4.1.2011.2.25.4.50.3.1.58
    optixElanSrvLDTrapMember OBJECT IDENTIFIER ::= { optixEthSrvObject 58 }

    -- 1.3.6.1.4.1.2011.2.25.4.50.3.1.58.1
    optixElanSrvLDTrapQue OBJECT-TYPE
        SYNTAX Unsigned32
        MAX-ACCESS accessible-for-notify
        STATUS current
        DESCRIPTION
            "This parameter indicates the service index of the reported event."
        ::= { optixElanSrvLDTrapMember 1 }

    -- 1.3.6.1.4.1.2011.2.25.4.50.3.1.58.2
    optixElanSrvLDTrapRcvIfValid OBJECT-TYPE
        SYNTAX INTEGER
        {
            invalid(0),
            valid(1)
        }
        MAX-ACCESS accessible-for-notify
        STATUS current
        DESCRIPTION
            "This parameter indicates the validity of the logical interface that receives the detection packet in the reported event."
        ::= { optixElanSrvLDTrapMember 2 }

    -- 1.3.6.1.4.1.2011.2.25.4.50.3.1.58.3
    optixElanSrvLDTrapSndMac OBJECT-TYPE
        SYNTAX OCTET STRING
        MAX-ACCESS accessible-for-notify
        STATUS current
        DESCRIPTION
            "This parameter indicates the source MAC address of the loopback detection device in the reported event."
        ::= { optixElanSrvLDTrapMember 3 }

    -- 1.3.6.1.4.1.2011.2.25.4.50.3.1.58.4
    optixElanSrvLDTrapTime OBJECT-TYPE
        SYNTAX DateAndTime
        MAX-ACCESS accessible-for-notify
        STATUS current
        DESCRIPTION
            "This parameter indicates the time when the change is detected."
        ::= { optixElanSrvLDTrapMember 4 }

    -- 1.3.6.1.4.1.2011.2.25.4.50.3.1.58.5
    optixElanSrvLDTrapCloseState OBJECT-TYPE
        SYNTAX INTEGER
        {
            close(0),
            open(1)
        }
        MAX-ACCESS accessible-for-notify
        STATUS current
        DESCRIPTION
            "This parameter indicates the open/close status of the service."
        ::= { optixElanSrvLDTrapMember 5 }

    -- 1.3.6.1.4.1.2011.2.25.4.50.3.1.58.6
    optixElanSrvLDTrapSrvIndex OBJECT-TYPE
        SYNTAX Unsigned32
        MAX-ACCESS accessible-for-notify
        STATUS current
        DESCRIPTION
            "This parameter indicates the service index of the reported event."
        ::= { optixElanSrvLDTrapMember 6 }

    -- 1.3.6.1.4.1.2011.2.25.4.50.3.1.58.7
    optixElanSrvLDTrapSndIfType OBJECT-TYPE
        SYNTAX INTEGER
        {
            vuni(1),
            vnni(2)
        }
        MAX-ACCESS accessible-for-notify
        STATUS current
        DESCRIPTION
            "This parameter indicates the type of the logical interface that sends the detection packet in the reported event."
        ::= { optixElanSrvLDTrapMember 7 }

    -- 1.3.6.1.4.1.2011.2.25.4.50.3.1.58.8
    optixElanSrvLDTrapSndIfID OBJECT-TYPE
        SYNTAX Unsigned32
        MAX-ACCESS accessible-for-notify
        STATUS current
        DESCRIPTION
            "This parameter indicates the ID of the logical interface that sends the detection packet in the reported event."
        ::= { optixElanSrvLDTrapMember 8 }

    -- 1.3.6.1.4.1.2011.2.25.4.50.3.1.58.9
    optixElanSrvLDTrapVlanID OBJECT-TYPE
        SYNTAX Unsigned32
        MAX-ACCESS accessible-for-notify
        STATUS current
        DESCRIPTION
            "This parameter indicates the VLAN ID of the reported event."
        ::= { optixElanSrvLDTrapMember 9 }

    -- 1.3.6.1.4.1.2011.2.25.4.50.3.1.58.10
    optixElanSrvLDTrapDetResult OBJECT-TYPE
        SYNTAX Unsigned32
        MAX-ACCESS accessible-for-notify
        STATUS current
        DESCRIPTION
            "This parameter indicates the detection result of the reported event."
        ::= { optixElanSrvLDTrapMember 10 }

    -- 1.3.6.1.4.1.2011.2.25.4.50.3.1.58.11
    optixElanSrvLDTrapRcvIfType OBJECT-TYPE
        SYNTAX INTEGER
        {
            vuni(1),
            vnni(2)
        }
        MAX-ACCESS accessible-for-notify
        STATUS current
        DESCRIPTION
            "This parameter indicates the type of the logical interface that receives the detection packet in the reported event."
        ::= { optixElanSrvLDTrapMember 11 }

    -- 1.3.6.1.4.1.2011.2.25.4.50.3.1.58.12
    optixElanSrvLDTrapRcvIfID OBJECT-TYPE
        SYNTAX Unsigned32
        MAX-ACCESS accessible-for-notify
        STATUS current
        DESCRIPTION
            "This parameter indicates the ID of the logical interface that receives the detection packet in the reported event."
        ::= { optixElanSrvLDTrapMember 12 }

    -- 1.3.6.1.4.1.2011.2.25.4.50.3.1.58.13
    optixElanSrvLDTrapSndIfValid OBJECT-TYPE
        SYNTAX INTEGER
        {
            invalid(0),
            valid(1)
        }
        MAX-ACCESS accessible-for-notify
        STATUS current
        DESCRIPTION
            "This parameter indicates the validity of the logical interface that sends the detection packet in the reported event."
        ::= { optixElanSrvLDTrapMember 13 }

    -- 1.3.6.1.4.1.2011.2.25.4.50.3.1.59
    optixElanSrvLDTrapEvent OBJECT IDENTIFIER ::= { optixEthSrvObject 59 }

    -- 1.3.6.1.4.1.2011.2.25.4.50.3.1.59.1
    optixElanSrvLDResponse NOTIFICATION-TYPE
        OBJECTS{ optixElanSrvLDTrapSrvIndex,optixElanSrvLDTrapSndIfType,optixElanSrvLDTrapSndIfID,optixElanSrvLDTrapVlanID,optixElanSrvLDTrapDetResult,optixElanSrvLDTrapRcvIfType,optixElanSrvLDTrapRcvIfID,optixElanSrvLDTrapCloseState,optixElanSrvLDTrapQue }
        STATUS current
        DESCRIPTION
            "This object is used to report elan loop detect response of events."
        ::= { optixElanSrvLDTrapEvent 1 }

    -- 1.3.6.1.4.1.2011.2.25.4.50.3.1.59.2
    optixElanSrvLDPktOverThreShold NOTIFICATION-TYPE
        OBJECTS{ optixElanSrvLDTrapSrvIndex,optixElanSrvLDTrapVlanID }
        STATUS current
        DESCRIPTION
            "This object is used to report elan loop detect overthreshold of events."
        ::= { optixElanSrvLDTrapEvent 2 }

    -- 1.3.6.1.4.1.2011.2.25.4.50.3.1.59.3
    optixElanSrvLDPath NOTIFICATION-TYPE
        OBJECTS{ optixElanSrvLDTrapSrvIndex,optixElanSrvLDTrapVlanID,optixElanSrvLDTrapRcvIfValid,optixElanSrvLDTrapRcvIfType,optixElanSrvLDTrapRcvIfID,optixElanSrvLDTrapSndIfValid,optixElanSrvLDTrapSndIfType,optixElanSrvLDTrapSndIfID,optixElanSrvLDTrapSndMac }
        STATUS current
        DESCRIPTION
            "This object is used to report elan loop detect path of events."
        ::= { optixElanSrvLDTrapEvent 3 }

    -- 1.3.6.1.4.1.2011.2.25.4.50.3.1.59.4
    optixElanSrvLDResponseEnd NOTIFICATION-TYPE
        OBJECTS{ optixElanSrvLDTrapSrvIndex,optixElanSrvLDTrapSndIfType,optixElanSrvLDTrapSndIfID,optixElanSrvLDTrapQue }
        STATUS current
        DESCRIPTION
            "This object is used to report elan loop detect end of events."
        ::= { optixElanSrvLDTrapEvent 4 }

    -- 1.3.6.1.4.1.2011.2.25.4.50.3.1.59.5
    optixElanSrvCycLDResponse NOTIFICATION-TYPE
        OBJECTS{ optixElanSrvLDTrapSrvIndex,optixElanSrvLDTrapSndIfType,optixElanSrvLDTrapSndIfID,optixElanSrvLDTrapVlanID,optixElanSrvLDTrapTime,optixElanSrvLDTrapDetResult,optixElanSrvLDTrapRcvIfType,optixElanSrvLDTrapRcvIfID,optixElanSrvLDTrapCloseState }
        STATUS current
        DESCRIPTION
            "This object is used to report elan loop cyc-detect response of events."
        ::= { optixElanSrvLDTrapEvent 5 }

    -- 1.3.6.1.4.1.2011.2.25.4.50.3.1.60
    optixTwampReflectorTable OBJECT-TYPE
        SYNTAX SEQUENCE OF OptixTwampReflectorEntry
        MAX-ACCESS not-accessible
        STATUS current
        DESCRIPTION
            "This table describes the TWAMP demapping function."
        ::= { optixEthSrvObject 60 }

    -- 1.3.6.1.4.1.2011.2.25.4.50.3.1.60.1
    optixTwampReflectorEntry OBJECT-TYPE
        SYNTAX OptixTwampReflectorEntry
        MAX-ACCESS not-accessible
        STATUS current
        DESCRIPTION
            "This entry describes the TWAMP demapping function."
        INDEX{ optixTwampReflectorID }
        ::= { optixTwampReflectorTable 1 }

    OptixTwampReflectorEntry ::=
        SEQUENCE {
            optixTwampReflectorID
                Unsigned32,
            optixTwampReflectorSrvType
                INTEGER,
            optixTwampReflectorSrvIndex
                Unsigned32,
            optixTwampReflectorVuniID
                Unsigned32,
            optixTwampReflectorSIP
                IpAddress,
            optixTwampReflectorDIP
                IpAddress,
            optixTwampReflectorSPort
                Unsigned32,
            optixTwampReflectorDPort
                Unsigned32,
            optixTwampReflectorClrFlag
                INTEGER,
            optixTwampReflectorRXGoodPkts
                Unsigned32,
            optixTwampReflectorRXBadPkts
                Unsigned32,
            optixTwampReflectorRXSNMisPkts
                Unsigned32,
            optixTwampReflectorLoopCheckEn
                INTEGER,
            optixTwampReflectorFrequence
                Unsigned32,
            optixTwampReflectorPkgLen
                Unsigned32,
            optixTwampReflectorRowStatus
                RowStatus
        }

    -- 1.3.6.1.4.1.2011.2.25.4.50.3.1.60.1.1
    optixTwampReflectorID OBJECT-TYPE
        SYNTAX Unsigned32
        MAX-ACCESS not-accessible
        STATUS current
        DESCRIPTION
            "This object indicates the TWAMP reflector instance ID."
        ::= { optixTwampReflectorEntry 1 }

    -- 1.3.6.1.4.1.2011.2.25.4.50.3.1.60.1.2
    optixTwampReflectorSrvType OBJECT-TYPE
        SYNTAX INTEGER
        {
            l2vpnEline(2)
        }
        MAX-ACCESS read-create
        STATUS current
        DESCRIPTION
            "This object indicates the TWAMP reflector service type."
        ::= { optixTwampReflectorEntry 2 }

    -- 1.3.6.1.4.1.2011.2.25.4.50.3.1.60.1.3
    optixTwampReflectorSrvIndex OBJECT-TYPE
        SYNTAX Unsigned32
        MAX-ACCESS read-create
        STATUS current
        DESCRIPTION
            "This object indicates the TWAMP reflector service index."
        ::= { optixTwampReflectorEntry 3 }

    -- 1.3.6.1.4.1.2011.2.25.4.50.3.1.60.1.4
    optixTwampReflectorVuniID OBJECT-TYPE
        SYNTAX Unsigned32
        MAX-ACCESS read-create
        STATUS current
        DESCRIPTION
            "This object indicates the TWAMP reflector VUNI ID."
        ::= { optixTwampReflectorEntry 4 }

    -- 1.3.6.1.4.1.2011.2.25.4.50.3.1.60.1.5
    optixTwampReflectorSIP OBJECT-TYPE
        SYNTAX IpAddress
        MAX-ACCESS read-create
        STATUS current
        DESCRIPTION
            "This object indicates the TWAMP reflector source IP address."
        ::= { optixTwampReflectorEntry 5 }

    -- 1.3.6.1.4.1.2011.2.25.4.50.3.1.60.1.6
    optixTwampReflectorDIP OBJECT-TYPE
        SYNTAX IpAddress
        MAX-ACCESS read-create
        STATUS current
        DESCRIPTION
            "This object indicates the TWAMP reflector destination IP address."
        ::= { optixTwampReflectorEntry 6 }

    -- 1.3.6.1.4.1.2011.2.25.4.50.3.1.60.1.7
    optixTwampReflectorSPort OBJECT-TYPE
        SYNTAX Unsigned32
        MAX-ACCESS read-create
        STATUS current
        DESCRIPTION
            "This object indicates the TWAMP reflector UDP source port."
        ::= { optixTwampReflectorEntry 7 }

    -- 1.3.6.1.4.1.2011.2.25.4.50.3.1.60.1.8
    optixTwampReflectorDPort OBJECT-TYPE
        SYNTAX Unsigned32
        MAX-ACCESS read-create
        STATUS current
        DESCRIPTION
            "This object indicates the TWAMP reflector UDP sink port."
        ::= { optixTwampReflectorEntry 8 }

    -- 1.3.6.1.4.1.2011.2.25.4.50.3.1.60.1.9
    optixTwampReflectorClrFlag OBJECT-TYPE
        SYNTAX INTEGER
        {
            clear(0)
        }
        MAX-ACCESS read-create
        STATUS current
        DESCRIPTION
            "This object indicates whether statistics on TWAMP reflector is cleared."
        ::= { optixTwampReflectorEntry 9 }

    -- 1.3.6.1.4.1.2011.2.25.4.50.3.1.60.1.10
    optixTwampReflectorRXGoodPkts OBJECT-TYPE
        SYNTAX Unsigned32
        MAX-ACCESS read-only
        STATUS current
        DESCRIPTION
            "This object indicates the count of received good packets on the TWAMP reflector."
        ::= { optixTwampReflectorEntry 10 }

    -- 1.3.6.1.4.1.2011.2.25.4.50.3.1.60.1.11
    optixTwampReflectorRXBadPkts OBJECT-TYPE
        SYNTAX Unsigned32
        MAX-ACCESS read-only
        STATUS current
        DESCRIPTION
            "This object indicates the count of received bad packets on the TWAMP reflector."
        ::= { optixTwampReflectorEntry 11 }

    -- 1.3.6.1.4.1.2011.2.25.4.50.3.1.60.1.12
    optixTwampReflectorRXSNMisPkts OBJECT-TYPE
        SYNTAX Unsigned32
        MAX-ACCESS read-only
        STATUS current
        DESCRIPTION
            "This object indicates the count of SN out-of-order on the TWAMP reflector."
        ::= { optixTwampReflectorEntry 12 }

    -- 1.3.6.1.4.1.2011.2.25.4.50.3.1.60.1.13
    optixTwampReflectorLoopCheckEn OBJECT-TYPE
        SYNTAX INTEGER
        {
            disable(0),
            enable(1)
        }
        MAX-ACCESS read-create
        STATUS current
        DESCRIPTION
            "This object indicates the enabling status of loopback detection on the TWAMP reflector. 0: disable, 1: enable"
        ::= { optixTwampReflectorEntry 13 }

    -- 1.3.6.1.4.1.2011.2.25.4.50.3.1.60.1.14
    optixTwampReflectorFrequence OBJECT-TYPE
        SYNTAX Unsigned32
        MAX-ACCESS read-create
        STATUS current
        DESCRIPTION
            "This object indicates the packet transmitting frequency on the TWAMP reflector."
        ::= { optixTwampReflectorEntry 14 }

    -- 1.3.6.1.4.1.2011.2.25.4.50.3.1.60.1.15
    optixTwampReflectorPkgLen OBJECT-TYPE
        SYNTAX Unsigned32
        MAX-ACCESS read-create
        STATUS current
        DESCRIPTION
            "This object indicates the packet length on the TWAMP reflector."
        ::= { optixTwampReflectorEntry 15 }

    -- 1.3.6.1.4.1.2011.2.25.4.50.3.1.60.1.255
    optixTwampReflectorRowStatus OBJECT-TYPE
        SYNTAX RowStatus
        MAX-ACCESS read-create
        STATUS current
        DESCRIPTION
            "This object indicates the TWAMP row status: active(1), createAndGo(4), and destroy(6)."
        ::= { optixTwampReflectorEntry 255 }

    -- 1.3.6.1.4.1.2011.2.25.4.50.3.1.61
    optixMACTableTable OBJECT-TYPE
        SYNTAX SEQUENCE OF OptixMACTableEntry
        MAX-ACCESS not-accessible
        STATUS current
        DESCRIPTION
            "This table is used to store MAC address learning result."
        ::= { optixEthSrvObject 61 }

    -- 1.3.6.1.4.1.2011.2.25.4.50.3.1.61.1
    optixMACTableEntry OBJECT-TYPE
        SYNTAX OptixMACTableEntry
        MAX-ACCESS not-accessible
        STATUS current
        DESCRIPTION
            "This entry is used to store MAC address learning result."
        INDEX{ optixMACTableSaveIndex }
        ::= { optixMACTableTable 1 }

    OptixMACTableEntry ::=
        SEQUENCE {
            optixMACTableSaveIndex
                Unsigned32,
            optixMACTableSaveTime
                OCTET STRING,
            optixMACTableSaveFileName
                OCTET STRING,
            optixMACTableEndSaveFileFlag
                INTEGER
        }

    -- 1.3.6.1.4.1.2011.2.25.4.50.3.1.61.1.1
    optixMACTableSaveIndex OBJECT-TYPE
        SYNTAX Unsigned32
        MAX-ACCESS not-accessible
        STATUS current
        DESCRIPTION
            "This object indicates how many times the MAC address learning result is stored for. By default, the MAC address is stored for one time."
        ::= { optixMACTableEntry 1 }

    -- 1.3.6.1.4.1.2011.2.25.4.50.3.1.61.1.2
    optixMACTableSaveTime OBJECT-TYPE
        SYNTAX OCTET STRING
        MAX-ACCESS read-write
        STATUS current
        DESCRIPTION
            "This object indicates the time needed to store the MAC address learning result (hour, minute, second)."
        ::= { optixMACTableEntry 2 }

    -- 1.3.6.1.4.1.2011.2.25.4.50.3.1.61.1.3
    optixMACTableSaveFileName OBJECT-TYPE
        SYNTAX OCTET STRING
        MAX-ACCESS read-only
        STATUS current
        DESCRIPTION
            "This object indicates the name of a file where the MAC address learning result is stored."
        ::= { optixMACTableEntry 3 }

    -- 1.3.6.1.4.1.2011.2.25.4.50.3.1.61.1.4
    optixMACTableEndSaveFileFlag OBJECT-TYPE
        SYNTAX INTEGER
        {
            end(0)
        }
        MAX-ACCESS read-write
        STATUS current
        DESCRIPTION
            "This object indicates the ending flag for MAC address learning result files. 0: end"
        ::= { optixMACTableEntry 4 }

    -- 1.3.6.1.4.1.2011.2.25.4.50.3.1.62
    optixLdDealStateTable OBJECT-TYPE
        SYNTAX SEQUENCE OF OptixLdDealStateEntry
        MAX-ACCESS not-accessible
        STATUS current
        DESCRIPTION
            "This table indicates whether the auto-shutdown function is configured on L2 VPN."
        ::= { optixEthSrvObject 62 }

    -- 1.3.6.1.4.1.2011.2.25.4.50.3.1.62.1
    optixLdDealStateEntry OBJECT-TYPE
        SYNTAX OptixLdDealStateEntry
        MAX-ACCESS not-accessible
        STATUS current
        DESCRIPTION
            "This entry indicates the type based on which the auto-shutdown state is set."
        INDEX{ optixLdDealType }
        ::= { optixLdDealStateTable 1 }

    OptixLdDealStateEntry ::=
        SEQUENCE {
            optixLdDealType
                INTEGER,
            optixLdShutstate
                INTEGER,
            optixLdOpenstate
                INTEGER
        }

    -- 1.3.6.1.4.1.2011.2.25.4.50.3.1.62.1.1
    optixLdDealType OBJECT-TYPE
        SYNTAX INTEGER
        {
            port(0),
            srv(1),
            all(2)
        }
        MAX-ACCESS not-accessible
        STATUS current
        DESCRIPTION
            "This object indicates the type based on which the auto-shutdown state is set."
        ::= { optixLdDealStateEntry 1 }

    -- 1.3.6.1.4.1.2011.2.25.4.50.3.1.62.1.2
    optixLdShutstate OBJECT-TYPE
        SYNTAX INTEGER
        {
            disable(0),
            enable(1)
        }
        MAX-ACCESS read-write
        STATUS current
        DESCRIPTION
            "This object indicates whether auto-shutdown is enabled."
        ::= { optixLdDealStateEntry 2 }

    -- 1.3.6.1.4.1.2011.2.25.4.50.3.1.62.1.3
    optixLdOpenstate OBJECT-TYPE
        SYNTAX INTEGER
        {
            disable(0),
            enable(1)
        }
        MAX-ACCESS read-write
        STATUS current
        DESCRIPTION
            "This object indicates whether the state of opening configuration automatically is enabled."
        ::= { optixLdDealStateEntry 3 }

    -- 1.3.6.1.4.1.2011.2.25.4.50.3.1.63
    optixSrvRefCaseExTable OBJECT-TYPE
        SYNTAX SEQUENCE OF OptixSrvRefCaseExEntry
        MAX-ACCESS not-accessible
        STATUS current
        DESCRIPTION
            "This table describes the reflector-related configurations in the RFC2544 meter-free test."
        ::= { optixEthSrvObject 63 }

    -- 1.3.6.1.4.1.2011.2.25.4.50.3.1.63.1
    optixSrvRefCaseExEntry OBJECT-TYPE
        SYNTAX OptixSrvRefCaseExEntry
        MAX-ACCESS not-accessible
        STATUS current
        DESCRIPTION
            "This entry describes the reflector-related configurations in the RFC2544 meter-free test."
        INDEX{ optixSrvRefCaseExID }
        ::= { optixSrvRefCaseExTable 1 }

    OptixSrvRefCaseExEntry ::=
        SEQUENCE {
            optixSrvRefCaseExID
                Unsigned32,
            optixSrvRefCaseExSrvIndex
                Unsigned32,
            optixSrvRefCaseExVuniType
                INTEGER,
            optixSrvRefCaseExVuniID
                Unsigned32,
            optixSrvRefCaseExFstVlan
                Unsigned32,
            optixSrvRefCaseExTimeOut
                Unsigned32,
            optixSrvRefCaseExState
                INTEGER,
            optixSrvRefCaseExName
                OCTET STRING,
            optixSrvRefCaseMode
                INTEGER,
            optixSrvRefCaseEthTypeNum
                Unsigned32,
            optixSrvRefCaseEthTypeList
                OCTET STRING,
            optixSrvRefCaseExRowStatus
                RowStatus
        }

    -- 1.3.6.1.4.1.2011.2.25.4.50.3.1.63.1.1
    optixSrvRefCaseExID OBJECT-TYPE
        SYNTAX Unsigned32
        MAX-ACCESS not-accessible
        STATUS current
        DESCRIPTION
            "This parameter indicates the reflector ID in the RFC2544 meter-free test. Value range: 1 to 0xffffffff"
        ::= { optixSrvRefCaseExEntry 1 }

    -- 1.3.6.1.4.1.2011.2.25.4.50.3.1.63.1.2
    optixSrvRefCaseExSrvIndex OBJECT-TYPE
        SYNTAX Unsigned32
        MAX-ACCESS read-create
        STATUS current
        DESCRIPTION
            "This parameter indicates the service index of the reflector in the RFC2544 meter-free test. Value range: 1 to 0xffffffff"
        ::= { optixSrvRefCaseExEntry 2 }

    -- 1.3.6.1.4.1.2011.2.25.4.50.3.1.63.1.3
    optixSrvRefCaseExVuniType OBJECT-TYPE
        SYNTAX INTEGER
        {
            vuni(1),
            vnni(2)
        }
        MAX-ACCESS read-create
        STATUS current
        DESCRIPTION
            "This parameter indicates the logical subinterface type for the service of the reflector in the RFC2544 meter-free test. Values: vuni(1) and vnni(2)"
        ::= { optixSrvRefCaseExEntry 3 }

    -- 1.3.6.1.4.1.2011.2.25.4.50.3.1.63.1.4
    optixSrvRefCaseExVuniID OBJECT-TYPE
        SYNTAX Unsigned32
        MAX-ACCESS read-create
        STATUS current
        DESCRIPTION
            "This parameter indicates the logical subinterface ID for the service of the reflector in the RFC2544 meter-free test. Value range: 1 to 65535"
        ::= { optixSrvRefCaseExEntry 4 }

    -- 1.3.6.1.4.1.2011.2.25.4.50.3.1.63.1.5
    optixSrvRefCaseExFstVlan OBJECT-TYPE
        SYNTAX Unsigned32
        MAX-ACCESS read-create
        STATUS current
        DESCRIPTION
            "This parameter indicates the layer-1 VLAN of the reflector in the RFC2544 meter-free test. Values: 1 to 4094"
        ::= { optixSrvRefCaseExEntry 5 }

    -- 1.3.6.1.4.1.2011.2.25.4.50.3.1.63.1.6
    optixSrvRefCaseExTimeOut OBJECT-TYPE
        SYNTAX Unsigned32
        MAX-ACCESS read-create
        STATUS current
        DESCRIPTION
            "This parameter indicates the timeout interval of the reflector in the RFC2544 meter-free test. Values: 10 to 173400, 0; default value: 14400; unit: second"
        ::= { optixSrvRefCaseExEntry 6 }

    -- 1.3.6.1.4.1.2011.2.25.4.50.3.1.63.1.7
    optixSrvRefCaseExState OBJECT-TYPE
        SYNTAX INTEGER
        {
            running(0),
            finished(1),
            ipconflict(2)
        }
        MAX-ACCESS read-only
        STATUS current
        DESCRIPTION
            "This parameter indicates the reflector status in the RFC2544 meter-free test. Values: running(0), finished(1), and ipconflict(2)"
        ::= { optixSrvRefCaseExEntry 7 }

    -- 1.3.6.1.4.1.2011.2.25.4.50.3.1.63.1.8
    optixSrvRefCaseExName OBJECT-TYPE
        SYNTAX OCTET STRING (SIZE(0..64))
        MAX-ACCESS read-create
        STATUS current
        DESCRIPTION
            "This parameter indicates the reflector name in the RFC2544 meter-free test."
        ::= { optixSrvRefCaseExEntry 8 }

    -- 1.3.6.1.4.1.2011.2.25.4.50.3.1.63.1.9
    optixSrvRefCaseMode OBJECT-TYPE
        SYNTAX INTEGER
        {
            normal(0),
            ethtype(1)
        }
        MAX-ACCESS read-create
        STATUS current
        DESCRIPTION
            "This parameter indicates the mode for the service of the reflector in the RFC2544 meter-free test. Values: normal(0) and ethtype(1)"
        ::= { optixSrvRefCaseExEntry 9 }

    -- 1.3.6.1.4.1.2011.2.25.4.50.3.1.63.1.10
    optixSrvRefCaseEthTypeNum OBJECT-TYPE
        SYNTAX Unsigned32
        MAX-ACCESS read-create
        STATUS current
        DESCRIPTION
            "This parameter specifies the number of Ethernet types supported by the reflector of an RFC 2544 meter-free test."
        ::= { optixSrvRefCaseExEntry 10 }

    -- 1.3.6.1.4.1.2011.2.25.4.50.3.1.63.1.11
    optixSrvRefCaseEthTypeList OBJECT-TYPE
        SYNTAX OCTET STRING
        MAX-ACCESS read-create
        STATUS current
        DESCRIPTION
            "This parameter specifies the list of Ethernet types supported by the reflector of an RFC 2544 meter-free test."
        ::= { optixSrvRefCaseExEntry 11 }

    -- 1.3.6.1.4.1.2011.2.25.4.50.3.1.63.1.255
    optixSrvRefCaseExRowStatus OBJECT-TYPE
        SYNTAX RowStatus
        MAX-ACCESS read-create
        STATUS current
        DESCRIPTION
            "This parameter indicates the row status of the table."
        ::= { optixSrvRefCaseExEntry 255 }

    -- 1.3.6.1.4.1.2011.2.25.4.50.3.1.64
    optixY1564SessionTable OBJECT-TYPE
        SYNTAX SEQUENCE OF OptixY1564SessionEntry
        MAX-ACCESS not-accessible
        STATUS current
        DESCRIPTION
            "This table describes the Y1564 session."
        ::= { optixEthSrvObject 64 }

    -- 1.3.6.1.4.1.2011.2.25.4.50.3.1.64.1
    optixY1564SessionEntry OBJECT-TYPE
        SYNTAX OptixY1564SessionEntry
        MAX-ACCESS not-accessible
        STATUS current
        DESCRIPTION
            "This entry describes the  Y1564 session."
        INDEX{ optixY1564SessionID }
        ::= { optixY1564SessionTable 1 }

    OptixY1564SessionEntry ::=
        SEQUENCE {
            optixY1564SessionID
                Unsigned32,
            optixY1564SessionLoc
                INTEGER,
            optixY1564SessionType
                INTEGER,
            optixY1564SessionSrvType
                INTEGER,
            optixY1564SessionSrvIndex
                Unsigned32,
            optixY1564SessionUniId
                Unsigned32,
            optixY1564SessionAgeTime
                Unsigned32,
            optixY1564SessionName
                OCTET STRING,
            optixY1564SessionCfgTestTime
                Unsigned32,
            optixY1564SessionPerfTestTime
                Unsigned32,
            optixY1564SessionTestState
                INTEGER,
            optixY1564SessionBindFlowNum
                Unsigned32,
            optixY1564SessionBindFlowList
                OCTET STRING,
            optixY1564SessionStartTest
                INTEGER,
            optixY1564SessionStopTest
                INTEGER,
            optixY1564SessionSwapOp
                INTEGER,
            optixY1564SessionRowStatus
                RowStatus
        }

    -- 1.3.6.1.4.1.2011.2.25.4.50.3.1.64.1.1
    optixY1564SessionID OBJECT-TYPE
        SYNTAX Unsigned32
        MAX-ACCESS not-accessible
        STATUS current
        DESCRIPTION
            "This object indicates the number of one Y1564 session."
        ::= { optixY1564SessionEntry 1 }

    -- 1.3.6.1.4.1.2011.2.25.4.50.3.1.64.1.2
    optixY1564SessionLoc OBJECT-TYPE
        SYNTAX INTEGER
        {
            launcher(0),
            reflector(1)
        }
        MAX-ACCESS read-create
        STATUS current
        DESCRIPTION
            "This object indicates the location of one Y1564 session. Launcher(0), reflector(1)"
        ::= { optixY1564SessionEntry 2 }

    -- 1.3.6.1.4.1.2011.2.25.4.50.3.1.64.1.3
    optixY1564SessionType OBJECT-TYPE
        SYNTAX INTEGER
        {
            nton(1),
            ctoc(2)
        }
        MAX-ACCESS read-create
        STATUS current
        DESCRIPTION
            "This object indicates the type of one Y1564 session. NTON(1),CTOC(2)"
        ::= { optixY1564SessionEntry 3 }

    -- 1.3.6.1.4.1.2011.2.25.4.50.3.1.64.1.4
    optixY1564SessionSrvType OBJECT-TYPE
        SYNTAX INTEGER
        {
            l2uni(1),
            l3uni(2)
        }
        MAX-ACCESS read-create
        STATUS current
        DESCRIPTION
            "This object indicates the service type of one Y1564 session. L2uni(1),l3uni(2)"
        ::= { optixY1564SessionEntry 4 }

    -- 1.3.6.1.4.1.2011.2.25.4.50.3.1.64.1.5
    optixY1564SessionSrvIndex OBJECT-TYPE
        SYNTAX Unsigned32
        MAX-ACCESS read-create
        STATUS current
        DESCRIPTION
            "This object indicates the service index of one Y1564 session."
        ::= { optixY1564SessionEntry 5 }

    -- 1.3.6.1.4.1.2011.2.25.4.50.3.1.64.1.6
    optixY1564SessionUniId OBJECT-TYPE
        SYNTAX Unsigned32
        MAX-ACCESS read-create
        STATUS current
        DESCRIPTION
            "This object indicates the vuni id of one Y1564 session."
        ::= { optixY1564SessionEntry 6 }

    -- 1.3.6.1.4.1.2011.2.25.4.50.3.1.64.1.7
    optixY1564SessionAgeTime OBJECT-TYPE
        SYNTAX Unsigned32
        MAX-ACCESS read-create
        STATUS current
        DESCRIPTION
            "This object indicates the age time of one Y1564 session."
        ::= { optixY1564SessionEntry 7 }

    -- 1.3.6.1.4.1.2011.2.25.4.50.3.1.64.1.8
    optixY1564SessionName OBJECT-TYPE
        SYNTAX OCTET STRING
        MAX-ACCESS read-create
        STATUS current
        DESCRIPTION
            "This object indicates the name of one Y1564 session."
        ::= { optixY1564SessionEntry 8 }

    -- 1.3.6.1.4.1.2011.2.25.4.50.3.1.64.1.9
    optixY1564SessionCfgTestTime OBJECT-TYPE
        SYNTAX Unsigned32 (0|10..60)
        MAX-ACCESS read-create
        STATUS current
        DESCRIPTION
            "This object indicates the time of testing configuration of one Y1564 session."
        ::= { optixY1564SessionEntry 9 }

    -- 1.3.6.1.4.1.2011.2.25.4.50.3.1.64.1.10
    optixY1564SessionPerfTestTime OBJECT-TYPE
        SYNTAX Unsigned32 (0|3|5|15|120|1440)
        MAX-ACCESS read-create
        STATUS current
        DESCRIPTION
            "This object indicates the time of testing performance of one Y1564 session."
        ::= { optixY1564SessionEntry 10 }

    -- 1.3.6.1.4.1.2011.2.25.4.50.3.1.64.1.11
    optixY1564SessionTestState OBJECT-TYPE
        SYNTAX INTEGER
        {
            begin(1),
            end(0)
        }
        MAX-ACCESS read-only
        STATUS current
        DESCRIPTION
            "This object indicates the testing state of one Y1564 session."
        ::= { optixY1564SessionEntry 11 }

    -- 1.3.6.1.4.1.2011.2.25.4.50.3.1.64.1.12
    optixY1564SessionBindFlowNum OBJECT-TYPE
        SYNTAX Unsigned32 (0..8|65535)
        MAX-ACCESS read-create
        STATUS current
        DESCRIPTION
            "This object indicates numbers of session-associated flows. 0: delete  0xffff : exclusive"
        ::= { optixY1564SessionEntry 12 }

    -- 1.3.6.1.4.1.2011.2.25.4.50.3.1.64.1.13
    optixY1564SessionBindFlowList OBJECT-TYPE
        SYNTAX OCTET STRING
        MAX-ACCESS read-create
        STATUS current
        DESCRIPTION
            "This object indicates session-associated flowlist."
        ::= { optixY1564SessionEntry 13 }

    -- 1.3.6.1.4.1.2011.2.25.4.50.3.1.64.1.14
    optixY1564SessionStartTest OBJECT-TYPE
        SYNTAX INTEGER
        {
            start(0)
        }
        MAX-ACCESS read-create
        STATUS current
        DESCRIPTION
            "This table describes the Y1564 session start testing."
        ::= { optixY1564SessionEntry 14 }

    -- 1.3.6.1.4.1.2011.2.25.4.50.3.1.64.1.15
    optixY1564SessionStopTest OBJECT-TYPE
        SYNTAX INTEGER
        {
            stop(0)
        }
        MAX-ACCESS read-create
        STATUS current
        DESCRIPTION
            "This table describes the Y1564 session start or stop testing."
        ::= { optixY1564SessionEntry 15 }

    -- 1.3.6.1.4.1.2011.2.25.4.50.3.1.64.1.16
    optixY1564SessionSwapOp OBJECT-TYPE
        SYNTAX INTEGER
        {
            noswap(0),
            mac(1),
            ip(2),
            macIp(3),
            udp(4),
            macIpUdp(5)
        }
        MAX-ACCESS read-create
        STATUS current
        DESCRIPTION
            "This table describes the Y1564 session swap."
        ::= { optixY1564SessionEntry 16 }

    -- 1.3.6.1.4.1.2011.2.25.4.50.3.1.64.1.255
    optixY1564SessionRowStatus OBJECT-TYPE
        SYNTAX RowStatus
        MAX-ACCESS read-create
        STATUS current
        DESCRIPTION
            "This object indicates the Y1564 row status: active(1), createAndGo(4), and destroy(6)."
        ::= { optixY1564SessionEntry 255 }

    -- 1.3.6.1.4.1.2011.2.25.4.50.3.1.65
    optixY1564FlowTable OBJECT-TYPE
        SYNTAX SEQUENCE OF OptixY1564FlowEntry
        MAX-ACCESS not-accessible
        STATUS current
        DESCRIPTION
            "This table describes the Y1564 testing flow."
        ::= { optixEthSrvObject 65 }

    -- 1.3.6.1.4.1.2011.2.25.4.50.3.1.65.1
    optixY1564FlowEntry OBJECT-TYPE
        SYNTAX OptixY1564FlowEntry
        MAX-ACCESS not-accessible
        STATUS current
        DESCRIPTION
            "This entry describes the  Y1564 testing flow."
        INDEX{ optixY1564FlowID }
        ::= { optixY1564FlowTable 1 }

    OptixY1564FlowEntry ::=
        SEQUENCE {
            optixY1564FlowID
                Unsigned32,
            optixY1564FlowDMac
                OCTET STRING,
            optixY1564FlowSMac
                OCTET STRING,
            optixY1564FlowFirstVlan
                Unsigned32,
            optixY1564FlowDei
                Unsigned32,
            optixY1564FlowSecVlan
                Unsigned32,
            optixY1564FlowDIP
                IpAddress,
            optixY1564FlowSIP
                IpAddress,
            optixY1564FlowDPort
                Unsigned32,
            optixY1564FlowSPort
                Unsigned32,
            optixY1564FlowSkipType
                INTEGER,
            optixY1564FlowSikipLoc
                Unsigned32,
            optixY1564FlowSikipNum
                Unsigned32,
            optixY1564FlowFlr
                Unsigned32,
            optixY1564FlowFtd
                Unsigned32,
            optixY1564FlowFdv
                Unsigned32,
            optixY1564FlowAvail
                Unsigned32,
            optixY1564FlowCir
                Unsigned32,
            optixY1564FlowCbs
                Unsigned32,
            optixY1564FlowPir
                Unsigned32,
            optixY1564FlowPbs
                Unsigned32,
            optixY1564FlowPolicyState
                INTEGER,
            optixY1564FlowColorMode
                INTEGER,
            optixY1564FlowGreenMinPri
                Unsigned32,
            optixY1564FlowGreenMaxPri
                Unsigned32,
            optixY1564FlowYellowMinPri
                Unsigned32,
            optixY1564FlowYellowMaxPri
                Unsigned32,
            optixY1564FlowPkgSizeNum
                Unsigned32,
            optixY1564FlowPkgSizeList
                OCTET STRING,
            optixY1564FlowRowStatus
                RowStatus
        }

    -- 1.3.6.1.4.1.2011.2.25.4.50.3.1.65.1.1
    optixY1564FlowID OBJECT-TYPE
        SYNTAX Unsigned32
        MAX-ACCESS not-accessible
        STATUS current
        DESCRIPTION
            "This object indicates the number of one Y1564 testing flow."
        ::= { optixY1564FlowEntry 1 }

    -- 1.3.6.1.4.1.2011.2.25.4.50.3.1.65.1.2
    optixY1564FlowDMac OBJECT-TYPE
        SYNTAX OCTET STRING
        MAX-ACCESS read-create
        STATUS current
        DESCRIPTION
            "This object indicates the destination MAC address of one Y1564 testing flow."
        ::= { optixY1564FlowEntry 2 }

    -- 1.3.6.1.4.1.2011.2.25.4.50.3.1.65.1.3
    optixY1564FlowSMac OBJECT-TYPE
        SYNTAX OCTET STRING
        MAX-ACCESS read-create
        STATUS current
        DESCRIPTION
            "This object indicates the Source MAC Address of one Y1564 testing flow."
        ::= { optixY1564FlowEntry 3 }

    -- 1.3.6.1.4.1.2011.2.25.4.50.3.1.65.1.4
    optixY1564FlowFirstVlan OBJECT-TYPE
        SYNTAX Unsigned32
        MAX-ACCESS read-create
        STATUS current
        DESCRIPTION
            "This object indicates the first vlan of one Y1564 testing flow."
        ::= { optixY1564FlowEntry 4 }

    -- 1.3.6.1.4.1.2011.2.25.4.50.3.1.65.1.5
    optixY1564FlowDei OBJECT-TYPE
        SYNTAX Unsigned32
        MAX-ACCESS read-create
        STATUS current
        DESCRIPTION
            "This object indicates the dei of one Y1564 testing flow."
        ::= { optixY1564FlowEntry 5 }

    -- 1.3.6.1.4.1.2011.2.25.4.50.3.1.65.1.6
    optixY1564FlowSecVlan OBJECT-TYPE
        SYNTAX Unsigned32
        MAX-ACCESS read-create
        STATUS current
        DESCRIPTION
            "This object indicates the second vlan of one Y1564 testing flow."
        ::= { optixY1564FlowEntry 6 }

    -- 1.3.6.1.4.1.2011.2.25.4.50.3.1.65.1.7
    optixY1564FlowDIP OBJECT-TYPE
        SYNTAX IpAddress
        MAX-ACCESS read-create
        STATUS current
        DESCRIPTION
            "This object indicates the destionation ip of one Y1564 testing flow."
        ::= { optixY1564FlowEntry 7 }

    -- 1.3.6.1.4.1.2011.2.25.4.50.3.1.65.1.8
    optixY1564FlowSIP OBJECT-TYPE
        SYNTAX IpAddress
        MAX-ACCESS read-create
        STATUS current
        DESCRIPTION
            "This object indicates the source ip of one Y1564 testing flow."
        ::= { optixY1564FlowEntry 8 }

    -- 1.3.6.1.4.1.2011.2.25.4.50.3.1.65.1.9
    optixY1564FlowDPort OBJECT-TYPE
        SYNTAX Unsigned32
        MAX-ACCESS read-create
        STATUS current
        DESCRIPTION
            "This object indicates the destination port of one Y1564 testing flow."
        ::= { optixY1564FlowEntry 9 }

    -- 1.3.6.1.4.1.2011.2.25.4.50.3.1.65.1.10
    optixY1564FlowSPort OBJECT-TYPE
        SYNTAX Unsigned32
        MAX-ACCESS read-create
        STATUS current
        DESCRIPTION
            "This object indicates the source port of one Y1564 testing flow."
        ::= { optixY1564FlowEntry 10 }

    -- 1.3.6.1.4.1.2011.2.25.4.50.3.1.65.1.11
    optixY1564FlowSkipType OBJECT-TYPE
        SYNTAX INTEGER
        {
            none(0),
            dstmac(1),
            srcmac(2),
            firstvlan(3),
            secvlan(4),
            dstip(5),
            srcip(6),
            dstport(7),
            srcport(8),
            color(9)
        }
        MAX-ACCESS read-create
        STATUS current
        DESCRIPTION
            "This object indicates the skipping type of one Y1564 testing flow. none(0),dstmac(1),srcmac(2),firstvlan(3),secvlan(4),dstip(5),srcip(6),dstport(7),srcport(8),color(9)"
        ::= { optixY1564FlowEntry 11 }

    -- 1.3.6.1.4.1.2011.2.25.4.50.3.1.65.1.12
    optixY1564FlowSikipLoc OBJECT-TYPE
        SYNTAX Unsigned32
        MAX-ACCESS read-create
        STATUS current
        DESCRIPTION
            "This object indicates the skipping location of one Y1564 testing flow."
        ::= { optixY1564FlowEntry 12 }

    -- 1.3.6.1.4.1.2011.2.25.4.50.3.1.65.1.13
    optixY1564FlowSikipNum OBJECT-TYPE
        SYNTAX Unsigned32
        MAX-ACCESS read-create
        STATUS current
        DESCRIPTION
            "This object indicates the skipping value of one Y1564 testing flow."
        ::= { optixY1564FlowEntry 13 }

    -- 1.3.6.1.4.1.2011.2.25.4.50.3.1.65.1.14
    optixY1564FlowFlr OBJECT-TYPE
        SYNTAX Unsigned32
        MAX-ACCESS read-create
        STATUS current
        DESCRIPTION
            "This object indicates the frame loss ratio of passing standards."
        ::= { optixY1564FlowEntry 14 }

    -- 1.3.6.1.4.1.2011.2.25.4.50.3.1.65.1.15
    optixY1564FlowFtd OBJECT-TYPE
        SYNTAX Unsigned32
        MAX-ACCESS read-create
        STATUS current
        DESCRIPTION
            "This object indicates the forward delay of passing standards."
        ::= { optixY1564FlowEntry 15 }

    -- 1.3.6.1.4.1.2011.2.25.4.50.3.1.65.1.16
    optixY1564FlowFdv OBJECT-TYPE
        SYNTAX Unsigned32
        MAX-ACCESS read-create
        STATUS current
        DESCRIPTION
            "This object indicates the forward delay variation of passing standards."
        ::= { optixY1564FlowEntry 16 }

    -- 1.3.6.1.4.1.2011.2.25.4.50.3.1.65.1.17
    optixY1564FlowAvail OBJECT-TYPE
        SYNTAX Unsigned32
        MAX-ACCESS read-create
        STATUS current
        DESCRIPTION
            "This object indicates the avail of passing standards."
        ::= { optixY1564FlowEntry 17 }

    -- 1.3.6.1.4.1.2011.2.25.4.50.3.1.65.1.18
    optixY1564FlowCir OBJECT-TYPE
        SYNTAX Unsigned32
        MAX-ACCESS read-create
        STATUS current
        DESCRIPTION
            "This object indicates the cir of one Y1564 testing flow."
        ::= { optixY1564FlowEntry 18 }

    -- 1.3.6.1.4.1.2011.2.25.4.50.3.1.65.1.19
    optixY1564FlowCbs OBJECT-TYPE
        SYNTAX Unsigned32
        MAX-ACCESS read-create
        STATUS current
        DESCRIPTION
            "This object indicates the cbs of one Y1564 testing flow."
        ::= { optixY1564FlowEntry 19 }

    -- 1.3.6.1.4.1.2011.2.25.4.50.3.1.65.1.20
    optixY1564FlowPir OBJECT-TYPE
        SYNTAX Unsigned32
        MAX-ACCESS read-create
        STATUS current
        DESCRIPTION
            "This object indicates the pir of one Y1564 testing flow."
        ::= { optixY1564FlowEntry 20 }

    -- 1.3.6.1.4.1.2011.2.25.4.50.3.1.65.1.21
    optixY1564FlowPbs OBJECT-TYPE
        SYNTAX Unsigned32
        MAX-ACCESS read-create
        STATUS current
        DESCRIPTION
            "This object indicates the pbs of one Y1564 testing flow."
        ::= { optixY1564FlowEntry 21 }

    -- 1.3.6.1.4.1.2011.2.25.4.50.3.1.65.1.22
    optixY1564FlowPolicyState OBJECT-TYPE
        SYNTAX INTEGER
        {
            disable(0),
            enable(1)
        }
        MAX-ACCESS read-create
        STATUS current
        DESCRIPTION
            "This object indicates the policy state of one Y1564 testing flow."
        ::= { optixY1564FlowEntry 22 }

    -- 1.3.6.1.4.1.2011.2.25.4.50.3.1.65.1.23
    optixY1564FlowColorMode OBJECT-TYPE
        SYNTAX INTEGER
        {
            none(0),
            outpir(1),
            inerpri(2),
            dscp(3)
        }
        MAX-ACCESS read-create
        STATUS current
        DESCRIPTION
            "This object indicates the color mode of one Y1564 testing flow."
        ::= { optixY1564FlowEntry 23 }

    -- 1.3.6.1.4.1.2011.2.25.4.50.3.1.65.1.24
    optixY1564FlowGreenMinPri OBJECT-TYPE
        SYNTAX Unsigned32
        MAX-ACCESS read-create
        STATUS current
        DESCRIPTION
            "This object indicates the minimum priority of green packets"
        ::= { optixY1564FlowEntry 24 }

    -- 1.3.6.1.4.1.2011.2.25.4.50.3.1.65.1.25
    optixY1564FlowGreenMaxPri OBJECT-TYPE
        SYNTAX Unsigned32
        MAX-ACCESS read-create
        STATUS current
        DESCRIPTION
            "This object indicates the maximum priority of green packets"
        ::= { optixY1564FlowEntry 25 }

    -- 1.3.6.1.4.1.2011.2.25.4.50.3.1.65.1.26
    optixY1564FlowYellowMinPri OBJECT-TYPE
        SYNTAX Unsigned32
        MAX-ACCESS read-create
        STATUS current
        DESCRIPTION
            "This object indicates the minimum priority of yellow packets"
        ::= { optixY1564FlowEntry 26 }

    -- 1.3.6.1.4.1.2011.2.25.4.50.3.1.65.1.27
    optixY1564FlowYellowMaxPri OBJECT-TYPE
        SYNTAX Unsigned32
        MAX-ACCESS read-create
        STATUS current
        DESCRIPTION
            "This object indicates the maximum priority of yellow packets"
        ::= { optixY1564FlowEntry 27 }

    -- 1.3.6.1.4.1.2011.2.25.4.50.3.1.65.1.28
    optixY1564FlowPkgSizeNum OBJECT-TYPE
        SYNTAX Unsigned32
        MAX-ACCESS read-create
        STATUS current
        DESCRIPTION
            "This object indicates the Number of packets."
        ::= { optixY1564FlowEntry 28 }

    -- 1.3.6.1.4.1.2011.2.25.4.50.3.1.65.1.29
    optixY1564FlowPkgSizeList OBJECT-TYPE
        SYNTAX OCTET STRING
        MAX-ACCESS read-create
        STATUS current
        DESCRIPTION
            "This object indicates the size of the packets."
        ::= { optixY1564FlowEntry 29 }

    -- 1.3.6.1.4.1.2011.2.25.4.50.3.1.65.1.255
    optixY1564FlowRowStatus OBJECT-TYPE
        SYNTAX RowStatus
        MAX-ACCESS read-create
        STATUS current
        DESCRIPTION
            "This object indicates the Y1564 row status: active(1), createAndGo(4), and destroy(6)."
        ::= { optixY1564FlowEntry 255 }

    -- 1.3.6.1.4.1.2011.2.25.4.50.3.1.66
    optixY1564SessionTestTable OBJECT-TYPE
        SYNTAX SEQUENCE OF OptixY1564SessionTestEntry
        MAX-ACCESS not-accessible
        STATUS current
        DESCRIPTION
            "This table describes the Y1564 testing result."
        ::= { optixEthSrvObject 66 }

    -- 1.3.6.1.4.1.2011.2.25.4.50.3.1.66.1
    optixY1564SessionTestEntry OBJECT-TYPE
        SYNTAX OptixY1564SessionTestEntry
        MAX-ACCESS not-accessible
        STATUS current
        DESCRIPTION
            "This entry describes the Y1564 testing result."
        INDEX{ optixY1564TestSessionID,optixY1564TestFlowID,optixY1564TestType }
        ::= { optixY1564SessionTestTable 1 }

    OptixY1564SessionTestEntry ::=
        SEQUENCE {
            optixY1564TestSessionID
                Unsigned32,
            optixY1564TestFlowID
                Unsigned32,
            optixY1564TestType
                INTEGER,
            optixY1564TestState
                INTEGER,
            optixY1564TestIRMin
                Unsigned32,
            optixY1564TestIRMean
                Unsigned32,
            optixY1564TestIRMax
                Unsigned32,
            optixY1564TestFlCount
                Unsigned32,
            optixY1564TestFlR
                Unsigned32,
            optixY1564TestFTDMin
                Unsigned32,
            optixY1564TestFTDMean
                Unsigned32,
            optixY1564TestFTDMax
                Unsigned32,
            optixY1564TestFDVMin
                Unsigned32,
            optixY1564TestFDVMean
                Unsigned32,
            optixY1564TestFDVMax
                Unsigned32,
            optixY1564TestDuration
                Unsigned32,
            optixY1564TestTrRate
                Unsigned32,
            optixY1564TestAvail
                Unsigned32,
            optixY1564TestUnCount
                Unsigned32,
            optixY1564TestBeginYear
                Unsigned32,
            optixY1564TestBeginMonth
                Unsigned32,
            optixY1564TestBeginDate
                Unsigned32,
            optixY1564TestBeginHour
                Unsigned32,
            optixY1564TestBeginMinute
                Unsigned32,
            optixY1564TestBeginSec
                Unsigned32,
            optixY1564TestEndYear
                Unsigned32,
            optixY1564TestEndMonth
                Unsigned32,
            optixY1564TestEndDate
                Unsigned32,
            optixY1564TestEndHour
                Unsigned32,
            optixY1564TestEndMinute
                Unsigned32,
            optixY1564TestEndSec
                Unsigned32
        }

    -- 1.3.6.1.4.1.2011.2.25.4.50.3.1.66.1.1
    optixY1564TestSessionID OBJECT-TYPE
        SYNTAX Unsigned32
        MAX-ACCESS not-accessible
        STATUS current
        DESCRIPTION
            "This object indicates the number of one Y1564 session."
        ::= { optixY1564SessionTestEntry 1 }

    -- 1.3.6.1.4.1.2011.2.25.4.50.3.1.66.1.2
    optixY1564TestFlowID OBJECT-TYPE
        SYNTAX Unsigned32
        MAX-ACCESS not-accessible
        STATUS current
        DESCRIPTION
            "This object indicates the number of one Y1564 flow."
        ::= { optixY1564SessionTestEntry 2 }

    -- 1.3.6.1.4.1.2011.2.25.4.50.3.1.66.1.3
    optixY1564TestType OBJECT-TYPE
        SYNTAX INTEGER
        {
            all(0),
            cirStep1(1),
            cirStep2(2),
            cirStep3(3),
            cirStep4(4),
            eirGreen(5),
            eirYellow(6),
            eirTotal(7),
            tpGreen(8),
            tpYellow(9),
            tpTotal(10),
            cbs(11),
            ebsGreen(12),
            ebsYellow(13),
            ebsTotal(14),
            perf(15)
        }
        MAX-ACCESS not-accessible
        STATUS current
        DESCRIPTION
            "This object indicates the testing type."
        ::= { optixY1564SessionTestEntry 3 }

    -- 1.3.6.1.4.1.2011.2.25.4.50.3.1.66.1.4
    optixY1564TestState OBJECT-TYPE
        SYNTAX INTEGER
        {
            pass(0),
            fail(1),
            na(2)
        }
        MAX-ACCESS read-only
        STATUS current
        DESCRIPTION
            "This object indicates the testing state."
        ::= { optixY1564SessionTestEntry 4 }

    -- 1.3.6.1.4.1.2011.2.25.4.50.3.1.66.1.5
    optixY1564TestIRMin OBJECT-TYPE
        SYNTAX Unsigned32
        MAX-ACCESS read-only
        STATUS current
        DESCRIPTION
            "This object indicates the minimum of throughput."
        ::= { optixY1564SessionTestEntry 5 }

    -- 1.3.6.1.4.1.2011.2.25.4.50.3.1.66.1.6
    optixY1564TestIRMean OBJECT-TYPE
        SYNTAX Unsigned32
        MAX-ACCESS read-only
        STATUS current
        DESCRIPTION
            "This object indicates the Average of throughput."
        ::= { optixY1564SessionTestEntry 6 }

    -- 1.3.6.1.4.1.2011.2.25.4.50.3.1.66.1.7
    optixY1564TestIRMax OBJECT-TYPE
        SYNTAX Unsigned32
        MAX-ACCESS read-only
        STATUS current
        DESCRIPTION
            "This object indicates the maximum of throughput."
        ::= { optixY1564SessionTestEntry 7 }

    -- 1.3.6.1.4.1.2011.2.25.4.50.3.1.66.1.8
    optixY1564TestFlCount OBJECT-TYPE
        SYNTAX Unsigned32
        MAX-ACCESS read-only
        STATUS current
        DESCRIPTION
            "This object indicates number of lost packets."
        ::= { optixY1564SessionTestEntry 8 }

    -- 1.3.6.1.4.1.2011.2.25.4.50.3.1.66.1.9
    optixY1564TestFlR OBJECT-TYPE
        SYNTAX Unsigned32
        MAX-ACCESS read-only
        STATUS current
        DESCRIPTION
            "This object indicates packet loss rate."
        ::= { optixY1564SessionTestEntry 9 }

    -- 1.3.6.1.4.1.2011.2.25.4.50.3.1.66.1.10
    optixY1564TestFTDMin OBJECT-TYPE
        SYNTAX Unsigned32
        MAX-ACCESS read-only
        STATUS current
        DESCRIPTION
            "This object indicates minimum delay."
        ::= { optixY1564SessionTestEntry 10 }

    -- 1.3.6.1.4.1.2011.2.25.4.50.3.1.66.1.11
    optixY1564TestFTDMean OBJECT-TYPE
        SYNTAX Unsigned32
        MAX-ACCESS read-only
        STATUS current
        DESCRIPTION
            "This object indicates average Delay."
        ::= { optixY1564SessionTestEntry 11 }

    -- 1.3.6.1.4.1.2011.2.25.4.50.3.1.66.1.12
    optixY1564TestFTDMax OBJECT-TYPE
        SYNTAX Unsigned32
        MAX-ACCESS read-only
        STATUS current
        DESCRIPTION
            "This object indicates maximum delay."
        ::= { optixY1564SessionTestEntry 12 }

    -- 1.3.6.1.4.1.2011.2.25.4.50.3.1.66.1.13
    optixY1564TestFDVMin OBJECT-TYPE
        SYNTAX Unsigned32
        MAX-ACCESS read-only
        STATUS current
        DESCRIPTION
            "This object indicates minimum forward delay variation."
        ::= { optixY1564SessionTestEntry 13 }

    -- 1.3.6.1.4.1.2011.2.25.4.50.3.1.66.1.14
    optixY1564TestFDVMean OBJECT-TYPE
        SYNTAX Unsigned32
        MAX-ACCESS read-only
        STATUS current
        DESCRIPTION
            "This object indicates average forward delay variation."
        ::= { optixY1564SessionTestEntry 14 }

    -- 1.3.6.1.4.1.2011.2.25.4.50.3.1.66.1.15
    optixY1564TestFDVMax OBJECT-TYPE
        SYNTAX Unsigned32
        MAX-ACCESS read-only
        STATUS current
        DESCRIPTION
            "This object indicates maximum forward delay variation."
        ::= { optixY1564SessionTestEntry 15 }

    -- 1.3.6.1.4.1.2011.2.25.4.50.3.1.66.1.16
    optixY1564TestDuration OBJECT-TYPE
        SYNTAX Unsigned32
        MAX-ACCESS read-only
        STATUS current
        DESCRIPTION
            "This object indicates duration(s)."
        ::= { optixY1564SessionTestEntry 16 }

    -- 1.3.6.1.4.1.2011.2.25.4.50.3.1.66.1.17
    optixY1564TestTrRate OBJECT-TYPE
        SYNTAX Unsigned32
        MAX-ACCESS read-only
        STATUS current
        DESCRIPTION
            "This object indicates transmit rater."
        ::= { optixY1564SessionTestEntry 17 }

    -- 1.3.6.1.4.1.2011.2.25.4.50.3.1.66.1.18
    optixY1564TestAvail OBJECT-TYPE
        SYNTAX Unsigned32
        MAX-ACCESS read-only
        STATUS current
        DESCRIPTION
            "This object indicates avail."
        ::= { optixY1564SessionTestEntry 18 }

    -- 1.3.6.1.4.1.2011.2.25.4.50.3.1.66.1.19
    optixY1564TestUnCount OBJECT-TYPE
        SYNTAX Unsigned32
        MAX-ACCESS read-only
        STATUS current
        DESCRIPTION
            "This object indicates the number of invalid packets."
        ::= { optixY1564SessionTestEntry 19 }

    -- 1.3.6.1.4.1.2011.2.25.4.50.3.1.66.1.20
    optixY1564TestBeginYear OBJECT-TYPE
        SYNTAX Unsigned32
        MAX-ACCESS read-only
        STATUS current
        DESCRIPTION
            "This object indicates begin Year."
        ::= { optixY1564SessionTestEntry 20 }

    -- 1.3.6.1.4.1.2011.2.25.4.50.3.1.66.1.21
    optixY1564TestBeginMonth OBJECT-TYPE
        SYNTAX Unsigned32
        MAX-ACCESS read-only
        STATUS current
        DESCRIPTION
            "This object indicates begin Month."
        ::= { optixY1564SessionTestEntry 21 }

    -- 1.3.6.1.4.1.2011.2.25.4.50.3.1.66.1.22
    optixY1564TestBeginDate OBJECT-TYPE
        SYNTAX Unsigned32
        MAX-ACCESS read-only
        STATUS current
        DESCRIPTION
            "This object indicates begin Date."
        ::= { optixY1564SessionTestEntry 22 }

    -- 1.3.6.1.4.1.2011.2.25.4.50.3.1.66.1.23
    optixY1564TestBeginHour OBJECT-TYPE
        SYNTAX Unsigned32
        MAX-ACCESS read-only
        STATUS current
        DESCRIPTION
            "This object indicates begin hour."
        ::= { optixY1564SessionTestEntry 23 }

    -- 1.3.6.1.4.1.2011.2.25.4.50.3.1.66.1.24
    optixY1564TestBeginMinute OBJECT-TYPE
        SYNTAX Unsigned32
        MAX-ACCESS read-only
        STATUS current
        DESCRIPTION
            "This object indicates begin minute."
        ::= { optixY1564SessionTestEntry 24 }

    -- 1.3.6.1.4.1.2011.2.25.4.50.3.1.66.1.25
    optixY1564TestBeginSec OBJECT-TYPE
        SYNTAX Unsigned32
        MAX-ACCESS read-only
        STATUS current
        DESCRIPTION
            "This object indicates begin second."
        ::= { optixY1564SessionTestEntry 25 }

    -- 1.3.6.1.4.1.2011.2.25.4.50.3.1.66.1.26
    optixY1564TestEndYear OBJECT-TYPE
        SYNTAX Unsigned32
        MAX-ACCESS read-only
        STATUS current
        DESCRIPTION
            "This object indicates end Year."
        ::= { optixY1564SessionTestEntry 26 }

    -- 1.3.6.1.4.1.2011.2.25.4.50.3.1.66.1.27
    optixY1564TestEndMonth OBJECT-TYPE
        SYNTAX Unsigned32
        MAX-ACCESS read-only
        STATUS current
        DESCRIPTION
            "This object indicates end Month."
        ::= { optixY1564SessionTestEntry 27 }

    -- 1.3.6.1.4.1.2011.2.25.4.50.3.1.66.1.28
    optixY1564TestEndDate OBJECT-TYPE
        SYNTAX Unsigned32
        MAX-ACCESS read-only
        STATUS current
        DESCRIPTION
            "This object indicates end Date."
        ::= { optixY1564SessionTestEntry 28 }

    -- 1.3.6.1.4.1.2011.2.25.4.50.3.1.66.1.29
    optixY1564TestEndHour OBJECT-TYPE
        SYNTAX Unsigned32
        MAX-ACCESS read-only
        STATUS current
        DESCRIPTION
            "This object indicates end hour."
        ::= { optixY1564SessionTestEntry 29 }

    -- 1.3.6.1.4.1.2011.2.25.4.50.3.1.66.1.30
    optixY1564TestEndMinute OBJECT-TYPE
        SYNTAX Unsigned32
        MAX-ACCESS read-only
        STATUS current
        DESCRIPTION
            "This object indicates end minute."
        ::= { optixY1564SessionTestEntry 30 }

    -- 1.3.6.1.4.1.2011.2.25.4.50.3.1.66.1.31
    optixY1564TestEndSec OBJECT-TYPE
        SYNTAX Unsigned32
        MAX-ACCESS read-only
        STATUS current
        DESCRIPTION
            "This object indicates end second."
        ::= { optixY1564SessionTestEntry 31 }

    -- 1.3.6.1.4.1.2011.2.25.4.50.3.1.67
    optixY1564TestTrapMember OBJECT IDENTIFIER ::= { optixEthSrvObject 67 }

    -- 1.3.6.1.4.1.2011.2.25.4.50.3.1.67.1
    optixY1564EvtSessionID OBJECT-TYPE
        SYNTAX Unsigned32
        MAX-ACCESS accessible-for-notify
        STATUS current
        DESCRIPTION
            "This object indicates the number of one Y1564 session."
        ::= { optixY1564TestTrapMember 1 }

    -- 1.3.6.1.4.1.2011.2.25.4.50.3.1.67.2
    optixY1564TestRefAgeResult OBJECT-TYPE
        SYNTAX INTEGER
        {
            finished(0)
        }
        MAX-ACCESS accessible-for-notify
        STATUS current
        DESCRIPTION
            "This parameter indicates the end of reflector aging."
        ::= { optixY1564TestTrapMember 2 }

    -- 1.3.6.1.4.1.2011.2.25.4.50.3.1.67.3
    optixY1564TestlauTestResult OBJECT-TYPE
        SYNTAX INTEGER
        {
            success(0),
            failed(1)
        }
        MAX-ACCESS accessible-for-notify
        STATUS current
        DESCRIPTION
            "This parameter indicates the testing result of the launch ."
        ::= { optixY1564TestTrapMember 3 }

    -- 1.3.6.1.4.1.2011.2.25.4.50.3.1.68
    optixY1564TestEvent OBJECT IDENTIFIER ::= { optixEthSrvObject 68 }

    -- 1.3.6.1.4.1.2011.2.25.4.50.3.1.68.1
    optixY1564RefAgeEvt NOTIFICATION-TYPE
        OBJECTS{ optixY1564EvtSessionID,optixY1564TestRefAgeResult }
        STATUS current
        DESCRIPTION
            "This object is used to report the end of Y1564 reflector aging."
        ::= { optixY1564TestEvent 1 }

    -- 1.3.6.1.4.1.2011.2.25.4.50.3.1.68.2
    optixY1564LauTestEnd NOTIFICATION-TYPE
        OBJECTS{ optixY1564EvtSessionID,optixY1564TestlauTestResult }
        STATUS current
        DESCRIPTION
            "This object is used to report the testing result of the Y1564 launch ."
        ::= { optixY1564TestEvent 2 }

    -- 1.3.6.1.4.1.2011.2.25.4.50.3.2
    optixEthSrvGroup OBJECT IDENTIFIER ::= { optixEthSrvMod 2 }

    -- 1.3.6.1.4.1.2011.2.25.4.50.3.2.1
    optixPktDropIpMarkBit OBJECT-TYPE
        SYNTAX INTEGER
        {
            tosbit3(0),
            tosbit4(1),
            tosbit5(2),
            tosbit6(3),
            tosbit7(4),
            flagsbit0(5)
        }
        MAX-ACCESS read-write
        STATUS current
        DESCRIPTION
            "This parameter indicates the bit in the IP address for packet coloring."
        ::= { optixEthSrvGroup 1 }

    -- 1.3.6.1.4.1.2011.2.25.4.50.3.2.2
    optixAutoBroadbaEn OBJECT-TYPE
        SYNTAX INTEGER
        {
            disable(0),
            enable(1)
        }
        MAX-ACCESS read-write
        STATUS current
        DESCRIPTION
            "This parameter indicates whether packet suppression is enabled."
        ::= { optixEthSrvGroup 2 }

    -- 1.3.6.1.4.1.2011.2.25.4.50.3.2.3
    optixVplsElanUniNum OBJECT-TYPE
        SYNTAX Unsigned32
        MAX-ACCESS read-write
        STATUS current
        DESCRIPTION
            "This parameter is used to configure the number of V-UNIs supported by the private network service (NE attribute) and the usage of VPLS services for RTN products. Value range: 1 to 65535."
        ::= { optixEthSrvGroup 3 }

    -- 1.3.6.1.4.1.2011.2.25.4.50.3.2.4
    optixAutoBrdcastLimit OBJECT-TYPE
        SYNTAX Unsigned32
        MAX-ACCESS read-write
        STATUS current
        DESCRIPTION
            "This parameter indicates the broadcast shutdown threshold."
        DEFVAL{ 80 }
        ::= { optixEthSrvGroup 4 }

END
