-- OPTIX-L2-LPT-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-L2-LPT-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,NOTIFICATION-TYPE
            FROM SNMPv2-SMI
        optixLogBoardId,optixLogSubCardId
            FROM OPTIX-BOARD-MANAGE-MIB
        RowStatus
            FROM SNMPv2-TC
        ;

    optixL2Lpt MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of L2 lpt"
        REVISION "201204200000Z"
        DESCRIPTION
            "The initial revision of this MIB module1."
        ::={ optixProvisionPtn 20 }

    -- 1.3.6.1.4.1.2011.2.25.4.50.20.1
    optixL2LptGroup OBJECT IDENTIFIER ::= { optixL2Lpt 1 }

    -- 1.3.6.1.4.1.2011.2.25.4.50.20.1.2
    optixL2LptTable OBJECT-TYPE
        SYNTAX SEQUENCE OF OptixL2LptEntry
        MAX-ACCESS not-accessible
        STATUS current
        DESCRIPTION
            "This table describes the configurations of the L2 LPT in the point-to-multipoint mode."
        ::= { optixL2LptGroup 2 }

    -- 1.3.6.1.4.1.2011.2.25.4.50.20.1.2.1
    optixL2LptEntry OBJECT-TYPE
        SYNTAX OptixL2LptEntry
        MAX-ACCESS not-accessible
        STATUS current
        DESCRIPTION
            "This entry describes the configurations of the L2 LPT in the point-to-multipoint mode."
        INDEX{ optixL2LptRootType,optixL2LptRootPara1,optixL2LptRootPara2,optixL2LptRootPara3 }
        ::= { optixL2LptTable 1 }

    OptixL2LptEntry ::=
        SEQUENCE {
            optixL2LptRootType
                INTEGER,
            optixL2LptRootPara1
                Unsigned32,
            optixL2LptRootPara2
                Unsigned32,
            optixL2LptRootPara3
                Unsigned32,
            optixL2LptPmpLeafType
                INTEGER,
            ooptixL2LptPmpLeafNum
                Unsigned32,
            optixL2LptPmpWtrTime
                Unsigned32,
            optixL2LptPmpDelayTime
                Unsigned32,
            optixL2LptPmpOamType
                INTEGER,
            optixL2LptPmpOamPeriod
                Unsigned32,
            optixL2LptPmpSwitchMode
                INTEGER,
            optixL2LptPmpEnable
                INTEGER,
            optixL2LptAcDefect
                Unsigned32,
            optixL2LptNetDefect
                Unsigned32,
            optixL2LptRemoteDefect
                Unsigned32,
            optixL2LptState
                INTEGER,
            optixL2LptPeerNetType
                INTEGER,
            optixL2LptPeerNetPara1
                Unsigned32,
            optixL2LptPeerNetPara2
                Unsigned32,
            optixL2LptPeerNetPara3
                Unsigned32,
            optixL2LptPeerVlanID
                Unsigned32,
            optixL2LptPeerBid
                Unsigned32,
            optixL2LptPeerSubid
                Unsigned32,
            optixL2LptPeerPortid
                Unsigned32,
            optixL2LptPtpCarryType
                INTEGER,
            optixL2LptPtpCarryIndex1
                Unsigned32,
            optixL2LptPtpCarryIndex2
                Unsigned32,
            optixL2LptPtpCarryIndex3
                Unsigned32,
            optixL2LptPtpEnable
                INTEGER,
            optixL2LptPtpWtrTime
                Unsigned32,
            optixL2LptPtpDelayTime
                Unsigned32,
            optixL2LptPtpOamType
                INTEGER,
            optixL2LptPtpOamPeriod
                Unsigned32,
            optixL2LptPtpSwitchMode
                INTEGER,
            optixL2LptPtpRowStatus
                RowStatus
        }

    -- 1.3.6.1.4.1.2011.2.25.4.50.20.1.2.1.1
    optixL2LptRootType OBJECT-TYPE
        SYNTAX INTEGER
        {
            uniport(1),
            pw(2),
            qinq(3),
            nniport(4),
            l2net(5)
        }
        MAX-ACCESS not-accessible
        STATUS current
        DESCRIPTION
            "This object indicates the root parameter type of the L2 LPT in the point-to-multipoint mode. 1: uniport, 2: pw, 3: qinq, 4: nniport, 5: l2net"
        ::= { optixL2LptEntry 1 }

    -- 1.3.6.1.4.1.2011.2.25.4.50.20.1.2.1.2
    optixL2LptRootPara1 OBJECT-TYPE
        SYNTAX Unsigned32
        MAX-ACCESS not-accessible
        STATUS current
        DESCRIPTION
            "This object indicates the root parameter1 of the L2 LPT in the point-to-multipoint mode. If the parameter type is uniport or nniport, it indicates a slot ID. If the parameter type is pw, qinq or l2net, it takes an invalid value (4294967295)."
        ::= { optixL2LptEntry 2 }

    -- 1.3.6.1.4.1.2011.2.25.4.50.20.1.2.1.3
    optixL2LptRootPara2 OBJECT-TYPE
        SYNTAX Unsigned32
        MAX-ACCESS not-accessible
        STATUS current
        DESCRIPTION
            "This object indicates the root parameter 2 of the L2 LPT in the point-to-multipoint mode. If the parameter type is uniport or nniport, it indicates a sub-slot ID. If the parameter type is pw, qinq or l2net, it takes an invalid value (4294967295)."
        ::= { optixL2LptEntry 3 }

    -- 1.3.6.1.4.1.2011.2.25.4.50.20.1.2.1.4
    optixL2LptRootPara3 OBJECT-TYPE
        SYNTAX Unsigned32
        MAX-ACCESS not-accessible
        STATUS current
        DESCRIPTION
            "This object indicates the root parameter 3 of the L2 LPT in the point-to-multipoint mode. If the parameter type is uniport or nniport, it indicates a port ID. If the parameter type is pw or qinq, it indicates the PW or QinQ index. If the parameter type is l2net, it indicates the channel ID of the virtual channel that passes through the third-party L2 network."
        ::= { optixL2LptEntry 4 }

    -- 1.3.6.1.4.1.2011.2.25.4.50.20.1.2.1.5
    optixL2LptPmpLeafType OBJECT-TYPE
        SYNTAX INTEGER
        {
            uniport(1),
            pw(2),
            qinq(3),
            nniport(4),
            l2net(5)
        }
        MAX-ACCESS read-only
        STATUS current
        DESCRIPTION
            "This object indicates the leaf parameter type of the L2 LPT in the point-to-multipointmode. 1: uniport, 2: pw, 3: qinq, 4: nniport, 5: l2net"
        ::= { optixL2LptEntry 5 }

    -- 1.3.6.1.4.1.2011.2.25.4.50.20.1.2.1.6
    ooptixL2LptPmpLeafNum OBJECT-TYPE
        SYNTAX Unsigned32
        MAX-ACCESS read-only
        STATUS current
        DESCRIPTION
            "This object indicates the number of L2 LPT leavesin the point-to-multipointmode. Value range: 0 to 16."
        ::= { optixL2LptEntry 6 }

    -- 1.3.6.1.4.1.2011.2.25.4.50.20.1.2.1.7
    optixL2LptPmpWtrTime OBJECT-TYPE
        SYNTAX Unsigned32
        MAX-ACCESS read-only
        STATUS current
        DESCRIPTION
            "This object indicates the WTR time of the L2 LPT in the point-to-multipoint mode. Value range: 1 to 600 (unit: s). The default value is 1."
        ::= { optixL2LptEntry 7 }

    -- 1.3.6.1.4.1.2011.2.25.4.50.20.1.2.1.8
    optixL2LptPmpDelayTime OBJECT-TYPE
        SYNTAX Unsigned32
        MAX-ACCESS read-only
        STATUS current
        DESCRIPTION
            "This object indicates the delay time of the L2 LPT in the point-to-multipointmode. Value range: 0 to 10000 (unit: ms). The default value is 1000 and the step length is 100."
        ::= { optixL2LptEntry 8 }

    -- 1.3.6.1.4.1.2011.2.25.4.50.20.1.2.1.9
    optixL2LptPmpOamType OBJECT-TYPE
        SYNTAX INTEGER
        {
            lptOam(0),
            pwOam(1)
        }
        MAX-ACCESS read-only
        STATUS current
        DESCRIPTION
            "This object indicates the OAM typeof the L2 LPT in the point-to-multipointmode. 0: IptOam, 1: pwOam"
        ::= { optixL2LptEntry 9 }

    -- 1.3.6.1.4.1.2011.2.25.4.50.20.1.2.1.10
    optixL2LptPmpOamPeriod OBJECT-TYPE
        SYNTAX Unsigned32
        MAX-ACCESS read-only
        STATUS current
        DESCRIPTION
            "This object indicates the OAM period of the L2 LPT in the point-to-multipoint mode. Value range: 10 to 100 (unit: ms). The default value is 10."
        ::= { optixL2LptEntry 10 }

    -- 1.3.6.1.4.1.2011.2.25.4.50.20.1.2.1.11
    optixL2LptPmpSwitchMode OBJECT-TYPE
        SYNTAX INTEGER
        {
            strict(0),
            noStrict(1)
        }
        MAX-ACCESS read-only
        STATUS current
        DESCRIPTION
            "This object indicates the switching mode of the L2 LPT in the point-to-multipoint mode. 0: strict, 1: nostrict"
        ::= { optixL2LptEntry 11 }

    -- 1.3.6.1.4.1.2011.2.25.4.50.20.1.2.1.12
    optixL2LptPmpEnable OBJECT-TYPE
        SYNTAX INTEGER
        {
            disable(0),
            enable(1)
        }
        MAX-ACCESS read-only
        STATUS current
        DESCRIPTION
            "This object indicates the enable status of the L2 LPT in the point-to-multipoint mode. 0: disable, 1: enable"
        ::= { optixL2LptEntry 12 }

    -- 1.3.6.1.4.1.2011.2.25.4.50.20.1.2.1.13
    optixL2LptAcDefect OBJECT-TYPE
        SYNTAX Unsigned32
        MAX-ACCESS read-only
        STATUS current
        DESCRIPTION
            "This object indicates the local user-side fault. 0: indicates that there is no fault. 1: indicates that there are faults."
        ::= { optixL2LptEntry 13 }

    -- 1.3.6.1.4.1.2011.2.25.4.50.20.1.2.1.14
    optixL2LptNetDefect OBJECT-TYPE
        SYNTAX Unsigned32
        MAX-ACCESS read-only
        STATUS current
        DESCRIPTION
            "This object indicates the local network-side fault. 0: indicates that there is no fault. 1: indicates that there are faults."
        ::= { optixL2LptEntry 14 }

    -- 1.3.6.1.4.1.2011.2.25.4.50.20.1.2.1.15
    optixL2LptRemoteDefect OBJECT-TYPE
        SYNTAX Unsigned32
        MAX-ACCESS read-only
        STATUS current
        DESCRIPTION
            "This object indicates the remote LPT instance fault. 0: indicates that there is no fault. 1: indicates that there are faults."
        ::= { optixL2LptEntry 15 }

    -- 1.3.6.1.4.1.2011.2.25.4.50.20.1.2.1.16
    optixL2LptState OBJECT-TYPE
        SYNTAX INTEGER
        {
            normal(0),
            useFault(1),
            networkFault(2),
            faultRecoverWait(3),
            faultRecover(4),
            init(5)
        }
        MAX-ACCESS read-only
        STATUS current
        DESCRIPTION
            "This object indicates the protocol status of the L2 LPT. 0: normal, 1: useFault, 2: networkFault, 3: faultRecoverWait, 4: faultRecover, 5: init"
        ::= { optixL2LptEntry 16 }

    -- 1.3.6.1.4.1.2011.2.25.4.50.20.1.2.1.17
    optixL2LptPeerNetType OBJECT-TYPE
        SYNTAX INTEGER
        {
            all(0),
            uniport(1),
            pw(2),
            qinq(3),
            nniport(4),
            l2net(5)
        }
        MAX-ACCESS read-only
        STATUS current
        DESCRIPTION
            "This object indicates the protocol type of the remote L2 LPT. 1: uniport, 2: pw, 3: qinq, 4: nniport, 5: l2net"
        ::= { optixL2LptEntry 17 }

    -- 1.3.6.1.4.1.2011.2.25.4.50.20.1.2.1.18
    optixL2LptPeerNetPara1 OBJECT-TYPE
        SYNTAX Unsigned32
        MAX-ACCESS read-only
        STATUS current
        DESCRIPTION
            "This object indicates the root parameter1 of the remote L2 LPT in the point-to-multipoint mode. If the parameter type is uniport or nniport, it indicates a slot ID. If the parameter type is pw, qinq or l2net, it takes an invalid value (4294967295)."
        ::= { optixL2LptEntry 18 }

    -- 1.3.6.1.4.1.2011.2.25.4.50.20.1.2.1.19
    optixL2LptPeerNetPara2 OBJECT-TYPE
        SYNTAX Unsigned32
        MAX-ACCESS read-only
        STATUS current
        DESCRIPTION
            "This object indicates the root parameter 2 of the remote L2 LPT in the point-to-multipoint mode. If the parameter type is uniport or nniport, it indicates a sub-slot ID. If the parameter type is pw, qinq or l2net, it takes an invalid value (4294967295)."
        ::= { optixL2LptEntry 19 }

    -- 1.3.6.1.4.1.2011.2.25.4.50.20.1.2.1.20
    optixL2LptPeerNetPara3 OBJECT-TYPE
        SYNTAX Unsigned32
        MAX-ACCESS read-only
        STATUS current
        DESCRIPTION
            "This object indicates the root parameter 3 of the remote L2 LPT in the point-to-multipoint mode. If the parameter type is uniport or nniport, it indicates a port ID. If the parameter type is pw or qinq, it indicates the PW or QinQ index. If the parameter type is l2net, it indicates the channel ID of the virtual channel that passes through the third-party L2 network."
        ::= { optixL2LptEntry 20 }

    -- 1.3.6.1.4.1.2011.2.25.4.50.20.1.2.1.21
    optixL2LptPeerVlanID OBJECT-TYPE
        SYNTAX Unsigned32
        MAX-ACCESS read-only
        STATUS current
        DESCRIPTION
            "This object indicates the Pass Vlan id of the L2 LPT. Value range: 1 to 4094 (valid values). This parameter can also be set to 0xFFFF (the default value), indicating that the VLAN ID of the LPT service packets is the PV ID of the egress port."
        ::= { optixL2LptEntry 21 }

    -- 1.3.6.1.4.1.2011.2.25.4.50.20.1.2.1.22
    optixL2LptPeerBid OBJECT-TYPE
        SYNTAX Unsigned32
        MAX-ACCESS read-only
        STATUS current
        DESCRIPTION
            "This object indicates the Board ID of the L2 LPT."
        ::= { optixL2LptEntry 22 }

    -- 1.3.6.1.4.1.2011.2.25.4.50.20.1.2.1.23
    optixL2LptPeerSubid OBJECT-TYPE
        SYNTAX Unsigned32
        MAX-ACCESS read-only
        STATUS current
        DESCRIPTION
            "This object indicates the Sub Board ID of the L2 LPT."
        ::= { optixL2LptEntry 23 }

    -- 1.3.6.1.4.1.2011.2.25.4.50.20.1.2.1.24
    optixL2LptPeerPortid OBJECT-TYPE
        SYNTAX Unsigned32
        MAX-ACCESS read-only
        STATUS current
        DESCRIPTION
            "This object indicates the Port ID of the L2 LPT."
        ::= { optixL2LptEntry 24 }

    -- 1.3.6.1.4.1.2011.2.25.4.50.20.1.2.1.25
    optixL2LptPtpCarryType OBJECT-TYPE
        SYNTAX INTEGER
        {
            uniport(1),
            pw(2),
            qinq(3),
            nniport(4),
            l2net(5)
        }
        MAX-ACCESS read-only
        STATUS current
        DESCRIPTION
            "This object indicates the carrier type of the L2 LPT in the point-to-point mode. 1: uniport, 2: pw, 3: qinq, 4: nniport, 5: l2net"
        ::= { optixL2LptEntry 25 }

    -- 1.3.6.1.4.1.2011.2.25.4.50.20.1.2.1.26
    optixL2LptPtpCarryIndex1 OBJECT-TYPE
        SYNTAX Unsigned32
        MAX-ACCESS read-only
        STATUS current
        DESCRIPTION
            "This object indicates the index 1 to the L2 LPT carrier in the point-to-point mode. If the parameter type is uniport or nniport, it indicates a slot ID. If the parameter type is pw, qinq or l2net, it takes an invalid value (4294967295)."
        ::= { optixL2LptEntry 26 }

    -- 1.3.6.1.4.1.2011.2.25.4.50.20.1.2.1.27
    optixL2LptPtpCarryIndex2 OBJECT-TYPE
        SYNTAX Unsigned32
        MAX-ACCESS read-only
        STATUS current
        DESCRIPTION
            "This object indicates the index 2 to the L2 LPT carrier in the point-to-point mode. If the parameter type is uniport or nniport, it indicates a sub-slot ID. If the parameter type is pw, qinq or l2net, it takes an invalid value (4294967295)."
        ::= { optixL2LptEntry 27 }

    -- 1.3.6.1.4.1.2011.2.25.4.50.20.1.2.1.28
    optixL2LptPtpCarryIndex3 OBJECT-TYPE
        SYNTAX Unsigned32
        MAX-ACCESS read-only
        STATUS current
        DESCRIPTION
            "This object indicates the index 3 to the L2 LPT carrier in the point-to-point mode. If the parameter type is uniport or nniport, it indicates a port ID. If the parameter type is pw or qinq, it indicates the PW or QinQ index. If the parameter type is l2net, it indicates the channel ID of the virtual channel that passes through the third-party L2 network."
        ::= { optixL2LptEntry 28 }

    -- 1.3.6.1.4.1.2011.2.25.4.50.20.1.2.1.29
    optixL2LptPtpEnable OBJECT-TYPE
        SYNTAX INTEGER
        {
            disable(0),
            enable(1)
        }
        MAX-ACCESS read-only
        STATUS current
        DESCRIPTION
            "This object indicates the enable status of the L2 LPT in the point-to-point mode."
        ::= { optixL2LptEntry 29 }

    -- 1.3.6.1.4.1.2011.2.25.4.50.20.1.2.1.30
    optixL2LptPtpWtrTime OBJECT-TYPE
        SYNTAX Unsigned32
        MAX-ACCESS read-only
        STATUS current
        DESCRIPTION
            "This object indicates the WTR time of the L2 LPT in the point-to-point mode."
        ::= { optixL2LptEntry 30 }

    -- 1.3.6.1.4.1.2011.2.25.4.50.20.1.2.1.31
    optixL2LptPtpDelayTime OBJECT-TYPE
        SYNTAX Unsigned32
        MAX-ACCESS read-only
        STATUS current
        DESCRIPTION
            "This object indicates the delay time of the L2 LPT in the point-to-point mode."
        ::= { optixL2LptEntry 31 }

    -- 1.3.6.1.4.1.2011.2.25.4.50.20.1.2.1.32
    optixL2LptPtpOamType OBJECT-TYPE
        SYNTAX INTEGER
        {
            lptOam(0),
            pwOam(1)
        }
        MAX-ACCESS read-only
        STATUS current
        DESCRIPTION
            "This object indicates the network fault detection mode of the L2 LPT."
        ::= { optixL2LptEntry 32 }

    -- 1.3.6.1.4.1.2011.2.25.4.50.20.1.2.1.33
    optixL2LptPtpOamPeriod OBJECT-TYPE
        SYNTAX Unsigned32
        MAX-ACCESS read-only
        STATUS current
        DESCRIPTION
            "This object indicates the network fault detection period of the L2 LPT."
        ::= { optixL2LptEntry 33 }

    -- 1.3.6.1.4.1.2011.2.25.4.50.20.1.2.1.34
    optixL2LptPtpSwitchMode OBJECT-TYPE
        SYNTAX INTEGER
        {
            strict(0),
            nostrict(1)
        }
        MAX-ACCESS read-only
        STATUS current
        DESCRIPTION
            "This object indicates the switching mode of the L2 LPT."
        ::= { optixL2LptEntry 34 }

    -- 1.3.6.1.4.1.2011.2.25.4.50.20.1.2.1.255
    optixL2LptPtpRowStatus OBJECT-TYPE
        SYNTAX RowStatus
        MAX-ACCESS read-only
        STATUS current
        DESCRIPTION
            "This object indicates the row status of the L2 LPT."
        ::= { optixL2LptEntry 255 }

    -- 1.3.6.1.4.1.2011.2.25.4.50.20.1.3
    optixL2SimpleLptSingleTable OBJECT-TYPE
        SYNTAX SEQUENCE OF OptixL2SimpleLptSingleEntry
        MAX-ACCESS not-accessible
        STATUS current
        DESCRIPTION
            "This table describes the mapping configurations of the L2 LPT in the point-to-multipoint mode."
        ::= { optixL2LptGroup 3 }

    -- 1.3.6.1.4.1.2011.2.25.4.50.20.1.3.1
    optixL2SimpleLptSingleEntry OBJECT-TYPE
        SYNTAX OptixL2SimpleLptSingleEntry
        MAX-ACCESS not-accessible
        STATUS current
        DESCRIPTION
            "This entry describes the mapping configurations of the L2 LPT in the point-to-multipoint mode."
        INDEX{ optixLogBoardId,optixLogSubCardId,optixL2SimpleLptMainPid,optixL2SimpleLptSlvBid,optixL2SimpleLptSlvSubid,optixL2SimpleLptSlvPid }
        ::= { optixL2SimpleLptSingleTable 1 }

    OptixL2SimpleLptSingleEntry ::=
        SEQUENCE {
            optixL2SimpleLptMainPid
                Unsigned32,
            optixL2SimpleLptSlvBid
                Unsigned32,
            optixL2SimpleLptSlvSubid
                Unsigned32,
            optixL2SimpleLptSlvPid
                Unsigned32,
            optixL2SimpleLptSlvNum
                Unsigned32,
            optixL2SimpleLptSingleRowStatus
                RowStatus
        }

    -- 1.3.6.1.4.1.2011.2.25.4.50.20.1.3.1.1
    optixL2SimpleLptMainPid OBJECT-TYPE
        SYNTAX Unsigned32
        MAX-ACCESS not-accessible
        STATUS current
        DESCRIPTION
            "This object indicates the master port of the L2 LPT mapping in the point-to-multipoint mode."
        ::= { optixL2SimpleLptSingleEntry 1 }

    -- 1.3.6.1.4.1.2011.2.25.4.50.20.1.3.1.2
    optixL2SimpleLptSlvBid OBJECT-TYPE
        SYNTAX Unsigned32
        MAX-ACCESS not-accessible
        STATUS current
        DESCRIPTION
            "This object indicates the slot ID of the slave portof the L2 LPT mapping in the point-to-multipoint mode."
        ::= { optixL2SimpleLptSingleEntry 2 }

    -- 1.3.6.1.4.1.2011.2.25.4.50.20.1.3.1.3
    optixL2SimpleLptSlvSubid OBJECT-TYPE
        SYNTAX Unsigned32
        MAX-ACCESS not-accessible
        STATUS current
        DESCRIPTION
            "This object indicates the subboard ID of the slave port of the L2 LPT mapping in the point-to-multipoint mode."
        ::= { optixL2SimpleLptSingleEntry 3 }

    -- 1.3.6.1.4.1.2011.2.25.4.50.20.1.3.1.4
    optixL2SimpleLptSlvPid OBJECT-TYPE
        SYNTAX Unsigned32
        MAX-ACCESS not-accessible
        STATUS current
        DESCRIPTION
            "This object indicates the port number of the slave port of the L2 LPT mapping in the point-to-multipoint mode. Value range: 1 to 512."
        ::= { optixL2SimpleLptSingleEntry 4 }

    -- 1.3.6.1.4.1.2011.2.25.4.50.20.1.3.1.5
    optixL2SimpleLptSlvNum OBJECT-TYPE
        SYNTAX Unsigned32
        MAX-ACCESS read-create
        STATUS current
        DESCRIPTION
            "This object indicates the number of slave ports of the L2 LPT mapping in the point-to-multipoint mode. Value range: 1 to 512."
        ::= { optixL2SimpleLptSingleEntry 5 }

    -- 1.3.6.1.4.1.2011.2.25.4.50.20.1.3.1.255
    optixL2SimpleLptSingleRowStatus OBJECT-TYPE
        SYNTAX RowStatus
        MAX-ACCESS read-create
        STATUS current
        DESCRIPTION
            "This Row Status describes the mapping configurations of the L2 LPT in the point-to-multipoint mode."
        ::= { optixL2SimpleLptSingleEntry 255 }

    -- 1.3.6.1.4.1.2011.2.25.4.50.20.1.4
    optixL2LptPortTable OBJECT-TYPE
        SYNTAX SEQUENCE OF OptixL2LptPortEntry
        MAX-ACCESS not-accessible
        STATUS current
        DESCRIPTION
            "This table describes the L2 LPT port configurations."
        ::= { optixL2LptGroup 4 }

    -- 1.3.6.1.4.1.2011.2.25.4.50.20.1.4.1
    optixL2LptPortEntry OBJECT-TYPE
        SYNTAX OptixL2LptPortEntry
        MAX-ACCESS not-accessible
        STATUS current
        DESCRIPTION
            "This entry describes the L2 LPT port configurations."
        INDEX{ optixLogBoardId,optixLogSubCardId,optixL2LptPortPid }
        ::= { optixL2LptPortTable 1 }

    OptixL2LptPortEntry ::=
        SEQUENCE {
            optixL2LptPortPid
                Unsigned32,
            optixL2LptPortState
                INTEGER
        }

    -- 1.3.6.1.4.1.2011.2.25.4.50.20.1.4.1.1
    optixL2LptPortPid OBJECT-TYPE
        SYNTAX Unsigned32
        MAX-ACCESS not-accessible
        STATUS current
        DESCRIPTION
            "This object indicates the L2LPT port number."
        ::= { optixL2LptPortEntry 1 }

    -- 1.3.6.1.4.1.2011.2.25.4.50.20.1.4.1.2
    optixL2LptPortState OBJECT-TYPE
        SYNTAX INTEGER
        {
            lptClose(0),
            lptOpen(1)
        }
        MAX-ACCESS read-only
        STATUS current
        DESCRIPTION
            "This object indicates the disable status of the L2 LPT. 0: IptClose, 1: IptOpen"
        ::= { optixL2LptPortEntry 2 }

    -- 1.3.6.1.4.1.2011.2.25.4.50.20.1.5
    optixL2LptPortStateEventMember OBJECT IDENTIFIER ::= { optixL2LptGroup 5 }

    -- 1.3.6.1.4.1.2011.2.25.4.50.20.1.5.1
    optixL2LptPortStateBoardID OBJECT-TYPE
        SYNTAX Unsigned32
        MAX-ACCESS accessible-for-notify
        STATUS current
        DESCRIPTION
            "This object indicates the slot ID of the reported event."
        ::= { optixL2LptPortStateEventMember 1 }

    -- 1.3.6.1.4.1.2011.2.25.4.50.20.1.5.2
    optixL2LptPortStateSubBoardID OBJECT-TYPE
        SYNTAX Unsigned32
        MAX-ACCESS accessible-for-notify
        STATUS current
        DESCRIPTION
            "This object indicates the subboard ID of the reported event."
        ::= { optixL2LptPortStateEventMember 2 }

    -- 1.3.6.1.4.1.2011.2.25.4.50.20.1.5.3
    optixL2LptPortStatePortID OBJECT-TYPE
        SYNTAX Unsigned32
        MAX-ACCESS accessible-for-notify
        STATUS current
        DESCRIPTION
            "This object indicates the port number of the reported event."
        ::= { optixL2LptPortStateEventMember 3 }

    -- 1.3.6.1.4.1.2011.2.25.4.50.20.1.5.4
    optixL2LptPortStateValue OBJECT-TYPE
        SYNTAX INTEGER
        {
            lptClose(0),
            lptOpen(1)
        }
        MAX-ACCESS accessible-for-notify
        STATUS current
        DESCRIPTION
            "This object indicates the port state of the reported event. 0: IptClose, 1: IptOpen"
        ::= { optixL2LptPortStateEventMember 4 }

    -- 1.3.6.1.4.1.2011.2.25.4.50.20.1.6
    optixL2LptPortStateEvent OBJECT IDENTIFIER ::= { optixL2LptGroup 6 }

    -- 1.3.6.1.4.1.2011.2.25.4.50.20.1.6.1
    optixL2LptPortStateTrap NOTIFICATION-TYPE
        OBJECTS{ optixL2LptPortStateBoardID,optixL2LptPortStateSubBoardID,optixL2LptPortStatePortID,optixL2LptPortStateValue }
        STATUS current
        DESCRIPTION
            "This object is used to report LPT port open/close status change events."
        ::= { optixL2LptPortStateEvent 1 }

    -- 1.3.6.1.4.1.2011.2.25.4.50.20.1.7
    optixL2LptPropertyTable OBJECT-TYPE
        SYNTAX SEQUENCE OF OptixL2LptPropertyEntry
        MAX-ACCESS not-accessible
        STATUS current
        DESCRIPTION
            "This table describes the configurations of the L2 LPT."
        ::= { optixL2LptGroup 7 }

    -- 1.3.6.1.4.1.2011.2.25.4.50.20.1.7.1
    optixL2LptPropertyEntry OBJECT-TYPE
        SYNTAX OptixL2LptPropertyEntry
        MAX-ACCESS not-accessible
        STATUS current
        DESCRIPTION
            "This entry describes the configurations of the L2 LPT."
        INDEX{ optixL2LptRootType,optixL2LptRootPara1,optixL2LptRootPara2,optixL2LptRootPara3 }
        ::= { optixL2LptPropertyTable 1 }

    OptixL2LptPropertyEntry ::=
        SEQUENCE {
            optixL2LptPropertyEnable
                INTEGER,
            optixL2LptPropertyWtrTime
                Unsigned32,
            optixL2LptPropertyDelayTime
                Unsigned32,
            optixL2LptPropertySwitchMode
                INTEGER,
            optixL2LptPropertyOamType
                INTEGER,
            optixL2LptPropertyLptOamPeriod
                Unsigned32,
            optixL2LptPropertyState
                INTEGER,
            optixL2LptPropertyAcDefect
                Unsigned32,
            optixL2LptPropertyNetDefect
                Unsigned32,
            optixL2LptPropertyRemoteDefect
                Unsigned32
        }

    -- 1.3.6.1.4.1.2011.2.25.4.50.20.1.7.1.1
    optixL2LptPropertyEnable OBJECT-TYPE
        SYNTAX INTEGER
        {
            disable(0),
            enable(1)
        }
        MAX-ACCESS read-write
        STATUS current
        DESCRIPTION
            "This object indicates the enable status of the L2 LPT. 0: disable, 1: enable"
        ::= { optixL2LptPropertyEntry 1 }

    -- 1.3.6.1.4.1.2011.2.25.4.50.20.1.7.1.2
    optixL2LptPropertyWtrTime OBJECT-TYPE
        SYNTAX Unsigned32
        MAX-ACCESS read-write
        STATUS current
        DESCRIPTION
            "This object indicates the WTR time of the L2 LPT. Value range: 1 to 600 (unit: s). The default value is 1."
        ::= { optixL2LptPropertyEntry 2 }

    -- 1.3.6.1.4.1.2011.2.25.4.50.20.1.7.1.3
    optixL2LptPropertyDelayTime OBJECT-TYPE
        SYNTAX Unsigned32
        MAX-ACCESS read-write
        STATUS current
        DESCRIPTION
            "This object indicates the delay time of the L2 LPT. Value range: 0 to 10000 (unit: ms). The default value is 1000 and the step length is 100."
        ::= { optixL2LptPropertyEntry 3 }

    -- 1.3.6.1.4.1.2011.2.25.4.50.20.1.7.1.4
    optixL2LptPropertySwitchMode OBJECT-TYPE
        SYNTAX INTEGER
        {
            strict(0),
            nostrict(1)
        }
        MAX-ACCESS read-write
        STATUS current
        DESCRIPTION
            "This object indicates the switching modeof the L2 LPT. 0: strict, 1: nostrict"
        ::= { optixL2LptPropertyEntry 4 }

    -- 1.3.6.1.4.1.2011.2.25.4.50.20.1.7.1.5
    optixL2LptPropertyOamType OBJECT-TYPE
        SYNTAX INTEGER
        {
            lptOam(0),
            pwOam(1)
        }
        MAX-ACCESS read-write
        STATUS current
        DESCRIPTION
            "This object indicates the OAM type of the L2 LPT. 0: IptOam, 1: pwOam"
        ::= { optixL2LptPropertyEntry 5 }

    -- 1.3.6.1.4.1.2011.2.25.4.50.20.1.7.1.6
    optixL2LptPropertyLptOamPeriod OBJECT-TYPE
        SYNTAX Unsigned32
        MAX-ACCESS read-write
        STATUS current
        DESCRIPTION
            "This object indicates the OAM period of the L2 LPT. Value range: 10 to 100 (unit: ms). The default value is 10."
        ::= { optixL2LptPropertyEntry 6 }

    -- 1.3.6.1.4.1.2011.2.25.4.50.20.1.7.1.7
    optixL2LptPropertyState OBJECT-TYPE
        SYNTAX INTEGER
        {
            normal(0),
            useFault(1),
            networkFault(2),
            faultRecoverWait(3),
            faultRecover(4),
            init(5)
        }
        MAX-ACCESS read-only
        STATUS current
        DESCRIPTION
            "This object indicates the protocol status of the L2 LPT. 0: normal, 1: useFault, 2: networkFault, 3: faultRecoverWait, 4: faultRecover, 5: init"
        ::= { optixL2LptPropertyEntry 7 }

    -- 1.3.6.1.4.1.2011.2.25.4.50.20.1.7.1.8
    optixL2LptPropertyAcDefect OBJECT-TYPE
        SYNTAX Unsigned32
        MAX-ACCESS read-only
        STATUS current
        DESCRIPTION
            "This object indicates the local user-side fault of the L2 LPT. 0: indicates that there is no fault. 1: indicates that there are faults."
        ::= { optixL2LptPropertyEntry 8 }

    -- 1.3.6.1.4.1.2011.2.25.4.50.20.1.7.1.9
    optixL2LptPropertyNetDefect OBJECT-TYPE
        SYNTAX Unsigned32
        MAX-ACCESS read-only
        STATUS current
        DESCRIPTION
            "This object indicates the local network-side fault of the L2 LPT. 0: indicates that there is no fault. 1: indicates that there are faults."
        ::= { optixL2LptPropertyEntry 9 }

    -- 1.3.6.1.4.1.2011.2.25.4.50.20.1.7.1.10
    optixL2LptPropertyRemoteDefect OBJECT-TYPE
        SYNTAX Unsigned32
        MAX-ACCESS read-only
        STATUS current
        DESCRIPTION
            "This object indicates the remote LPT instance fault of the L2 LPT. 0: indicates that there is no fault. 1: indicates that there are faults."
        ::= { optixL2LptPropertyEntry 10 }

    -- 1.3.6.1.4.1.2011.2.25.4.50.20.1.8
    optixL2LptPtpTable OBJECT-TYPE
        SYNTAX SEQUENCE OF OptixL2LptPtpEntry
        MAX-ACCESS not-accessible
        STATUS current
        DESCRIPTION
            "This table describes the configurations of the L2 LPT  in the point-to-point mode."
        ::= { optixL2LptGroup 8 }

    -- 1.3.6.1.4.1.2011.2.25.4.50.20.1.8.1
    optixL2LptPtpEntry OBJECT-TYPE
        SYNTAX OptixL2LptPtpEntry
        MAX-ACCESS not-accessible
        STATUS current
        DESCRIPTION
            "This entry describes the configurations of the L2 LPT  in the point-to-point mode."
        INDEX{ optixLogBoardId,optixLogSubCardId,optixL2LptPortPid }
        ::= { optixL2LptPtpTable 1 }

    OptixL2LptPtpEntry ::=
        SEQUENCE {
            optixL2LptPtpLeafType
                INTEGER,
            optixL2LptPtpLeafPara1
                Unsigned32,
            optixL2LptPtpLeafPara2
                Unsigned32,
            optixL2LptPtpLeafPara3
                Unsigned32,
            optixL2LptPtpL2netMyPara3
                Unsigned32,
            optixL2LptPtpL2netPeerPara3
                Unsigned32,
            optixL2LptPtpL2netVlanID
                Unsigned32,
            optixL2LptPtpL2netBid
                Unsigned32,
            optixL2LptPtpL2netSubid
                Unsigned32,
            optixL2LptPtpL2netPortid
                Unsigned32,
            optixL2LptPtpRowStatusExt
                RowStatus
        }

    -- 1.3.6.1.4.1.2011.2.25.4.50.20.1.8.1.1
    optixL2LptPtpLeafType OBJECT-TYPE
        SYNTAX INTEGER
        {
            uniport(1),
            pw(2),
            qinq(3),
            nniport(4),
            l2net(5)
        }
        MAX-ACCESS read-create
        STATUS current
        DESCRIPTION
            "This object indicates the carrier type of the L2 LPT in the point-to-point mode. 1: uniport, 2: pw, 3: qinq, 4: nniport, 5: l2net"
        ::= { optixL2LptPtpEntry 1 }

    -- 1.3.6.1.4.1.2011.2.25.4.50.20.1.8.1.2
    optixL2LptPtpLeafPara1 OBJECT-TYPE
        SYNTAX Unsigned32
        MAX-ACCESS read-create
        STATUS current
        DESCRIPTION
            "This object indicates the parameter 1 to the L2 LPT in the point-to-point mode. If the parameter type is uniport or nniport, it indicates a slot ID. If the parameter type is pw, qinq or l2net, it takes an invalid value (4294967295)."
        ::= { optixL2LptPtpEntry 2 }

    -- 1.3.6.1.4.1.2011.2.25.4.50.20.1.8.1.3
    optixL2LptPtpLeafPara2 OBJECT-TYPE
        SYNTAX Unsigned32
        MAX-ACCESS read-create
        STATUS current
        DESCRIPTION
            "This object indicates the parameter 2 to the L2 LPT in the point-to-point mode. If the parameter type is uniport or nniport, it indicates a sub-slot ID. If the parameter type is pw, qinq or l2net, it takes an invalid value (4294967295)."
        ::= { optixL2LptPtpEntry 3 }

    -- 1.3.6.1.4.1.2011.2.25.4.50.20.1.8.1.4
    optixL2LptPtpLeafPara3 OBJECT-TYPE
        SYNTAX Unsigned32
        MAX-ACCESS read-create
        STATUS current
        DESCRIPTION
            "This object indicates the parameter 3 to the L2 LPT in the point-to-point mode. If the parameter type is uniport or nniport, it indicates a port ID. If the parameter type is pw or qinq, it indicates the PW or QinQ index. If the parameter type is l2net, it indicates the channel ID of the virtual channel that passes through the third-party L2 network."
        ::= { optixL2LptPtpEntry 4 }

    -- 1.3.6.1.4.1.2011.2.25.4.50.20.1.8.1.5
    optixL2LptPtpL2netMyPara3 OBJECT-TYPE
        SYNTAX Unsigned32
        MAX-ACCESS read-create
        STATUS current
        DESCRIPTION
            "This object indicates the local parameter 3 of the L2net in the point-to-point mode. Value range: 1 to 0xffffffff."
        ::= { optixL2LptPtpEntry 5 }

    -- 1.3.6.1.4.1.2011.2.25.4.50.20.1.8.1.6
    optixL2LptPtpL2netPeerPara3 OBJECT-TYPE
        SYNTAX Unsigned32
        MAX-ACCESS read-create
        STATUS current
        DESCRIPTION
            "This object indicates the peer parameter 3 of the remote L2net in the point-to-point mode. Value range: 1 to 0xffffffff."
        ::= { optixL2LptPtpEntry 6 }

    -- 1.3.6.1.4.1.2011.2.25.4.50.20.1.8.1.7
    optixL2LptPtpL2netVlanID OBJECT-TYPE
        SYNTAX Unsigned32
        MAX-ACCESS read-create
        STATUS current
        DESCRIPTION
            "This object indicates the Pass Vlan id of the remote L2net in the point-to-point mode. Value range: 1 to 4094 (valid values). This parameter can also be set to 0xFFFF (the default value), indicating that the VLAN ID of the LPT service packets is the PV ID of the egress port."
        ::= { optixL2LptPtpEntry 7 }

    -- 1.3.6.1.4.1.2011.2.25.4.50.20.1.8.1.8
    optixL2LptPtpL2netBid OBJECT-TYPE
        SYNTAX Unsigned32
        MAX-ACCESS read-create
        STATUS current
        DESCRIPTION
            "This object indicates the Board ID of the remote L2net in the point-to-point mode."
        ::= { optixL2LptPtpEntry 8 }

    -- 1.3.6.1.4.1.2011.2.25.4.50.20.1.8.1.9
    optixL2LptPtpL2netSubid OBJECT-TYPE
        SYNTAX Unsigned32
        MAX-ACCESS read-create
        STATUS current
        DESCRIPTION
            "This object indicates the Sub Board ID of the remote L2net in the point-to-point mode."
        ::= { optixL2LptPtpEntry 9 }

    -- 1.3.6.1.4.1.2011.2.25.4.50.20.1.8.1.10
    optixL2LptPtpL2netPortid OBJECT-TYPE
        SYNTAX Unsigned32
        MAX-ACCESS read-create
        STATUS current
        DESCRIPTION
            "This object indicates the Port ID of the remote L2net in the point-to-point mode."
        ::= { optixL2LptPtpEntry 10 }

    -- 1.3.6.1.4.1.2011.2.25.4.50.20.1.8.1.11
    optixL2LptPtpRowStatusExt OBJECT-TYPE
        SYNTAX RowStatus
        MAX-ACCESS read-create
        STATUS current
        DESCRIPTION
            "This object indicates the row status of the L2 LPT in the point-to-point mode."
        ::= { optixL2LptPtpEntry 11 }

    -- 1.3.6.1.4.1.2011.2.25.4.50.20.1.9
    optixL2LptPmpTable OBJECT-TYPE
        SYNTAX SEQUENCE OF OptixL2LptPmpEntry
        MAX-ACCESS not-accessible
        STATUS current
        DESCRIPTION
            "This table describes the configurations of the L2 LPT in the point-to-multipoint mode."
        ::= { optixL2LptGroup 9 }

    -- 1.3.6.1.4.1.2011.2.25.4.50.20.1.9.1
    optixL2LptPmpEntry OBJECT-TYPE
        SYNTAX OptixL2LptPmpEntry
        MAX-ACCESS not-accessible
        STATUS current
        DESCRIPTION
            "This entry describes the configurations of the L2 LPT in the point-to-multipoint mode."
        INDEX{ optixL2LptRootType,optixL2LptRootPara1,optixL2LptRootPara2,optixL2LptRootPara3 }
        ::= { optixL2LptPmpTable 1 }

    OptixL2LptPmpEntry ::=
        SEQUENCE {
            optixL2LptPmpLeafTypeExt
                INTEGER,
            optixL2LptPmpLeafNumExt
                Unsigned32,
            optixL2LptPmpLeafParaList
                OCTET STRING,
            optixL2LptPmpL2netMyPara3
                Unsigned32,
            optixL2LptPmpL2netPeerPara3
                Unsigned32,
            optixL2LptPmpL2netVlanID
                Unsigned32,
            optixL2LptPmpL2netBid
                Unsigned32,
            optixL2LptPmpL2netSubid
                Unsigned32,
            optixL2LptPmpL2netPortid
                Unsigned32,
            optixL2LptPmpRowStatus
                RowStatus
        }

    -- 1.3.6.1.4.1.2011.2.25.4.50.20.1.9.1.1
    optixL2LptPmpLeafTypeExt OBJECT-TYPE
        SYNTAX INTEGER
        {
            uniport(1),
            pw(2),
            qinq(3),
            nniport(4),
            l2net(5)
        }
        MAX-ACCESS read-create
        STATUS current
        DESCRIPTION
            "This object indicates the leaf parameter type of the L2 LPT in the point-to-multipoint mode. 1: uniport, 2: pw, 3: qinq, 4: nniport, 5: l2net"
        ::= { optixL2LptPmpEntry 1 }

    -- 1.3.6.1.4.1.2011.2.25.4.50.20.1.9.1.2
    optixL2LptPmpLeafNumExt OBJECT-TYPE
        SYNTAX Unsigned32
        MAX-ACCESS read-create
        STATUS current
        DESCRIPTION
            "This object indicates the number of L2 LPT in the point-to-multipointmode. Value range: 0 to 16."
        ::= { optixL2LptPmpEntry 2 }

    -- 1.3.6.1.4.1.2011.2.25.4.50.20.1.9.1.3
    optixL2LptPmpLeafParaList OBJECT-TYPE
        SYNTAX OCTET STRING (SIZE(0..1024))
        MAX-ACCESS read-create
        STATUS current
        DESCRIPTION
            "This object indicates the leaf parameter of the L2 LPT in the point-to-multipoint mode."
        ::= { optixL2LptPmpEntry 3 }

    -- 1.3.6.1.4.1.2011.2.25.4.50.20.1.9.1.4
    optixL2LptPmpL2netMyPara3 OBJECT-TYPE
        SYNTAX Unsigned32
        MAX-ACCESS read-create
        STATUS current
        DESCRIPTION
            "This object indicates the local parameter 3 of the L2net in the point-to-multipoint mode. Value range: 1 to 0xffffffff."
        ::= { optixL2LptPmpEntry 4 }

    -- 1.3.6.1.4.1.2011.2.25.4.50.20.1.9.1.5
    optixL2LptPmpL2netPeerPara3 OBJECT-TYPE
        SYNTAX Unsigned32
        MAX-ACCESS read-create
        STATUS current
        DESCRIPTION
            "This object indicates the peer parameter 3 of the remote L2net in the point-to-multipoint mode. Value range: 1 to 0xffffffff."
        ::= { optixL2LptPmpEntry 5 }

    -- 1.3.6.1.4.1.2011.2.25.4.50.20.1.9.1.6
    optixL2LptPmpL2netVlanID OBJECT-TYPE
        SYNTAX Unsigned32
        MAX-ACCESS read-create
        STATUS current
        DESCRIPTION
            "This object indicates the Pass Vlan id of the remote L2net in the point-to-multipoint mode. Value range: 1 to 4094 (valid values). This parameter can also be set to 0xFFFF (the default value), indicating that the VLAN ID of the LPT service packets is the PV ID of the egress port."
        ::= { optixL2LptPmpEntry 6 }

    -- 1.3.6.1.4.1.2011.2.25.4.50.20.1.9.1.7
    optixL2LptPmpL2netBid OBJECT-TYPE
        SYNTAX Unsigned32
        MAX-ACCESS read-create
        STATUS current
        DESCRIPTION
            "This object indicates the Board ID of the remote L2net in the point-to-multipointmode."
        ::= { optixL2LptPmpEntry 7 }

    -- 1.3.6.1.4.1.2011.2.25.4.50.20.1.9.1.8
    optixL2LptPmpL2netSubid OBJECT-TYPE
        SYNTAX Unsigned32
        MAX-ACCESS read-create
        STATUS current
        DESCRIPTION
            "This object indicates the Sub Board ID of the remote L2net in the point-to-multipoint mode."
        ::= { optixL2LptPmpEntry 8 }

    -- 1.3.6.1.4.1.2011.2.25.4.50.20.1.9.1.9
    optixL2LptPmpL2netPortid OBJECT-TYPE
        SYNTAX Unsigned32
        MAX-ACCESS read-create
        STATUS current
        DESCRIPTION
            "This object indicates the Port ID of the remote L2net in the point-to-multipointmode."
        ::= { optixL2LptPmpEntry 9 }

    -- 1.3.6.1.4.1.2011.2.25.4.50.20.1.9.1.255
    optixL2LptPmpRowStatus OBJECT-TYPE
        SYNTAX RowStatus
        MAX-ACCESS read-create
        STATUS current
        DESCRIPTION
            "This object indicates the row status of the L2 LPT in the point-to-multipointmode."
        ::= { optixL2LptPmpEntry 255 }

    -- 1.3.6.1.4.1.2011.2.25.4.50.20.1.10
    optixL2SimpleLptTable OBJECT-TYPE
        SYNTAX SEQUENCE OF OptixL2SimpleLptEntry
        MAX-ACCESS not-accessible
        STATUS current
        DESCRIPTION
            "This table describes the mapping configurations of the Simple Lpt."
        ::= { optixL2LptGroup 10 }

    -- 1.3.6.1.4.1.2011.2.25.4.50.20.1.10.1
    optixL2SimpleLptEntry OBJECT-TYPE
        SYNTAX OptixL2SimpleLptEntry
        MAX-ACCESS not-accessible
        STATUS current
        DESCRIPTION
            "This entry describes the mapping configurations of the Simple Lpt."
        INDEX{ optixLogBoardId,optixLogSubCardId,optixL2LptPortPid }
        ::= { optixL2SimpleLptTable 1 }

    OptixL2SimpleLptEntry ::=
        SEQUENCE {
            optixL2SimpleLptSlaveNum
                Unsigned32,
            optixL2SimpleLptSlaveList
                OCTET STRING,
            optixL2SimpleLptAction
                INTEGER,
            optixL2SimpleLptRowStatus
                RowStatus
        }

    -- 1.3.6.1.4.1.2011.2.25.4.50.20.1.10.1.1
    optixL2SimpleLptSlaveNum OBJECT-TYPE
        SYNTAX Unsigned32
        MAX-ACCESS read-create
        STATUS current
        DESCRIPTION
            "This object indicates the number of slave ports of the Simple LPT. Value range: 1 to 512."
        ::= { optixL2SimpleLptEntry 1 }

    -- 1.3.6.1.4.1.2011.2.25.4.50.20.1.10.1.2
    optixL2SimpleLptSlaveList OBJECT-TYPE
        SYNTAX OCTET STRING (SIZE(0..1024))
        MAX-ACCESS read-create
        STATUS current
        DESCRIPTION
            "This object indicates the slave port list of the Simple Lpt. &amp;amp; is used to separate multiple lists. For example, 3 &amp;amp; 25 &amp;amp; 1 &amp;amp; 3 &amp;amp; 255 &amp;amp; 2."
        ::= { optixL2SimpleLptEntry 2 }

    -- 1.3.6.1.4.1.2011.2.25.4.50.20.1.10.1.3
    optixL2SimpleLptAction OBJECT-TYPE
        SYNTAX INTEGER
        {
            add(1),
            delete(2),
            noaction(255)
        }
        MAX-ACCESS read-create
        STATUS current
        DESCRIPTION
            "This object indicates the action of the Simple LPT."
        ::= { optixL2SimpleLptEntry 3 }

    -- 1.3.6.1.4.1.2011.2.25.4.50.20.1.10.1.255
    optixL2SimpleLptRowStatus OBJECT-TYPE
        SYNTAX RowStatus
        MAX-ACCESS read-create
        STATUS current
        DESCRIPTION
            "This object indicates the row status of the Simple LPT."
        ::= { optixL2SimpleLptEntry 255 }

    -- 1.3.6.1.4.1.2011.2.25.4.50.20.1.11
    optixL2LptL2netTable OBJECT-TYPE
        SYNTAX SEQUENCE OF OptixL2LptL2netEntry
        MAX-ACCESS not-accessible
        STATUS current
        DESCRIPTION
            "This table describes the configurations of the L2Net LPT ."
        ::= { optixL2LptGroup 11 }

    -- 1.3.6.1.4.1.2011.2.25.4.50.20.1.11.1
    optixL2LptL2netEntry OBJECT-TYPE
        SYNTAX OptixL2LptL2netEntry
        MAX-ACCESS not-accessible
        STATUS current
        DESCRIPTION
            "This entry describes the configurations of the L2Net LPT ."
        INDEX{ optixL2LptL2netMyType,optixL2LptRootPara1,optixL2LptRootPara2,optixL2LptRootPara3 }
        ::= { optixL2LptL2netTable 1 }

    OptixL2LptL2netEntry ::=
        SEQUENCE {
            optixL2LptL2netMyType
                INTEGER,
            optixL2LptL2netPeerType
                INTEGER,
            optixL2LptL2netPeerPara1
                Unsigned32,
            optixL2LptL2netPeerPara2
                Unsigned32,
            optixL2LptL2netPeerPara3
                Unsigned32,
            optixL2LptL2netVlanID
                Unsigned32,
            optixL2LptL2netBid
                Unsigned32,
            optixL2LptL2netSubid
                Unsigned32,
            optixL2LptL2netPortid
                Unsigned32
        }

    -- 1.3.6.1.4.1.2011.2.25.4.50.20.1.11.1.1
    optixL2LptL2netMyType OBJECT-TYPE
        SYNTAX INTEGER
        {
            l2net(5)
        }
        MAX-ACCESS not-accessible
        STATUS current
        DESCRIPTION
            "This object indicates the My type of the L2Net LPT. 5: l2net"
        ::= { optixL2LptL2netEntry 1 }

    -- 1.3.6.1.4.1.2011.2.25.4.50.20.1.11.1.2
    optixL2LptL2netPeerType OBJECT-TYPE
        SYNTAX INTEGER
        {
            l2net(5)
        }
        MAX-ACCESS read-write
        STATUS current
        DESCRIPTION
            "This object indicates the peer type of theL2Net LPT. 5: l2net"
        ::= { optixL2LptL2netEntry 2 }

    -- 1.3.6.1.4.1.2011.2.25.4.50.20.1.11.1.3
    optixL2LptL2netPeerPara1 OBJECT-TYPE
        SYNTAX Unsigned32
        MAX-ACCESS read-write
        STATUS current
        DESCRIPTION
            "This object indicates the peer parameter1 of the L2Net LPT. If the parameter type is l2net, it takes an invalid value (4294967295)."
        ::= { optixL2LptL2netEntry 3 }

    -- 1.3.6.1.4.1.2011.2.25.4.50.20.1.11.1.4
    optixL2LptL2netPeerPara2 OBJECT-TYPE
        SYNTAX Unsigned32
        MAX-ACCESS read-write
        STATUS current
        DESCRIPTION
            "This object indicates the peer parameter 2 of the L2Net LPT. If the parameter type is l2net, it takes an invalid value (4294967295)."
        ::= { optixL2LptL2netEntry 4 }

    -- 1.3.6.1.4.1.2011.2.25.4.50.20.1.11.1.5
    optixL2LptL2netPeerPara3 OBJECT-TYPE
        SYNTAX Unsigned32
        MAX-ACCESS read-write
        STATUS current
        DESCRIPTION
            "This object indicates the peer parameter 3 of the L2Net LPT. Value range: 1 to 0xffffffff."
        ::= { optixL2LptL2netEntry 5 }

    -- 1.3.6.1.4.1.2011.2.25.4.50.20.1.11.1.6
    optixL2LptL2netVlanID OBJECT-TYPE
        SYNTAX Unsigned32
        MAX-ACCESS read-write
        STATUS current
        DESCRIPTION
            "This object indicates the Vlan id of the L2Net LPT. Value range: 1 to 4094 (valid values). This parameter can also be set to 0xFFFF (the default value), indicating that the VLAN ID of the LPT service packets is the PV ID of the egress port."
        ::= { optixL2LptL2netEntry 6 }

    -- 1.3.6.1.4.1.2011.2.25.4.50.20.1.11.1.7
    optixL2LptL2netBid OBJECT-TYPE
        SYNTAX Unsigned32
        MAX-ACCESS read-write
        STATUS current
        DESCRIPTION
            "This object indicates the Board ID of the L2Net LPT."
        ::= { optixL2LptL2netEntry 7 }

    -- 1.3.6.1.4.1.2011.2.25.4.50.20.1.11.1.8
    optixL2LptL2netSubid OBJECT-TYPE
        SYNTAX Unsigned32
        MAX-ACCESS read-write
        STATUS current
        DESCRIPTION
            "This object indicates the Sub Board ID of the L2Net LPT."
        ::= { optixL2LptL2netEntry 8 }

    -- 1.3.6.1.4.1.2011.2.25.4.50.20.1.11.1.9
    optixL2LptL2netPortid OBJECT-TYPE
        SYNTAX Unsigned32
        MAX-ACCESS read-write
        STATUS current
        DESCRIPTION
            "This object indicates the Port ID of the L2Net LPT."
        ::= { optixL2LptL2netEntry 9 }

    -- 1.3.6.1.4.1.2011.2.25.4.50.20.1.12
    optixL2LptLeafTable OBJECT-TYPE
        SYNTAX SEQUENCE OF OptixL2LptLeafEntry
        MAX-ACCESS not-accessible
        STATUS current
        DESCRIPTION
            "This table describes the configurations of the L2 LPT in the  leaf of point-to-multipoint mode."
        ::= { optixL2LptGroup 12 }

    -- 1.3.6.1.4.1.2011.2.25.4.50.20.1.12.1
    optixL2LptLeafEntry OBJECT-TYPE
        SYNTAX OptixL2LptLeafEntry
        MAX-ACCESS not-accessible
        STATUS current
        DESCRIPTION
            "This entry describes the configurations of the L2 LPT in the  leaf of point-to-multipoint mode."
        INDEX{ optixL2LptRootType,optixL2LptRootPara1,optixL2LptRootPara2,optixL2LptRootPara3 }
        ::= { optixL2LptLeafTable 1 }

    OptixL2LptLeafEntry ::=
        SEQUENCE {
            optixL2LptLeafType
                INTEGER,
            optixL2LptLeafNum
                Unsigned32,
            optixL2LptLeafParaList
                OCTET STRING,
            optixL2LptLeafL2netMyPara3
                Unsigned32,
            optixL2LptLeafL2netPeerPara3
                Unsigned32,
            optixL2LptLeafL2netVlanID
                Unsigned32,
            optixL2LptLeafL2netBid
                Unsigned32,
            optixL2LptLeafL2netSubid
                Unsigned32,
            optixL2LptLeafL2netPortid
                Unsigned32,
            optixL2LptLeafRowStatus
                RowStatus
        }

    -- 1.3.6.1.4.1.2011.2.25.4.50.20.1.12.1.1
    optixL2LptLeafType OBJECT-TYPE
        SYNTAX INTEGER
        {
            uniport(1),
            pw(2),
            qinq(3),
            nniport(4),
            l2net(5)
        }
        MAX-ACCESS read-create
        STATUS current
        DESCRIPTION
            "This object indicates the leaf parameter type of the L2 LPT in the leaf of point-to-multipointmode. 1: uniport, 2: pw, 3: qinq, 4: nniport, 5: l2net"
        ::= { optixL2LptLeafEntry 1 }

    -- 1.3.6.1.4.1.2011.2.25.4.50.20.1.12.1.2
    optixL2LptLeafNum OBJECT-TYPE
        SYNTAX Unsigned32
        MAX-ACCESS read-create
        STATUS current
        DESCRIPTION
            "This object indicates the number of L2 LPT in the leaf of point-to-multipoint mode. Value range: 0 to 16."
        ::= { optixL2LptLeafEntry 2 }

    -- 1.3.6.1.4.1.2011.2.25.4.50.20.1.12.1.3
    optixL2LptLeafParaList OBJECT-TYPE
        SYNTAX OCTET STRING (SIZE(0..1024))
        MAX-ACCESS read-create
        STATUS current
        DESCRIPTION
            "This object indicates the leaf parameter of the L2 LPT in the leaf of point-to-multipoint mode."
        ::= { optixL2LptLeafEntry 3 }

    -- 1.3.6.1.4.1.2011.2.25.4.50.20.1.12.1.4
    optixL2LptLeafL2netMyPara3 OBJECT-TYPE
        SYNTAX Unsigned32
        MAX-ACCESS read-create
        STATUS current
        DESCRIPTION
            "This object indicates the local parameter 3 of the L2net in the leaf of point-to-multipoint mode. Value range: 1 to 0xffffffff."
        ::= { optixL2LptLeafEntry 4 }

    -- 1.3.6.1.4.1.2011.2.25.4.50.20.1.12.1.5
    optixL2LptLeafL2netPeerPara3 OBJECT-TYPE
        SYNTAX Unsigned32
        MAX-ACCESS read-create
        STATUS current
        DESCRIPTION
            "This object indicates the peer parameter 3 of the remote L2net in the leaf of point-to-multipoint mode. Value range: 1 to 0xffffffff."
        ::= { optixL2LptLeafEntry 5 }

    -- 1.3.6.1.4.1.2011.2.25.4.50.20.1.12.1.6
    optixL2LptLeafL2netVlanID OBJECT-TYPE
        SYNTAX Unsigned32
        MAX-ACCESS read-create
        STATUS current
        DESCRIPTION
            "This object indicates the Pass Vlan id of the remote L2net in the leaf of point-to-multipoint mode. Value range: 1 to 4094 (valid values). This parameter can also be set to 0xFFFF (the default value), indicating that the VLAN ID of the LPT service packets is the PV ID of the egress port."
        ::= { optixL2LptLeafEntry 6 }

    -- 1.3.6.1.4.1.2011.2.25.4.50.20.1.12.1.7
    optixL2LptLeafL2netBid OBJECT-TYPE
        SYNTAX Unsigned32
        MAX-ACCESS read-create
        STATUS current
        DESCRIPTION
            "This object indicates the Board ID of the remote L2net in the leaf of point-to-multipoint mode."
        ::= { optixL2LptLeafEntry 7 }

    -- 1.3.6.1.4.1.2011.2.25.4.50.20.1.12.1.8
    optixL2LptLeafL2netSubid OBJECT-TYPE
        SYNTAX Unsigned32
        MAX-ACCESS read-create
        STATUS current
        DESCRIPTION
            "This object indicates the Sub Board ID of the remote L2net in the leaf of point-to-multipoint mode."
        ::= { optixL2LptLeafEntry 8 }

    -- 1.3.6.1.4.1.2011.2.25.4.50.20.1.12.1.9
    optixL2LptLeafL2netPortid OBJECT-TYPE
        SYNTAX Unsigned32
        MAX-ACCESS read-create
        STATUS current
        DESCRIPTION
            "This object indicates the Port ID of the remote L2net in the leaf of point-to-multipoint mode."
        ::= { optixL2LptLeafEntry 9 }

    -- 1.3.6.1.4.1.2011.2.25.4.50.20.1.12.1.255
    optixL2LptLeafRowStatus OBJECT-TYPE
        SYNTAX RowStatus
        MAX-ACCESS read-create
        STATUS current
        DESCRIPTION
            "This object indicates the row status of the L2 LPT in the leaf of point-to-multipoint mode."
        ::= { optixL2LptLeafEntry 255 }

END
