-- OPTIX-SDH-PORT-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-PORT-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        optixLogBoardId,optixLogSubCardId
            FROM OPTIX-BOARD-MANAGE-MIB
        optixPortId
            FROM OPTIX-PORT-MANAGE-MIB
        ;

    optixSdhPort MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations ofSDH port management."
        REVISION "201204200000Z"
        DESCRIPTION
            "The initial revision of this MIB module1."
        ::={ optixProvisionSdh 45 }

    -- 1.3.6.1.4.1.2011.2.25.4.10.45.1
    optixSdhPortGroup OBJECT IDENTIFIER ::= { optixSdhPort 1 }

    -- 1.3.6.1.4.1.2011.2.25.4.10.45.1.1
    optixSdhPortTable OBJECT-TYPE
        SYNTAX SEQUENCE OF OptixSdhPortEntry
        MAX-ACCESS not-accessible
        STATUS current
        DESCRIPTION
            "This table describes the SDH port configurations."
        ::= { optixSdhPortGroup 1 }

    -- 1.3.6.1.4.1.2011.2.25.4.10.45.1.1.1
    optixSdhPortEntry OBJECT-TYPE
        SYNTAX OptixSdhPortEntry
        MAX-ACCESS not-accessible
        STATUS current
        DESCRIPTION
            "Thisentry describes the SDH port configurations."
        INDEX{ optixLogBoardId,optixLogSubCardId,optixPortId }
        ::= { optixSdhPortTable 1 }

    OptixSdhPortEntry ::=
        SEQUENCE {
            optixSdhLaserState
                INTEGER,
            optixSdhAlsEnable
                INTEGER,
            optixSdhAlsOpenTime
                Unsigned32,
            optixSdhAlsCloseTime
                Unsigned32,
            optixSdhAlsTestTime
                Unsigned32,
            optixSdhLsrDistance
                OCTET STRING,
            optixSdhLsrSpeed
                OCTET STRING,
            optixSdhLsrSN
                OCTET STRING,
            optixSdhPortRowStatus
                RowStatus
        }

    -- 1.3.6.1.4.1.2011.2.25.4.10.45.1.1.1.2
    optixSdhLaserState OBJECT-TYPE
        SYNTAX INTEGER
        {
            close(0),
            open(1),
            als(2)
        }
        MAX-ACCESS read-create
        STATUS current
        DESCRIPTION
            "This object indicates the enable status of the laser. 0: close, 1: open, 2: als"
        ::= { optixSdhPortEntry 2 }

    -- 1.3.6.1.4.1.2011.2.25.4.10.45.1.1.1.3
    optixSdhAlsEnable OBJECT-TYPE
        SYNTAX INTEGER
        {
            disable(0),
            enable(1)
        }
        MAX-ACCESS read-create
        STATUS current
        DESCRIPTION
            "This object indicates the enable status of ALS. 0: disable, 1: enable"
        ::= { optixSdhPortEntry 3 }

    -- 1.3.6.1.4.1.2011.2.25.4.10.45.1.1.1.4
    optixSdhAlsOpenTime OBJECT-TYPE
        SYNTAX Unsigned32
        MAX-ACCESS read-create
        STATUS current
        DESCRIPTION
            "This object indicates the enable time of the laser. Value range: 100 to 300 (unit: 10 ms). The default value is 200 (2s)."
        ::= { optixSdhPortEntry 4 }

    -- 1.3.6.1.4.1.2011.2.25.4.10.45.1.1.1.5
    optixSdhAlsCloseTime OBJECT-TYPE
        SYNTAX Unsigned32
        MAX-ACCESS read-create
        STATUS current
        DESCRIPTION
            "This object indicates the disable time of the laser. Value range: 200 to 30000 (unit: 10 ms). The default value is 6000 (60s)."
        ::= { optixSdhPortEntry 5 }

    -- 1.3.6.1.4.1.2011.2.25.4.10.45.1.1.1.6
    optixSdhAlsTestTime OBJECT-TYPE
        SYNTAX Unsigned32
        MAX-ACCESS read-create
        STATUS current
        DESCRIPTION
            "This object indicates the test time of the laser. Value range: 200 to 30000 (unit: 10 ms). The default value is 9000 (90s)."
        ::= { optixSdhPortEntry 6 }

    -- 1.3.6.1.4.1.2011.2.25.4.10.45.1.1.1.7
    optixSdhLsrDistance OBJECT-TYPE
        SYNTAX OCTET STRING (SIZE(0..4))
        MAX-ACCESS read-only
        STATUS current
        DESCRIPTION
            "This object indicates the transmission distance of the laser."
        ::= { optixSdhPortEntry 7 }

    -- 1.3.6.1.4.1.2011.2.25.4.10.45.1.1.1.8
    optixSdhLsrSpeed OBJECT-TYPE
        SYNTAX OCTET STRING (SIZE(0..2))
        MAX-ACCESS read-only
        STATUS current
        DESCRIPTION
            "This object indicates the optical modulerate."
        ::= { optixSdhPortEntry 8 }

    -- 1.3.6.1.4.1.2011.2.25.4.10.45.1.1.1.9
    optixSdhLsrSN OBJECT-TYPE
        SYNTAX OCTET STRING (SIZE(0..16))
        MAX-ACCESS read-only
        STATUS current
        DESCRIPTION
            "This object indicates the sequence number of the optical module."
        ::= { optixSdhPortEntry 9 }

    -- 1.3.6.1.4.1.2011.2.25.4.10.45.1.1.1.255
    optixSdhPortRowStatus OBJECT-TYPE
        SYNTAX RowStatus
        MAX-ACCESS read-create
        STATUS current
        DESCRIPTION
            "This object indicates the row status of the port."
        ::= { optixSdhPortEntry 255 }

END
