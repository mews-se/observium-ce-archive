-- OPTIX-MPLSTP-OAM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-MPLSTP-OAM-MIB DEFINITIONS ::= BEGIN
    IMPORTS
        OBJECT-GROUP,MODULE-COMPLIANCE
            FROM SNMPv2-CONF
        MODULE-IDENTITY,OBJECT-TYPE,Unsigned32,Integer32,IpAddress,NOTIFICATION-TYPE
            FROM SNMPv2-SMI
        RowStatus
            FROM SNMPv2-TC
        optixProvisionPtn
            FROM OPTIX-OID-MIB
        ;

    optixMplsTpOamMod MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage the MPLS-TP OAM based on Y.1731. The MPLS-TP OAM is used to maintain and manage MPLS-TP networks, which caneffectivelydetect, identify, and locate faults of the MPLS-TP network and quickly perform a protection switching when the link is defective or faulty. The MPLS-TP network can be classified into three layers: section, LSP, and PW.The section layer is the server layer of the LSP layer which is the server layer of the PW layer. The PW layer is the server layer of the service layer. In other words, the LSP layer is the client layer of the section layer, the PW layer is the client layer of the LSP layer, and the service layer is the client layer of the PW layer.The MPLS-TP OAM is applied to the section, LSP, and PW layers of the MPLS-TP network to detect, identify, and locate faults."
        REVISION "201204170000Z"
        DESCRIPTION
            "Initial version of this MIB module"
        ::={ optixProvisionPtn 4 }

    -- 1.3.6.1.4.1.2011.2.25.4.50.4.1
    optixMplsTpOamObject OBJECT IDENTIFIER ::= { optixMplsTpOamMod 1 }

    -- 1.3.6.1.4.1.2011.2.25.4.50.4.1.1
    optixMplsTpOamDefaultStandard OBJECT-TYPE
        SYNTAX INTEGER
        {
            y1711(1),
            y1731(2)
        }
        MAX-ACCESS read-write
        STATUS current
        DESCRIPTION
            "This object indicates the automatically created default OAM protocol standard when the tunnel/PW is created. 1: 1711 2: 1731"
        DEFVAL{ 1 }
        ::= { optixMplsTpOamObject 1 }

    -- 1.3.6.1.4.1.2011.2.25.4.50.4.1.2
    optixMplsTpOamOperator OBJECT-TYPE
        SYNTAX OCTET STRING(SIZE(0..6))
        MAX-ACCESS read-write
        STATUS current
        DESCRIPTION
            "This object indicates the operator ID, which is a character string containing 6 bytes."
        ::= { optixMplsTpOamObject 2 }

    -- 1.3.6.1.4.1.2011.2.25.4.50.4.1.3
    optixMplsTpOamCsfEnable OBJECT-TYPE
        SYNTAX INTEGER
        {
            disable(0),
            enable(1)
        }
        MAX-ACCESS read-write
        STATUS current
        DESCRIPTION
            "This object indicates whether the CSF is enabled. 1: enable 0: disable"
        DEFVAL{ 1 }
        ::= { optixMplsTpOamObject 3 }

    -- 1.3.6.1.4.1.2011.2.25.4.50.4.1.4
    optixMplsTpOamLckReportEnable OBJECT-TYPE
        SYNTAX INTEGER
        {
            disable(0),
            enable(1)
        }
        MAX-ACCESS read-only
        STATUS current
        DESCRIPTION
            "This object indicates whether the LCK report function is enabled. 1: enable 0: disable"
        ::= { optixMplsTpOamObject 4 }

    -- 1.3.6.1.4.1.2011.2.25.4.50.4.1.5
    optixMplsTpOamPortAisEnable OBJECT-TYPE
        SYNTAX INTEGER
        {
            disable(0),
            enable(1)
        }
        MAX-ACCESS read-write
        STATUS current
        DESCRIPTION
            "This object indicates whether the AIS alarm is enabled. 1: enable 0: disable"
        DEFVAL{ 0 }
        ::= { optixMplsTpOamObject 5 }

    -- 1.3.6.1.4.1.2011.2.25.4.50.4.1.6
    optixMplsTpOamChannelType OBJECT-TYPE
        SYNTAX Unsigned32(0..65535)
        MAX-ACCESS read-write
        STATUS current
        DESCRIPTION
            "This object indicates the channel type. Default: 0x7FFA Valid values range from 0 to oxffff."
        DEFVAL{ 32762 }
        ::= { optixMplsTpOamObject 6 }

    -- 1.3.6.1.4.1.2011.2.25.4.50.4.1.7
    optixMplsTpOamWholeStandard OBJECT-TYPE
        SYNTAX INTEGER
        {
            noconfigure(0),
            y1711(1),
            y1731(2),
            mix(3)
        }
        MAX-ACCESS read-only
        STATUS current
        DESCRIPTION
            "This object indicates the global OAM standard mode. 0: The OAM is not enabled. 1: 1711 2: 1731 3: hybrid configuration (both 1731 and 1711)"
        ::= { optixMplsTpOamObject 7 }

    -- 1.3.6.1.4.1.2011.2.25.4.50.4.1.8
    optixTunnelTpOamMepTable OBJECT-TYPE
        SYNTAX SEQUENCE OF OptixTunnelTpOamMepEntry
        MAX-ACCESS not-accessible
        STATUS current
        DESCRIPTION
            "This table is used to configure and manage the tunnel TP OAM Meps based on Y.1731. These configurations include the OAM standard, OAM ID, enable status, MEG information, MEP ID, MEP ID, CC/LCK/AIS packet period, packet priority, and SD/SF thresholds."
        ::= { optixMplsTpOamObject 8 }

    -- 1.3.6.1.4.1.2011.2.25.4.50.4.1.8.1
    optixTunnelTpOamMepEntry OBJECT-TYPE
        SYNTAX OptixTunnelTpOamMepEntry
        MAX-ACCESS not-accessible
        STATUS current
        DESCRIPTION
            "This entry indicates the parameter table for the tunnel TP OAM MEPs based on Y.1731."
        INDEX{ optixTunnelTpOamMepIndex }
        ::= { optixTunnelTpOamMepTable 1 }

    OptixTunnelTpOamMepEntry ::=
        SEQUENCE {
            optixTunnelTpOamMepIndex
                Unsigned32,
            optixTunnelTpOamMepEnable
                INTEGER,
            optixTunnelTpOamMepLevel
                Unsigned32,
            optixTunnelTpOamMepMegType
                INTEGER,
            optixTunnelTpOamMepId
                Unsigned32,
            optixTunnelTpOamMepPeerId
                Unsigned32,
            optixTunnelTpOamMepCheckWay
                INTEGER,
            optixTunnelTpOamMepCcTime
                Unsigned32,
            optixTunnelTpOamMepCcPri
                Unsigned32,
            optixTunnelTpOamMepCcSend
                INTEGER,
            optixTunnelTpOamMepSf
                Unsigned32,
            optixTunnelTpOamMepSd
                Unsigned32,
            optixTunnelTpOamMepMegInfo
                OCTET STRING,
            optixTunnelTpOamMepLckEnable
                INTEGER,
            optixTunnelTpOamMepLckTime
                Unsigned32,
            optixTunnelTpOamMepLckPri
                Unsigned32,
            optixTunnelTpOamMepAisEnable
                INTEGER,
            optixTunnelTpOamMepAisTime
                Unsigned32,
            optixTunnelTpOamMepAisPri
                Unsigned32,
            optixTunnelTpOamMepLmMode
                INTEGER,
            optixTunnelTpOamMepRevTnliIndex
                Unsigned32,
            optixTunnelTpOamMepStandard
                INTEGER,
            optixTunnelTpOamMepGalMode
                INTEGER,
            optixTunnelTpOamMepTSTState
                INTEGER,
            optixTunnelTpOamMepRCVPKTNum
                Unsigned32,
            optixTunnelTpOamMepSendPKTNum
                Unsigned32,
            optixTunnelTpOamMepMISCRCNum
                Unsigned32,
            optixTunnelTpOamMepMISCodeNum
                Unsigned32,
            optixTunnelTpOamMepMISOrderNum
                Unsigned32,
            optixTunnelTpOamMepClrTSTDir
                INTEGER,
            optixTunnelTpOamMepPKTLength
                Unsigned32,
            optixTunnelTpOamMepTimeSpace
                Unsigned32,
            optixTunnelTpOamMepPrio
                Unsigned32,
            optixTunnelTpOamMepTranskind
                INTEGER,
            optixTunnelTpOamMepIsOffOper
                INTEGER,
            optixTunnelTpOamMepTSTRecvEn
                INTEGER,
            optixTunnelTpOamMepprotocolformat
                INTEGER
        }

    -- 1.3.6.1.4.1.2011.2.25.4.50.4.1.8.1.1
    optixTunnelTpOamMepIndex OBJECT-TYPE
        SYNTAX Unsigned32
        MAX-ACCESS not-accessible
        STATUS current
        DESCRIPTION
            "This object indicates the tunnel OAM MEP index, ranging from 1 to 0x00ffffff."
        ::= { optixTunnelTpOamMepEntry 1 }

    -- 1.3.6.1.4.1.2011.2.25.4.50.4.1.8.1.2
    optixTunnelTpOamMepEnable OBJECT-TYPE
        SYNTAX INTEGER
        {
            disable(0),
            enable(1)
        }
        MAX-ACCESS read-write
        STATUS current
        DESCRIPTION
            "This object indicates whether the OAM is enabled. 1: enable 0: disable"
        ::= { optixTunnelTpOamMepEntry 2 }

    -- 1.3.6.1.4.1.2011.2.25.4.50.4.1.8.1.3
    optixTunnelTpOamMepLevel OBJECT-TYPE
        SYNTAX Unsigned32(0..7)
        MAX-ACCESS read-write
        STATUS current
        DESCRIPTION
            "This object indicates the MEG level. Default: 7. Valid values range from 0 to 7."
        DEFVAL{ 7 }
        ::= { optixTunnelTpOamMepEntry 3 }

    -- 1.3.6.1.4.1.2011.2.25.4.50.4.1.8.1.4
    optixTunnelTpOamMepMegType OBJECT-TYPE
        SYNTAX INTEGER
        {
            ipbased(1),
            iccbased(2),
            customerbased(3)
        }
        MAX-ACCESS read-write
        STATUS current
        DESCRIPTION
            "This object indicates the identifier type. 1: ip-based 2: icc-based 3: customer-based"
        DEFVAL{ 1 }
        ::= { optixTunnelTpOamMepEntry 4 }

    -- 1.3.6.1.4.1.2011.2.25.4.50.4.1.8.1.5
    optixTunnelTpOamMepId OBJECT-TYPE
        SYNTAX Unsigned32
        MAX-ACCESS read-write
        STATUS current
        DESCRIPTION
            "This object indicates the MEP ID."
        ::= { optixTunnelTpOamMepEntry 5 }

    -- 1.3.6.1.4.1.2011.2.25.4.50.4.1.8.1.6
    optixTunnelTpOamMepPeerId OBJECT-TYPE
        SYNTAX Unsigned32
        MAX-ACCESS read-write
        STATUS current
        DESCRIPTION
            "This object indicates the remote MEP ID."
        ::= { optixTunnelTpOamMepEntry 6 }

    -- 1.3.6.1.4.1.2011.2.25.4.50.4.1.8.1.7
    optixTunnelTpOamMepCheckWay OBJECT-TYPE
        SYNTAX INTEGER
        {
            auto(1),
            manual(2),
            invalid(255)
        }
        MAX-ACCESS read-write
        STATUS current
        DESCRIPTION
            "This object indicates the OAM detection mode. 1: auto 2: manual 255: invalid detection mode This parameter is unconfigurable when the tunnel is a unidirectional ingress node. The queried value is invalid."
        DEFVAL{ 1 }
        ::= { optixTunnelTpOamMepEntry 7 }

    -- 1.3.6.1.4.1.2011.2.25.4.50.4.1.8.1.8
    optixTunnelTpOamMepCcTime OBJECT-TYPE
        SYNTAX Unsigned32(1..7|255)
        MAX-ACCESS read-write
        STATUS current
        DESCRIPTION
            "This object indicates the CC packet period. 1: 3.33ms 2: 10 ms 3: 100 ms 4: 1s (default) 5: 10s 6: 1 minute 7: 10 minutes 255: invalid"
        DEFVAL{ 4 }
        ::= { optixTunnelTpOamMepEntry 8 }

    -- 1.3.6.1.4.1.2011.2.25.4.50.4.1.8.1.9
    optixTunnelTpOamMepCcPri OBJECT-TYPE
        SYNTAX Unsigned32(0..7|255)
        MAX-ACCESS read-write
        STATUS current
        DESCRIPTION
            "This object indicates the CC priority. Valid values range from 0 to 7. 0xff: invalid"
        DEFVAL{ 7 }
        ::= { optixTunnelTpOamMepEntry 9 }

    -- 1.3.6.1.4.1.2011.2.25.4.50.4.1.8.1.10
    optixTunnelTpOamMepCcSend OBJECT-TYPE
        SYNTAX INTEGER
        {
            disable(0),
            enable(1),
            invalid(255)
        }
        MAX-ACCESS read-write
        STATUS current
        DESCRIPTION
            "This object indicates the CC start/stop status. 0: disable1: enable 255: invalid This parameter is unconfigurable when the tunnel is a unidirectional ingress node. The queried value is invalid."
        DEFVAL{ 1 }
        ::= { optixTunnelTpOamMepEntry 10 }

    -- 1.3.6.1.4.1.2011.2.25.4.50.4.1.8.1.11
    optixTunnelTpOamMepSf OBJECT-TYPE
        SYNTAX Unsigned32(0..255)
        MAX-ACCESS read-write
        STATUS current
        DESCRIPTION
            "This object indicates the SF threshold (packet loss rate). Valid values range from 0 to 100."
        DEFVAL{ 0 }
        ::= { optixTunnelTpOamMepEntry 11 }

    -- 1.3.6.1.4.1.2011.2.25.4.50.4.1.8.1.12
    optixTunnelTpOamMepSd OBJECT-TYPE
        SYNTAX Unsigned32(0..255)
        MAX-ACCESS read-write
        STATUS current
        DESCRIPTION
            "This object indicates the SD threshold (packet loss rate). Valid values range from 0 to 100."
        DEFVAL{ 0 }
        ::= { optixTunnelTpOamMepEntry 12 }

    -- 1.3.6.1.4.1.2011.2.25.4.50.4.1.8.1.13
    optixTunnelTpOamMepMegInfo OBJECT-TYPE
        SYNTAX OCTET STRING(SIZE(0..96))
        MAX-ACCESS read-write
        STATUS current
        DESCRIPTION
            "This object indicates the MEG ID, which is a character string."
        ::= { optixTunnelTpOamMepEntry 13 }

    -- 1.3.6.1.4.1.2011.2.25.4.50.4.1.8.1.14
    optixTunnelTpOamMepLckEnable OBJECT-TYPE
        SYNTAX INTEGER
        {
            disable(0),
            enable(1)
        }
        MAX-ACCESS read-write
        STATUS current
        DESCRIPTION
            "This object indicates the locking status. 1: enable 0: disable"
        DEFVAL{ 0 }
        ::= { optixTunnelTpOamMepEntry 14 }

    -- 1.3.6.1.4.1.2011.2.25.4.50.4.1.8.1.15
    optixTunnelTpOamMepLckTime OBJECT-TYPE
        SYNTAX Unsigned32(1..7)
        MAX-ACCESS read-write
        STATUS current
        DESCRIPTION
            "This object indicates theLCK packet period. 1: 3.33 ms 2: 10 ms 3: 100 ms 4: 1000 ms (1s) 5: 10000 ms (10s) 6:60000 ms (1 minute) 7: 600000 ms(10min)"
        DEFVAL{ 4 }
        ::= { optixTunnelTpOamMepEntry 15 }

    -- 1.3.6.1.4.1.2011.2.25.4.50.4.1.8.1.16
    optixTunnelTpOamMepLckPri OBJECT-TYPE
        SYNTAX Unsigned32(0..7|255)
        MAX-ACCESS read-write
        STATUS current
        DESCRIPTION
            "This object indicates the LCK packet priority. Valid values range from 0 to 7. 0xff indicates thatthe priority is synchronized with the CC packet priority."
        DEFVAL{ 255 }
        ::= { optixTunnelTpOamMepEntry 16 }

    -- 1.3.6.1.4.1.2011.2.25.4.50.4.1.8.1.17
    optixTunnelTpOamMepAisEnable OBJECT-TYPE
        SYNTAX INTEGER
        {
            disable(0),
            enable(1)
        }
        MAX-ACCESS read-write
        STATUS current
        DESCRIPTION
            "This object indicates whether the AIS is enabled. 1: enable 0: disable"
        DEFVAL{ 0 }
        ::= { optixTunnelTpOamMepEntry 17 }

    -- 1.3.6.1.4.1.2011.2.25.4.50.4.1.8.1.18
    optixTunnelTpOamMepAisTime OBJECT-TYPE
        SYNTAX Unsigned32(1..7)
        MAX-ACCESS read-write
        STATUS current
        DESCRIPTION
            "This object indicates the AIS packet period. 1: 3.3 ms 2: 10 ms 3: 100 ms 4: 1000 ms (1s) 5: 10000 ms (10s) 6: 60000 ms (1 minute) 7: 600000 ms (10 minutes)"
        DEFVAL{ 4 }
        ::= { optixTunnelTpOamMepEntry 18 }

    -- 1.3.6.1.4.1.2011.2.25.4.50.4.1.8.1.19
    optixTunnelTpOamMepAisPri OBJECT-TYPE
        SYNTAX Unsigned32(0..7|255)
        MAX-ACCESS read-write
        STATUS current
        DESCRIPTION
            "This object indicates the AIS packet priority. Valid values range from 0 to 7. 0xff indicates that the priority is synchronized with the CC packet priority."
        DEFVAL{ 255 }
        ::= { optixTunnelTpOamMepEntry 19 }

    -- 1.3.6.1.4.1.2011.2.25.4.50.4.1.8.1.20
    optixTunnelTpOamMepLmMode OBJECT-TYPE
        SYNTAX INTEGER
        {
            standard(0),
            huawei(1)
        }
        MAX-ACCESS read-write
        STATUS current
        DESCRIPTION
            "This object indicates the LM packet mode. 0: standard 1: Huawei"
        DEFVAL{ 0 }
        ::= { optixTunnelTpOamMepEntry 20 }

    -- 1.3.6.1.4.1.2011.2.25.4.50.4.1.8.1.21
    optixTunnelTpOamMepRevTnliIndex OBJECT-TYPE
        SYNTAX Unsigned32
        MAX-ACCESS read-write
        STATUS current
        DESCRIPTION
            "This object indicates the reverse tunnel index. This parameter is applicable only when the tunnel serves as an egress node. When the value is 0xffffffff, the reverse tunnel index is not comnfigured."
        DEFVAL{ 4294967295 }
        ::= { optixTunnelTpOamMepEntry 21 }

    -- 1.3.6.1.4.1.2011.2.25.4.50.4.1.8.1.22
    optixTunnelTpOamMepStandard OBJECT-TYPE
        SYNTAX INTEGER
        {
            y1711(1),
            y1731(2)
        }
        MAX-ACCESS read-write
        STATUS current
        DESCRIPTION
            "This object indicates the OAM protocol standard. 1: 1711,2: 1731"
        DEFVAL{ 2 }
        ::= { optixTunnelTpOamMepEntry 22 }

    -- 1.3.6.1.4.1.2011.2.25.4.50.4.1.8.1.23
    optixTunnelTpOamMepGalMode OBJECT-TYPE
        SYNTAX INTEGER
        {
            rFC5586(0),
            y1711(1)
        }
        MAX-ACCESS read-write
        STATUS current
        DESCRIPTION
            "This parameter indicates the GAL label mode. 0: RFC5586 (13 label) 1: Y.1711 (14 label)"
        ::= { optixTunnelTpOamMepEntry 23 }

    -- 1.3.6.1.4.1.2011.2.25.4.50.4.1.8.1.24
    optixTunnelTpOamMepTSTState OBJECT-TYPE
        SYNTAX INTEGER
        {
            stop(0),
            testing(1)
        }
        MAX-ACCESS read-write
        STATUS current
        DESCRIPTION
            "This parameter indicates the sending status of TST packets. 0:stop 1:testing."
        ::= { optixTunnelTpOamMepEntry 24 }

    -- 1.3.6.1.4.1.2011.2.25.4.50.4.1.8.1.25
    optixTunnelTpOamMepRCVPKTNum OBJECT-TYPE
        SYNTAX Unsigned32
        MAX-ACCESS read-only
        STATUS current
        DESCRIPTION
            "This parameter indicates the total number of received TST packets."
        ::= { optixTunnelTpOamMepEntry 25 }

    -- 1.3.6.1.4.1.2011.2.25.4.50.4.1.8.1.26
    optixTunnelTpOamMepSendPKTNum OBJECT-TYPE
        SYNTAX Unsigned32
        MAX-ACCESS read-only
        STATUS current
        DESCRIPTION
            "This parameter indicates the total number of sent TST packets."
        ::= { optixTunnelTpOamMepEntry 26 }

    -- 1.3.6.1.4.1.2011.2.25.4.50.4.1.8.1.27
    optixTunnelTpOamMepMISCRCNum OBJECT-TYPE
        SYNTAX Unsigned32
        MAX-ACCESS read-only
        STATUS current
        DESCRIPTION
            "This parameter indicates the number of received CRC error TST packets."
        ::= { optixTunnelTpOamMepEntry 27 }

    -- 1.3.6.1.4.1.2011.2.25.4.50.4.1.8.1.28
    optixTunnelTpOamMepMISCodeNum OBJECT-TYPE
        SYNTAX Unsigned32
        MAX-ACCESS read-only
        STATUS current
        DESCRIPTION
            "This parameter indicates the number of received TST packets with error codes."
        ::= { optixTunnelTpOamMepEntry 28 }

    -- 1.3.6.1.4.1.2011.2.25.4.50.4.1.8.1.29
    optixTunnelTpOamMepMISOrderNum OBJECT-TYPE
        SYNTAX Unsigned32
        MAX-ACCESS read-only
        STATUS current
        DESCRIPTION
            "This parameter indicates the number of received TST packets with error orders."
        ::= { optixTunnelTpOamMepEntry 29 }

    -- 1.3.6.1.4.1.2011.2.25.4.50.4.1.8.1.30
    optixTunnelTpOamMepClrTSTDir OBJECT-TYPE
        SYNTAX INTEGER
        {
            bi(0),
            recv(1),
            send(2)
        }
        MAX-ACCESS read-write
        STATUS current
        DESCRIPTION
            "This parameter indicates the direction in which the TST packet statistical results are deleted. 0: send&amp;amp;receive 1: receive 2: send"
        ::= { optixTunnelTpOamMepEntry 30 }

    -- 1.3.6.1.4.1.2011.2.25.4.50.4.1.8.1.31
    optixTunnelTpOamMepPKTLength OBJECT-TYPE
        SYNTAX Unsigned32
        MAX-ACCESS read-write
        STATUS current
        DESCRIPTION
            "This parameter indicates the length of a TST testing packet. The unit is byte. The value 0xffff indicates that setting the length is invalid."
        ::= { optixTunnelTpOamMepEntry 31 }

    -- 1.3.6.1.4.1.2011.2.25.4.50.4.1.8.1.32
    optixTunnelTpOamMepTimeSpace OBJECT-TYPE
        SYNTAX Unsigned32 (1..7)
        MAX-ACCESS read-write
        STATUS current
        DESCRIPTION
            "This parameter indicates the TST testing interval."
        ::= { optixTunnelTpOamMepEntry 32 }

    -- 1.3.6.1.4.1.2011.2.25.4.50.4.1.8.1.33
    optixTunnelTpOamMepPrio OBJECT-TYPE
        SYNTAX Unsigned32 (0..7|255)
        MAX-ACCESS read-write
        STATUS current
        DESCRIPTION
            "This parameter indicates the priority of TST testing."
        ::= { optixTunnelTpOamMepEntry 33 }

    -- 1.3.6.1.4.1.2011.2.25.4.50.4.1.8.1.34
    optixTunnelTpOamMepTranskind OBJECT-TYPE
        SYNTAX INTEGER
        {
            null(0),
            nullCrc32(1),
            prbs(2),
            prbsCrc32(3)
        }
        MAX-ACCESS read-write
        STATUS current
        DESCRIPTION
            "This parameter indicates the type of the transfer code. 0:null 1:nullCrc32 2:prbs 3:prbsCrc32."
        ::= { optixTunnelTpOamMepEntry 34 }

    -- 1.3.6.1.4.1.2011.2.25.4.50.4.1.8.1.35
    optixTunnelTpOamMepIsOffOper OBJECT-TYPE
        SYNTAX INTEGER
        {
            undisrupt(0),
            disrupt(1)
        }
        MAX-ACCESS read-write
        STATUS current
        DESCRIPTION
            "This parameter indicates whether TST interrupts services. 0:undisrupt 1:disrupt"
        ::= { optixTunnelTpOamMepEntry 35 }

    -- 1.3.6.1.4.1.2011.2.25.4.50.4.1.8.1.36
    optixTunnelTpOamMepTSTRecvEn OBJECT-TYPE
        SYNTAX INTEGER
        {
            enable(1),
            disable(0)
        }
        MAX-ACCESS read-write
        STATUS current
        DESCRIPTION
            "This parameter indicates the receive enable status of TST packets."
        ::= { optixTunnelTpOamMepEntry 36 }

    -- 1.3.6.1.4.1.2011.2.25.4.50.4.1.8.1.37
    optixTunnelTpOamMepprotocolformat OBJECT-TYPE
        SYNTAX INTEGER
        {
            standard(1),
            huawei(2)
        }
        MAX-ACCESS read-write
        STATUS current
        DESCRIPTION
            "This object indicates the format of the protocol,1:standard,2:huawei"
        ::= { optixTunnelTpOamMepEntry 37 }

    -- 1.3.6.1.4.1.2011.2.25.4.50.4.1.9
    optixPWTpOamMepTable OBJECT-TYPE
        SYNTAX SEQUENCE OF OptixPWTpOamMepEntry
        MAX-ACCESS not-accessible
        STATUS current
        DESCRIPTION
            "Thistable indicates the configuration and management of thePW TP OAM MEPs based on Y.1731. These configurations include the OAM standard, OAM ID, enable status, MEG information, MEP ID, CC/LCK/AIS packet period and priority, SD/SF thresholds."
        ::= { optixMplsTpOamObject 9 }

    -- 1.3.6.1.4.1.2011.2.25.4.50.4.1.9.1
    optixPWTpOamMepEntry OBJECT-TYPE
        SYNTAX OptixPWTpOamMepEntry
        MAX-ACCESS not-accessible
        STATUS current
        DESCRIPTION
            "Thisentry indicatesthe parameter table for thePW TP OAM MEPs based on Y.1731."
        INDEX{ optixPWTpOamMepIndex }
        ::= { optixPWTpOamMepTable 1 }

    OptixPWTpOamMepEntry ::=
        SEQUENCE {
            optixPWTpOamMepIndex
                Unsigned32,
            optixPWTpOamMepEnable
                INTEGER,
            optixPWTpOamMepLevel
                Unsigned32,
            optixPWTpOamMepMegType
                INTEGER,
            optixPWTpOamMepId
                Unsigned32,
            optixPWTpOamMepPeerId
                Unsigned32,
            optixPWTpOamMepCheckWay
                INTEGER,
            optixPWTpOamMepCcTime
                Unsigned32,
            optixPWTpOamMepCcPri
                Unsigned32,
            optixPWTpOamMepCcSend
                INTEGER,
            optixPWTpOamMepSf
                Unsigned32,
            optixPWTpOamMepSd
                Unsigned32,
            optixPWTpOamMepMegInfo
                OCTET STRING,
            optixPWTpOamMepLckEnable
                INTEGER,
            optixPWTpOamMepLckTime
                Unsigned32,
            optixPWTpOamMepLckPri
                Unsigned32,
            optixPWTpOamMepLmMode
                INTEGER,
            optixPWTpOamMepPeerLsrId
                IpAddress,
            optixPWTpOamMepPeerPwId
                Unsigned32,
            optixPWTpOamMepGalEnable
                INTEGER,
            optixPWTpOamMepStandard
                INTEGER,
            optixPWTpOamMepGalMode
                INTEGER,
            optixPWTpOamMepTSTState
                INTEGER,
            optixPWTpOamMepRCVPKTNum
                Unsigned32,
            optixPWTpOamMepSendPKTNum
                Unsigned32,
            optixPWTpOamMepMISCRCNum
                Unsigned32,
            optixPWTpOamMepMISCodeNum
                Unsigned32,
            optixPWTpOamMepMISOrderNum
                Unsigned32,
            optixPWTpOamMepClrTSTDir
                INTEGER,
            optixPWTpOamMepPKTLength
                Unsigned32,
            optixPWTpOamMepTimeSpace
                Unsigned32,
            optixPWTpOamMepPrio
                Unsigned32,
            optixPWTpOamMepTranskind
                INTEGER,
            optixPWTpOamMepIsOffOper
                INTEGER,
            optixPWTpOamMepTSTRecvEn
                INTEGER,
            optixPWTpOamMepprotocolformat
                INTEGER
        }

    -- 1.3.6.1.4.1.2011.2.25.4.50.4.1.9.1.1
    optixPWTpOamMepIndex OBJECT-TYPE
        SYNTAX Unsigned32
        MAX-ACCESS not-accessible
        STATUS current
        DESCRIPTION
            "This object indicates thePW OAM MEP index, ranging from 1 to 0x00ffffff."
        ::= { optixPWTpOamMepEntry 1 }

    -- 1.3.6.1.4.1.2011.2.25.4.50.4.1.9.1.2
    optixPWTpOamMepEnable OBJECT-TYPE
        SYNTAX INTEGER
        {
            disable(0),
            enable(1)
        }
        MAX-ACCESS read-write
        STATUS current
        DESCRIPTION
            "This object indicates whether the OAM is enabled. 1: enable 0: disable"
        DEFVAL{ 0 }
        ::= { optixPWTpOamMepEntry 2 }

    -- 1.3.6.1.4.1.2011.2.25.4.50.4.1.9.1.3
    optixPWTpOamMepLevel OBJECT-TYPE
        SYNTAX Unsigned32(0..7)
        MAX-ACCESS read-write
        STATUS current
        DESCRIPTION
            "This object indicates the MEG level. Default: 7. Valid values range from 0 to 7."
        DEFVAL{ 7 }
        ::= { optixPWTpOamMepEntry 3 }

    -- 1.3.6.1.4.1.2011.2.25.4.50.4.1.9.1.4
    optixPWTpOamMepMegType OBJECT-TYPE
        SYNTAX INTEGER
        {
            ipbased(1),
            iccbased(2),
            customerbased(3)
        }
        MAX-ACCESS read-write
        STATUS current
        DESCRIPTION
            "This object indicates the identifier type. 1: ip-based 2: icc-based 3: customer-based"
        DEFVAL{ 1 }
        ::= { optixPWTpOamMepEntry 4 }

    -- 1.3.6.1.4.1.2011.2.25.4.50.4.1.9.1.5
    optixPWTpOamMepId OBJECT-TYPE
        SYNTAX Unsigned32
        MAX-ACCESS read-write
        STATUS current
        DESCRIPTION
            "This object indicates the MEP ID."
        ::= { optixPWTpOamMepEntry 5 }

    -- 1.3.6.1.4.1.2011.2.25.4.50.4.1.9.1.6
    optixPWTpOamMepPeerId OBJECT-TYPE
        SYNTAX Unsigned32
        MAX-ACCESS read-write
        STATUS current
        DESCRIPTION
            "This object indicates the remote MEP ID."
        ::= { optixPWTpOamMepEntry 6 }

    -- 1.3.6.1.4.1.2011.2.25.4.50.4.1.9.1.7
    optixPWTpOamMepCheckWay OBJECT-TYPE
        SYNTAX INTEGER
        {
            auto(1),
            manual(2)
        }
        MAX-ACCESS read-write
        STATUS current
        DESCRIPTION
            "This object indicates the OAM detection mode. 1: auto 2: manual"
        DEFVAL{ 1 }
        ::= { optixPWTpOamMepEntry 7 }

    -- 1.3.6.1.4.1.2011.2.25.4.50.4.1.9.1.8
    optixPWTpOamMepCcTime OBJECT-TYPE
        SYNTAX Unsigned32(1..7)
        MAX-ACCESS read-write
        STATUS current
        DESCRIPTION
            "This object indicates the CC packet period. 1: 3.33 ms 2: 10 ms 3: 100 ms 4: 1s (default) 5: 10s 6: 1 minute 7: 10 minutes"
        DEFVAL{ 4 }
        ::= { optixPWTpOamMepEntry 8 }

    -- 1.3.6.1.4.1.2011.2.25.4.50.4.1.9.1.9
    optixPWTpOamMepCcPri OBJECT-TYPE
        SYNTAX Unsigned32(0..7|255)
        MAX-ACCESS read-write
        STATUS current
        DESCRIPTION
            "This object indicates the CC priority. Valid values rang from 0 to 7. 0xff: invalid"
        DEFVAL{ 7 }
        ::= { optixPWTpOamMepEntry 9 }

    -- 1.3.6.1.4.1.2011.2.25.4.50.4.1.9.1.10
    optixPWTpOamMepCcSend OBJECT-TYPE
        SYNTAX INTEGER
        {
            stop(0),
            start(1)
        }
        MAX-ACCESS read-write
        STATUS current
        DESCRIPTION
            "This object indicates the CC start/stop status. 0: stop 1: start"
        DEFVAL{ 1 }
        ::= { optixPWTpOamMepEntry 10 }

    -- 1.3.6.1.4.1.2011.2.25.4.50.4.1.9.1.11
    optixPWTpOamMepSf OBJECT-TYPE
        SYNTAX Unsigned32(0..255)
        MAX-ACCESS read-write
        STATUS current
        DESCRIPTION
            "This object indicates the SF threshold (packet loss rate). Valid values range from 0 to 100."
        DEFVAL{ 0 }
        ::= { optixPWTpOamMepEntry 11 }

    -- 1.3.6.1.4.1.2011.2.25.4.50.4.1.9.1.12
    optixPWTpOamMepSd OBJECT-TYPE
        SYNTAX Unsigned32(0..255)
        MAX-ACCESS read-write
        STATUS current
        DESCRIPTION
            "This object indicates the SD threshold (packet loss rate). Valid values range from 0 to 100."
        DEFVAL{ 0 }
        ::= { optixPWTpOamMepEntry 12 }

    -- 1.3.6.1.4.1.2011.2.25.4.50.4.1.9.1.13
    optixPWTpOamMepMegInfo OBJECT-TYPE
        SYNTAX OCTET STRING(SIZE(0..96))
        MAX-ACCESS read-write
        STATUS current
        DESCRIPTION
            "This object indicates the MEG ID, which is a character string."
        ::= { optixPWTpOamMepEntry 13 }

    -- 1.3.6.1.4.1.2011.2.25.4.50.4.1.9.1.14
    optixPWTpOamMepLckEnable OBJECT-TYPE
        SYNTAX INTEGER
        {
            disable(0),
            enable(1)
        }
        MAX-ACCESS read-write
        STATUS current
        DESCRIPTION
            "This object indicates the locking status. 1: enable 0: disable"
        DEFVAL{ 0 }
        ::= { optixPWTpOamMepEntry 14 }

    -- 1.3.6.1.4.1.2011.2.25.4.50.4.1.9.1.15
    optixPWTpOamMepLckTime OBJECT-TYPE
        SYNTAX Unsigned32(1..7)
        MAX-ACCESS read-write
        STATUS current
        DESCRIPTION
            "This object indicates the LCK packet period. 1: 3.3 ms 2: 10 ms 3: 100 ms 4: 1000 ms (1s) 5: 10000 ms (10s) 6: 60000 ms (1 minute) 7: 600000 ms (10 minutes)"
        DEFVAL{ 4 }
        ::= { optixPWTpOamMepEntry 15 }

    -- 1.3.6.1.4.1.2011.2.25.4.50.4.1.9.1.16
    optixPWTpOamMepLckPri OBJECT-TYPE
        SYNTAX Unsigned32(0..7|255)
        MAX-ACCESS read-write
        STATUS current
        DESCRIPTION
            "This object indicates the LCK packet priority. Valid values range from 0 to 7. 0xff indicates that the priority is synchronized with the CC packet priority."
        DEFVAL{ 255 }
        ::= { optixPWTpOamMepEntry 16 }

    -- 1.3.6.1.4.1.2011.2.25.4.50.4.1.9.1.17
    optixPWTpOamMepLmMode OBJECT-TYPE
        SYNTAX INTEGER
        {
            standard(0),
            huawei(1)
        }
        MAX-ACCESS read-write
        STATUS current
        DESCRIPTION
            "This object indicates the LM packet mode. 0: standard 1: huawei"
        DEFVAL{ 0 }
        ::= { optixPWTpOamMepEntry 17 }

    -- 1.3.6.1.4.1.2011.2.25.4.50.4.1.9.1.18
    optixPWTpOamMepPeerLsrId OBJECT-TYPE
        SYNTAX IpAddress
        MAX-ACCESS read-write
        STATUS current
        DESCRIPTION
            "This object indicates the LSR IDto receive, which is the LSR ID of the valid MPLS device. 0.0.0.0: indicates that the peer IP address ofthe local PW is automatically obtained."
        DEFVAL{ 0 }
        ::= { optixPWTpOamMepEntry 18 }

    -- 1.3.6.1.4.1.2011.2.25.4.50.4.1.9.1.19
    optixPWTpOamMepPeerPwId OBJECT-TYPE
        SYNTAX Unsigned32
        MAX-ACCESS read-write
        STATUS current
        DESCRIPTION
            "This object indicates the remote PW ID, which is a valid MPLS PW ID. 0: indicates that the ID of the local PW is automatically obtained."
        DEFVAL{ 0 }
        ::= { optixPWTpOamMepEntry 19 }

    -- 1.3.6.1.4.1.2011.2.25.4.50.4.1.9.1.20
    optixPWTpOamMepGalEnable OBJECT-TYPE
        SYNTAX INTEGER
        {
            disable(0),
            enable(1)
        }
        MAX-ACCESS read-write
        STATUS current
        DESCRIPTION
            "This object indicates the enable status of the GAL label. 1: enable 0: disable"
        DEFVAL{ 0 }
        ::= { optixPWTpOamMepEntry 20 }

    -- 1.3.6.1.4.1.2011.2.25.4.50.4.1.9.1.21
    optixPWTpOamMepStandard OBJECT-TYPE
        SYNTAX INTEGER
        {
            y1711(1),
            y1731(2)
        }
        MAX-ACCESS read-write
        STATUS current
        DESCRIPTION
            "This object indicates the OAM protocol standard&amp;nbsp; 1: 1711 2: 1731"
        DEFVAL{ 2 }
        ::= { optixPWTpOamMepEntry 21 }

    -- 1.3.6.1.4.1.2011.2.25.4.50.4.1.9.1.22
    optixPWTpOamMepGalMode OBJECT-TYPE
        SYNTAX INTEGER
        {
            rFC5586(0),
            y1711(1)
        }
        MAX-ACCESS read-write
        STATUS current
        DESCRIPTION
            "This parameter indicates the GAL label mode. 0: RFC5586 (13 label) 1: Y.1711 (14 label)"
        ::= { optixPWTpOamMepEntry 22 }

    -- 1.3.6.1.4.1.2011.2.25.4.50.4.1.9.1.23
    optixPWTpOamMepTSTState OBJECT-TYPE
        SYNTAX INTEGER
        {
            stop(0),
            testing(1)
        }
        MAX-ACCESS read-write
        STATUS current
        DESCRIPTION
            "This parameter indicates the sending status of TST packets."
        ::= { optixPWTpOamMepEntry 23 }

    -- 1.3.6.1.4.1.2011.2.25.4.50.4.1.9.1.24
    optixPWTpOamMepRCVPKTNum OBJECT-TYPE
        SYNTAX Unsigned32
        MAX-ACCESS read-only
        STATUS current
        DESCRIPTION
            "This parameter indicates the total number of received TST packets."
        ::= { optixPWTpOamMepEntry 24 }

    -- 1.3.6.1.4.1.2011.2.25.4.50.4.1.9.1.25
    optixPWTpOamMepSendPKTNum OBJECT-TYPE
        SYNTAX Unsigned32
        MAX-ACCESS read-only
        STATUS current
        DESCRIPTION
            "This parameter indicates the total number of sent TST packets."
        ::= { optixPWTpOamMepEntry 25 }

    -- 1.3.6.1.4.1.2011.2.25.4.50.4.1.9.1.26
    optixPWTpOamMepMISCRCNum OBJECT-TYPE
        SYNTAX Unsigned32
        MAX-ACCESS read-only
        STATUS current
        DESCRIPTION
            "This parameter indicates the number of received CRC error TST packets."
        ::= { optixPWTpOamMepEntry 26 }

    -- 1.3.6.1.4.1.2011.2.25.4.50.4.1.9.1.27
    optixPWTpOamMepMISCodeNum OBJECT-TYPE
        SYNTAX Unsigned32
        MAX-ACCESS read-only
        STATUS current
        DESCRIPTION
            "This parameter indicates the number of received TST packets with error codes."
        ::= { optixPWTpOamMepEntry 27 }

    -- 1.3.6.1.4.1.2011.2.25.4.50.4.1.9.1.28
    optixPWTpOamMepMISOrderNum OBJECT-TYPE
        SYNTAX Unsigned32
        MAX-ACCESS read-only
        STATUS current
        DESCRIPTION
            "This parameter indicates the number of received TST packets with error orders."
        ::= { optixPWTpOamMepEntry 28 }

    -- 1.3.6.1.4.1.2011.2.25.4.50.4.1.9.1.29
    optixPWTpOamMepClrTSTDir OBJECT-TYPE
        SYNTAX INTEGER
        {
            bi(0),
            recv(1),
            send(2)
        }
        MAX-ACCESS read-write
        STATUS current
        DESCRIPTION
            "This parameter indicates the direction in which the TST packet statistical results are deleted. 0: send&amp;amp;receive 1: receive 2: send"
        ::= { optixPWTpOamMepEntry 29 }

    -- 1.3.6.1.4.1.2011.2.25.4.50.4.1.9.1.30
    optixPWTpOamMepPKTLength OBJECT-TYPE
        SYNTAX Unsigned32
        MAX-ACCESS read-write
        STATUS current
        DESCRIPTION
            "This parameter indicates the length of a TST testing packet. The unit is byte. The value 0xffff indicates the setting the length is invalid."
        ::= { optixPWTpOamMepEntry 30 }

    -- 1.3.6.1.4.1.2011.2.25.4.50.4.1.9.1.31
    optixPWTpOamMepTimeSpace OBJECT-TYPE
        SYNTAX Unsigned32 (1..7)
        MAX-ACCESS read-write
        STATUS current
        DESCRIPTION
            "This parameter indicates the TST testing interval."
        ::= { optixPWTpOamMepEntry 31 }

    -- 1.3.6.1.4.1.2011.2.25.4.50.4.1.9.1.32
    optixPWTpOamMepPrio OBJECT-TYPE
        SYNTAX Unsigned32 (0..7|255)
        MAX-ACCESS read-write
        STATUS current
        DESCRIPTION
            "This parameter indicates the priority of the TST testing."
        ::= { optixPWTpOamMepEntry 32 }

    -- 1.3.6.1.4.1.2011.2.25.4.50.4.1.9.1.33
    optixPWTpOamMepTranskind OBJECT-TYPE
        SYNTAX INTEGER
        {
            null(0),
            nullCrc32(1),
            prbs(2),
            prbsCrc32(3)
        }
        MAX-ACCESS read-write
        STATUS current
        DESCRIPTION
            "This parameter indicates the kind of transfer code. 0:null 1:nullCrc32 2:prbs 3:prbsCrc32"
        ::= { optixPWTpOamMepEntry 33 }

    -- 1.3.6.1.4.1.2011.2.25.4.50.4.1.9.1.34
    optixPWTpOamMepIsOffOper OBJECT-TYPE
        SYNTAX INTEGER
        {
            undisrupt(0),
            disrupt(1)
        }
        MAX-ACCESS read-write
        STATUS current
        DESCRIPTION
            "This parameter indicates whether TST interrupts services. 0:undisrupt 1:disrupt."
        ::= { optixPWTpOamMepEntry 34 }

    -- 1.3.6.1.4.1.2011.2.25.4.50.4.1.9.1.35
    optixPWTpOamMepTSTRecvEn OBJECT-TYPE
        SYNTAX INTEGER
        {
            enable(1),
            disable(0)
        }
        MAX-ACCESS read-write
        STATUS current
        DESCRIPTION
            "This parameter indicates the receive enable status of TST packets."
        ::= { optixPWTpOamMepEntry 35 }

    -- 1.3.6.1.4.1.2011.2.25.4.50.4.1.9.1.36
    optixPWTpOamMepprotocolformat OBJECT-TYPE
        SYNTAX INTEGER
        {
            standard(1),
            huawei(2)
        }
        MAX-ACCESS read-write
        STATUS current
        DESCRIPTION
            "This object indicates the format of the potocol.1:standard,2:huawei"
        ::= { optixPWTpOamMepEntry 36 }

    -- 1.3.6.1.4.1.2011.2.25.4.50.4.1.10
    optixTunnelTpOamMipTable OBJECT-TYPE
        SYNTAX SEQUENCE OF OptixTunnelTpOamMipEntry
        MAX-ACCESS not-accessible
        STATUS current
        DESCRIPTION
            "Thistable indicates the configuration and management of the tunnel TP OAM MIPs based on Y.1731. These configurations include theidentifier type, MEG information, and MIP ID."
        ::= { optixMplsTpOamObject 10 }

    -- 1.3.6.1.4.1.2011.2.25.4.50.4.1.10.1
    optixTunnelTpOamMipEntry OBJECT-TYPE
        SYNTAX OptixTunnelTpOamMipEntry
        MAX-ACCESS not-accessible
        STATUS current
        DESCRIPTION
            "Thisentry indicates theparameter table for the tunnel TP OAM MIPs based on Y.1731."
        INDEX{ optixTunnelTpOamMipIndex }
        ::= { optixTunnelTpOamMipTable 1 }

    OptixTunnelTpOamMipEntry ::=
        SEQUENCE {
            optixTunnelTpOamMipIndex
                Unsigned32,
            optixTunnelTpOamMipMegType
                INTEGER,
            optixTunnelTpOamMipMegInfo
                OCTET STRING,
            optixTunnelTpOamMipId
                Unsigned32,
            optixTunnelTpOamMipRowStatus
                RowStatus
        }

    -- 1.3.6.1.4.1.2011.2.25.4.50.4.1.10.1.1
    optixTunnelTpOamMipIndex OBJECT-TYPE
        SYNTAX Unsigned32
        MAX-ACCESS not-accessible
        STATUS current
        DESCRIPTION
            "This object indicates the tunnel OAM MIP index, ranging from 1 to 0x00ffffff."
        ::= { optixTunnelTpOamMipEntry 1 }

    -- 1.3.6.1.4.1.2011.2.25.4.50.4.1.10.1.2
    optixTunnelTpOamMipMegType OBJECT-TYPE
        SYNTAX INTEGER
        {
            ipbased(1),
            iccbased(2),
            customerbased(3)
        }
        MAX-ACCESS read-create
        STATUS current
        DESCRIPTION
            "This object indicates the identifier type. 1: ip-based 2: icc-based 3: customer-based"
        DEFVAL{ 1 }
        ::= { optixTunnelTpOamMipEntry 2 }

    -- 1.3.6.1.4.1.2011.2.25.4.50.4.1.10.1.3
    optixTunnelTpOamMipMegInfo OBJECT-TYPE
        SYNTAX OCTET STRING(SIZE(0..96))
        MAX-ACCESS read-create
        STATUS current
        DESCRIPTION
            "This object indicates the MEG ID, which is a character string."
        ::= { optixTunnelTpOamMipEntry 3 }

    -- 1.3.6.1.4.1.2011.2.25.4.50.4.1.10.1.4
    optixTunnelTpOamMipId OBJECT-TYPE
        SYNTAX Unsigned32
        MAX-ACCESS read-create
        STATUS current
        DESCRIPTION
            "This object indicates the MEP ID."
        ::= { optixTunnelTpOamMipEntry 4 }

    -- 1.3.6.1.4.1.2011.2.25.4.50.4.1.10.1.255
    optixTunnelTpOamMipRowStatus OBJECT-TYPE
        SYNTAX RowStatus
        MAX-ACCESS read-create
        STATUS current
        DESCRIPTION
            "This object indicates the row status. 1: active 4: createAndGo 6: destroy"
        ::= { optixTunnelTpOamMipEntry 255 }

    -- 1.3.6.1.4.1.2011.2.25.4.50.4.1.11
    optixPWTpOamMipTable OBJECT-TYPE
        SYNTAX SEQUENCE OF OptixPWTpOamMipEntry
        MAX-ACCESS not-accessible
        STATUS current
        DESCRIPTION
            "Thistable indicates the configuration and management of thePW TP OAM MIPs based on Y.1731. These configurations include the identifier type, MEG information, and MIP ID."
        ::= { optixMplsTpOamObject 11 }

    -- 1.3.6.1.4.1.2011.2.25.4.50.4.1.11.1
    optixPWTpOamMipEntry OBJECT-TYPE
        SYNTAX OptixPWTpOamMipEntry
        MAX-ACCESS not-accessible
        STATUS current
        DESCRIPTION
            "Thisentry indicates the parameter table for the PW TP OAM MIPs based on Y.1731."
        INDEX{ optixPWTpOamMipIndex }
        ::= { optixPWTpOamMipTable 1 }

    OptixPWTpOamMipEntry ::=
        SEQUENCE {
            optixPWTpOamMipIndex
                Unsigned32,
            optixPWTpOamMipMegType
                INTEGER,
            optixPWTpOamMipMegInfo
                OCTET STRING,
            optixPWTpOamMipId
                Unsigned32,
            optixPWTpOamMipRowStatus
                RowStatus
        }

    -- 1.3.6.1.4.1.2011.2.25.4.50.4.1.11.1.1
    optixPWTpOamMipIndex OBJECT-TYPE
        SYNTAX Unsigned32
        MAX-ACCESS not-accessible
        STATUS current
        DESCRIPTION
            "This object indicates the PW OAM MIP index, ranging from 1 to 0x00ffffff."
        ::= { optixPWTpOamMipEntry 1 }

    -- 1.3.6.1.4.1.2011.2.25.4.50.4.1.11.1.2
    optixPWTpOamMipMegType OBJECT-TYPE
        SYNTAX INTEGER
        {
            ipbased(1),
            iccbased(2),
            customerbased(3)
        }
        MAX-ACCESS read-create
        STATUS current
        DESCRIPTION
            "This object indicates the identifier type. 1: ip-based 2: icc-based 3: customer-based"
        DEFVAL{ 1 }
        ::= { optixPWTpOamMipEntry 2 }

    -- 1.3.6.1.4.1.2011.2.25.4.50.4.1.11.1.3
    optixPWTpOamMipMegInfo OBJECT-TYPE
        SYNTAX OCTET STRING(SIZE(0..96))
        MAX-ACCESS read-create
        STATUS current
        DESCRIPTION
            "This object indicates the MEG ID, which is a character string."
        ::= { optixPWTpOamMipEntry 3 }

    -- 1.3.6.1.4.1.2011.2.25.4.50.4.1.11.1.4
    optixPWTpOamMipId OBJECT-TYPE
        SYNTAX Unsigned32
        MAX-ACCESS read-create
        STATUS current
        DESCRIPTION
            "This object indicates the MIP ID."
        ::= { optixPWTpOamMipEntry 4 }

    -- 1.3.6.1.4.1.2011.2.25.4.50.4.1.11.1.255
    optixPWTpOamMipRowStatus OBJECT-TYPE
        SYNTAX RowStatus
        MAX-ACCESS read-create
        STATUS current
        DESCRIPTION
            "This object indicates the row status. 1: active 4: createAndGo 6: destroy"
        ::= { optixPWTpOamMipEntry 255 }

    -- 1.3.6.1.4.1.2011.2.25.4.50.4.1.12
    optixTunnelTpOamMepStateTable OBJECT-TYPE
        SYNTAX SEQUENCE OF OptixTunnelTpOamMepStateEntry
        MAX-ACCESS not-accessible
        STATUS current
        DESCRIPTION
            "This object indicates the status query of the tunnel TP OAM MEPs based on Y.1731."
        ::= { optixMplsTpOamObject 12 }

    -- 1.3.6.1.4.1.2011.2.25.4.50.4.1.12.1
    optixTunnelTpOamMepStateEntry OBJECT-TYPE
        SYNTAX OptixTunnelTpOamMepStateEntry
        MAX-ACCESS not-accessible
        STATUS current
        DESCRIPTION
            "This object indicates the status management of the tunnel TP OAM MEPs based on Y.1731."
        INDEX{ optixTunnelTpOamMepIndex,optixTunnelTpOamMepDirection }
        ::= { optixTunnelTpOamMepStateTable 1 }

    OptixTunnelTpOamMepStateEntry ::=
        SEQUENCE {
            optixTunnelTpOamMepDirection
                INTEGER,
            optixTunnelTpOamMepState
                INTEGER,
            optixTunnelTpOamMepDefectType
                INTEGER,
            optixTnlTpOamMepUnavailableTime
                Unsigned32,
            optixTnlTpOamMepDefectPosition
                IpAddress
        }

    -- 1.3.6.1.4.1.2011.2.25.4.50.4.1.12.1.1
    optixTunnelTpOamMepDirection OBJECT-TYPE
        SYNTAX INTEGER
        {
            farend(0),
            nearend(1)
        }
        MAX-ACCESS not-accessible
        STATUS current
        DESCRIPTION
            "For bidirectional tunnels, the status query is performaned in two directions, local and remote end. The query for the tunnel OAM is performed only in one direction, local or remote end. For the unidirectional ingress tunnel, only the local query result is returned. While for the unidirectional egress tunnel, only the remotequery result is returned."
        ::= { optixTunnelTpOamMepStateEntry 1 }

    -- 1.3.6.1.4.1.2011.2.25.4.50.4.1.12.1.2
    optixTunnelTpOamMepState OBJECT-TYPE
        SYNTAX INTEGER
        {
            initialstate(0),
            nearendavailable(1),
            nearenddefectavailable(2),
            nearenddefectunavailable(3),
            nearendunavailable(4),
            farendavailable(5),
            farenddefectavailable(6),
            farenddefectunavailable(7),
            farendunavailable(8)
        }
        MAX-ACCESS read-only
        STATUS current
        DESCRIPTION
            "This object indicates the tunnel OAM status. 0: Thetunnel OAMis in initializing state. 1: The tunnel OAM is available at the local end. 2: The tunnel OAM is available but defectiveat the local end. 3: The tunnel OAM is defective and unavailable at the local end. 4: The tunnel OAM is unavailable at the local end. 5: The tunnel OAM is available at theremote end. 6: The tunnel OAM is defective but available at the remote end. 7: The tunnel OAM is defective and unavailable at the remote end. 8: The tunnel OAM is unavailable at the remote end."
        ::= { optixTunnelTpOamMepStateEntry 2 }

    -- 1.3.6.1.4.1.2011.2.25.4.50.4.1.12.1.3
    optixTunnelTpOamMepDefectType OBJECT-TYPE
        SYNTAX INTEGER
        {
            dserver(1),
            dpeerme(2),
            dlocv(3),
            dttsimismatch(4),
            dttsimismerge(5),
            dexcess(6),
            dunknown(7),
            dunexpmeg(8),
            dunexpper(9),
            dunexpmep(10),
            invalid(255)
        }
        MAX-ACCESS read-only
        STATUS current
        DESCRIPTION
            "This object indicates the defect type of the tunnel OAM. 1: dServer 2: dPeerME 3: dLOCV 4: dTTSI_Mismatch 5: dTTSI_Mismerge 6: dExcess 7: dUnknown 8: dUnExpMeg 9: dUnExpPer 10: dunExpMep 255: invalid"
        ::= { optixTunnelTpOamMepStateEntry 3 }

    -- 1.3.6.1.4.1.2011.2.25.4.50.4.1.12.1.4
    optixTnlTpOamMepUnavailableTime OBJECT-TYPE
        SYNTAX Unsigned32
        MAX-ACCESS read-only
        STATUS current
        DESCRIPTION
            "This object indicates the unavailable time of the tunnel OAM. The time ranges from 0 to 300,000 ms. 4294967295: invalid"
        ::= { optixTunnelTpOamMepStateEntry 4 }

    -- 1.3.6.1.4.1.2011.2.25.4.50.4.1.12.1.5
    optixTnlTpOamMepDefectPosition OBJECT-TYPE
        SYNTAX IpAddress
        MAX-ACCESS read-only
        STATUS current
        DESCRIPTION
            "This object indicates the position of the tunnel defect: node identified by IP addresses."
        ::= { optixTunnelTpOamMepStateEntry 5 }

    -- 1.3.6.1.4.1.2011.2.25.4.50.4.1.13
    optixPWTpOamMepStateTable OBJECT-TYPE
        SYNTAX SEQUENCE OF OptixPWTpOamMepStateEntry
        MAX-ACCESS not-accessible
        STATUS current
        DESCRIPTION
            "Thistable is used toquery thestatus of thePW TP OAM MEPs based on Y.1731."
        ::= { optixMplsTpOamObject 13 }

    -- 1.3.6.1.4.1.2011.2.25.4.50.4.1.13.1
    optixPWTpOamMepStateEntry OBJECT-TYPE
        SYNTAX OptixPWTpOamMepStateEntry
        MAX-ACCESS not-accessible
        STATUS current
        DESCRIPTION
            "Thisentry indicates the status management of thePW TP OAM MEPs based on Y.1731."
        INDEX{ optixPWTpOamMepIndex,optixPWTpOamMepDirection }
        ::= { optixPWTpOamMepStateTable 1 }

    OptixPWTpOamMepStateEntry ::=
        SEQUENCE {
            optixPWTpOamMepDirection
                INTEGER,
            optixPWTpOamMepState
                INTEGER,
            optixPWTpOamMepDefectType
                INTEGER,
            optixPWTpOamMepUnavailableTime
                Unsigned32,
            optixPWTpOamMepDefectPosition
                IpAddress
        }

    -- 1.3.6.1.4.1.2011.2.25.4.50.4.1.13.1.1
    optixPWTpOamMepDirection OBJECT-TYPE
        SYNTAX INTEGER
        {
            farend(0),
            nearend(1)
        }
        MAX-ACCESS not-accessible
        STATUS current
        DESCRIPTION
            "For bidirectional MPLS PWs, the status query is performaned in two directions, local and remote ends. ForPW OAM, the status query is performend in single direction: localor remote end."
        ::= { optixPWTpOamMepStateEntry 1 }

    -- 1.3.6.1.4.1.2011.2.25.4.50.4.1.13.1.2
    optixPWTpOamMepState OBJECT-TYPE
        SYNTAX INTEGER
        {
            initialstate(0),
            nearendavailable(1),
            nearenddefectavailable(2),
            nearenddefectunavailable(3),
            nearendunavailable(4),
            farendavailable(5),
            farenddefectavailable(6),
            farenddefectunavailable(7),
            farendunavailable(8)
        }
        MAX-ACCESS read-only
        STATUS current
        DESCRIPTION
            "This object indicates the PW OAM status. 0: ThePW OAM is in initializing state. 1: ThePW OAM is available at the local end. 2: ThePW OAM is available at the local end. 3: The PWOAM is defective and unavailable at the local end. 4: ThePW OAM is unavailable at the local end. 5: ThePW OAM is available at the remote end. 6: ThePW OAM is defective but available at the remote end. 7: ThePW OAM is defective and unavailable at the remote end. 8: ThePW OAM is unavailable at the remote end."
        ::= { optixPWTpOamMepStateEntry 2 }

    -- 1.3.6.1.4.1.2011.2.25.4.50.4.1.13.1.3
    optixPWTpOamMepDefectType OBJECT-TYPE
        SYNTAX INTEGER
        {
            dserver(1),
            dpeerme(2),
            dlocv(3),
            dttsimismatch(4),
            dttsimismerge(5),
            dexcess(6),
            dunknown(7),
            dunexpmeg(8),
            dunexpper(9),
            dunexpmep(10),
            invalid(255)
        }
        MAX-ACCESS read-only
        STATUS current
        DESCRIPTION
            "This object indicates the defect type of the PW OAM. 1: dServer 2: dPeerME 3: dLOCV 4: dTTSI_Mismatch 5: dTTSI_Mismerge 6: dExcess 7: dUnknown 8: dUnExpMeg 9: dUnExpPer 10: dunExpMep 255: invalid"
        ::= { optixPWTpOamMepStateEntry 3 }

    -- 1.3.6.1.4.1.2011.2.25.4.50.4.1.13.1.4
    optixPWTpOamMepUnavailableTime OBJECT-TYPE
        SYNTAX Unsigned32
        MAX-ACCESS read-only
        STATUS current
        DESCRIPTION
            "This object indicates the unavailable time of thePW OAM. The time ranges from 0 to 300,000 ms. 4294967295: invalid"
        ::= { optixPWTpOamMepStateEntry 4 }

    -- 1.3.6.1.4.1.2011.2.25.4.50.4.1.13.1.5
    optixPWTpOamMepDefectPosition OBJECT-TYPE
        SYNTAX IpAddress
        MAX-ACCESS read-only
        STATUS current
        DESCRIPTION
            "This object indicates the position of the PW OAM defect: a node identified by IP address."
        ::= { optixPWTpOamMepStateEntry 5 }

    -- 1.3.6.1.4.1.2011.2.25.4.50.4.1.14
    optixTunnelTpOamSwitchTable OBJECT-TYPE
        SYNTAX SEQUENCE OF OptixTunnelTpOamSwitchEntry
        MAX-ACCESS not-accessible
        STATUS current
        DESCRIPTION
            "This?table is used to Switch the identifier type of tunnel TP OAM based on Y.1731."
        ::= { optixMplsTpOamObject 14 }

    -- 1.3.6.1.4.1.2011.2.25.4.50.4.1.14.1
    optixTunnelTpOamSwitchEntry OBJECT-TYPE
        SYNTAX OptixTunnelTpOamSwitchEntry
        MAX-ACCESS not-accessible
        STATUS current
        DESCRIPTION
            "This&nbsp;entry is used to Switch the identifier type of tunnel TP OAM based on Y.1731."
        INDEX{ optixTunnelTpOamMepIndex }
        ::= { optixTunnelTpOamSwitchTable 1 }

    OptixTunnelTpOamSwitchEntry ::=
        SEQUENCE {
            optixTunnelTpOamSwitchMegType
                INTEGER,
            optixTunnelTpOamSwitchMepId
                Unsigned32,
            optixTunnelTpOamSwitchMepPeerId
                Unsigned32,
            optixTunnelTpOamSwitchMegInfo
                OCTET STRING
        }

    -- 1.3.6.1.4.1.2011.2.25.4.50.4.1.14.1.1
    optixTunnelTpOamSwitchMegType OBJECT-TYPE
        SYNTAX INTEGER
        {
            ipbased(1),
            iccbased(2),
            customerbased(3)
        }
        MAX-ACCESS read-write
        STATUS current
        DESCRIPTION
            "This object indicates the identifier type. 1: ip-based 2: icc-based 3: customer-based Only icc-based and customer-based modes can be configured,ip-based mode Can be inquired merely"
        ::= { optixTunnelTpOamSwitchEntry 1 }

    -- 1.3.6.1.4.1.2011.2.25.4.50.4.1.14.1.2
    optixTunnelTpOamSwitchMepId OBJECT-TYPE
        SYNTAX Unsigned32
        MAX-ACCESS read-write
        STATUS current
        DESCRIPTION
            "This object indicates the MEP ID."
        ::= { optixTunnelTpOamSwitchEntry 2 }

    -- 1.3.6.1.4.1.2011.2.25.4.50.4.1.14.1.3
    optixTunnelTpOamSwitchMepPeerId OBJECT-TYPE
        SYNTAX Unsigned32
        MAX-ACCESS read-write
        STATUS current
        DESCRIPTION
            "This object indicates the remote MEP ID."
        ::= { optixTunnelTpOamSwitchEntry 3 }

    -- 1.3.6.1.4.1.2011.2.25.4.50.4.1.14.1.4
    optixTunnelTpOamSwitchMegInfo OBJECT-TYPE
        SYNTAX OCTET STRING (SIZE(0..96))
        MAX-ACCESS read-write
        STATUS current
        DESCRIPTION
            "This object indicates the MEG ID, which is a character string. In icc-based mode, the MEG ID information is does not surpass 13 Characters."
        ::= { optixTunnelTpOamSwitchEntry 4 }

    -- 1.3.6.1.4.1.2011.2.25.4.50.4.1.15
    optixPWTpOamSwitchTable OBJECT-TYPE
        SYNTAX SEQUENCE OF OptixPWTpOamSwitchEntry
        MAX-ACCESS not-accessible
        STATUS current
        DESCRIPTION
            "This?table is used to Switch the identifier type of PW TP OAM based on Y.1731."
        ::= { optixMplsTpOamObject 15 }

    -- 1.3.6.1.4.1.2011.2.25.4.50.4.1.15.1
    optixPWTpOamSwitchEntry OBJECT-TYPE
        SYNTAX OptixPWTpOamSwitchEntry
        MAX-ACCESS not-accessible
        STATUS current
        DESCRIPTION
            "This?entry  is used to Switch the identifier type of PW TP OAM based on Y.1731."
        INDEX{ optixPWTpOamMepIndex }
        ::= { optixPWTpOamSwitchTable 1 }

    OptixPWTpOamSwitchEntry ::=
        SEQUENCE {
            optixPWTpOamSwitchMegType
                INTEGER,
            optixPWTpOamSwitchMepId
                Unsigned32,
            optixPWTpOamSwitchMepPeerId
                Unsigned32,
            optixPWTpOamSwitchMegInfo
                OCTET STRING
        }

    -- 1.3.6.1.4.1.2011.2.25.4.50.4.1.15.1.1
    optixPWTpOamSwitchMegType OBJECT-TYPE
        SYNTAX INTEGER
        {
            ipbased(1),
            iccbased(2),
            customerbased(3)
        }
        MAX-ACCESS read-write
        STATUS current
        DESCRIPTION
            "This object indicates the identifier type. 1: ip-based 2: icc-based 3: customer-based Only icc-based and customer-based modes can be configured,ip-based mode Can be inquired merely"
        ::= { optixPWTpOamSwitchEntry 1 }

    -- 1.3.6.1.4.1.2011.2.25.4.50.4.1.15.1.2
    optixPWTpOamSwitchMepId OBJECT-TYPE
        SYNTAX Unsigned32
        MAX-ACCESS read-write
        STATUS current
        DESCRIPTION
            "This object indicates the MEP ID."
        ::= { optixPWTpOamSwitchEntry 2 }

    -- 1.3.6.1.4.1.2011.2.25.4.50.4.1.15.1.3
    optixPWTpOamSwitchMepPeerId OBJECT-TYPE
        SYNTAX Unsigned32
        MAX-ACCESS read-write
        STATUS current
        DESCRIPTION
            "This object indicates the remote MEP ID."
        ::= { optixPWTpOamSwitchEntry 3 }

    -- 1.3.6.1.4.1.2011.2.25.4.50.4.1.15.1.4
    optixPWTpOamSwitchMegInfo OBJECT-TYPE
        SYNTAX OCTET STRING (SIZE(0..96))
        MAX-ACCESS read-write
        STATUS current
        DESCRIPTION
            "This object indicates the MEG ID, which is a character string. In icc-based mode, the MEG ID information is does not surpass 13 Characters."
        ::= { optixPWTpOamSwitchEntry 4 }

    -- 1.3.6.1.4.1.2011.2.25.4.50.4.1.16
    optixMPLSOamTrap OBJECT IDENTIFIER ::= { optixMplsTpOamObject 16 }

    -- 1.3.6.1.4.1.2011.2.25.4.50.4.1.16.1
    optixMplsOamLbRsp NOTIFICATION-TYPE
        OBJECTS{ optixMplsOamMegType,optixMplsOamIndex,optixMplsOamMepMipId,optixMplsOamPktLen,optixMplsOamSeqNum,optixMplsOamDelay,optixMplsOamTTL,optixMplsOamRetCode,optixMplsOamSubCode }
        STATUS current
        DESCRIPTION
            "This object is used to report an LB response event."
        ::= { optixMPLSOamTrap 1 }

    -- 1.3.6.1.4.1.2011.2.25.4.50.4.1.16.2
    optixMplsOamLbOverTime NOTIFICATION-TYPE
        OBJECTS{ optixMplsOamMegType,optixMplsOamIndex }
        STATUS current
        DESCRIPTION
            "This object is used to report an LB response timeout event."
        ::= { optixMPLSOamTrap 2 }

    -- 1.3.6.1.4.1.2011.2.25.4.50.4.1.16.3
    optixMplsOamLbStat NOTIFICATION-TYPE
        OBJECTS{ optixMplsOamMegType,optixMplsOamIndex,optixMplsOamTxNum,optixMplsOamRxNum,optixMplsOamLoseRate,optixMplsOamMinDelay,optixMplsOamMaxDelay,optixMplsOamAverDelay }
        STATUS current
        DESCRIPTION
            "This object is used to report an LB statistics result event."
        ::= { optixMPLSOamTrap 3 }

    -- 1.3.6.1.4.1.2011.2.25.4.50.4.1.17
    optixMPLSOamTrapMember OBJECT IDENTIFIER ::= { optixMplsTpOamObject 17 }

    -- 1.3.6.1.4.1.2011.2.25.4.50.4.1.17.1
    optixMplsOamMegType OBJECT-TYPE
        SYNTAX INTEGER
        {
            all(0),
            lsp(1),
            pw(2),
            section(3),
            mspw(4)
        }
        MAX-ACCESS accessible-for-notify
        STATUS current
        DESCRIPTION
            "This object indicates the MEG type."
        ::= { optixMPLSOamTrapMember 1 }

    -- 1.3.6.1.4.1.2011.2.25.4.50.4.1.17.2
    optixMplsOamIndex OBJECT-TYPE
        SYNTAX Unsigned32
        MAX-ACCESS accessible-for-notify
        STATUS current
        DESCRIPTION
            "This object indicates the index to the tunnel/PW/section."
        ::= { optixMPLSOamTrapMember 2 }

    -- 1.3.6.1.4.1.2011.2.25.4.50.4.1.17.3
    optixMplsOamMepMipId OBJECT-TYPE
        SYNTAX Unsigned32
        MAX-ACCESS accessible-for-notify
        STATUS current
        DESCRIPTION
            "This object indicates the opposite MEP/MIP address or ID."
        ::= { optixMPLSOamTrapMember 3 }

    -- 1.3.6.1.4.1.2011.2.25.4.50.4.1.17.4
    optixMplsOamPktLen OBJECT-TYPE
        SYNTAX Unsigned32
        MAX-ACCESS accessible-for-notify
        STATUS current
        DESCRIPTION
            "This object indicates the number of bytes in a packet."
        ::= { optixMPLSOamTrapMember 4 }

    -- 1.3.6.1.4.1.2011.2.25.4.50.4.1.17.5
    optixMplsOamSeqNum OBJECT-TYPE
        SYNTAX Unsigned32
        MAX-ACCESS accessible-for-notify
        STATUS current
        DESCRIPTION
            "This object indicates the sequence number of a packet."
        ::= { optixMPLSOamTrapMember 5 }

    -- 1.3.6.1.4.1.2011.2.25.4.50.4.1.17.6
    optixMplsOamDelay OBJECT-TYPE
        SYNTAX Unsigned32
        MAX-ACCESS accessible-for-notify
        STATUS current
        DESCRIPTION
            "This object indicates the response time."
        ::= { optixMPLSOamTrapMember 6 }

    -- 1.3.6.1.4.1.2011.2.25.4.50.4.1.17.7
    optixMplsOamTTL OBJECT-TYPE
        SYNTAX Unsigned32
        MAX-ACCESS accessible-for-notify
        STATUS current
        DESCRIPTION
            "This object indicates the TTL of sent packets."
        ::= { optixMPLSOamTrapMember 7 }

    -- 1.3.6.1.4.1.2011.2.25.4.50.4.1.17.8
    optixMplsOamRetCode OBJECT-TYPE
        SYNTAX Unsigned32
        MAX-ACCESS accessible-for-notify
        STATUS current
        DESCRIPTION
            "This object indicates the return code."
        ::= { optixMPLSOamTrapMember 8 }

    -- 1.3.6.1.4.1.2011.2.25.4.50.4.1.17.9
    optixMplsOamSubCode OBJECT-TYPE
        SYNTAX Unsigned32
        MAX-ACCESS accessible-for-notify
        STATUS current
        DESCRIPTION
            "This object indicates the return subcode."
        ::= { optixMPLSOamTrapMember 9 }

    -- 1.3.6.1.4.1.2011.2.25.4.50.4.1.17.10
    optixMplsOamTxNum OBJECT-TYPE
        SYNTAX Unsigned32
        MAX-ACCESS accessible-for-notify
        STATUS current
        DESCRIPTION
            "This object indicates the total number of sent packets."
        ::= { optixMPLSOamTrapMember 10 }

    -- 1.3.6.1.4.1.2011.2.25.4.50.4.1.17.11
    optixMplsOamRxNum OBJECT-TYPE
        SYNTAX Unsigned32
        MAX-ACCESS accessible-for-notify
        STATUS current
        DESCRIPTION
            "This object indicates the total number of received packets."
        ::= { optixMPLSOamTrapMember 11 }

    -- 1.3.6.1.4.1.2011.2.25.4.50.4.1.17.12
    optixMplsOamLoseRate OBJECT-TYPE
        SYNTAX Unsigned32
        MAX-ACCESS accessible-for-notify
        STATUS current
        DESCRIPTION
            "This object indicates the packet loss rate."
        ::= { optixMPLSOamTrapMember 12 }

    -- 1.3.6.1.4.1.2011.2.25.4.50.4.1.17.13
    optixMplsOamMinDelay OBJECT-TYPE
        SYNTAX Unsigned32
        MAX-ACCESS accessible-for-notify
        STATUS current
        DESCRIPTION
            "This object indicates the minimum delay. (unit:us)"
        ::= { optixMPLSOamTrapMember 13 }

    -- 1.3.6.1.4.1.2011.2.25.4.50.4.1.17.14
    optixMplsOamMaxDelay OBJECT-TYPE
        SYNTAX Unsigned32
        MAX-ACCESS accessible-for-notify
        STATUS current
        DESCRIPTION
            "This object indicates the maximum delay. (unit:us)"
        ::= { optixMPLSOamTrapMember 14 }

    -- 1.3.6.1.4.1.2011.2.25.4.50.4.1.17.15
    optixMplsOamAverDelay OBJECT-TYPE
        SYNTAX Unsigned32
        MAX-ACCESS accessible-for-notify
        STATUS current
        DESCRIPTION
            "This object indicates the average delay. (unit:us)"
        ::= { optixMPLSOamTrapMember 15 }

    -- 1.3.6.1.4.1.2011.2.25.4.50.4.1.17.16
    optixMplsOamSaltusNum OBJECT-TYPE
        SYNTAX Unsigned32
        MAX-ACCESS accessible-for-notify
        STATUS current
        DESCRIPTION
            "This object indicates the saltus change number."
        ::= { optixMPLSOamTrapMember 16 }

    -- 1.3.6.1.4.1.2011.2.25.4.50.4.1.17.17
    optixMplsOamSaltusBit OBJECT-TYPE
        SYNTAX Unsigned32
        MAX-ACCESS accessible-for-notify
        STATUS current
        DESCRIPTION
            "This object indicates the saltus change bit."
        ::= { optixMPLSOamTrapMember 17 }

    -- 1.3.6.1.4.1.2011.2.25.4.50.4.1.17.18
    optixMplsOamChangeNum OBJECT-TYPE
        SYNTAX Unsigned32
        MAX-ACCESS accessible-for-notify
        STATUS current
        DESCRIPTION
            "This object indicates the total number of payload change packets."
        ::= { optixMPLSOamTrapMember 18 }

    -- 1.3.6.1.4.1.2011.2.25.4.50.4.1.18
    optixPWPingTrcRtTable OBJECT-TYPE
        SYNTAX SEQUENCE OF OptixPWPingTrcRtEntry
        MAX-ACCESS not-accessible
        STATUS current
        DESCRIPTION
            "This table manages the PW PING and PW TRACEOUTE configurations including the PW PING start/stop and PW TRACEOUTE start/stop."
        ::= { optixMplsTpOamObject 18 }

    -- 1.3.6.1.4.1.2011.2.25.4.50.4.1.18.1
    optixPWPingTrcRtEntry OBJECT-TYPE
        SYNTAX OptixPWPingTrcRtEntry
        MAX-ACCESS not-accessible
        STATUS current
        DESCRIPTION
            "This entry indicates the parameter table for the PW PING and PW TRACEROUTE."
        INDEX{ optixPWPingTrcRtIndex }
        ::= { optixPWPingTrcRtTable 1 }

    OptixPWPingTrcRtEntry ::=
        SEQUENCE {
            optixPWPingTrcRtIndex
                Unsigned32,
            optixPWPingPeerIP
                IpAddress,
            optixPWPingPeerPwID
                Unsigned32,
            optixPWPingReqNum
                Unsigned32,
            optixPWPingExp
                Unsigned32,
            optixPWPingTTL
                Unsigned32,
            optixPWPingSendint
                Unsigned32,
            optixPWPingReplymode
                Unsigned32,
            optixPWPingPktlen
                Unsigned32,
            optixPWPingTimeOut
                Unsigned32,
            optixPWTrcRtExp
                Unsigned32,
            optixPWTrcRtTTL
                Unsigned32,
            optixPWTrcRtReplymode
                Unsigned32,
            optixPWTrcRtPktlen
                Unsigned32,
            optixPWTrcRtTimeOut
                Unsigned32,
            optixPWPingTrcRtStop
                INTEGER
        }

    -- 1.3.6.1.4.1.2011.2.25.4.50.4.1.18.1.1
    optixPWPingTrcRtIndex OBJECT-TYPE
        SYNTAX Unsigned32
        MAX-ACCESS not-accessible
        STATUS current
        DESCRIPTION
            "This object indicates the PW PING or PW TRACEOUTE index ranging from 1 to 0x00ffffff."
        ::= { optixPWPingTrcRtEntry 1 }

    -- 1.3.6.1.4.1.2011.2.25.4.50.4.1.18.1.2
    optixPWPingPeerIP OBJECT-TYPE
        SYNTAX IpAddress
        MAX-ACCESS read-write
        STATUS current
        DESCRIPTION
            "This object indicates the IP address of the peer end that initiates PW PING."
        ::= { optixPWPingTrcRtEntry 2 }

    -- 1.3.6.1.4.1.2011.2.25.4.50.4.1.18.1.3
    optixPWPingPeerPwID OBJECT-TYPE
        SYNTAX Unsigned32
        MAX-ACCESS read-write
        STATUS current
        DESCRIPTION
            "This object indicates the PW ID of the peer end that initiates PW PING."
        ::= { optixPWPingTrcRtEntry 3 }

    -- 1.3.6.1.4.1.2011.2.25.4.50.4.1.18.1.4
    optixPWPingReqNum OBJECT-TYPE
        SYNTAX Unsigned32
        MAX-ACCESS read-write
        STATUS current
        DESCRIPTION
            "This object indicates the number of Echo Request packets initiating PW PING. Valid values range from 0 to 0xffffffff. The default value is 3."
        DEFVAL{ 3 }
        ::= { optixPWPingTrcRtEntry 4 }

    -- 1.3.6.1.4.1.2011.2.25.4.50.4.1.18.1.5
    optixPWPingExp OBJECT-TYPE
        SYNTAX Unsigned32
        MAX-ACCESS read-write
        STATUS current
        DESCRIPTION
            "This object indicates the EXP value for the transmitted packets. Valid values range from 0 to 7. The default value is 7."
        DEFVAL{ 7 }
        ::= { optixPWPingTrcRtEntry 5 }

    -- 1.3.6.1.4.1.2011.2.25.4.50.4.1.18.1.6
    optixPWPingTTL OBJECT-TYPE
        SYNTAX Unsigned32
        MAX-ACCESS read-write
        STATUS current
        DESCRIPTION
            "This object indicates the TTL value for the transmitted packets (the value indicates the number of attempt hops). Valid values range from 1 to 255. The default value is 255."
        DEFVAL{ 255 }
        ::= { optixPWPingTrcRtEntry 6 }

    -- 1.3.6.1.4.1.2011.2.25.4.50.4.1.18.1.7
    optixPWPingSendint OBJECT-TYPE
        SYNTAX Unsigned32
        MAX-ACCESS read-write
        STATUS current
        DESCRIPTION
            "This object indicates the interval at which packets are transmitted. Valid values range from 10 to 1000 with the unit of 10 ms. The default value is 100 (that is 1s)."
        DEFVAL{ 100 }
        ::= { optixPWPingTrcRtEntry 7 }

    -- 1.3.6.1.4.1.2011.2.25.4.50.4.1.18.1.8
    optixPWPingReplymode OBJECT-TYPE
        SYNTAX Unsigned32
        MAX-ACCESS read-write
        STATUS current
        DESCRIPTION
            "This object indicates the Reply mode. The default value is 2. Valid values are as follows: 1:no response 2: IPv4 UDP response 4: application control channel"
        DEFVAL{ 2 }
        ::= { optixPWPingTrcRtEntry 8 }

    -- 1.3.6.1.4.1.2011.2.25.4.50.4.1.18.1.9
    optixPWPingPktlen OBJECT-TYPE
        SYNTAX Unsigned32
        MAX-ACCESS read-write
        STATUS current
        DESCRIPTION
            "This object indicates the length of a transmitted packet. The default value is 84. Valid values range from 84 to 1400."
        DEFVAL{ 84 }
        ::= { optixPWPingTrcRtEntry 9 }

    -- 1.3.6.1.4.1.2011.2.25.4.50.4.1.18.1.10
    optixPWPingTimeOut OBJECT-TYPE
        SYNTAX Unsigned32
        MAX-ACCESS read-write
        STATUS current
        DESCRIPTION
            "This object indicates the timeout period. Valid values range from 50 to 6000 with the unit of 10 ms. The default value is 300 (that is 3s)."
        DEFVAL{ 300 }
        ::= { optixPWPingTrcRtEntry 10 }

    -- 1.3.6.1.4.1.2011.2.25.4.50.4.1.18.1.11
    optixPWTrcRtExp OBJECT-TYPE
        SYNTAX Unsigned32
        MAX-ACCESS read-write
        STATUS current
        DESCRIPTION
            "This object indicates the EXP value for the transmitted packets. Valid values range from 0 to 7. The default value is 7."
        DEFVAL{ 7 }
        ::= { optixPWPingTrcRtEntry 11 }

    -- 1.3.6.1.4.1.2011.2.25.4.50.4.1.18.1.12
    optixPWTrcRtTTL OBJECT-TYPE
        SYNTAX Unsigned32
        MAX-ACCESS read-write
        STATUS current
        DESCRIPTION
            "This object indicates the TTL value for the transmitted packets (the value indicates the number of attempt hops). Valid values range from 1 to 255. The default value is 255."
        DEFVAL{ 255 }
        ::= { optixPWPingTrcRtEntry 12 }

    -- 1.3.6.1.4.1.2011.2.25.4.50.4.1.18.1.13
    optixPWTrcRtReplymode OBJECT-TYPE
        SYNTAX Unsigned32
        MAX-ACCESS read-write
        STATUS current
        DESCRIPTION
            "This object indicates the Reply mode. The default value is 2. Valid values are as follows: 1:no response 2: IPv4 UDP response 4: application control channel"
        DEFVAL{ 2 }
        ::= { optixPWPingTrcRtEntry 13 }

    -- 1.3.6.1.4.1.2011.2.25.4.50.4.1.18.1.14
    optixPWTrcRtPktlen OBJECT-TYPE
        SYNTAX Unsigned32
        MAX-ACCESS read-write
        STATUS current
        DESCRIPTION
            "This object indicates the length of a transmitted packet. The default value is 84. Valid values range from 84 to 1400."
        DEFVAL{ 84 }
        ::= { optixPWPingTrcRtEntry 14 }

    -- 1.3.6.1.4.1.2011.2.25.4.50.4.1.18.1.15
    optixPWTrcRtTimeOut OBJECT-TYPE
        SYNTAX Unsigned32
        MAX-ACCESS read-write
        STATUS current
        DESCRIPTION
            "This object indicates the timeout period. Valid values range from 50 to 6000 with the unit of 10 ms. The default value is 300 (that is 3s)."
        DEFVAL{ 300 }
        ::= { optixPWPingTrcRtEntry 15 }

    -- 1.3.6.1.4.1.2011.2.25.4.50.4.1.18.1.16
    optixPWPingTrcRtStop OBJECT-TYPE
        SYNTAX INTEGER
        {
            stop(0)
        }
        MAX-ACCESS read-write
        STATUS current
        DESCRIPTION
            "This object indicates to stop PW PING and PW TRACEROUTE."
        ::= { optixPWPingTrcRtEntry 16 }

    -- 1.3.6.1.4.1.2011.2.25.4.50.4.1.19
    optixMplsTpOamLbTestTable OBJECT-TYPE
        SYNTAX SEQUENCE OF OptixMplsTpOamLbTestEntry
        MAX-ACCESS not-accessible
        STATUS current
        DESCRIPTION
            "This table describes LB test configurations."
        ::= { optixMplsTpOamObject 19 }

    -- 1.3.6.1.4.1.2011.2.25.4.50.4.1.19.1
    optixMplsTpOamLbTestEntry OBJECT-TYPE
        SYNTAX OptixMplsTpOamLbTestEntry
        MAX-ACCESS not-accessible
        STATUS current
        DESCRIPTION
            "This entry describes LB test configurations."
        INDEX{ optixMplsTpOamLbTestMegType,optixMplsTpOamLbTestIndex }
        ::= { optixMplsTpOamLbTestTable 1 }

    OptixMplsTpOamLbTestEntry ::=
        SEQUENCE {
            optixMplsTpOamLbTestMegType
                INTEGER,
            optixMplsTpOamLbTestIndex
                Unsigned32,
            optixMplsTpOamLbTestTargetType
                INTEGER,
            optixMplsTpOamLbTestTargetID
                Unsigned32,
            optixMplsTpOamLbTestTTL
                Unsigned32,
            optixMplsTpOamLbTestPktNum
                Unsigned32,
            optixMplsTpOamLbTestPktLen
                Unsigned32,
            optixMplsTpOamLbTestSendInt
                Unsigned32,
            optixMplsTpOamLbTestPri
                Unsigned32,
            optixMplsTpOamLbTestStop
                INTEGER
        }

    -- 1.3.6.1.4.1.2011.2.25.4.50.4.1.19.1.1
    optixMplsTpOamLbTestMegType OBJECT-TYPE
        SYNTAX INTEGER
        {
            lsp(1),
            pw(2)
        }
        MAX-ACCESS not-accessible
        STATUS current
        DESCRIPTION
            "This object describes the type of the maintenance entity group."
        ::= { optixMplsTpOamLbTestEntry 1 }

    -- 1.3.6.1.4.1.2011.2.25.4.50.4.1.19.1.2
    optixMplsTpOamLbTestIndex OBJECT-TYPE
        SYNTAX Unsigned32
        MAX-ACCESS not-accessible
        STATUS current
        DESCRIPTION
            "This object describes the index of the tunnel OAM MEP."
        ::= { optixMplsTpOamLbTestEntry 2 }

    -- 1.3.6.1.4.1.2011.2.25.4.50.4.1.19.1.3
    optixMplsTpOamLbTestTargetType OBJECT-TYPE
        SYNTAX INTEGER
        {
            mep(1),
            mip(2)
        }
        MAX-ACCESS read-write
        STATUS current
        DESCRIPTION
            "This object indicates the target node type."
        ::= { optixMplsTpOamLbTestEntry 3 }

    -- 1.3.6.1.4.1.2011.2.25.4.50.4.1.19.1.4
    optixMplsTpOamLbTestTargetID OBJECT-TYPE
        SYNTAX Unsigned32
        MAX-ACCESS read-write
        STATUS current
        DESCRIPTION
            "This object indicates the target node ID."
        ::= { optixMplsTpOamLbTestEntry 4 }

    -- 1.3.6.1.4.1.2011.2.25.4.50.4.1.19.1.5
    optixMplsTpOamLbTestTTL OBJECT-TYPE
        SYNTAX Unsigned32
        MAX-ACCESS read-write
        STATUS current
        DESCRIPTION
            "This object indicates the time to live of LB test packets."
        ::= { optixMplsTpOamLbTestEntry 5 }

    -- 1.3.6.1.4.1.2011.2.25.4.50.4.1.19.1.6
    optixMplsTpOamLbTestPktNum OBJECT-TYPE
        SYNTAX Unsigned32
        MAX-ACCESS read-write
        STATUS current
        DESCRIPTION
            "This object indicates the number of LB test packets."
        ::= { optixMplsTpOamLbTestEntry 6 }

    -- 1.3.6.1.4.1.2011.2.25.4.50.4.1.19.1.7
    optixMplsTpOamLbTestPktLen OBJECT-TYPE
        SYNTAX Unsigned32
        MAX-ACCESS read-write
        STATUS current
        DESCRIPTION
            "This object indicates the length of LB test packets."
        ::= { optixMplsTpOamLbTestEntry 7 }

    -- 1.3.6.1.4.1.2011.2.25.4.50.4.1.19.1.8
    optixMplsTpOamLbTestSendInt OBJECT-TYPE
        SYNTAX Unsigned32
        MAX-ACCESS read-write
        STATUS current
        DESCRIPTION
            "This object indicates the interval at which LB test packets are transmitted."
        ::= { optixMplsTpOamLbTestEntry 8 }

    -- 1.3.6.1.4.1.2011.2.25.4.50.4.1.19.1.9
    optixMplsTpOamLbTestPri OBJECT-TYPE
        SYNTAX Unsigned32
        MAX-ACCESS read-write
        STATUS current
        DESCRIPTION
            "This object indicates the priority of LB test packets."
        ::= { optixMplsTpOamLbTestEntry 9 }

    -- 1.3.6.1.4.1.2011.2.25.4.50.4.1.19.1.10
    optixMplsTpOamLbTestStop OBJECT-TYPE
        SYNTAX INTEGER
        {
            stop(0)
        }
        MAX-ACCESS read-write
        STATUS current
        DESCRIPTION
            "This object indicates to stop the LB test."
        ::= { optixMplsTpOamLbTestEntry 10 }

    -- 1.3.6.1.4.1.2011.2.25.4.50.4.1.20
    optixLSPPingTrcRtTable OBJECT-TYPE
        SYNTAX SEQUENCE OF OptixLSPPingTrcRtEntry
        MAX-ACCESS not-accessible
        STATUS current
        DESCRIPTION
            "This table indicates LSP PING and LSP TRACEROUTE configurations including the LSP PING start/stop and LSP TRACEOUT start/stop."
        ::= { optixMplsTpOamObject 20 }

    -- 1.3.6.1.4.1.2011.2.25.4.50.4.1.20.1
    optixLSPPingTrcRtEntry OBJECT-TYPE
        SYNTAX OptixLSPPingTrcRtEntry
        MAX-ACCESS not-accessible
        STATUS current
        DESCRIPTION
            "This entry indicates the parameter table for the LSP PING and LSP TRACETOURE."
        INDEX{ optixLSPPingTrcRtIndex }
        ::= { optixLSPPingTrcRtTable 1 }

    OptixLSPPingTrcRtEntry ::=
        SEQUENCE {
            optixLSPPingTrcRtIndex
                Unsigned32,
            optixLSPPingReqNum
                Unsigned32,
            optixLSPPingExp
                Unsigned32,
            optixLSPPingTTL
                Unsigned32,
            optixLSPPingSendint
                Unsigned32,
            optixLSPPingReplymode
                Unsigned32,
            optixLSPPingPktlen
                Unsigned32,
            optixLSPingTimeOut
                Unsigned32,
            optixLSPTrcRtExp
                Unsigned32,
            optixLSPTrcRtTTL
                Unsigned32,
            optixLSPTrcRtReplymode
                Unsigned32,
            optixLSPTrcRtPktlen
                Unsigned32,
            optixLSTrcRtTimeOut
                Unsigned32,
            optixLSPPingTrcRtStop
                INTEGER
        }

    -- 1.3.6.1.4.1.2011.2.25.4.50.4.1.20.1.1
    optixLSPPingTrcRtIndex OBJECT-TYPE
        SYNTAX Unsigned32
        MAX-ACCESS not-accessible
        STATUS current
        DESCRIPTION
            "This object indicates the LSP index."
        ::= { optixLSPPingTrcRtEntry 1 }

    -- 1.3.6.1.4.1.2011.2.25.4.50.4.1.20.1.2
    optixLSPPingReqNum OBJECT-TYPE
        SYNTAX Unsigned32
        MAX-ACCESS read-write
        STATUS current
        DESCRIPTION
            "This object indicates the number of Echo Request packets for initiating LSP PING. Valid values range from 0 to 0xffffffff. The default value is 3."
        DEFVAL{ 3 }
        ::= { optixLSPPingTrcRtEntry 2 }

    -- 1.3.6.1.4.1.2011.2.25.4.50.4.1.20.1.3
    optixLSPPingExp OBJECT-TYPE
        SYNTAX Unsigned32
        MAX-ACCESS read-write
        STATUS current
        DESCRIPTION
            "This object indicates the EXP value for the transmitted packets. Valid values range from 0 to 7. The default value is 7."
        DEFVAL{ 7 }
        ::= { optixLSPPingTrcRtEntry 3 }

    -- 1.3.6.1.4.1.2011.2.25.4.50.4.1.20.1.4
    optixLSPPingTTL OBJECT-TYPE
        SYNTAX Unsigned32
        MAX-ACCESS read-write
        STATUS current
        DESCRIPTION
            "This object indicates the TTL value for the transmitted packets (the value indicates the number of attempt hops). Valid values range from 1 to 255. The default value is 255."
        DEFVAL{ 255 }
        ::= { optixLSPPingTrcRtEntry 4 }

    -- 1.3.6.1.4.1.2011.2.25.4.50.4.1.20.1.5
    optixLSPPingSendint OBJECT-TYPE
        SYNTAX Unsigned32
        MAX-ACCESS read-write
        STATUS current
        DESCRIPTION
            "This object indicates the interval at which packets are transmitted. Valid values range from 10 to 1000 with the unit of 10 ms. The default value is 100 (that is 1s)."
        DEFVAL{ 100 }
        ::= { optixLSPPingTrcRtEntry 5 }

    -- 1.3.6.1.4.1.2011.2.25.4.50.4.1.20.1.6
    optixLSPPingReplymode OBJECT-TYPE
        SYNTAX Unsigned32
        MAX-ACCESS read-write
        STATUS current
        DESCRIPTION
            "This object indicates the Reply mode. The default value is 2. Valid values are as follows: 1:no response 2: IPv4 UDP response 4: application control channel"
        DEFVAL{ 2 }
        ::= { optixLSPPingTrcRtEntry 6 }

    -- 1.3.6.1.4.1.2011.2.25.4.50.4.1.20.1.7
    optixLSPPingPktlen OBJECT-TYPE
        SYNTAX Unsigned32
        MAX-ACCESS read-write
        STATUS current
        DESCRIPTION
            "This object indicates the length of a transmitted packet. The default value is 64. Valid values range from 64 to 1400."
        DEFVAL{ 64 }
        ::= { optixLSPPingTrcRtEntry 7 }

    -- 1.3.6.1.4.1.2011.2.25.4.50.4.1.20.1.8
    optixLSPingTimeOut OBJECT-TYPE
        SYNTAX Unsigned32
        MAX-ACCESS read-write
        STATUS current
        DESCRIPTION
            "This object indicates the timeout period. Valid values range from 50 to 6000 with the unit of 10 ms. The default value is 300 (that is 3s)."
        DEFVAL{ 300 }
        ::= { optixLSPPingTrcRtEntry 8 }

    -- 1.3.6.1.4.1.2011.2.25.4.50.4.1.20.1.9
    optixLSPTrcRtExp OBJECT-TYPE
        SYNTAX Unsigned32
        MAX-ACCESS read-write
        STATUS current
        DESCRIPTION
            "This object indicates the EXP value for the transmitted packets. Valid values range from 0 to 7. The default value is 7."
        DEFVAL{ 7 }
        ::= { optixLSPPingTrcRtEntry 9 }

    -- 1.3.6.1.4.1.2011.2.25.4.50.4.1.20.1.10
    optixLSPTrcRtTTL OBJECT-TYPE
        SYNTAX Unsigned32
        MAX-ACCESS read-write
        STATUS current
        DESCRIPTION
            "This object indicates the TTL value for the transmitted packets (the value indicates the number of attempt hops). Valid values range from 1 to 255. The default value is 255."
        DEFVAL{ 255 }
        ::= { optixLSPPingTrcRtEntry 10 }

    -- 1.3.6.1.4.1.2011.2.25.4.50.4.1.20.1.11
    optixLSPTrcRtReplymode OBJECT-TYPE
        SYNTAX Unsigned32
        MAX-ACCESS read-write
        STATUS current
        DESCRIPTION
            "This object indicates the Reply mode. The default value is 2. Valid values are as follows: 1:no response 2: IPv4 UDP response 4: application control channel"
        DEFVAL{ 2 }
        ::= { optixLSPPingTrcRtEntry 11 }

    -- 1.3.6.1.4.1.2011.2.25.4.50.4.1.20.1.12
    optixLSPTrcRtPktlen OBJECT-TYPE
        SYNTAX Unsigned32
        MAX-ACCESS read-write
        STATUS current
        DESCRIPTION
            "This object indicates the length of a transmitted packet. The default value is 64. Valid values range from 64 to 1400."
        DEFVAL{ 64 }
        ::= { optixLSPPingTrcRtEntry 12 }

    -- 1.3.6.1.4.1.2011.2.25.4.50.4.1.20.1.13
    optixLSTrcRtTimeOut OBJECT-TYPE
        SYNTAX Unsigned32
        MAX-ACCESS read-write
        STATUS current
        DESCRIPTION
            "This object indicates the timeout period. Valid values range from 50 to 6000 with the unit of 10 ms. The default value is 300 (that is 3s)."
        DEFVAL{ 300 }
        ::= { optixLSPPingTrcRtEntry 13 }

    -- 1.3.6.1.4.1.2011.2.25.4.50.4.1.20.1.14
    optixLSPPingTrcRtStop OBJECT-TYPE
        SYNTAX INTEGER
        {
            stop(0)
        }
        MAX-ACCESS read-write
        STATUS current
        DESCRIPTION
            "This object indicates to stop PW PING and PW TRACEROUTE."
        ::= { optixLSPPingTrcRtEntry 14 }

    -- 1.3.6.1.4.1.2011.2.25.4.50.4.1.21
    optixMplsPingRecvSwitch OBJECT-TYPE
        SYNTAX INTEGER
        {
            close(0),
            open(1)
        }
        MAX-ACCESS read-write
        STATUS current
        DESCRIPTION
            "This object indicates the enable status of the MPLS ping receive function.0:close,1:open"
        ::= { optixMplsTpOamObject 21 }

    -- 1.3.6.1.4.1.2011.2.25.4.50.4.1.22
    optixLSPPingExtTrcRtTable OBJECT-TYPE
        SYNTAX SEQUENCE OF OptixLSPPingExtTrcRtEntry
        MAX-ACCESS not-accessible
        STATUS current
        DESCRIPTION
            "This table indicates LSP PING and LSP TRACEROUTE configurations including the LSP PING start/stop and LSP TRACEOUT start/stop."
        ::= { optixMplsTpOamObject 22 }

    -- 1.3.6.1.4.1.2011.2.25.4.50.4.1.22.1
    optixLSPPingExtTrcRtEntry OBJECT-TYPE
        SYNTAX OptixLSPPingExtTrcRtEntry
        MAX-ACCESS not-accessible
        STATUS current
        DESCRIPTION
            "This entry indicates the parameter table for the LSP PING and LSP TRACETOURE."
        INDEX{ optixLSPPingTrcRtIndex }
        ::= { optixLSPPingExtTrcRtTable 1 }

    OptixLSPPingExtTrcRtEntry ::=
        SEQUENCE {
            optixLSPPingExtTrcRtIndex
                Unsigned32,
            optixLSPPingExtReqNum
                Unsigned32,
            optixLSPPingExtExp
                Unsigned32,
            optixLSPPingExtTTL
                Unsigned32,
            optixLSPPingExtSendint
                Unsigned32,
            optixLSPPingExtReplymode
                Unsigned32,
            optixLSPPingExtPktlen
                Unsigned32,
            optixLSPPingExtTimeOut
                Unsigned32,
            optixLSPPingExtBitMode
                Unsigned32
        }

    -- 1.3.6.1.4.1.2011.2.25.4.50.4.1.22.1.1
    optixLSPPingExtTrcRtIndex OBJECT-TYPE
        SYNTAX Unsigned32
        MAX-ACCESS not-accessible
        STATUS current
        DESCRIPTION
            "This object indicates the LSP index."
        ::= { optixLSPPingExtTrcRtEntry 1 }

    -- 1.3.6.1.4.1.2011.2.25.4.50.4.1.22.1.2
    optixLSPPingExtReqNum OBJECT-TYPE
        SYNTAX Unsigned32
        MAX-ACCESS read-write
        STATUS current
        DESCRIPTION
            "This object indicates the number of Echo Request packets for initiating LSP PING. Valid values range from 0 to 0xffffffff. The default value is 3."
        ::= { optixLSPPingExtTrcRtEntry 2 }

    -- 1.3.6.1.4.1.2011.2.25.4.50.4.1.22.1.3
    optixLSPPingExtExp OBJECT-TYPE
        SYNTAX Unsigned32
        MAX-ACCESS read-write
        STATUS current
        DESCRIPTION
            "This object indicates the EXP value for the transmitted packets. Valid values range from 0 to 7. The default value is 7."
        ::= { optixLSPPingExtTrcRtEntry 3 }

    -- 1.3.6.1.4.1.2011.2.25.4.50.4.1.22.1.4
    optixLSPPingExtTTL OBJECT-TYPE
        SYNTAX Unsigned32
        MAX-ACCESS read-write
        STATUS current
        DESCRIPTION
            "This object indicates the TTL value of transmitted packets, which also indicates the number of retry hops. Valid values range from 1 to 255. The default value is 255."
        ::= { optixLSPPingExtTrcRtEntry 4 }

    -- 1.3.6.1.4.1.2011.2.25.4.50.4.1.22.1.5
    optixLSPPingExtSendint OBJECT-TYPE
        SYNTAX Unsigned32
        MAX-ACCESS read-write
        STATUS current
        DESCRIPTION
            "This object indicates the interval at which packets are transmitted. Valid values range from 10 to 1000 with the unit of 10 ms. The default value is 100 (that is 1s)."
        ::= { optixLSPPingExtTrcRtEntry 5 }

    -- 1.3.6.1.4.1.2011.2.25.4.50.4.1.22.1.6
    optixLSPPingExtReplymode OBJECT-TYPE
        SYNTAX Unsigned32
        MAX-ACCESS read-write
        STATUS current
        DESCRIPTION
            "This object indicates the Reply mode. The default value is 2. Valid values are as follows: 1:no response 2: IPv4 UDP response 4: application control channel"
        ::= { optixLSPPingExtTrcRtEntry 6 }

    -- 1.3.6.1.4.1.2011.2.25.4.50.4.1.22.1.7
    optixLSPPingExtPktlen OBJECT-TYPE
        SYNTAX Unsigned32
        MAX-ACCESS read-write
        STATUS current
        DESCRIPTION
            "This object indicates the length of a transmitted packet. The default value is 64. Valid values range from 64 to 1400."
        ::= { optixLSPPingExtTrcRtEntry 7 }

    -- 1.3.6.1.4.1.2011.2.25.4.50.4.1.22.1.8
    optixLSPPingExtTimeOut OBJECT-TYPE
        SYNTAX Unsigned32
        MAX-ACCESS read-write
        STATUS current
        DESCRIPTION
            "This object indicates the timeout period. Valid values range from 50 to 6000 with the unit of 10 ms. The default value is 300 (that is 3s)."
        ::= { optixLSPPingExtTrcRtEntry 8 }

    -- 1.3.6.1.4.1.2011.2.25.4.50.4.1.22.1.9
    optixLSPPingExtBitMode OBJECT-TYPE
        SYNTAX Unsigned32
        MAX-ACCESS read-write
        STATUS current
        DESCRIPTION
            "This object indicates the check mode. 0:not check bit mode,1:all 0 mode,2:all f mode."
        ::= { optixLSPPingExtTrcRtEntry 9 }

    -- 1.3.6.1.4.1.2011.2.25.4.50.4.1.23
    optixPWPingExtTrcRtTable OBJECT-TYPE
        SYNTAX SEQUENCE OF OptixPWPingExtTrcRtEntry
        MAX-ACCESS not-accessible
        STATUS current
        DESCRIPTION
            "This table manages the PW PING and PW TRACEOUTE configurations including the PW PING start/stop and PW TRACEOUTE start/stop."
        ::= { optixMplsTpOamObject 23 }

    -- 1.3.6.1.4.1.2011.2.25.4.50.4.1.23.1
    optixPWPingExtTrcRtEntry OBJECT-TYPE
        SYNTAX OptixPWPingExtTrcRtEntry
        MAX-ACCESS not-accessible
        STATUS current
        DESCRIPTION
            "This entry indicates the parameter table for the PW PING and PW TRACEROUTE."
        INDEX{ optixPWPingTrcRtIndex }
        ::= { optixPWPingExtTrcRtTable 1 }

    OptixPWPingExtTrcRtEntry ::=
        SEQUENCE {
            optixPWPingExtTrcRtIndex
                Unsigned32,
            optixPWPingExtPeerIP
                IpAddress,
            optixPWPingExtPeerPwID
                Unsigned32,
            optixPWPingExtReqNum
                Unsigned32,
            optixPWPingExtExp
                Unsigned32,
            optixPWPingExtTTL
                Unsigned32,
            optixPWPingExtSendint
                Unsigned32,
            optixPWPingExtReplymode
                Unsigned32,
            optixPWPingExtPktlen
                Unsigned32,
            optixPWPingExtTimeOut
                Unsigned32,
            optixPWPingExtBitMode
                Unsigned32
        }

    -- 1.3.6.1.4.1.2011.2.25.4.50.4.1.23.1.1
    optixPWPingExtTrcRtIndex OBJECT-TYPE
        SYNTAX Unsigned32
        MAX-ACCESS not-accessible
        STATUS current
        DESCRIPTION
            "This object indicates the PW PING or PW TRACEOUTE index ranging from 1 to 0x00ffffff."
        ::= { optixPWPingExtTrcRtEntry 1 }

    -- 1.3.6.1.4.1.2011.2.25.4.50.4.1.23.1.2
    optixPWPingExtPeerIP OBJECT-TYPE
        SYNTAX IpAddress
        MAX-ACCESS read-write
        STATUS current
        DESCRIPTION
            "This object indicates the PW ID of the peer end that initiates PW PING."
        ::= { optixPWPingExtTrcRtEntry 2 }

    -- 1.3.6.1.4.1.2011.2.25.4.50.4.1.23.1.3
    optixPWPingExtPeerPwID OBJECT-TYPE
        SYNTAX Unsigned32
        MAX-ACCESS read-write
        STATUS current
        DESCRIPTION
            "This object indicates the PW ID of the peer end that initiates PW PING."
        ::= { optixPWPingExtTrcRtEntry 3 }

    -- 1.3.6.1.4.1.2011.2.25.4.50.4.1.23.1.4
    optixPWPingExtReqNum OBJECT-TYPE
        SYNTAX Unsigned32
        MAX-ACCESS read-write
        STATUS current
        DESCRIPTION
            "This object indicates the number of Echo Request packets initiating PW PING. Valid values range from 0 to 0xffffffff. The default value is 3."
        ::= { optixPWPingExtTrcRtEntry 4 }

    -- 1.3.6.1.4.1.2011.2.25.4.50.4.1.23.1.5
    optixPWPingExtExp OBJECT-TYPE
        SYNTAX Unsigned32
        MAX-ACCESS read-write
        STATUS current
        DESCRIPTION
            "This object indicates the EXP value for the transmitted packets. Valid values range from 0 to 7. The default value is 7."
        ::= { optixPWPingExtTrcRtEntry 5 }

    -- 1.3.6.1.4.1.2011.2.25.4.50.4.1.23.1.6
    optixPWPingExtTTL OBJECT-TYPE
        SYNTAX Unsigned32
        MAX-ACCESS read-write
        STATUS current
        DESCRIPTION
            "This object indicates the TTL value for the transmitted packets (the value indicates the number of attempt hops). Valid values range from 1 to 255. The default value is 255."
        ::= { optixPWPingExtTrcRtEntry 6 }

    -- 1.3.6.1.4.1.2011.2.25.4.50.4.1.23.1.7
    optixPWPingExtSendint OBJECT-TYPE
        SYNTAX Unsigned32
        MAX-ACCESS read-write
        STATUS current
        DESCRIPTION
            "This object indicates the interval at which packets are transmitted. Valid values range from 10 to 1000 with the unit of 10 ms. The default value is 100 (that is 1s)."
        ::= { optixPWPingExtTrcRtEntry 7 }

    -- 1.3.6.1.4.1.2011.2.25.4.50.4.1.23.1.8
    optixPWPingExtReplymode OBJECT-TYPE
        SYNTAX Unsigned32
        MAX-ACCESS read-write
        STATUS current
        DESCRIPTION
            "This object indicates the Reply mode. The default value is 2. Valid values are as follows: 1:no response 2: IPv4 UDP response 4: application control channel."
        ::= { optixPWPingExtTrcRtEntry 8 }

    -- 1.3.6.1.4.1.2011.2.25.4.50.4.1.23.1.9
    optixPWPingExtPktlen OBJECT-TYPE
        SYNTAX Unsigned32
        MAX-ACCESS read-write
        STATUS current
        DESCRIPTION
            "This object indicates the length of a transmitted packet. The default value is 84. Valid values range from 84 to 1400."
        ::= { optixPWPingExtTrcRtEntry 9 }

    -- 1.3.6.1.4.1.2011.2.25.4.50.4.1.23.1.10
    optixPWPingExtTimeOut OBJECT-TYPE
        SYNTAX Unsigned32
        MAX-ACCESS read-write
        STATUS current
        DESCRIPTION
            "This object indicates the timeout period. Valid values range from 50 to 6000 with the unit of 10 ms. The default value is 300 (that is 3s)."
        ::= { optixPWPingExtTrcRtEntry 10 }

    -- 1.3.6.1.4.1.2011.2.25.4.50.4.1.23.1.11
    optixPWPingExtBitMode OBJECT-TYPE
        SYNTAX Unsigned32
        MAX-ACCESS read-write
        STATUS current
        DESCRIPTION
            "This object indicates the check mode, 0:not check bit mode,1:all 0 mode,2:all f mode."
        ::= { optixPWPingExtTrcRtEntry 11 }

    -- 1.3.6.1.4.1.2011.2.25.4.50.4.1.24
    optixMplsTpOamExtLbTestTable OBJECT-TYPE
        SYNTAX SEQUENCE OF OptixMplsTpOamExtLbTestEntry
        MAX-ACCESS not-accessible
        STATUS current
        DESCRIPTION
            "This table describes LB test configurations."
        ::= { optixMplsTpOamObject 24 }

    -- 1.3.6.1.4.1.2011.2.25.4.50.4.1.24.1
    optixMplsTpOamExtLbTestEntry OBJECT-TYPE
        SYNTAX OptixMplsTpOamExtLbTestEntry
        MAX-ACCESS not-accessible
        STATUS current
        DESCRIPTION
            "This entry describes LB test configurations."
        INDEX{ optixMplsTpOamLbTestIndex,optixMplsTpOamLbTestMegType }
        ::= { optixMplsTpOamExtLbTestTable 1 }

    OptixMplsTpOamExtLbTestEntry ::=
        SEQUENCE {
            optixMplsTpOamExtLbTestMegType
                INTEGER,
            optixMplsTpOamExtLbTestIndex
                Unsigned32,
            optixMplsTpOamExtLbTestTargetType
                INTEGER,
            optixMplsTpOamExtLbTestTargetID
                Unsigned32,
            optixMplsTpOamExtLbTestTTL
                Unsigned32,
            optixMplsTpOamExtLbTestPktNum
                Unsigned32,
            optixMplsTpOamExtLbTestPktLen
                Unsigned32,
            optixMplsTpOamExtLbTestSendInt
                Unsigned32,
            optixMplsTpOamExtLbTestPri
                Unsigned32,
            optixMplsTpOamExtLbTestBitMode
                Unsigned32
        }

    -- 1.3.6.1.4.1.2011.2.25.4.50.4.1.24.1.1
    optixMplsTpOamExtLbTestMegType OBJECT-TYPE
        SYNTAX INTEGER
        {
            lsp(1),
            pw(2)
        }
        MAX-ACCESS not-accessible
        STATUS current
        DESCRIPTION
            "This object describes the type of the maintenance entity group."
        ::= { optixMplsTpOamExtLbTestEntry 1 }

    -- 1.3.6.1.4.1.2011.2.25.4.50.4.1.24.1.2
    optixMplsTpOamExtLbTestIndex OBJECT-TYPE
        SYNTAX Unsigned32
        MAX-ACCESS not-accessible
        STATUS current
        DESCRIPTION
            "This object describes the index of the tunnel OAM MEP."
        ::= { optixMplsTpOamExtLbTestEntry 2 }

    -- 1.3.6.1.4.1.2011.2.25.4.50.4.1.24.1.3
    optixMplsTpOamExtLbTestTargetType OBJECT-TYPE
        SYNTAX INTEGER
        {
            mep(1),
            mip(2)
        }
        MAX-ACCESS read-write
        STATUS current
        DESCRIPTION
            "This object indicates the target node type."
        ::= { optixMplsTpOamExtLbTestEntry 3 }

    -- 1.3.6.1.4.1.2011.2.25.4.50.4.1.24.1.4
    optixMplsTpOamExtLbTestTargetID OBJECT-TYPE
        SYNTAX Unsigned32
        MAX-ACCESS read-write
        STATUS current
        DESCRIPTION
            "This object indicates the target node ID."
        ::= { optixMplsTpOamExtLbTestEntry 4 }

    -- 1.3.6.1.4.1.2011.2.25.4.50.4.1.24.1.5
    optixMplsTpOamExtLbTestTTL OBJECT-TYPE
        SYNTAX Unsigned32
        MAX-ACCESS read-write
        STATUS current
        DESCRIPTION
            "This object indicates the time to live of LB test packets."
        ::= { optixMplsTpOamExtLbTestEntry 5 }

    -- 1.3.6.1.4.1.2011.2.25.4.50.4.1.24.1.6
    optixMplsTpOamExtLbTestPktNum OBJECT-TYPE
        SYNTAX Unsigned32
        MAX-ACCESS read-write
        STATUS current
        DESCRIPTION
            "This object indicates the number of LB test packets."
        ::= { optixMplsTpOamExtLbTestEntry 6 }

    -- 1.3.6.1.4.1.2011.2.25.4.50.4.1.24.1.7
    optixMplsTpOamExtLbTestPktLen OBJECT-TYPE
        SYNTAX Unsigned32
        MAX-ACCESS read-write
        STATUS current
        DESCRIPTION
            "This object indicates the length of LB test packets."
        ::= { optixMplsTpOamExtLbTestEntry 7 }

    -- 1.3.6.1.4.1.2011.2.25.4.50.4.1.24.1.8
    optixMplsTpOamExtLbTestSendInt OBJECT-TYPE
        SYNTAX Unsigned32
        MAX-ACCESS read-write
        STATUS current
        DESCRIPTION
            "This object indicates the interval at which LB test packets are transmitted."
        ::= { optixMplsTpOamExtLbTestEntry 8 }

    -- 1.3.6.1.4.1.2011.2.25.4.50.4.1.24.1.9
    optixMplsTpOamExtLbTestPri OBJECT-TYPE
        SYNTAX Unsigned32
        MAX-ACCESS read-write
        STATUS current
        DESCRIPTION
            "This object indicates the priority of LB test packets."
        ::= { optixMplsTpOamExtLbTestEntry 9 }

    -- 1.3.6.1.4.1.2011.2.25.4.50.4.1.24.1.10
    optixMplsTpOamExtLbTestBitMode OBJECT-TYPE
        SYNTAX Unsigned32
        MAX-ACCESS read-write
        STATUS current
        DESCRIPTION
            "This object indicates the check mode,0:not check bit mode,1:all 0 mode,2:all f mode."
        ::= { optixMplsTpOamExtLbTestEntry 10 }

    -- 1.3.6.1.4.1.2011.2.25.4.50.4.2
    optixMplsTpOamTrap OBJECT IDENTIFIER ::= { optixMplsTpOamMod 2 }

    -- 1.3.6.1.4.1.2011.2.25.4.50.4.2.1
    optixLspTrapMember OBJECT IDENTIFIER ::= { optixMplsTpOamTrap 1 }

    -- 1.3.6.1.4.1.2011.2.25.4.50.4.2.1.1
    optixLspPingTrapTunnelIndex OBJECT-TYPE
        SYNTAX Unsigned32
        MAX-ACCESS accessible-for-notify
        STATUS current
        DESCRIPTION
            "This object indicates the index to the tunnel that initiates LSP ping."
        ::= { optixLspTrapMember 1 }

    -- 1.3.6.1.4.1.2011.2.25.4.50.4.2.1.2
    optixLspPingTrapLsrRspIp OBJECT-TYPE
        SYNTAX OCTET STRING
        MAX-ACCESS accessible-for-notify
        STATUS current
        DESCRIPTION
            "This object indicates the IP address of the response LSR."
        ::= { optixLspTrapMember 2 }

    -- 1.3.6.1.4.1.2011.2.25.4.50.4.2.1.3
    optixLspPingTrapSndPktLen OBJECT-TYPE
        SYNTAX Unsigned32
        MAX-ACCESS accessible-for-notify
        STATUS current
        DESCRIPTION
            "This object indicates the number of bytes in the sent packet."
        ::= { optixLspTrapMember 3 }

    -- 1.3.6.1.4.1.2011.2.25.4.50.4.2.1.4
    optixLspPingTrapChangeNum OBJECT-TYPE
        SYNTAX Unsigned32
        MAX-ACCESS accessible-for-notify
        STATUS current
        DESCRIPTION
            "This object indicates the total number of payload change packets."
        ::= { optixLspTrapMember 4 }

    -- 1.3.6.1.4.1.2011.2.25.4.50.4.2.1.5
    optixLspPingTrapDelay OBJECT-TYPE
        SYNTAX Unsigned32
        MAX-ACCESS accessible-for-notify
        STATUS current
        DESCRIPTION
            "This object indicates the response time of the event. Unit:us"
        ::= { optixLspTrapMember 5 }

    -- 1.3.6.1.4.1.2011.2.25.4.50.4.2.1.6
    optixLspPingTrapTTL OBJECT-TYPE
        SYNTAX Unsigned32
        MAX-ACCESS accessible-for-notify
        STATUS current
        DESCRIPTION
            "This object indicates the total length of sent packets."
        ::= { optixLspTrapMember 6 }

    -- 1.3.6.1.4.1.2011.2.25.4.50.4.2.1.7
    optixLspPingTrapRetCode OBJECT-TYPE
        SYNTAX INTEGER
        {
            noReturn(0),
            errorRequest(1),
            unknownTLV(2),
            egress(3),
            noMappingFEC(4),
            mapMismatch(5),
            unknownUpInterface(6),
            labelSwitch(8),
            labelSwitchNoMPLSForward(9),
            noLabelMapping(10),
            noLabelEntry(11),
            procUnloadInterface(12),
            endPingCmd(13),
            reserved(7)
        }
        MAX-ACCESS accessible-for-notify
        STATUS current
        DESCRIPTION
            "This object indicates the return code of the event."
        ::= { optixLspTrapMember 7 }

    -- 1.3.6.1.4.1.2011.2.25.4.50.4.2.1.8
    optixLspPingTrapSubCode OBJECT-TYPE
        SYNTAX Unsigned32
        MAX-ACCESS accessible-for-notify
        STATUS current
        DESCRIPTION
            "This object indicates the subcode of the return code."
        ::= { optixLspTrapMember 8 }

    -- 1.3.6.1.4.1.2011.2.25.4.50.4.2.1.9
    optixLspPingTrapSeqNum OBJECT-TYPE
        SYNTAX Unsigned32
        MAX-ACCESS accessible-for-notify
        STATUS current
        DESCRIPTION
            "This object indicates the sequence number."
        ::= { optixLspTrapMember 9 }

    -- 1.3.6.1.4.1.2011.2.25.4.50.4.2.1.10
    optixLspPingTrapTXNum OBJECT-TYPE
        SYNTAX Unsigned32
        MAX-ACCESS accessible-for-notify
        STATUS current
        DESCRIPTION
            "This object indicates the number of transmitted packets."
        ::= { optixLspTrapMember 10 }

    -- 1.3.6.1.4.1.2011.2.25.4.50.4.2.1.11
    optixLspPingTrapRXNum OBJECT-TYPE
        SYNTAX Unsigned32
        MAX-ACCESS accessible-for-notify
        STATUS current
        DESCRIPTION
            "This object indicates the number of received packets."
        ::= { optixLspTrapMember 11 }

    -- 1.3.6.1.4.1.2011.2.25.4.50.4.2.1.12
    optixLspPingTrapLossRate OBJECT-TYPE
        SYNTAX Unsigned32
        MAX-ACCESS accessible-for-notify
        STATUS current
        DESCRIPTION
            "This object indicates the packet loss rate."
        ::= { optixLspTrapMember 12 }

    -- 1.3.6.1.4.1.2011.2.25.4.50.4.2.1.13
    optixLspPingTrapMinDelay OBJECT-TYPE
        SYNTAX Unsigned32
        MAX-ACCESS accessible-for-notify
        STATUS current
        DESCRIPTION
            "This object indicates the minimum delay of LSP ping. Unit: us"
        ::= { optixLspTrapMember 13 }

    -- 1.3.6.1.4.1.2011.2.25.4.50.4.2.1.14
    optixLspPingTrapMaxDelay OBJECT-TYPE
        SYNTAX Unsigned32
        MAX-ACCESS accessible-for-notify
        STATUS current
        DESCRIPTION
            "This object indicates the maximum delay of LSP ping. Unit:us"
        ::= { optixLspTrapMember 14 }

    -- 1.3.6.1.4.1.2011.2.25.4.50.4.2.1.15
    optixLspPingTrapAverageDelay OBJECT-TYPE
        SYNTAX Unsigned32
        MAX-ACCESS accessible-for-notify
        STATUS current
        DESCRIPTION
            "This object indicates the average delay of LSP ping. Unit:us"
        ::= { optixLspTrapMember 15 }

    -- 1.3.6.1.4.1.2011.2.25.4.50.4.2.1.16
    optixLspTrcRtTrapTunnelIndex OBJECT-TYPE
        SYNTAX Unsigned32
        MAX-ACCESS accessible-for-notify
        STATUS current
        DESCRIPTION
            "This object indicates the index to the tunnel that initiates LSP TraceRoute."
        ::= { optixLspTrapMember 16 }

    -- 1.3.6.1.4.1.2011.2.25.4.50.4.2.1.17
    optixLspTrcRtTrapType OBJECT-TYPE
        SYNTAX INTEGER
        {
            ingress(1),
            transit(2),
            egress(3)
        }
        MAX-ACCESS accessible-for-notify
        STATUS current
        DESCRIPTION
            "This object indicates the type of the response node."
        ::= { optixLspTrapMember 17 }

    -- 1.3.6.1.4.1.2011.2.25.4.50.4.2.1.18
    optixLspTrcRtTrapDownStreamIp OBJECT-TYPE
        SYNTAX OCTET STRING
        MAX-ACCESS accessible-for-notify
        STATUS current
        DESCRIPTION
            "This object indicates the IP address of the downstream node."
        ::= { optixLspTrapMember 18 }

    -- 1.3.6.1.4.1.2011.2.25.4.50.4.2.1.19
    optixLspTrcRtTrapDownStreamLbl OBJECT-TYPE
        SYNTAX Unsigned32
        MAX-ACCESS accessible-for-notify
        STATUS current
        DESCRIPTION
            "This object indicates the label of the downstream node."
        ::= { optixLspTrapMember 19 }

    -- 1.3.6.1.4.1.2011.2.25.4.50.4.2.1.20
    optixLspLBTrapIndex OBJECT-TYPE
        SYNTAX Unsigned32
        MAX-ACCESS accessible-for-notify
        STATUS current
        DESCRIPTION
            "This object indicates the LSP index."
        ::= { optixLspTrapMember 20 }

    -- 1.3.6.1.4.1.2011.2.25.4.50.4.2.1.21
    optixLspPingTrapSrcIp OBJECT-TYPE
        SYNTAX OCTET STRING
        MAX-ACCESS accessible-for-notify
        STATUS current
        DESCRIPTION
            "This object indicates the source IP address."
        ::= { optixLspTrapMember 21 }

    -- 1.3.6.1.4.1.2011.2.25.4.50.4.2.1.22
    optixLspTrcRtTrapSrcIp OBJECT-TYPE
        SYNTAX OCTET STRING
        MAX-ACCESS accessible-for-notify
        STATUS current
        DESCRIPTION
            "This object indicates the source IP address."
        ::= { optixLspTrapMember 22 }

    -- 1.3.6.1.4.1.2011.2.25.4.50.4.2.1.23
    optixLspTrcRtTrapLsrRspIp OBJECT-TYPE
        SYNTAX OCTET STRING
        MAX-ACCESS accessible-for-notify
        STATUS current
        DESCRIPTION
            "This object indicates the source IP address."
        ::= { optixLspTrapMember 23 }

    -- 1.3.6.1.4.1.2011.2.25.4.50.4.2.1.24
    optixLspTrcRtTrapDelay OBJECT-TYPE
        SYNTAX Unsigned32
        MAX-ACCESS accessible-for-notify
        STATUS current
        DESCRIPTION
            "This object indicates the response time of the event. Unit:us"
        ::= { optixLspTrapMember 24 }

    -- 1.3.6.1.4.1.2011.2.25.4.50.4.2.1.25
    optixLspTrcRtTrapTTL OBJECT-TYPE
        SYNTAX Unsigned32
        MAX-ACCESS accessible-for-notify
        STATUS current
        DESCRIPTION
            "This object indicates the total length of sent packets."
        ::= { optixLspTrapMember 25 }

    -- 1.3.6.1.4.1.2011.2.25.4.50.4.2.1.26
    optixLspTrcRtTrapRetCode OBJECT-TYPE
        SYNTAX INTEGER
        {
            noReturn(0),
            errorRequest(1),
            unknownTLV(2),
            egress(3),
            noMappingFEC(4),
            mapMismatch(5),
            unknownUpInterface(6),
            labelSwitch(8),
            labelSwitchNoMPLSForward(9),
            noLabelMapping(10),
            noLabelEntry(11),
            procUnloadInterface(12),
            endPingCmd(13),
            reserved(7)
        }
        MAX-ACCESS accessible-for-notify
        STATUS current
        DESCRIPTION
            "This object indicates the return code of the event."
        ::= { optixLspTrapMember 26 }

    -- 1.3.6.1.4.1.2011.2.25.4.50.4.2.1.27
    optixLspPingTrapSaltusNum OBJECT-TYPE
        SYNTAX Unsigned32
        MAX-ACCESS accessible-for-notify
        STATUS current
        DESCRIPTION
            "This object indicates the saltus change bit."
        ::= { optixLspTrapMember 27 }

    -- 1.3.6.1.4.1.2011.2.25.4.50.4.2.1.28
    optixLspPingTrapSaltusBit OBJECT-TYPE
        SYNTAX Unsigned32
        MAX-ACCESS accessible-for-notify
        STATUS current
        DESCRIPTION
            "This object indicates the saltus change bit."
        ::= { optixLspTrapMember 28 }

    -- 1.3.6.1.4.1.2011.2.25.4.50.4.2.1.29
    optixLspPingTrapType OBJECT-TYPE
        SYNTAX INTEGER
        {
            all(0),
            lsp(1),
            pw(2),
            section(3),
            mspw(4),
            lspping(5),
            pwping(6)
        }
        MAX-ACCESS accessible-for-notify
        STATUS current
        DESCRIPTION
            "This object indicates the ping type."
        ::= { optixLspTrapMember 29 }

    -- 1.3.6.1.4.1.2011.2.25.4.50.4.2.2
    optixLspOamTrapEvent OBJECT IDENTIFIER ::= { optixMplsTpOamTrap 2 }

    -- 1.3.6.1.4.1.2011.2.25.4.50.4.2.2.1
    optixLspPingRspTrap NOTIFICATION-TYPE
        OBJECTS{ optixLspPingTrapTunnelIndex,optixLspPingTrapLsrRspIp,optixLspPingTrapSndPktLen,optixLspPingTrapSeqNum,optixLspPingTrapDelay,optixLspPingTrapTTL,optixLspPingTrapRetCode,optixLspPingTrapSubCode }
        STATUS current
        DESCRIPTION
            "This object indicates the LSP ping response event."
        ::= { optixLspOamTrapEvent 1 }

    -- 1.3.6.1.4.1.2011.2.25.4.50.4.2.2.2
    optixLspPingOvertimeTrap NOTIFICATION-TYPE
        OBJECTS{ optixLspPingTrapTunnelIndex,optixLspPingTrapSeqNum }
        STATUS current
        DESCRIPTION
            "This object indicates the LSP ping response timeout event."
        ::= { optixLspOamTrapEvent 2 }

    -- 1.3.6.1.4.1.2011.2.25.4.50.4.2.2.3
    optixLspPingStatisticTrap NOTIFICATION-TYPE
        OBJECTS{ optixLspPingTrapTunnelIndex,optixLspPingTrapTXNum,optixLspPingTrapRXNum,optixLspPingTrapLossRate,optixLspPingTrapMinDelay,optixLspPingTrapMaxDelay,optixLspPingTrapAverageDelay }
        STATUS current
        DESCRIPTION
            "This object indicates the LSP ping statistics result event."
        ::= { optixLspOamTrapEvent 3 }

    -- 1.3.6.1.4.1.2011.2.25.4.50.4.2.2.4
    optixLspTrcRtRspTrap NOTIFICATION-TYPE
        OBJECTS{ optixLspTrcRtTrapTunnelIndex,optixLspTrcRtTrapLsrRspIp,optixLspTrcRtTrapDelay,optixLspTrcRtTrapType,optixLspTrcRtTrapDownStreamIp,optixLspTrcRtTrapDownStreamLbl,optixLspTrcRtTrapTTL,optixLspTrcRtTrapRetCode }
        STATUS current
        DESCRIPTION
            "This object indicates the LSP traceroute response event."
        ::= { optixLspOamTrapEvent 4 }

    -- 1.3.6.1.4.1.2011.2.25.4.50.4.2.2.5
    optixLspTrcRtRspEndTrap NOTIFICATION-TYPE
        OBJECTS{ optixLspTrcRtTrapTunnelIndex }
        STATUS current
        DESCRIPTION
            "This object indicates the LSP traceroute end event."
        ::= { optixLspOamTrapEvent 5 }

    -- 1.3.6.1.4.1.2011.2.25.4.50.4.2.2.6
    optixLspTrcRtOvertimeTrap NOTIFICATION-TYPE
        OBJECTS{ optixLspTrcRtTrapTunnelIndex,optixLspTrcRtTrapTTL }
        STATUS current
        DESCRIPTION
            "This object indicates the LSP traceroute response timeout event."
        ::= { optixLspOamTrapEvent 6 }

    -- 1.3.6.1.4.1.2011.2.25.4.50.4.2.2.7
    optixLspLBRspTrap NOTIFICATION-TYPE
        OBJECTS{ optixLspLBTrapIndex }
        STATUS current
        DESCRIPTION
            "This object indicates the unidirectional tunnel LB response event."
        ::= { optixLspOamTrapEvent 7 }

    -- 1.3.6.1.4.1.2011.2.25.4.50.4.2.2.8
    optixLspPingNoRspTrap NOTIFICATION-TYPE
        OBJECTS{ optixLspPingTrapTunnelIndex,optixLspPingTrapTTL,optixLspPingTrapSrcIp }
        STATUS current
        DESCRIPTION
            "This object indicates the reporting of the LSP PING event in no-reply mode."
        ::= { optixLspOamTrapEvent 8 }

    -- 1.3.6.1.4.1.2011.2.25.4.50.4.2.2.9
    optixLspTrcRtNoRspTrap NOTIFICATION-TYPE
        OBJECTS{ optixLspTrcRtTrapTunnelIndex,optixLspTrcRtTrapTTL,optixLspTrcRtTrapSrcIp }
        STATUS current
        DESCRIPTION
            "This object indicates the reporting of the LSP TRACEROUTE event in no-reply mode."
        ::= { optixLspOamTrapEvent 9 }

    -- 1.3.6.1.4.1.2011.2.25.4.50.4.3
    optixMplsTpOamGroup OBJECT IDENTIFIER ::= { optixMplsTpOamMod 3 }

    -- 1.3.6.1.4.1.2011.2.25.4.50.4.3.1
    optixMplsPingRecvSwitchext OBJECT-TYPE
        SYNTAX INTEGER
        {
            close(0),
            open(1)
        }
        MAX-ACCESS read-write
        STATUS current
        DESCRIPTION
            "This object indicates the enable status of the MPLS ping receive function.0:close,1:open"
        ::= { optixMplsTpOamGroup 1 }

END
