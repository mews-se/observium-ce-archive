-- OPTIX-PKT-SYN-CLOCK-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-SYN-CLOCK-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        MacAddress,RowStatus
            FROM SNMPv2-TC
        ;

    optixPktSynClock MODULE-IDENTITY
        LAST-UPDATED "201307031406Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the configuration information of system clock"
        REVISION "201307031406Z"
        DESCRIPTION
            "201204200000Z"
        ::={ optixProvisionPtn 21 }

    -- 1.3.6.1.4.1.2011.2.25.4.50.21.1
    optixPktSynClockGroup OBJECT IDENTIFIER ::= { optixPktSynClock 1 }

    -- 1.3.6.1.4.1.2011.2.25.4.50.21.1.1
    optixPktPtpSysClockLockState OBJECT-TYPE
        SYNTAX INTEGER
        {
            unlock(0),
            lock(1)
        }
        MAX-ACCESS read-only
        STATUS current
        DESCRIPTION
            "This parameter describes the system clock lock state. 0: unlock, 1: lock"
        ::= { optixPktSynClockGroup 1 }

    -- 1.3.6.1.4.1.2011.2.25.4.50.21.1.2
    optixPktPtpSysTimeLockState OBJECT-TYPE
        SYNTAX INTEGER
        {
            unlock(0),
            lock(1)
        }
        MAX-ACCESS read-only
        STATUS current
        DESCRIPTION
            "This parameter describes the system time lock state. 0: unlock, 1: lock"
        ::= { optixPktSynClockGroup 2 }

END
