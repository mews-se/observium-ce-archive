-- OPTIX-RTN-GENNERAL-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-GENNERAL-MIB DEFINITIONS ::= BEGIN
    IMPORTS
        OBJECT-GROUP,MODULE-COMPLIANCE
            FROM SNMPv2-CONF
        Unsigned32,OBJECT-TYPE,MODULE-IDENTITY
            FROM SNMPv2-SMI
        optixProvisionRtn
            FROM OPTIX-OID-MIB
        TEXTUAL-CONVENTION
            FROM SNMPv2-TC
        ;

    optixRtnGeneral MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to query public information about RTN equipment in use, including the management for RTN license capacities."
        REVISION "201204160935Z"
        DESCRIPTION
            "The initial revision of this MIB module1."
        ::={ optixProvisionRtn 2 }

    OPTIXRtnLicenseLcsType ::= TEXTUAL-CONVENTION
        STATUS current
        DESCRIPTION
            "Indicates the license file type of RTN equipment."
        SYNTAX Unsigned32
        {
            am(1),
            hbrid(2),
            tdm(3),
            clock1588v2(4),
            atmAndIma(5),
            radioLag(6),
            e1Priority(7),
            synchronousEthernet(8),
            mpls(10),
            xpic(12),
            erps(13),
            pla(14),
            e1num(15),
            enqos(18),
            combo(19),
            fadmargin(22),
            wred(23),
            amac(24),
            l3vpn(25),
            highqos(26),
            l2dcn(27),
            extY1731(28),
            lldp(29),
            stm1(30),
            poe(31),
            is3model(32),
            fpm(33),
            qam2048(38),
            enhanceNj1(39),
            focusEth(40),
            ifDirection(41),
            qam2048for300(42),
            aes(43),
            qam4096(44),
            xpicForIsm6(45),
            ctrlForSdn(46),
            apForSdn(47),
            apCntForSdn(48),
            sdb(50),
            sdbfunLcs(51),
            bandwidthNotification(52),
            antiTheftLcs(54),	    
            airInterfaceCompression(9),
            gePort(11),
            highCapaMod(16),
            secondMwPort(20),
            mstpTpOam(21),
            mimo(53),
            lcs10ge(55),
            qam8192(56),
            am112m(57),
            am56m(58),
            lowdelay(59),
            switchingcap(60),
            buffer(61),
	    calcs(62),
	    ccic(63),
	    singleifcable(65),
	    xpiclshp(66),
	    ibt(67),
	    superlcs(68),
	    am80m(69)
        }

    OPTIXRtnLicenseLoadType ::= TEXTUAL-CONVENTION
        STATUS current
        DESCRIPTION
            "Indicates the license loading status.
The values:
0: not loaded
1: loaded"
        SYNTAX Unsigned32
        {
            unLoaded(0),
            loaded(1)
        }

    OPTIXRtnLicenseUnitType ::= TEXTUAL-CONVENTION
        STATUS current
        DESCRIPTION
            "Indicates the license capacity unit.
The values:
0: Mbps
1: E1
2: STM1
3: Dir
4: Port
5: board
255: Invalid"
        SYNTAX Unsigned32
        {
            invalid(255),
            mbps(0),
            e1(1),
            stm1(2),
            dir(3),
	    port(4),
	    board(5)
        }

    OPTIXRtnEnableStateType ::= TEXTUAL-CONVENTION
        STATUS current
        DESCRIPTION
            "Indicates the enable status.
The values:
0: disabled
1: enabled"
        SYNTAX INTEGER
        {
            disabled(0),
            enabled(1)
        }

    -- 1.3.6.1.4.1.2011.2.25.4.40.2.7
    optixRtnIndexTable OBJECT-TYPE
        SYNTAX SEQUENCE OF OptixRtnIndexEntry
        MAX-ACCESS not-accessible
        STATUS current
        DESCRIPTION
            "Used as the public index table for IF board attribute tables."
        ::= { optixRtnGeneral 7 }

    -- 1.3.6.1.4.1.2011.2.25.4.40.2.7.1
    optixRtnIndexEntry OBJECT-TYPE
        SYNTAX OptixRtnIndexEntry
        MAX-ACCESS not-accessible
        STATUS current
        DESCRIPTION
            "Indicates the index entry for IF ports."
        INDEX{ optixRtnIndex1,optixRtnIndex2,optixRtnIndex3,optixRtnIndex4 }
        ::= { optixRtnIndexTable 1 }

    OptixRtnIndexEntry ::=
        SEQUENCE {
            optixRtnIndex1
                Unsigned32,
            optixRtnIndex2
                Unsigned32,
            optixRtnIndex3
                Unsigned32,
            optixRtnIndex4
                Unsigned32
        }

    -- 1.3.6.1.4.1.2011.2.25.4.40.2.7.1.1
    optixRtnIndex1 OBJECT-TYPE
        SYNTAX Unsigned32
        MAX-ACCESS not-accessible
        STATUS current
        DESCRIPTION
            "Indicates the slot ID."
        ::= { optixRtnIndexEntry 1 }

    -- 1.3.6.1.4.1.2011.2.25.4.40.2.7.1.2
    optixRtnIndex2 OBJECT-TYPE
        SYNTAX Unsigned32
        MAX-ACCESS not-accessible
        STATUS current
        DESCRIPTION
            "Indicates the subboard ID."
        ::= { optixRtnIndexEntry 2 }

    -- 1.3.6.1.4.1.2011.2.25.4.40.2.7.1.3
    optixRtnIndex3 OBJECT-TYPE
        SYNTAX Unsigned32
        MAX-ACCESS not-accessible
        STATUS current
        DESCRIPTION
            "Indicates the port ID."
        ::= { optixRtnIndexEntry 3 }

    -- 1.3.6.1.4.1.2011.2.25.4.40.2.7.1.4
    optixRtnIndex4 OBJECT-TYPE
        SYNTAX Unsigned32
        MAX-ACCESS not-accessible
        STATUS current
        DESCRIPTION
            "Indicates the port ID."
        ::= { optixRtnIndexEntry 4 }

    -- 1.3.6.1.4.1.2011.2.25.4.40.2.8
    optixRtnIFPortlistTable OBJECT-TYPE
        SYNTAX SEQUENCE OF OptixRtnIFPortlistEntry
        MAX-ACCESS not-accessible
        STATUS current
        DESCRIPTION
            "Indicates the list."
        ::= { optixRtnGeneral 8 }

    -- 1.3.6.1.4.1.2011.2.25.4.40.2.8.1
    optixRtnIFPortlistEntry OBJECT-TYPE
        SYNTAX OptixRtnIFPortlistEntry
        MAX-ACCESS not-accessible
        STATUS current
        DESCRIPTION
            "Indicates the index entry for IF ports."
        INDEX{ optixRtnIFPortlist }
        ::= { optixRtnIFPortlistTable 1 }

    OptixRtnIFPortlistEntry ::=
        SEQUENCE {
            optixRtnIFPortlist
                Unsigned32
        }

    -- 1.3.6.1.4.1.2011.2.25.4.40.2.8.1.1
    optixRtnIFPortlist OBJECT-TYPE
        SYNTAX Unsigned32
        MAX-ACCESS not-accessible
        STATUS current
        DESCRIPTION
            "Indicates the slot ID."
        ::= { optixRtnIFPortlistEntry 1 }

    -- 1.3.6.1.4.1.2011.2.25.4.40.2.9
    optixRtnIFPrbsTable OBJECT-TYPE
        SYNTAX SEQUENCE OF OptixRtnIFPrbsEntry
        MAX-ACCESS not-accessible
        STATUS current
        DESCRIPTION
            "Used as the public index table for IF board attribute tables."
        ::= { optixRtnGeneral 9 }

    -- 1.3.6.1.4.1.2011.2.25.4.40.2.9.1
    optixRtnIFPrbsEntry OBJECT-TYPE
        SYNTAX OptixRtnIFPrbsEntry
        MAX-ACCESS not-accessible
        STATUS current
        DESCRIPTION
            "Indicates the index entry for IF ports."
        INDEX{ optixRtnIFPrbsType,optixRtnIFPrbsPathId,optixRtnIFPrbsDirection }
        ::= { optixRtnIFPrbsTable 1 }

    OptixRtnIFPrbsEntry ::=
        SEQUENCE {
            optixRtnIFPrbsType
                Unsigned32,
            optixRtnIFPrbsPathId
                Unsigned32,
            optixRtnIFPrbsDirection
                Unsigned32
        }

    -- 1.3.6.1.4.1.2011.2.25.4.40.2.9.1.1
    optixRtnIFPrbsType OBJECT-TYPE
        SYNTAX Unsigned32
        MAX-ACCESS not-accessible
        STATUS current
        DESCRIPTION
            "Indicates the Type."
        ::= { optixRtnIFPrbsEntry 1 }

    -- 1.3.6.1.4.1.2011.2.25.4.40.2.9.1.2
    optixRtnIFPrbsPathId OBJECT-TYPE
        SYNTAX Unsigned32
        MAX-ACCESS not-accessible
        STATUS current
        DESCRIPTION
            "Indicates the subboard ID."
        ::= { optixRtnIFPrbsEntry 2 }

    -- 1.3.6.1.4.1.2011.2.25.4.40.2.9.1.3
    optixRtnIFPrbsDirection OBJECT-TYPE
        SYNTAX Unsigned32
        MAX-ACCESS not-accessible
        STATUS current
        DESCRIPTION
            "Indicates the Direction."
        ::= { optixRtnIFPrbsEntry 3 }

    -- 1.3.6.1.4.1.2011.2.25.4.40.2.10
    optixRtnLicense OBJECT IDENTIFIER ::= { optixRtnGeneral 10 }

    -- 1.3.6.1.4.1.2011.2.25.4.40.2.10.10
    optixRtnLicenseTable OBJECT-TYPE
        SYNTAX SEQUENCE OF OptixRtnLicenseEntry
        MAX-ACCESS not-accessible
        STATUS current
        DESCRIPTION
            "Describes licenses for the OptiX RTN 900 series equipment."
        ::= { optixRtnLicense 10 }

    -- 1.3.6.1.4.1.2011.2.25.4.40.2.10.10.1
    optixRtnLicenseEntry OBJECT-TYPE
        SYNTAX OptixRtnLicenseEntry
        MAX-ACCESS not-accessible
        STATUS current
        DESCRIPTION
            "Indicates the license entry for the OptiX RTN 900 series equipment."
        INDEX{ optixRtnLicenseBoardID,optixRtnLicenseSubCardID,optixRtnLicensePortID,optixRtnLicenseLcsType }
        ::= { optixRtnLicenseTable 1 }

    OptixRtnLicenseEntry ::=
        SEQUENCE {
            optixRtnLicenseBoardID
                Unsigned32,
            optixRtnLicenseSubCardID
                Unsigned32,
            optixRtnLicensePortID
                Unsigned32,
            optixRtnLicenseLcsType
                OPTIXRtnLicenseLcsType,
            optixRtnLicenseLoadState
                OPTIXRtnLicenseLoadType,
            optixRtnLicenseCapacity
                Unsigned32,
            optixRtnLicenseUnit
                OPTIXRtnLicenseUnitType,
            optixRtnLicenseTDMCapacity
                Unsigned32,
            optixRtnLicenseTDMUnit
                OPTIXRtnLicenseUnitType
        }

    -- 1.3.6.1.4.1.2011.2.25.4.40.2.10.10.1.1
    optixRtnLicenseBoardID OBJECT-TYPE
        SYNTAX Unsigned32
        MAX-ACCESS not-accessible
        STATUS current
        DESCRIPTION
            "Indicates the slot ID.
The values:
OptiX RTN 910:
1: system control board
3 and 4: IF board
OptiX RTN 950:
7 and 8: system control board
1 to 6: IF board
OptiX RTN 950:
15 and 20: system control board
1 to 14: IF board
The value for an NE-level license is 0xffff."
        ::= { optixRtnLicenseEntry 1 }

    -- 1.3.6.1.4.1.2011.2.25.4.40.2.10.10.1.2
    optixRtnLicenseSubCardID OBJECT-TYPE
        SYNTAX Unsigned32
        MAX-ACCESS not-accessible
        STATUS current
        DESCRIPTION
            "Indicates the subboard ID. The node is reserved. The default value is 255."
        ::= { optixRtnLicenseEntry 2 }

    -- 1.3.6.1.4.1.2011.2.25.4.40.2.10.10.1.3
    optixRtnLicensePortID OBJECT-TYPE
        SYNTAX Unsigned32
        MAX-ACCESS not-accessible
        STATUS current
        DESCRIPTION
            "Indicates the port ID. The node is reserved. The default value is 65535."
        ::= { optixRtnLicenseEntry 3 }

    -- 1.3.6.1.4.1.2011.2.25.4.40.2.10.10.1.4
    optixRtnLicenseLcsType OBJECT-TYPE
        SYNTAX OPTIXRtnLicenseLcsType
        MAX-ACCESS not-accessible
        STATUS current
        DESCRIPTION
            "Indicates the license file type.
1: AM
2: HBRID
3: TDM
4: 1588v2
5: ATM/IMA
6: RADIO LAG
7: E1 Priority
8: Synchronous Ethernet
9: Air interface compression
10: MPLS
11: GE port
12: XPIC
13: ERPS
14: PLA
15: Number of E1 services
16: High capacity modification mode
18: WRED
19: Stacking
20: Second IF port
21: MPLS-TP OAM"
        ::= { optixRtnLicenseEntry 4 }

    -- 1.3.6.1.4.1.2011.2.25.4.40.2.10.10.1.5
    optixRtnLicenseLoadState OBJECT-TYPE
        SYNTAX OPTIXRtnLicenseLoadType
        MAX-ACCESS read-only
        STATUS current
        DESCRIPTION
            "Indicates the license loading status.
Values:
0: not loaded
1: loaded"
        ::= { optixRtnLicenseEntry 5 }

    -- 1.3.6.1.4.1.2011.2.25.4.40.2.10.10.1.6
    optixRtnLicenseCapacity OBJECT-TYPE
        SYNTAX Unsigned32
        MAX-ACCESS read-only
        STATUS current
        DESCRIPTION
            "Indicates the license capacity value. (The default capacity value is returned when the license is not loaded.)"
        ::= { optixRtnLicenseEntry 6 }

    -- 1.3.6.1.4.1.2011.2.25.4.40.2.10.10.1.7
    optixRtnLicenseUnit OBJECT-TYPE
        SYNTAX OPTIXRtnLicenseUnitType
        MAX-ACCESS read-only
        STATUS current
        DESCRIPTION
            "Indicates the license capacity unit.
The values:
0: Mbps
1: E1
2: STM1
3: Dir
4: Port
255: Invalid"
        ::= { optixRtnLicenseEntry 7 }

    -- 1.3.6.1.4.1.2011.2.25.4.40.2.10.10.1.8
    optixRtnLicenseTDMCapacity OBJECT-TYPE
        SYNTAX Unsigned32
        MAX-ACCESS read-only
        STATUS current
        DESCRIPTION
            "Indicates the used license capacity."
        ::= { optixRtnLicenseEntry 8 }

    -- 1.3.6.1.4.1.2011.2.25.4.40.2.10.10.1.9
    optixRtnLicenseTDMUnit OBJECT-TYPE
        SYNTAX OPTIXRtnLicenseUnitType
        MAX-ACCESS read-only
        STATUS current
        DESCRIPTION
            "Indicates the TDM capacity unit.
0: Mbps
1: E1
2: STM1
3: Board
4: Port
255: Invalid"
        ::= { optixRtnLicenseEntry 9 }

    -- 1.3.6.1.4.1.2011.2.25.4.40.2.10.11
    optixRtnGetLcsBoardCfginfoTable OBJECT-TYPE
    	SYNTAX SEQUENCE OF OptixRtnGetLcsBoardCfginfoEntry
        MAX-ACCESS not-accessible
        STATUS current
        DESCRIPTION
            "Describes the Lcs board configuration information table."
        ::= { optixRtnLicense 11 }  
         
     -- 1.3.6.1.4.1.2011.2.25.4.40.2.10.11.1       
     optixRtnGetLcsBoardCfginfoEntry  OBJECT-TYPE
        SYNTAX OptixRtnGetLcsBoardCfginfoEntry
        MAX-ACCESS not-accessible
        STATUS current
        DESCRIPTION
            "Describes the Lcs board configuration information table."  
        INDEX{optixRtnIndex1,optixRtnIndex2,optixRtnIndex3, optixRtnIndex4 }  
        ::= {optixRtnGetLcsBoardCfginfoTable 1 } 
                                      
     OptixRtnGetLcsBoardCfginfoEntry ::=
     	SEQUENCE {
     	    optixRtnLcsCfgInfoINum
                 Unsigned32,
            optixRtnLcsCfgInfoIType
                 Unsigned32, 
            optixRtnLcsCfgInfoIValue
                 Unsigned32
     	}  

     -- 1.3.6.1.4.1.2011.2.25.4.40.2.10.11.1.5
     optixRtnLcsCfgInfoINum OBJECT-TYPE 
     	SYNTAX Unsigned32
        MAX-ACCESS read-only
        STATUS current
        DESCRIPTION
            "Indicates the configuration type number."
        ::= { optixRtnGetLcsBoardCfginfoEntry 5 }  
        
     -- 1.3.6.1.4.1.2011.2.25.4.40.2.10.11.1.6
     optixRtnLcsCfgInfoIType OBJECT-TYPE 
     	SYNTAX Unsigned32
        MAX-ACCESS read-only
        STATUS current
        DESCRIPTION
            "Indicates the configuration type."
        ::= { optixRtnGetLcsBoardCfginfoEntry 6}
                
     -- 1.3.6.1.4.1.2011.2.25.4.40.2.10.11.1.7
     optixRtnLcsCfgInfoIValue OBJECT-TYPE 
     	SYNTAX Unsigned32
        MAX-ACCESS read-only
        STATUS current
        DESCRIPTION
            "Indicates configuration value."
        ::= { optixRtnGetLcsBoardCfginfoEntry 7}

     -- 1.3.6.1.4.1.2011.2.25.4.40.2.11
     optixRtnLicenseTypeMgr  OBJECT IDENTIFIER ::= { optixRtnGeneral 11 } 
     
     -- 1.3.6.1.4.1.2011.2.25.4.40.2.11.1		
     optixRtnLicenseType    OBJECT-TYPE
        SYNTAX    Unsigned32
        MAX-ACCESS read-only
        STATUS current
        DESCRIPTION
            "license type."
        ::= { optixRtnLicenseTypeMgr 1 }

    -- 1.3.6.1.4.1.2011.2.25.4.40.2.20
    optixRtnPhyLagPGIDTable OBJECT-TYPE
        SYNTAX SEQUENCE OF OptixRtnPhyLagPGIDEntry
        MAX-ACCESS not-accessible
        STATUS current
        DESCRIPTION
            "Used as the public index table for IF board attribute tables."
        ::= { optixRtnGeneral 20 }

    -- 1.3.6.1.4.1.2011.2.25.4.40.2.20.1
    optixRtnPhyLagPGIDEntry OBJECT-TYPE
        SYNTAX OptixRtnPhyLagPGIDEntry
        MAX-ACCESS not-accessible
        STATUS current
        DESCRIPTION
            "Indicates the index entry for IF ports."
        INDEX{ optixRtnPhyLagPGID,optixRtnCascadingPhyLagPGID }
        ::= { optixRtnPhyLagPGIDTable 1 }

    OptixRtnPhyLagPGIDEntry ::=
        SEQUENCE {
            optixRtnPhyLagPGID
                Unsigned32,
            optixRtnCascadingPhyLagPGID
                Unsigned32
        }

    -- 1.3.6.1.4.1.2011.2.25.4.40.2.20.1.1
    optixRtnPhyLagPGID OBJECT-TYPE
        SYNTAX Unsigned32
        MAX-ACCESS not-accessible
        STATUS current
        DESCRIPTION
            "Indicates the Type."
        ::= { optixRtnPhyLagPGIDEntry 1 }

    -- 1.3.6.1.4.1.2011.2.25.4.40.2.20.1.2
    optixRtnCascadingPhyLagPGID OBJECT-TYPE
        SYNTAX Unsigned32
        MAX-ACCESS not-accessible
        STATUS current
        DESCRIPTION
            "Indicates the subboard ID."
        ::= { optixRtnPhyLagPGIDEntry 2 }

    -- 1.3.6.1.4.1.2011.2.25.4.40.2.30
    optixRtnMimoIdexTable OBJECT-TYPE
        SYNTAX SEQUENCE OF OptixRtnMimoIdexEntry
        MAX-ACCESS not-accessible
        STATUS current
        DESCRIPTION
            "Used as the public index table for IF board attribute tables."
        ::= { optixRtnGeneral 30 }

    -- 1.3.6.1.4.1.2011.2.25.4.40.2.30.1
    optixRtnMimoIdexEntry OBJECT-TYPE
        SYNTAX OptixRtnMimoIdexEntry
        MAX-ACCESS not-accessible
        STATUS current
        DESCRIPTION
            "Indicates the index entry for IF ports."
        INDEX{ optixRtnMimoBid,optixRtnMimoSubid,optixRtnMimoPortid }
        ::= { optixRtnMimoIdexTable 1 }

    OptixRtnMimoIdexEntry ::=
        SEQUENCE {
            optixRtnMimoBid
                Unsigned32,
            optixRtnMimoSubid
                Unsigned32,
            optixRtnMimoPortid
                Unsigned32
        }

    -- 1.3.6.1.4.1.2011.2.25.4.40.2.30.1.1
    optixRtnMimoBid OBJECT-TYPE
        SYNTAX Unsigned32
        MAX-ACCESS not-accessible
        STATUS current
        DESCRIPTION
            "Indicates the Type."
        ::= { optixRtnMimoIdexEntry 1 }

    -- 1.3.6.1.4.1.2011.2.25.4.40.2.30.1.2
    optixRtnMimoSubid OBJECT-TYPE
        SYNTAX Unsigned32
        MAX-ACCESS not-accessible
        STATUS current
        DESCRIPTION
            "Indicates the subboard ID."
        ::= { optixRtnMimoIdexEntry 2 }

    -- 1.3.6.1.4.1.2011.2.25.4.40.2.30.1.3
    optixRtnMimoPortid OBJECT-TYPE
        SYNTAX Unsigned32
        MAX-ACCESS not-accessible
        STATUS current
        DESCRIPTION
            "Indicates the Direction."
        ::= { optixRtnMimoIdexEntry 3 }

    -- 1.3.6.1.4.1.2011.2.25.4.40.2.40
    optixRtnPhyLagIndexTable OBJECT-TYPE
        SYNTAX SEQUENCE OF OptixRtnPhyLagIndexEntry
        MAX-ACCESS not-accessible
        STATUS current
        DESCRIPTION
            "Used as the public index table for IF board attribute tables."
        ::= { optixRtnGeneral 40 }

    -- 1.3.6.1.4.1.2011.2.25.4.40.2.40.1
    optixRtnPhyLagIndexEntry OBJECT-TYPE
        SYNTAX OptixRtnPhyLagIndexEntry
        MAX-ACCESS not-accessible
        STATUS current
        DESCRIPTION
            "Indicates the index entry for IF ports."
        INDEX{ optixRtnPhyLagPGIDExt,optixRtnPhyLagSerParaPGID,optixRtnPhyLagSerParaPGType,optixRtnPhyLagMemStaPGId,optixRtnPhyLagSdbPGID,optixRtnPhyLagPGID }
        ::= { optixRtnPhyLagIndexTable 1 }

    OptixRtnPhyLagIndexEntry ::=
        SEQUENCE {
            optixRtnPhyLagPGIDExt
                Unsigned32,
            optixRtnPhyLagSerParaPGID
                Unsigned32,
            optixRtnPhyLagSerParaPGType
                Unsigned32,
            optixRtnPhyLagMemStaPGId
                Unsigned32,
            optixRtnPhyLagSdbPGID
                Unsigned32,
            optixRtnPhyLagPGId
                Unsigned32
        }

    -- 1.3.6.1.4.1.2011.2.25.4.40.2.40.1.1
    optixRtnPhyLagPGIDExt OBJECT-TYPE
        SYNTAX Unsigned32
        MAX-ACCESS not-accessible
        STATUS current
        DESCRIPTION
            "Indicates the Laggroup ext ID."
        ::= { optixRtnPhyLagIndexEntry 1 }

    -- 1.3.6.1.4.1.2011.2.25.4.40.2.40.1.2
    optixRtnPhyLagSerParaPGID OBJECT-TYPE
        SYNTAX Unsigned32
        MAX-ACCESS not-accessible
        STATUS current
        DESCRIPTION
            "Indicates the LagSerPara ID."
        ::= { optixRtnPhyLagIndexEntry 2 }

    -- 1.3.6.1.4.1.2011.2.25.4.40.2.40.1.3
    optixRtnPhyLagSerParaPGType OBJECT-TYPE
        SYNTAX Unsigned32
        MAX-ACCESS not-accessible
        STATUS current
        DESCRIPTION
            "Indicates the LagSerPara Type."
        ::= { optixRtnPhyLagIndexEntry 3 }

    -- 1.3.6.1.4.1.2011.2.25.4.40.2.40.1.4
    optixRtnPhyLagMemStaPGId OBJECT-TYPE
        SYNTAX Unsigned32
        MAX-ACCESS not-accessible
        STATUS current
        DESCRIPTION
            "Indicates the LagMemSta ID."
        ::= { optixRtnPhyLagIndexEntry 4 }

    -- 1.3.6.1.4.1.2011.2.25.4.40.2.40.1.5
    optixRtnPhyLagSdbPGID OBJECT-TYPE
        SYNTAX Unsigned32
        MAX-ACCESS not-accessible
        STATUS current
        DESCRIPTION
            "Indicates the LagSdb ID."
        ::= { optixRtnPhyLagIndexEntry 5 }

    -- 1.3.6.1.4.1.2011.2.25.4.40.2.40.1.6
    optixRtnPhyLagPGId OBJECT-TYPE
        SYNTAX Unsigned32
        MAX-ACCESS not-accessible
        STATUS current
        DESCRIPTION
            "Indicates the Laggroup ID."
        ::= { optixRtnPhyLagIndexEntry 6 }

    -- 1.3.6.1.4.1.2011.2.25.4.40.2.50
    optixRtnEplaIndexTable OBJECT-TYPE
        SYNTAX SEQUENCE OF OptixRtnEplaIndexEntry
        MAX-ACCESS not-accessible
        STATUS current
        DESCRIPTION
            "the EPLA Index tables."
        ::= { optixRtnGeneral 50 }

    -- 1.3.6.1.4.1.2011.2.25.4.40.2.50.1
    optixRtnEplaIndexEntry OBJECT-TYPE
        SYNTAX OptixRtnEplaIndexEntry
        MAX-ACCESS not-accessible
        STATUS current
        DESCRIPTION
            "Indicates the index entry for IF ports."
        INDEX{ optixRtngroupIndex,optixRtnboardIndex,optixRtnsubboardIndex,optixRtnportIndex }
        ::= { optixRtnEplaIndexTable 1 }

    OptixRtnEplaIndexEntry ::=
        SEQUENCE {
            optixRtngroupIndex
                Unsigned32,
            optixRtnboardIndex
                Unsigned32,
            optixRtnsubboardIndex
                Unsigned32,
            optixRtnportIndex
                Unsigned32
        }

    -- 1.3.6.1.4.1.2011.2.25.4.40.2.50.1.1
    optixRtngroupIndex OBJECT-TYPE
        SYNTAX Unsigned32
        MAX-ACCESS not-accessible
        STATUS current
        DESCRIPTION
            "Indicates the groupIndex."
        ::= { optixRtnEplaIndexEntry 1 }

    -- 1.3.6.1.4.1.2011.2.25.4.40.2.50.1.2
    optixRtnboardIndex OBJECT-TYPE
        SYNTAX Unsigned32
        MAX-ACCESS not-accessible
        STATUS current
        DESCRIPTION
            "Indicates the boardIndex."
        ::= { optixRtnEplaIndexEntry 2 }

    -- 1.3.6.1.4.1.2011.2.25.4.40.2.50.1.3
    optixRtnsubboardIndex OBJECT-TYPE
        SYNTAX Unsigned32
        MAX-ACCESS not-accessible
        STATUS current
        DESCRIPTION
            "Indicates the subboardIndex."
        ::= { optixRtnEplaIndexEntry 3 }

    -- 1.3.6.1.4.1.2011.2.25.4.40.2.50.1.4
    optixRtnportIndex OBJECT-TYPE
        SYNTAX Unsigned32
        MAX-ACCESS not-accessible
        STATUS current
        DESCRIPTION
            "Indicates the portIndex."
        ::= { optixRtnEplaIndexEntry 4 }

    -- 1.3.6.1.4.1.2011.2.25.4.40.2.60
    optixRtnIFPortAMIndexTable OBJECT-TYPE
        SYNTAX SEQUENCE OF OptixRtnIFPortAMIndexEntry
        MAX-ACCESS not-accessible
        STATUS current
        DESCRIPTION
            "Used as the public index table for IF port AM tables."
        ::= { optixRtnGeneral 60 }

    -- 1.3.6.1.4.1.2011.2.25.4.40.2.60.1
    optixRtnIFPortAMIndexEntry OBJECT-TYPE
        SYNTAX OptixRtnIFPortAMIndexEntry
        MAX-ACCESS not-accessible
        STATUS current
        DESCRIPTION
            "Indicates the index entry for IF ports."
        INDEX{ optixRtnIFPortAMBandWidth,optixRtnIFPortAMMode }
        ::= { optixRtnIFPortAMIndexTable 1 }

    OptixRtnIFPortAMIndexEntry ::=
        SEQUENCE {
            optixRtnIFPortAMBandWidth
                Unsigned32,
            optixRtnIFPortAMMode
                Unsigned32
        }

    -- 1.3.6.1.4.1.2011.2.25.4.40.2.60.1.1
    optixRtnIFPortAMBandWidth OBJECT-TYPE
        SYNTAX Unsigned32
        MAX-ACCESS not-accessible
        STATUS current
        DESCRIPTION
            "Indicates the AMBandWidth."
        ::= { optixRtnIFPortAMIndexEntry 1 }

    -- 1.3.6.1.4.1.2011.2.25.4.40.2.60.1.2
    optixRtnIFPortAMMode OBJECT-TYPE
        SYNTAX Unsigned32
        MAX-ACCESS not-accessible
        STATUS current
        DESCRIPTION
            "Indicates the port AMMode."
        ::= { optixRtnIFPortAMIndexEntry 2 }

END
