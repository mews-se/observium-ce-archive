-- OPTIX-RTN-CCIC-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-CCIC-MGR-MIB DEFINITIONS ::= BEGIN
    IMPORTS
        OBJECT-GROUP,MODULE-COMPLIANCE
            FROM SNMPv2-CONF
        Unsigned32,OBJECT-TYPE,MODULE-IDENTITY,Integer32
            FROM SNMPv2-SMI
        TEXTUAL-CONVENTION,RowStatus
            FROM SNMPv2-TC
        optixProvisionRtn
            FROM OPTIX-OID-MIB
        optixRtnBoardID,optixRtnSubCardID,optixRtnPortID,optixRtnIFPortAcmBandWidth,optixRtnIFPortAcmModulationMode
            FROM OPTIX-RTN-IFBOARD-ATTRIB-MIB
        ;

    optixRtnCcicParaMgr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query IF board related parameters required in radio link configuration and preventive maintenance, including the IF board modulation mode, bandwidth, AM management, and link identifier."
        REVISION "201204160935Z"
        DESCRIPTION
            "The initial revision of this MIB module1."
        ::={ optixProvisionRtn 11 }

    OPTIXRtnCcicModulateModeType ::= TEXTUAL-CONVENTION
        STATUS current
        DESCRIPTION
            "Describes the modulation mode supported by an IF board. Values: 1: QPSK 2: 16QAM 3: 32QAM 4: 64QAM 5: 128QAM 6: 256QAM 7: 512QAM 8: 1024QAM 9: QPSKSTRONG 10: 16QAMSTRONG 11: 512QAMLIGHT 12: 1024QAMLIGHT  13: 2048QAM -1: null"
        SYNTAX INTEGER
        {
            modeQPSK(1),
            mode16QAM(2),
            mode32QAM(3),
            mode64QAM(4),
            mode128QAM(5),
            mode256QAM(6),
            mode512QAM(7),
            mode1024QAM(8),
            modeQPSKSTRONG(9),
            mode16QAMSTRONG(10),
            mode512QAMLIGHT(11),
            mode1024QAMLIGHT(12),
            mode2048QAM(13),
            modeNULL(-1)
        }

    -- 1.3.6.1.4.1.2011.2.25.4.40.11.10
    optixRtnCcicGroup OBJECT IDENTIFIER ::= { optixRtnCcicParaMgr 10 }

    -- 1.3.6.1.4.1.2011.2.25.4.40.11.10.10
    optixRtnCcicGroupTable OBJECT-TYPE
        SYNTAX SEQUENCE OF OptixRtnCcicGroupEntry
        MAX-ACCESS not-accessible
        STATUS current
        DESCRIPTION
            "Indicates the CCIC work group"
        ::= { optixRtnCcicGroup 10 }

    -- 1.3.6.1.4.1.2011.2.25.4.40.11.10.10.1
    optixRtnCcicGroupEntry OBJECT-TYPE
        SYNTAX OptixRtnCcicGroupEntry
        MAX-ACCESS not-accessible
        STATUS current
        DESCRIPTION
            "Indicates the CCIC work group"
        INDEX{ optixRtnCcicGroupID }
        ::= { optixRtnCcicGroupTable 1 }

    OptixRtnCcicGroupEntry ::=
        SEQUENCE {
            optixRtnCcicGroupID
                Unsigned32,
            optixRtnCcicGroupType
                Unsigned32,
            optixRtnCcicMemberInfo
                OCTET STRING,
            optixRtnCcicDelGroup
                Unsigned32
        }

    -- 1.3.6.1.4.1.2011.2.25.4.40.11.10.10.1.1
    optixRtnCcicGroupID OBJECT-TYPE
        SYNTAX Unsigned32
        MAX-ACCESS not-accessible
        STATUS current
        DESCRIPTION
            "Indicates the CCIC work group ID."
        ::= { optixRtnCcicGroupEntry 1 }

    -- 1.3.6.1.4.1.2011.2.25.4.40.11.10.10.1.2
    optixRtnCcicGroupType OBJECT-TYPE
        SYNTAX Unsigned32
        {
            hubinner(0),
            hubcascade(1),
            tail(2)
        }
        MAX-ACCESS read-create
        STATUS current
        DESCRIPTION
            "Indicates the CCIC work group type"
        ::= { optixRtnCcicGroupEntry 2 }

    -- 1.3.6.1.4.1.2011.2.25.4.40.11.10.10.1.3
    optixRtnCcicMemberInfo OBJECT-TYPE
        SYNTAX OCTET STRING
        MAX-ACCESS read-create
        STATUS current
        DESCRIPTION
            "Indicates the Ccic MemberPara."
        ::= { optixRtnCcicGroupEntry 3 }

    -- 1.3.6.1.4.1.2011.2.25.4.40.11.10.10.1.4
    optixRtnCcicDelGroup OBJECT-TYPE
        SYNTAX Unsigned32
        {
            false(0),
            true(1)
        }
        MAX-ACCESS read-create
        STATUS current
        DESCRIPTION
            "Indicates whether to delete configurations of the adjacent NE.
	    0: false
	    1: true"
        ::= { optixRtnCcicGroupEntry 4 }

    -- 1.3.6.1.4.1.2011.2.25.4.40.11.10.20
    optixRtnCcicParaTable OBJECT-TYPE
        SYNTAX SEQUENCE OF OptixRtnCcicParaEntry
        MAX-ACCESS not-accessible
        STATUS current
        DESCRIPTION
            "Indicates the CCIC work group"
        ::= { optixRtnCcicGroup 20 }

    -- 1.3.6.1.4.1.2011.2.25.4.40.11.10.20.1
    optixRtnCcicParaEntry OBJECT-TYPE
        SYNTAX OptixRtnCcicParaEntry
        MAX-ACCESS not-accessible
        STATUS current
        DESCRIPTION
            "Indicates the CCIC work group"
        INDEX{ optixRtnCcicGroupID }
        ::= { optixRtnCcicParaTable 1 }

    OptixRtnCcicParaEntry ::=
        SEQUENCE {
            optixRtnCcicGroupID
                Unsigned32,
            optixRtnCcicBandWidth
                Unsigned32,
            optixRtnCcicAmEnableStatus
                Unsigned32,
            optixRtnCcicAmBottomMode
                OPTIXRtnCcicModulateModeType,
            optixRtnCcicAmPeakMode
                OPTIXRtnCcicModulateModeType,
            optixRtnCcicAmManualMode
                OPTIXRtnCcicModulateModeType,
            optixRtnCcicOduMaxTxpower
                Integer32,
            optixRtnCcicATPCAutoThEnable
                Unsigned32,
            optixRtnCcicATPCEnable
                Unsigned32,
            optixRtnCcicATPCStep
                Unsigned32,
            optixRtnCcicATPCHighThreshold
                Integer32,
            optixRtnCcicATPCLowThreshold
                Integer32,
            optixRtnCcicOduTRSpacing
                Unsigned32,
            optixRtnCcicOduTxFreq
                Unsigned32,
            optixRtnCcicOduTxPower
                Integer32,
            optixRtnCcicOduWorkState
                Unsigned32
        }

    -- 1.3.6.1.4.1.2011.2.25.4.40.11.10.20.1.2
    optixRtnCcicBandWidth OBJECT-TYPE
        SYNTAX Unsigned32
        {
            bw3p5M(1),
            bw7M(2),
            bw14M(3),
            bw28M(4),
            bw40M(5),
            bw56M(6),
            bw112M(23)
        }
        MAX-ACCESS read-write
        STATUS current
        DESCRIPTION
            "Indicates the channel bandwidth."
        ::= { optixRtnCcicParaEntry 2 }

    -- 1.3.6.1.4.1.2011.2.25.4.40.11.10.20.1.3
    optixRtnCcicAmEnableStatus OBJECT-TYPE
        SYNTAX Unsigned32
        {
            disabled(0),
            enabled(1)
        }
        MAX-ACCESS read-write
        STATUS current
        DESCRIPTION
            "Indicates the reverse switching status. Values: 0: disabled 1: enabled."
        ::= { optixRtnCcicParaEntry 3 }

    -- 1.3.6.1.4.1.2011.2.25.4.40.11.10.20.1.4
    optixRtnCcicAmBottomMode OBJECT-TYPE
        SYNTAX OPTIXRtnCcicModulateModeType
        MAX-ACCESS read-write
        STATUS current
        DESCRIPTION
            "Indicates the guaranteed-capacity mode."
        ::= { optixRtnCcicParaEntry 4 }

    -- 1.3.6.1.4.1.2011.2.25.4.40.11.10.20.1.5
    optixRtnCcicAmPeakMode OBJECT-TYPE
        SYNTAX OPTIXRtnCcicModulateModeType
        MAX-ACCESS read-write
        STATUS current
        DESCRIPTION
            "Indicates the full-capacity mode."
        ::= { optixRtnCcicParaEntry 5 }
		
    -- 1.3.6.1.4.1.2011.2.25.4.40.11.10.20.1.6
    optixRtnCcicAmManualMode OBJECT-TYPE
        SYNTAX OPTIXRtnCcicModulateModeType
        MAX-ACCESS read-write
        STATUS current
        DESCRIPTION
            "Indicate the manually-specified-capacity mode."
        ::= { optixRtnCcicParaEntry 6 }

    -- 1.3.6.1.4.1.2011.2.25.4.40.11.10.20.1.7
    optixRtnCcicOduMaxTxpower OBJECT-TYPE
        SYNTAX Integer32
        MAX-ACCESS read-write
        STATUS current
        DESCRIPTION
            "Indicates the maximum transmit power of an ODU board in an CCIC protection group. When the AM function is disabled, the maximum transmit power in the current mode is returned. When the AM function is enabled, the maximum transmit power in the guaranteed capability modulation mode is returned."
        ::= { optixRtnCcicParaEntry 7 }

    -- 1.3.6.1.4.1.2011.2.25.4.40.11.10.20.1.8
    optixRtnCcicATPCAutoThEnable OBJECT-TYPE
        SYNTAX Unsigned32
        {
            disabled(0),
            enabled(1)
        }
        MAX-ACCESS read-write
        STATUS current
        DESCRIPTION
            "Indicates the enable status of the ATPC automatic threshold configuration function in an CCIC protection group. The ATPC function enables the transmit power of a transmitter to automatically trace the change of the RSL at the receive end within the ATPC control range. The equipment automatically uses the preset ATPC upper and lower thresholds based on the working mode of the IF board. When the function is disabled, the manually set ATPC upper and lower thresholds are used. Values: 0: disabled 1: enabled."
        ::= { optixRtnCcicParaEntry 8 }

    -- 1.3.6.1.4.1.2011.2.25.4.40.11.10.20.1.9
    optixRtnCcicATPCEnable OBJECT-TYPE
        SYNTAX Unsigned32
        {
            disabled(0),
            enabled(1)
        }
        MAX-ACCESS read-write
        STATUS current
        DESCRIPTION
            "Indicates the enable status of the ATPC function in an CCIC protection group. Values: 0: disabled 1: enabled."
        ::= { optixRtnCcicParaEntry 9 }
		
    -- 1.3.6.1.4.1.2011.2.25.4.40.11.10.20.1.10
    optixRtnCcicATPCStep OBJECT-TYPE
        SYNTAX Unsigned32
        MAX-ACCESS read-write
        STATUS current
        DESCRIPTION
            "Indicates the ATPC adjustment step in an CCIC protection group. The parameter refers to every increase or decrease in the ODU transmit power. Value range: 10 to 50"
        ::= { optixRtnCcicParaEntry 10 }

    -- 1.3.6.1.4.1.2011.2.25.4.40.11.10.20.1.11
    optixRtnCcicATPCHighThreshold OBJECT-TYPE
        SYNTAX Integer32
        MAX-ACCESS read-write
        STATUS current
        DESCRIPTION
            "Indicates the ATPC adjustment upper threshold in an CCIC protection group. When the receive signal level (RSL) is higher than the threshold, the transmitter automatically adjusts its transmit power. Signed type Value range: -850 to -200 Unit: 0.1 dBm."
        ::= { optixRtnCcicParaEntry 11 }

    -- 1.3.6.1.4.1.2011.2.25.4.40.11.10.20.1.12
    optixRtnCcicATPCLowThreshold OBJECT-TYPE
        SYNTAX Integer32
        MAX-ACCESS read-write
        STATUS current
        DESCRIPTION
            "Indicates the ATPC adjustment lower threshold in an CCIC protection group. When the receive signal level (RSL) is lower than the threshold, the transmitter automatically adjusts its transmit power. Signed type Value range: -900 to -250 Unit: 0.1 dBm."
        ::= { optixRtnCcicParaEntry 12 }
		
    -- 1.3.6.1.4.1.2011.2.25.4.40.11.10.20.1.13
    optixRtnCcicOduTRSpacing OBJECT-TYPE
        SYNTAX Unsigned32
        MAX-ACCESS read-write
        STATUS current
        DESCRIPTION
            "Indicates the T/R spacing of an ODU board in an CCIC protection group to avoid interference. Unit: kHz."
        ::= { optixRtnCcicParaEntry 13 }

    -- 1.3.6.1.4.1.2011.2.25.4.40.11.10.20.1.14
    optixRtnCcicOduTxFreq OBJECT-TYPE
        SYNTAX Unsigned32
        MAX-ACCESS read-write
        STATUS current
        DESCRIPTION
            "Indicates the transmission frequency of an ODU board in an CCIC protection group. When frequencies of the transmitter/receiver at both ends match, signals can be received and transmitted successfully. Unit: kHz."
        ::= { optixRtnCcicParaEntry 14 }

    -- 1.3.6.1.4.1.2011.2.25.4.40.11.10.20.1.15
    optixRtnCcicOduTxPower OBJECT-TYPE
        SYNTAX Integer32
        MAX-ACCESS read-write
        STATUS current
        DESCRIPTION
            "Indicates the transmit power of an ODU board in an CCIC protection group. Signed type Unit: 0.1 dBm Value range: 100 to 350."
        ::= { optixRtnCcicParaEntry 15 }

    -- 1.3.6.1.4.1.2011.2.25.4.40.11.10.20.1.16
    optixRtnCcicOduWorkState OBJECT-TYPE
        SYNTAX Unsigned32
        {
            muted(0),
            unmuted(1)
        }
        MAX-ACCESS read-write
        STATUS current
        DESCRIPTION
            "Indicates the transmission status of the corresponding RF transmitter for an CCIC protection group. Values: 0: muted 1: unmuted."
        ::= { optixRtnCcicParaEntry 16 }

    -- 1.3.6.1.4.1.2011.2.25.4.40.11.10.30
    optixRtnIFPortAllModeCcicCapacityTable OBJECT-TYPE
        SYNTAX SEQUENCE OF OptixRtnIFPortAllModeCcicCapacityEntry
        MAX-ACCESS not-accessible
        STATUS current
        DESCRIPTION
            "Describes the service capacity supported by an IF board in each mode when the CCIC function is enabled."
        ::= { optixRtnCcicGroup 30 }

    -- 1.3.6.1.4.1.2011.2.25.4.40.11.10.30.1
    optixRtnIFPortAllModeCcicCapacityEntry OBJECT-TYPE
        SYNTAX OptixRtnIFPortAllModeCcicCapacityEntry
        MAX-ACCESS not-accessible
        STATUS current
        DESCRIPTION
            "Indicates the query entry for service capacities of an IF port in each mode when the CCIC function is enabled."
        INDEX{ optixRtnBoardID,optixRtnSubCardID,optixRtnPortID,optixRtnIFPortAcmBandWidth,optixRtnIFPortAcmModulationMode }
        ::= { optixRtnIFPortAllModeCcicCapacityTable 1 }

    OptixRtnIFPortAllModeCcicCapacityEntry ::=
        SEQUENCE {
            optixRtnIFPortAmCapacityForCcic
                Unsigned32,
            optixRtnIFPortAmMaxE1NumForCcic
                Unsigned32
        }

    -- 1.3.6.1.4.1.2011.2.25.4.40.11.10.30.1.6
    optixRtnIFPortAmCapacityForCcic OBJECT-TYPE
        SYNTAX Unsigned32
        MAX-ACCESS read-only
        STATUS current
        DESCRIPTION
            "Indicates the service capacity supported by a mode when the CCIC function is enabled. Unit: M"
        ::= { optixRtnIFPortAllModeCcicCapacityEntry 6 }

    -- 1.3.6.1.4.1.2011.2.25.4.40.11.10.30.1.7
    optixRtnIFPortAmMaxE1NumForCcic OBJECT-TYPE
        SYNTAX Unsigned32
        MAX-ACCESS read-only
        STATUS current
        DESCRIPTION
            "Indicates the maximum number of E1s supported by a mode when the CCIC function is enabled."
        ::= { optixRtnIFPortAllModeCcicCapacityEntry 7 }

END
