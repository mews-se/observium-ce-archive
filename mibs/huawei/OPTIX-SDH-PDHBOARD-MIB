-- OPTIX-SDH-PDHBOARD-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-PDHBOARD-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY,NOTIFICATION-TYPE
            FROM SNMPv2-SMI
        optixLogBoardId
            FROM OPTIX-BOARD-MANAGE-MIB
        optixPortId
            FROM OPTIX-PORT-MANAGE-MIB
        DateAndTime
            FROM SNMPv2-TC
        ;

    optixPdhBoard MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations of tributary board management."
        REVISION "201204200000Z"
        DESCRIPTION
            "The initial revision of this MIB module1."
        ::={ optixProvisionSdh 44 }

    -- 1.3.6.1.4.1.2011.2.25.4.10.44.1
    optixPdhBoardGroup OBJECT IDENTIFIER ::= { optixPdhBoard 1 }

    -- 1.3.6.1.4.1.2011.2.25.4.10.44.1.1
    optixPdhBoardTable OBJECT-TYPE
        SYNTAX SEQUENCE OF OptixPdhBoardEntry
        MAX-ACCESS not-accessible
        STATUS current
        DESCRIPTION
            "This table describes configurations of SDH tributary board management."
        ::= { optixPdhBoardGroup 1 }

    -- 1.3.6.1.4.1.2011.2.25.4.10.44.1.1.1
    optixPdhBoardEntry OBJECT-TYPE
        SYNTAX OptixPdhBoardEntry
        MAX-ACCESS not-accessible
        STATUS current
        DESCRIPTION
            "Thisentry describes configurations of SDH tributary board management."
        INDEX{ optixLogBoardId,optixPortId }
        ::= { optixPdhBoardTable 1 }

    OptixPdhBoardEntry ::=
        SEQUENCE {
            optixPdhBoardSRJ2Mode
                Unsigned32,
            optixPdhBoardSRJ2Value
                OCTET STRING,
            optixPdhBoardRJ2Mode
                Unsigned32,
            optixPdhBoardRJ2Value
                OCTET STRING,
            optixPdhBoardSRV5Value
                Unsigned32,
            optixPdhBoardSTV5Value
                Unsigned32,
            optixPdhBoardRV5Value
                Unsigned32,
            optixPdhBoardUsedFlag
                INTEGER,
            optixPdhBoardRetimingClk
                INTEGER,
            optixPdhBoardSignalInBalance
                INTEGER,
            optixPdhBoardSignalOutBalance
                INTEGER,
            optixPdhBoardPayLoadType
                INTEGER,
            optixPdhBoardE1Frame
                INTEGER,
            optixPdhBoardSTJ2Mode
                Unsigned32,
            optixPdhBoardSTJ2Value
                OCTET STRING,
            optixPdhBoardPathE1eq
                INTEGER,
            optixPdhBoardDefaultBus
                INTEGER,
            optixPdhBoardWorkBus
                INTEGER,
            optixPdhBoardCodeType
                INTEGER,
            optixPdhBdPayloadTypeNew
                INTEGER
        }

    -- 1.3.6.1.4.1.2011.2.25.4.10.44.1.1.1.1
    optixPdhBoardSRJ2Mode OBJECT-TYPE
        SYNTAX Unsigned32
        MAX-ACCESS read-write
        STATUS current
        DESCRIPTION
            "This object indicates the J2 byte to be received mode. 0: single-type mode, 1: 16-type mode"
        ::= { optixPdhBoardEntry 1 }

    -- 1.3.6.1.4.1.2011.2.25.4.10.44.1.1.1.2
    optixPdhBoardSRJ2Value OBJECT-TYPE
        SYNTAX OCTET STRING(SIZE(0..32))
        MAX-ACCESS read-write
        STATUS current
        DESCRIPTION
            "This object indicates the value of the J2 byte to be received."
        ::= { optixPdhBoardEntry 2 }

    -- 1.3.6.1.4.1.2011.2.25.4.10.44.1.1.1.3
    optixPdhBoardRJ2Mode OBJECT-TYPE
        SYNTAX Unsigned32
        MAX-ACCESS read-only
        STATUS current
        DESCRIPTION
            "This object indicates the received J2 byte mode. Value range: 0 to 63."
        ::= { optixPdhBoardEntry 3 }

    -- 1.3.6.1.4.1.2011.2.25.4.10.44.1.1.1.4
    optixPdhBoardRJ2Value OBJECT-TYPE
        SYNTAX OCTET STRING(SIZE(0..32))
        MAX-ACCESS read-only
        STATUS current
        DESCRIPTION
            "This object indicates the value of the received J2 byte."
        ::= { optixPdhBoardEntry 4 }

    -- 1.3.6.1.4.1.2011.2.25.4.10.44.1.1.1.5
    optixPdhBoardSRV5Value OBJECT-TYPE
        SYNTAX Unsigned32
        MAX-ACCESS read-write
        STATUS current
        DESCRIPTION
            "This object indicates the value of theV5 byte to be received. Value range: 0 to 7."
        ::= { optixPdhBoardEntry 5 }

    -- 1.3.6.1.4.1.2011.2.25.4.10.44.1.1.1.6
    optixPdhBoardSTV5Value OBJECT-TYPE
        SYNTAX Unsigned32
        MAX-ACCESS read-write
        STATUS current
        DESCRIPTION
            "This object indicates the value of the V5 byte to be transmitted. Value range: 0 to 7."
        ::= { optixPdhBoardEntry 6 }

    -- 1.3.6.1.4.1.2011.2.25.4.10.44.1.1.1.7
    optixPdhBoardRV5Value OBJECT-TYPE
        SYNTAX Unsigned32
        MAX-ACCESS read-only
        STATUS current
        DESCRIPTION
            "This object indicates the value of the receivedV5 byte. Value range: 0 to 2."
        ::= { optixPdhBoardEntry 7 }

    -- 1.3.6.1.4.1.2011.2.25.4.10.44.1.1.1.8
    optixPdhBoardUsedFlag OBJECT-TYPE
        SYNTAX INTEGER
        {
            unuse(0),
            use(1)
        }
        MAX-ACCESS read-write
        STATUS current
        DESCRIPTION
            "This object indicates whether the SDH tributary board management channel is used. 0: unuse, 1: use"
        ::= { optixPdhBoardEntry 8 }

    -- 1.3.6.1.4.1.2011.2.25.4.10.44.1.1.1.9
    optixPdhBoardRetimingClk OBJECT-TYPE
        SYNTAX INTEGER
        {
            noret(0),
            liu(1),
            xc(2)
        }
        MAX-ACCESS read-write
        STATUS current
        DESCRIPTION
            "This object indicates the retiming mode. 0: noret, 1: liu, 2: xc"
        ::= { optixPdhBoardEntry 9 }

    -- 1.3.6.1.4.1.2011.2.25.4.10.44.1.1.1.10
    optixPdhBoardSignalInBalance OBJECT-TYPE
        SYNTAX INTEGER
        {
            unbalance(0),
            balance(1)
        }
        MAX-ACCESS read-write
        STATUS current
        DESCRIPTION
            "This object indicates the balance of input signals. 0: unbalance, 1: balance"
        ::= { optixPdhBoardEntry 10 }

    -- 1.3.6.1.4.1.2011.2.25.4.10.44.1.1.1.11
    optixPdhBoardSignalOutBalance OBJECT-TYPE
        SYNTAX INTEGER
        {
            unbalance(0),
            balance(1)
        }
        MAX-ACCESS read-write
        STATUS current
        DESCRIPTION
            "This object indicates the balance of output signals. 0: unbalance, 1: balance"
        ::= { optixPdhBoardEntry 11 }

    -- 1.3.6.1.4.1.2011.2.25.4.10.44.1.1.1.12
    optixPdhBoardPayLoadType OBJECT-TYPE
        SYNTAX INTEGER
        {
            e1(0),
            t1(1),
            e3(2),
            t3(3),
            e4(4),
            stm1(5)
        }
        MAX-ACCESS read-write
        STATUS current
        DESCRIPTION
            "This object indicatesthe service type. 0: E1, 1: T1, 2: E3, 3: T3, 4: E4, 5: STM-1"
        ::= { optixPdhBoardEntry 12 }

    -- 1.3.6.1.4.1.2011.2.25.4.10.44.1.1.1.13
    optixPdhBoardE1Frame OBJECT-TYPE
        SYNTAX INTEGER
        {
            unframed(0),
            framed(1),
            crcFramed(2)
        }
        MAX-ACCESS read-write
        STATUS current
        DESCRIPTION
            "This object indicates the E1 frame format. 0: unframed, 1: framed, 2: crcFramed"
        ::= { optixPdhBoardEntry 13 }

    -- 1.3.6.1.4.1.2011.2.25.4.10.44.1.1.1.14
    optixPdhBoardSTJ2Mode OBJECT-TYPE
        SYNTAX Unsigned32
        MAX-ACCESS read-write
        STATUS current
        DESCRIPTION
            "This object indicates the J2 byte to be transmitted mode. Value range: 0 to 16."
        ::= { optixPdhBoardEntry 14 }

    -- 1.3.6.1.4.1.2011.2.25.4.10.44.1.1.1.15
    optixPdhBoardSTJ2Value OBJECT-TYPE
        SYNTAX OCTET STRING (SIZE(0..32))
        MAX-ACCESS read-write
        STATUS current
        DESCRIPTION
            "This object indicates the value of the J2 byte to be transmitted."
        ::= { optixPdhBoardEntry 15 }

    -- 1.3.6.1.4.1.2011.2.25.4.10.44.1.1.1.16
    optixPdhBoardPathE1eq OBJECT-TYPE
        SYNTAX INTEGER
        {
            ohm75(1),
            ohm120(2),
            ohm100(4)
        }
        MAX-ACCESS read-only
        STATUS current
        DESCRIPTION
            "This object indicates the impedance of the SDH tributary board Path. 1: ohm75, 2: ohm120, 4: ohm100"
        ::= { optixPdhBoardEntry 16 }

    -- 1.3.6.1.4.1.2011.2.25.4.10.44.1.1.1.17
    optixPdhBoardDefaultBus OBJECT-TYPE
        SYNTAX INTEGER
        {
            a(0),
            b(1)
        }
        MAX-ACCESS read-write
        STATUS current
        DESCRIPTION
            "This object indicates the default bus of the down Path. 0: a, 1: b"
        ::= { optixPdhBoardEntry 17 }

    -- 1.3.6.1.4.1.2011.2.25.4.10.44.1.1.1.18
    optixPdhBoardWorkBus OBJECT-TYPE
        SYNTAX INTEGER
        {
            a(0),
            b(1)
        }
        MAX-ACCESS read-only
        STATUS current
        DESCRIPTION
            "This object indicates the work bus of the down Path. 0: a, 1: b"
        ::= { optixPdhBoardEntry 18 }

    -- 1.3.6.1.4.1.2011.2.25.4.10.44.1.1.1.19
    optixPdhBoardCodeType OBJECT-TYPE
        SYNTAX INTEGER
        {
            b8zs(0),
            ami(1)
        }
        MAX-ACCESS read-write
        STATUS current
        DESCRIPTION
            "This object indicates the code type of the SDH tributary board Path. 0: b8zs, 1: ami"
        ::= { optixPdhBoardEntry 19 }

    -- 1.3.6.1.4.1.2011.2.25.4.10.44.1.1.1.20
    optixPdhBdPayloadTypeNew OBJECT-TYPE
        SYNTAX INTEGER
        {
            e1(0),
            t1(1),
            e3(2),
            t3(3),
            e4(4),
            stm1(5)
        }
        MAX-ACCESS read-write
        STATUS current
        DESCRIPTION
            "This object indicatesthe service type. 0: E1, 1: T1, 2: E3, 3: T3, 4: E4, 5: STM-1"
        ::= { optixPdhBoardEntry 20 }

    -- 1.3.6.1.4.1.2011.2.25.4.10.44.1.2
    optixPdhBoardBipThTable OBJECT-TYPE
        SYNTAX SEQUENCE OF OptixPdhBoardBipThEntry
        MAX-ACCESS not-accessible
        STATUS current
        DESCRIPTION
            "This table describes the configurations of the bit error threshold or deterioration threshold."
        ::= { optixPdhBoardGroup 2 }

    -- 1.3.6.1.4.1.2011.2.25.4.10.44.1.2.1
    optixPdhBoardBipThEntry OBJECT-TYPE
        SYNTAX OptixPdhBoardBipThEntry
        MAX-ACCESS not-accessible
        STATUS current
        DESCRIPTION
            "This entry describes the configurations of bit error threshold or deterioration threshold."
        INDEX{ optixLogBoardId,optixPortId,optixPdhBoardThType }
        ::= { optixPdhBoardBipThTable 1 }

    OptixPdhBoardBipThEntry ::=
        SEQUENCE {
            optixPdhBoardThType
                Unsigned32,
            optixPdhBoardExecTh
                Unsigned32,
            optixPdhBoardSdTh
                Unsigned32
        }

    -- 1.3.6.1.4.1.2011.2.25.4.10.44.1.2.1.1
    optixPdhBoardThType OBJECT-TYPE
        SYNTAX Unsigned32
        MAX-ACCESS not-accessible
        STATUS current
        DESCRIPTION
            "This object indicates the threshold type. 1: B1 threshold, 2: B2 threshold, 3: B3 threshold in VC-4s, 4: B3 threshold in VC-3s, 5: BIP2 threshold, 6: B3-IEC"
        ::= { optixPdhBoardBipThEntry 1 }

    -- 1.3.6.1.4.1.2011.2.25.4.10.44.1.2.1.2
    optixPdhBoardExecTh OBJECT-TYPE
        SYNTAX Unsigned32
        MAX-ACCESS read-write
        STATUS current
        DESCRIPTION
            "This object indicates the level of performance threshold-crossing. 1: 1.0E-9, 2: 1.0E-8, 3: 1.0E-7, 4: 1.0E-6, 5: 1.0E-5, 6: 1.0E-4, 7: 1.0E-3. The value range for bip2th: 3 to 7."
        ::= { optixPdhBoardBipThEntry 2 }

    -- 1.3.6.1.4.1.2011.2.25.4.10.44.1.2.1.3
    optixPdhBoardSdTh OBJECT-TYPE
        SYNTAX Unsigned32
        MAX-ACCESS read-write
        STATUS current
        DESCRIPTION
            "This object indicates the level of performance deterioration. 1: 1.0E-9, 2: 1.0E-8, 3: 1.0E-7, 4: 1.0E-6, 5: 1.0E-5, 6: 1.0E-4, 7: 1.0E-3. The value range for bip2th: 2 to 6."
        ::= { optixPdhBoardBipThEntry 3 }

    -- 1.3.6.1.4.1.2011.2.25.4.10.44.1.3
    optixPdhBoardInsUneqTable OBJECT-TYPE
        SYNTAX SEQUENCE OF OptixPdhBoardInsUneqEntry
        MAX-ACCESS not-accessible
        STATUS current
        DESCRIPTION
            "This table describes configurations of inserted alarm management of the SDH tributary board."
        ::= { optixPdhBoardGroup 3 }

    -- 1.3.6.1.4.1.2011.2.25.4.10.44.1.3.1
    optixPdhBoardInsUneqEntry OBJECT-TYPE
        SYNTAX OptixPdhBoardInsUneqEntry
        MAX-ACCESS not-accessible
        STATUS current
        DESCRIPTION
            "Thisentry describes configurations of inserted alarm management of the SDH tributary board."
        INDEX{ optixLogBoardId,optixPortId,optixPdhBoardEid }
        ::= { optixPdhBoardInsUneqTable 1 }

    OptixPdhBoardInsUneqEntry ::=
        SEQUENCE {
            optixPdhBoardEid
                Unsigned32,
            optixPdhBoardUneqFlag
                INTEGER
        }

    -- 1.3.6.1.4.1.2011.2.25.4.10.44.1.3.1.1
    optixPdhBoardEid OBJECT-TYPE
        SYNTAX Unsigned32
        MAX-ACCESS not-accessible
        STATUS current
        DESCRIPTION
            "This object indicates the conditions for inserting the UNEQ."
        ::= { optixPdhBoardInsUneqEntry 1 }

    -- 1.3.6.1.4.1.2011.2.25.4.10.44.1.3.1.2
    optixPdhBoardUneqFlag OBJECT-TYPE
        SYNTAX INTEGER
        {
            disable(0),
            enable(1)
        }
        MAX-ACCESS read-write
        STATUS current
        DESCRIPTION
            "This object indicates whether to insert the UNEQ or not. 0: disable, 1: enable"
        ::= { optixPdhBoardInsUneqEntry 2 }

    -- 1.3.6.1.4.1.2011.2.25.4.10.44.1.4
    optixPdhBoardOhTable OBJECT-TYPE
        SYNTAX SEQUENCE OF OptixPdhBoardOhEntry
        MAX-ACCESS not-accessible
        STATUS current
        DESCRIPTION
            "This table describes configurations of overhead of the SDH tributary board."
        ::= { optixPdhBoardGroup 4 }

    -- 1.3.6.1.4.1.2011.2.25.4.10.44.1.4.1
    optixPdhBoardOhEntry OBJECT-TYPE
        SYNTAX OptixPdhBoardOhEntry
        MAX-ACCESS not-accessible
        STATUS current
        DESCRIPTION
            "Thisentry describes configurations of overhead  of the SDH tributary board."
        INDEX{ optixLogBoardId,optixPortId,optixPdhBoardLeavel,optixPdhBoardOhpos }
        ::= { optixPdhBoardOhTable 1 }

    OptixPdhBoardOhEntry ::=
        SEQUENCE {
            optixPdhBoardLeavel
                INTEGER,
            optixPdhBoardOhpos
                INTEGER,
            optixPdhBoardRpoh
                Unsigned32,
            optixPdhBoardTpoh
                Unsigned32
        }

    -- 1.3.6.1.4.1.2011.2.25.4.10.44.1.4.1.1
    optixPdhBoardLeavel OBJECT-TYPE
        SYNTAX INTEGER
        {
            vc4(1),
            au44c(2),
            au48c(3),
            au416c(4),
            au464c(5),
            vc12(6),
            vc3(7),
            au3(9)
        }
        MAX-ACCESS not-accessible
        STATUS current
        DESCRIPTION
            "This object indicates the leavel of the path. 6: vc12, 7: vc3, 1: vc4, 2: au44c, 3: au48c, 4: au416c, 5: au464c, 9: au3"
        ::= { optixPdhBoardOhEntry 1 }

    -- 1.3.6.1.4.1.2011.2.25.4.10.44.1.4.1.2
    optixPdhBoardOhpos OBJECT-TYPE
        SYNTAX INTEGER
        {
            c2(3),
            g1(4),
            f2(5),
            f3(7),
            k3(8),
            n1(9),
            v5(11),
            n2(13),
            k4(14)
        }
        MAX-ACCESS not-accessible
        STATUS current
        DESCRIPTION
            "This object indicates overhead pos of the path. 3: C2, 4: G1, 5: F2, 7: F3, 8: K3, 9: N1, 11: V5, 13: N2, 14: K4"
        ::= { optixPdhBoardOhEntry 2 }

    -- 1.3.6.1.4.1.2011.2.25.4.10.44.1.4.1.3
    optixPdhBoardRpoh OBJECT-TYPE
        SYNTAX Unsigned32
        MAX-ACCESS read-only
        STATUS current
        DESCRIPTION
            "This object indicates the receiving overhead byte of SDH tributary path board. The byte ranges from 0 to 255"
        ::= { optixPdhBoardOhEntry 3 }

    -- 1.3.6.1.4.1.2011.2.25.4.10.44.1.4.1.4
    optixPdhBoardTpoh OBJECT-TYPE
        SYNTAX Unsigned32
        MAX-ACCESS read-write
        STATUS current
        DESCRIPTION
            "This object indicates the sending overhead byte of SDH tributary path board. The byte ranges from 0 to 255"
        ::= { optixPdhBoardOhEntry 4 }

    -- 1.3.6.1.4.1.2011.2.25.4.10.44.1.5
    optixBitTestTable OBJECT-TYPE
        SYNTAX SEQUENCE OF OptixBitTestEntry
        MAX-ACCESS not-accessible
        STATUS current
        DESCRIPTION
            "This table describes configurations of bit test of the SDH board."
        ::= { optixPdhBoardGroup 5 }

    -- 1.3.6.1.4.1.2011.2.25.4.10.44.1.5.1
    optixBitTestEntry OBJECT-TYPE
        SYNTAX OptixBitTestEntry
        MAX-ACCESS not-accessible
        STATUS current
        DESCRIPTION
            "This entry describes configurations of bit test of the SDH board."
        INDEX{ optixLogBoardId,optixBitTestXcLeavel,optixPortId }
        ::= { optixBitTestTable 1 }

    OptixBitTestEntry ::=
        SEQUENCE {
            optixBitTestXcLeavel
                Unsigned32,
            optixBitTestDir
                INTEGER,
            optixBitTestMode
                Unsigned32,
            optixBitTestStartTime
                DateAndTime,
            optixBitTestCurrentcyc
                Unsigned32,
            optixBitTestStartcyc
                Unsigned32,
            optixBitTestErrNum1
                OCTET STRING,
            optixBitTestErrNum2
                OCTET STRING,
            optixBitTestErrNum3
                OCTET STRING,
            optixBitTestAction
                INTEGER,
            optixBitTestTime
                Unsigned32
        }

    -- 1.3.6.1.4.1.2011.2.25.4.10.44.1.5.1.1
    optixBitTestXcLeavel OBJECT-TYPE
        SYNTAX Unsigned32
        MAX-ACCESS not-accessible
        STATUS current
        DESCRIPTION
            "This object indicates the level of the bit test. 1: vc4, 2: vc3, 3: vc12"
        ::= { optixBitTestEntry 1 }

    -- 1.3.6.1.4.1.2011.2.25.4.10.44.1.5.1.2
    optixBitTestDir OBJECT-TYPE
        SYNTAX INTEGER
        {
            xc(1),
            liu(2)
        }
        MAX-ACCESS read-write
        STATUS current
        DESCRIPTION
            "This object indicates direction of the bit test. 1: xc, 2: liu"
        ::= { optixBitTestEntry 2 }

    -- 1.3.6.1.4.1.2011.2.25.4.10.44.1.5.1.3
    optixBitTestMode OBJECT-TYPE
        SYNTAX Unsigned32
        MAX-ACCESS read-write
        STATUS current
        DESCRIPTION
            "This object indicates mode of the bit test. 1: short-term test, 2: long-term test, 3: extra-long-term test"
        ::= { optixBitTestEntry 3 }

    -- 1.3.6.1.4.1.2011.2.25.4.10.44.1.5.1.4
    optixBitTestStartTime OBJECT-TYPE
        SYNTAX DateAndTime
        MAX-ACCESS read-only
        STATUS current
        DESCRIPTION
            "This object indicates start time of the bit test."
        ::= { optixBitTestEntry 4 }

    -- 1.3.6.1.4.1.2011.2.25.4.10.44.1.5.1.5
    optixBitTestCurrentcyc OBJECT-TYPE
        SYNTAX Unsigned32
        MAX-ACCESS read-only
        STATUS current
        DESCRIPTION
            "This object indicates current cycle of the bit test. Value range: 0 to 255."
        ::= { optixBitTestEntry 5 }

    -- 1.3.6.1.4.1.2011.2.25.4.10.44.1.5.1.6
    optixBitTestStartcyc OBJECT-TYPE
        SYNTAX Unsigned32
        MAX-ACCESS read-only
        STATUS current
        DESCRIPTION
            "This object indicates start cycle of the bit test. Value range: 0 to 255."
        ::= { optixBitTestEntry 6 }

    -- 1.3.6.1.4.1.2011.2.25.4.10.44.1.5.1.7
    optixBitTestErrNum1 OBJECT-TYPE
        SYNTAX OCTET STRING (SIZE(0..1024))
        MAX-ACCESS read-only
        STATUS current
        DESCRIPTION
            "This object indicates start cycle number of the bit test(1-93)."
        ::= { optixBitTestEntry 7 }

    -- 1.3.6.1.4.1.2011.2.25.4.10.44.1.5.1.8
    optixBitTestErrNum2 OBJECT-TYPE
        SYNTAX OCTET STRING (SIZE(0..1024))
        MAX-ACCESS read-only
        STATUS current
        DESCRIPTION
            "This object indicates start cycle number of the bit test(94-186)."
        ::= { optixBitTestEntry 8 }

    -- 1.3.6.1.4.1.2011.2.25.4.10.44.1.5.1.9
    optixBitTestErrNum3 OBJECT-TYPE
        SYNTAX OCTET STRING (SIZE(0..1024))
        MAX-ACCESS read-only
        STATUS current
        DESCRIPTION
            "This object indicates start cycle number of the bit test(187-255)."
        ::= { optixBitTestEntry 9 }

    -- 1.3.6.1.4.1.2011.2.25.4.10.44.1.5.1.10
    optixBitTestAction OBJECT-TYPE
        SYNTAX INTEGER
        {
            stop(0),
            start(1),
            invalid(255)
        }
        MAX-ACCESS read-write
        STATUS current
        DESCRIPTION
            "This object query invalid,be used to start or stop bit test. 0: stop, 1: start, 255: invalid"
        ::= { optixBitTestEntry 10 }

    -- 1.3.6.1.4.1.2011.2.25.4.10.44.1.5.1.11
    optixBitTestTime OBJECT-TYPE
        SYNTAX Unsigned32
        MAX-ACCESS read-write
        STATUS current
        DESCRIPTION
            "This object query invalid,be used to set bit test time. Value range: 0 to 255."
        ::= { optixBitTestEntry 11 }

    -- 1.3.6.1.4.1.2011.2.25.4.10.44.1.6
    optixBitTestExtTable OBJECT-TYPE
        SYNTAX SEQUENCE OF OptixBitTestExtEntry
        MAX-ACCESS not-accessible
        STATUS current
        DESCRIPTION
            "This table describes configurations of expand bit test of the SDH board."
        ::= { optixPdhBoardGroup 6 }

    -- 1.3.6.1.4.1.2011.2.25.4.10.44.1.6.1
    optixBitTestExtEntry OBJECT-TYPE
        SYNTAX OptixBitTestExtEntry
        MAX-ACCESS not-accessible
        STATUS current
        DESCRIPTION
            "This entry describes configurations of expand bit test of the SDH board."
        INDEX{ optixLogBoardId,optixBitTestXcLeavel,optixPortId,optixBitTestDir,optixBitTestMode,optixBitTestStartTime,optixBitTestEndTime }
        ::= { optixBitTestExtTable 1 }

    OptixBitTestExtEntry ::=
        SEQUENCE {
            optixBitTestEndTime
                DateAndTime,
            optixBitTestProgress
                Unsigned32,
            optixBitTestRealTestPeriod
                Unsigned32
        }

    -- 1.3.6.1.4.1.2011.2.25.4.10.44.1.6.1.1
    optixBitTestEndTime OBJECT-TYPE
        SYNTAX DateAndTime
        MAX-ACCESS not-accessible
        STATUS current
        DESCRIPTION
            "This object indicates end time of the bit test."
        ::= { optixBitTestExtEntry 1 }

    -- 1.3.6.1.4.1.2011.2.25.4.10.44.1.6.1.2
    optixBitTestProgress OBJECT-TYPE
        SYNTAX Unsigned32
        MAX-ACCESS read-only
        STATUS current
        DESCRIPTION
            "This object indicates current progress of the bit test. Current progress: 1 to 100."
        ::= { optixBitTestExtEntry 2 }

    -- 1.3.6.1.4.1.2011.2.25.4.10.44.1.6.1.3
    optixBitTestRealTestPeriod OBJECT-TYPE
        SYNTAX Unsigned32
        MAX-ACCESS read-only
        STATUS current
        DESCRIPTION
            "This object indicates real test period of the bit test. Value range: 0 to 255."
        ::= { optixBitTestExtEntry 3 }

    -- 1.3.6.1.4.1.2011.2.25.4.10.44.1.7
    optixBitTestExtTypeNumTable OBJECT-TYPE
        SYNTAX SEQUENCE OF OptixBitTestExtTypeNumEntry
        MAX-ACCESS not-accessible
        STATUS current
        DESCRIPTION
            "This table describes configurations of the result of expand bit test of the SDH board."
        ::= { optixPdhBoardGroup 7 }

    -- 1.3.6.1.4.1.2011.2.25.4.10.44.1.7.1
    optixBitTestExtTypeNumEntry OBJECT-TYPE
        SYNTAX OptixBitTestExtTypeNumEntry
        MAX-ACCESS not-accessible
        STATUS current
        DESCRIPTION
            "This entry describes configurations of the result of expand bit test of the SDH board."
        INDEX{ optixLogBoardId,optixBitTestXcLeavel,optixPortId,optixBitTestDir,optixBitTestMode,optixBitTestStartTime,optixBitTestEndTime,optixBitTestTypeNumID }
        ::= { optixBitTestExtTypeNumTable 1 }

    OptixBitTestExtTypeNumEntry ::=
        SEQUENCE {
            optixBitTestTypeNumID
                Unsigned32,
            optixBitTestTypeNumType
                Unsigned32,
            optixBitTestTypeNumResult
                Unsigned32
        }

    -- 1.3.6.1.4.1.2011.2.25.4.10.44.1.7.1.1
    optixBitTestTypeNumID OBJECT-TYPE
        SYNTAX Unsigned32
        MAX-ACCESS not-accessible
        STATUS current
        DESCRIPTION
            "This object indicates type number of the bit test."
        ::= { optixBitTestExtTypeNumEntry 1 }

    -- 1.3.6.1.4.1.2011.2.25.4.10.44.1.7.1.2
    optixBitTestTypeNumType OBJECT-TYPE
        SYNTAX Unsigned32
        MAX-ACCESS read-only
        STATUS current
        DESCRIPTION
            "This object indicates type of the bit test. Value range: 0 to 255."
        ::= { optixBitTestExtTypeNumEntry 2 }

    -- 1.3.6.1.4.1.2011.2.25.4.10.44.1.7.1.3
    optixBitTestTypeNumResult OBJECT-TYPE
        SYNTAX Unsigned32
        MAX-ACCESS read-only
        STATUS current
        DESCRIPTION
            "This object indicates type result of the bit test."
        ::= { optixBitTestExtTypeNumEntry 3 }

    -- 1.3.6.1.4.1.2011.2.25.4.10.44.1.8
    optixStartBitTestExtTable OBJECT-TYPE
        SYNTAX SEQUENCE OF OptixStartBitTestExtEntry
        MAX-ACCESS not-accessible
        STATUS current
        DESCRIPTION
            "This table describes start or stop expand bit test."
        ::= { optixPdhBoardGroup 8 }

    -- 1.3.6.1.4.1.2011.2.25.4.10.44.1.8.1
    optixStartBitTestExtEntry OBJECT-TYPE
        SYNTAX OptixStartBitTestExtEntry
        MAX-ACCESS not-accessible
        STATUS current
        DESCRIPTION
            "This entry describes start or stop expand bit test ."
        INDEX{ optixLogBoardId,optixPortId }
        ::= { optixStartBitTestExtTable 1 }

    OptixStartBitTestExtEntry ::=
        SEQUENCE {
            optixStartBitTestExtAction
                INTEGER,
            optixStartBitTestExtDir
                INTEGER,
            optixStartBitTestExtMode
                Unsigned32,
            optixStartBitTestExtTime
                Unsigned32
        }

    -- 1.3.6.1.4.1.2011.2.25.4.10.44.1.8.1.1
    optixStartBitTestExtAction OBJECT-TYPE
        SYNTAX INTEGER
        {
            stop(0),
            start(1),
            invalid(255)
        }
        MAX-ACCESS read-write
        STATUS current
        DESCRIPTION
            "This object query invalid,be used to start or stop expand bit test. 0: stop, 1: start, 255: invalid"
        ::= { optixStartBitTestExtEntry 1 }

    -- 1.3.6.1.4.1.2011.2.25.4.10.44.1.8.1.2
    optixStartBitTestExtDir OBJECT-TYPE
        SYNTAX INTEGER
        {
            xc(1),
            liu(2)
        }
        MAX-ACCESS read-write
        STATUS current
        DESCRIPTION
            "This object indicates direction of the bit test. 1: xc, 2: liu"
        ::= { optixStartBitTestExtEntry 2 }

    -- 1.3.6.1.4.1.2011.2.25.4.10.44.1.8.1.3
    optixStartBitTestExtMode OBJECT-TYPE
        SYNTAX Unsigned32
        MAX-ACCESS read-write
        STATUS current
        DESCRIPTION
            "This object indicates mode of the bit test. 1: short-term test, 2: long-term test, 3: extra-long-term test"
        ::= { optixStartBitTestExtEntry 3 }

    -- 1.3.6.1.4.1.2011.2.25.4.10.44.1.8.1.4
    optixStartBitTestExtTime OBJECT-TYPE
        SYNTAX Unsigned32
        MAX-ACCESS read-write
        STATUS current
        DESCRIPTION
            "This object query invalid,be used to set expand bit test time. Value range: 0 to 255."
        ::= { optixStartBitTestExtEntry 4 }

    -- 1.3.6.1.4.1.2011.2.25.4.10.44.1.9
    optixSdhBitTestEvent OBJECT IDENTIFIER ::= { optixPdhBoardGroup 9 }

    -- 1.3.6.1.4.1.2011.2.25.4.10.44.1.9.1
    optixSdhBitTest NOTIFICATION-TYPE
        STATUS current
        DESCRIPTION
            "This objectis used to reportthe SDH bit test event."
        ::= { optixSdhBitTestEvent 1 }

    -- 1.3.6.1.4.1.2011.2.25.4.10.44.1.9.2
    optixSdhBitTestExt NOTIFICATION-TYPE
        STATUS current
        DESCRIPTION
            "This objectis used to reportthe SDH expand bit test event."
        ::= { optixSdhBitTestEvent 2 }

    -- 1.3.6.1.4.1.2011.2.25.4.10.44.1.10
    optixSdhBitTestEventMember OBJECT IDENTIFIER ::= { optixPdhBoardGroup 10 }

    -- 1.3.6.1.4.1.2011.2.25.4.10.44.1.10.1
    optixSdhBitTestBoardId OBJECT-TYPE
        SYNTAX Unsigned32
        MAX-ACCESS accessible-for-notify
        STATUS current
        DESCRIPTION
            "This object indicates the board id of the bit test."
        ::= { optixSdhBitTestEventMember 1 }

    -- 1.3.6.1.4.1.2011.2.25.4.10.44.1.10.2
    optixSdhBitTestTimeStamp OBJECT-TYPE
        SYNTAX Unsigned32
        MAX-ACCESS accessible-for-notify
        STATUS current
        DESCRIPTION
            "This object indicates the Time Stamp of the bit test."
        ::= { optixSdhBitTestEventMember 2 }

    -- 1.3.6.1.4.1.2011.2.25.4.10.44.1.10.3
    optixSdhBitTestPortId OBJECT-TYPE
        SYNTAX Unsigned32
        MAX-ACCESS accessible-for-notify
        STATUS current
        DESCRIPTION
            "This object indicates the port id of the bit test."
        ::= { optixSdhBitTestEventMember 3 }

    -- 1.3.6.1.4.1.2011.2.25.4.10.44.1.10.4
    optixSdhBitTestTSlot OBJECT-TYPE
        SYNTAX Unsigned32
        MAX-ACCESS accessible-for-notify
        STATUS current
        DESCRIPTION
            "This object indicates the slot id of the bit test."
        ::= { optixSdhBitTestEventMember 4 }

    -- 1.3.6.1.4.1.2011.2.25.4.10.44.1.10.5
    optixSdhBitTestErrNum OBJECT-TYPE
        SYNTAX Unsigned32
        MAX-ACCESS accessible-for-notify
        STATUS current
        DESCRIPTION
            "This object indicates start cycle number of the bit test."
        ::= { optixSdhBitTestEventMember 5 }

    -- 1.3.6.1.4.1.2011.2.25.4.10.44.1.10.6
    optixSdhBitTestLevel OBJECT-TYPE
        SYNTAX Unsigned32
        MAX-ACCESS accessible-for-notify
        STATUS current
        DESCRIPTION
            "This object indicates the leavel of the bit test."
        ::= { optixSdhBitTestEventMember 6 }

    -- 1.3.6.1.4.1.2011.2.25.4.10.44.1.10.7
    optixSdhBitTestDir OBJECT-TYPE
        SYNTAX INTEGER
        {
            xc(1),
            liu(2)
        }
        MAX-ACCESS accessible-for-notify
        STATUS current
        DESCRIPTION
            "This object indicates direction of the bit test."
        ::= { optixSdhBitTestEventMember 7 }

    -- 1.3.6.1.4.1.2011.2.25.4.10.44.1.10.8
    optixSdhBitTestMode OBJECT-TYPE
        SYNTAX Unsigned32
        MAX-ACCESS accessible-for-notify
        STATUS current
        DESCRIPTION
            "This object indicates mode of the bit test."
        ::= { optixSdhBitTestEventMember 8 }

    -- 1.3.6.1.4.1.2011.2.25.4.10.44.1.10.9
    optixSdhBitTestStartTime OBJECT-TYPE
        SYNTAX DateAndTime
        MAX-ACCESS accessible-for-notify
        STATUS current
        DESCRIPTION
            "This object indicates start time of the bit test."
        ::= { optixSdhBitTestEventMember 9 }

    -- 1.3.6.1.4.1.2011.2.25.4.10.44.1.10.10
    optixSdhBitTestEndTime OBJECT-TYPE
        SYNTAX DateAndTime
        MAX-ACCESS accessible-for-notify
        STATUS current
        DESCRIPTION
            "This object indicates end time of the bit test."
        ::= { optixSdhBitTestEventMember 10 }

    -- 1.3.6.1.4.1.2011.2.25.4.10.44.1.10.11
    optixSdhBitTestProgress OBJECT-TYPE
        SYNTAX Unsigned32
        MAX-ACCESS accessible-for-notify
        STATUS current
        DESCRIPTION
            "This object indicates current progress of the bit test."
        ::= { optixSdhBitTestEventMember 11 }

    -- 1.3.6.1.4.1.2011.2.25.4.10.44.1.10.12
    optixSdhBitTestTypeNum OBJECT-TYPE
        SYNTAX Unsigned32
        MAX-ACCESS accessible-for-notify
        STATUS current
        DESCRIPTION
            "This object indicates type number of the bit test."
        ::= { optixSdhBitTestEventMember 12 }

    -- 1.3.6.1.4.1.2011.2.25.4.10.44.1.10.13
    optixSdhBitTestType1 OBJECT-TYPE
        SYNTAX Unsigned32
        MAX-ACCESS accessible-for-notify
        STATUS current
        DESCRIPTION
            "This object indicates type1 of the bit test."
        ::= { optixSdhBitTestEventMember 13 }

    -- 1.3.6.1.4.1.2011.2.25.4.10.44.1.10.14
    optixSdhBitTestTestResult1 OBJECT-TYPE
        SYNTAX Unsigned32
        MAX-ACCESS accessible-for-notify
        STATUS current
        DESCRIPTION
            "This object indicates type1 result of the bit test."
        ::= { optixSdhBitTestEventMember 14 }

    -- 1.3.6.1.4.1.2011.2.25.4.10.44.1.10.15
    optixSdhBitTestType2 OBJECT-TYPE
        SYNTAX Unsigned32
        MAX-ACCESS accessible-for-notify
        STATUS current
        DESCRIPTION
            "This object indicates type2 of the bit test."
        ::= { optixSdhBitTestEventMember 15 }

    -- 1.3.6.1.4.1.2011.2.25.4.10.44.1.10.16
    optixSdhBitTestTestResult2 OBJECT-TYPE
        SYNTAX Unsigned32
        MAX-ACCESS accessible-for-notify
        STATUS current
        DESCRIPTION
            "This object indicates type2 result of the bit test."
        ::= { optixSdhBitTestEventMember 16 }

END
