-- OPTIX-PER-CFG-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PER-CFG-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        ;

    optixPerCfgManage MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the Configuration of Performance"
        REVISION "201204170000Z"
        DESCRIPTION
            "The initial revision of this MIB module."
        REVISION "201204170000Z"
        DESCRIPTION
            "The initial revision of this MIB module."
        ::={ optixProvisionEqpt 22 }

    -- 1.3.6.1.4.1.2011.2.25.4.30.22.1
    optixPerCfg OBJECT IDENTIFIER ::= { optixPerCfgManage 1 }

    -- 1.3.6.1.4.1.2011.2.25.4.30.22.1.1
    optixSDHPerTable OBJECT-TYPE
        SYNTAX SEQUENCE OF OptixSDHPerEntry
        MAX-ACCESS not-accessible
        STATUS current
        DESCRIPTION
            "Thistable describes SDH performance management."
        ::= { optixPerCfg 1 }

    -- 1.3.6.1.4.1.2011.2.25.4.30.22.1.1.1
    optixSDHPerEntry OBJECT-TYPE
        SYNTAX OptixSDHPerEntry
        MAX-ACCESS not-accessible
        STATUS current
        DESCRIPTION
            "Thisentry describes SDH performance management."
        INDEX{ optixSDHPerIdIndex,optixSDHPerPeriod,optixSDHPerObjtype,optixSDHPerObjpara }
        ::= { optixSDHPerTable 1 }

    OptixSDHPerEntry ::=
        SEQUENCE {
            optixSDHPerIdIndex
                Unsigned32,
            optixSDHPerPeriod
                INTEGER,
            optixSDHPerObjtype
                Unsigned32,
            optixSDHPerObjpara
                OCTET STRING,
            optixSDHPerMonstate
                INTEGER,
            optixSDHPerAutoRep
                INTEGER,
            optixSDHPerTrenable
                INTEGER,
            optixSDHPerHthr
                Unsigned32,
            optixSDHPerLthr
                Unsigned32,
            optixSDHPerRowStatus
                RowStatus
        }

    -- 1.3.6.1.4.1.2011.2.25.4.30.22.1.1.1.1
    optixSDHPerIdIndex OBJECT-TYPE
        SYNTAX Unsigned32
        MAX-ACCESS not-accessible
        STATUS current
        DESCRIPTION
            "This object indicates the SDH performance event ID."
        ::= { optixSDHPerEntry 1 }

    -- 1.3.6.1.4.1.2011.2.25.4.30.22.1.1.1.2
    optixSDHPerPeriod OBJECT-TYPE
        SYNTAX INTEGER
        {
            snmp15m(1),
            snmp24h(2),
            snmp30s(17),
            snmp30m(18),
            alt1(19),
            alt2(20),
            rt(21),
            all(0)
        }
        MAX-ACCESS not-accessible
        STATUS current
        DESCRIPTION
            "This object indicates the SDH performance monitoring period. 1: snmp15m, 2: snmp24h, 17: snmp30s, 18: snmp30m, 19: alt1, 20: alt2, 21: rt, 0: all"
        DEFVAL{ 0 }
        ::= { optixSDHPerEntry 2 }

    -- 1.3.6.1.4.1.2011.2.25.4.30.22.1.1.1.3
    optixSDHPerObjtype OBJECT-TYPE
        SYNTAX Unsigned32
        MAX-ACCESS not-accessible
        STATUS current
        DESCRIPTION
            "This object indicates the type of the monitored SDH performance object ."
        ::= { optixSDHPerEntry 3 }

    -- 1.3.6.1.4.1.2011.2.25.4.30.22.1.1.1.4
    optixSDHPerObjpara OBJECT-TYPE
        SYNTAX OCTET STRING
        MAX-ACCESS not-accessible
        STATUS current
        DESCRIPTION
            "This object indicates the parameter contents of the monitored SDH performance object."
        DEFVAL{ "" }
        ::= { optixSDHPerEntry 4 }

    -- 1.3.6.1.4.1.2011.2.25.4.30.22.1.1.1.5
    optixSDHPerMonstate OBJECT-TYPE
        SYNTAX INTEGER
        {
            enable(1),
            disable(0)
        }
        MAX-ACCESS read-create
        STATUS current
        DESCRIPTION
            "This object indicates the monitoring status of the SDH performance event. 0: disable, 1: enable"
        DEFVAL{ 0 }
        ::= { optixSDHPerEntry 5 }

    -- 1.3.6.1.4.1.2011.2.25.4.30.22.1.1.1.6
    optixSDHPerAutoRep OBJECT-TYPE
        SYNTAX INTEGER
        {
            enable(1),
            disable(0)
        }
        MAX-ACCESS read-create
        STATUS current
        DESCRIPTION
            "This object indicates the auto-reporting status of the SDH performance event. 0: disable, 1: enable"
        DEFVAL{ 0 }
        ::= { optixSDHPerEntry 6 }

    -- 1.3.6.1.4.1.2011.2.25.4.30.22.1.1.1.7
    optixSDHPerTrenable OBJECT-TYPE
        SYNTAX INTEGER
        {
            enable(1),
            disable(0)
        }
        MAX-ACCESS read-create
        STATUS current
        DESCRIPTION
            "This object indicates the permission status of the SDH performance threshold-crossing event. 0: disable, 1: enable"
        DEFVAL{ 0 }
        ::= { optixSDHPerEntry 7 }

    -- 1.3.6.1.4.1.2011.2.25.4.30.22.1.1.1.8
    optixSDHPerHthr OBJECT-TYPE
        SYNTAX Unsigned32
        MAX-ACCESS read-create
        STATUS current
        DESCRIPTION
            "This object indicates the upper threshold of the SDH performance event, which is associated with the lower threshold of the SDH performance event."
        ::= { optixSDHPerEntry 8 }

    -- 1.3.6.1.4.1.2011.2.25.4.30.22.1.1.1.9
    optixSDHPerLthr OBJECT-TYPE
        SYNTAX Unsigned32
        MAX-ACCESS read-create
        STATUS current
        DESCRIPTION
            "This object indicates the lower threshold of the SDH performance event, which is associated with the upper threshold of the SDH performance event."
        ::= { optixSDHPerEntry 9 }

    -- 1.3.6.1.4.1.2011.2.25.4.30.22.1.1.1.255
    optixSDHPerRowStatus OBJECT-TYPE
        SYNTAX RowStatus
        MAX-ACCESS read-create
        STATUS current
        DESCRIPTION
            "This Row Status describes long-parameter data performance event management."
        ::= { optixSDHPerEntry 255 }

    -- 1.3.6.1.4.1.2011.2.25.4.30.22.1.2
    optixDataPerTable OBJECT-TYPE
        SYNTAX SEQUENCE OF OptixDataPerEntry
        MAX-ACCESS not-accessible
        STATUS current
        DESCRIPTION
            "This table describes long-parameter data performance event management."
        ::= { optixPerCfg 2 }

    -- 1.3.6.1.4.1.2011.2.25.4.30.22.1.2.1
    optixDataPerEntry OBJECT-TYPE
        SYNTAX OptixDataPerEntry
        MAX-ACCESS not-accessible
        STATUS current
        DESCRIPTION
            "Thisentry describes long-parameter data performance event management."
        INDEX{ optixDataPerIdIndex,optixDataPerPeriod,optixDataPerObjtype,optixDataPerObjpara }
        ::= { optixDataPerTable 1 }

    OptixDataPerEntry ::=
        SEQUENCE {
            optixDataPerIdIndex
                Unsigned32,
            optixDataPerPeriod
                INTEGER,
            optixDataPerObjtype
                Unsigned32,
            optixDataPerObjpara
                OCTET STRING,
            optixDataPerMonstate
                INTEGER,
            optixDataPerAutoRep
                INTEGER
        }

    -- 1.3.6.1.4.1.2011.2.25.4.30.22.1.2.1.1
    optixDataPerIdIndex OBJECT-TYPE
        SYNTAX Unsigned32
        MAX-ACCESS not-accessible
        STATUS current
        DESCRIPTION
            "Thisobject indicates the long-parameter data performance event ID."
        ::= { optixDataPerEntry 1 }

    -- 1.3.6.1.4.1.2011.2.25.4.30.22.1.2.1.2
    optixDataPerPeriod OBJECT-TYPE
        SYNTAX INTEGER
        {
            snmp15m(1),
            snmp24h(2),
            snmp30s(17),
            snmp30m(18),
            alt1(19),
            alt2(20),
            rt(21),
            all(0)
        }
        MAX-ACCESS not-accessible
        STATUS current
        DESCRIPTION
            "This object indicates the long-parameter data performance monitoring period. 1: snmp15m, 2: snmp24h, 17: snmp30s, 18: snmp30m, 19: alt1, 20: alt2, 21: rt, 0: all"
        DEFVAL{ 0 }
        ::= { optixDataPerEntry 2 }

    -- 1.3.6.1.4.1.2011.2.25.4.30.22.1.2.1.3
    optixDataPerObjtype OBJECT-TYPE
        SYNTAX Unsigned32
        MAX-ACCESS not-accessible
        STATUS current
        DESCRIPTION
            "This object indicates the type of the monitored long-parameter data performance object."
        ::= { optixDataPerEntry 3 }

    -- 1.3.6.1.4.1.2011.2.25.4.30.22.1.2.1.4
    optixDataPerObjpara OBJECT-TYPE
        SYNTAX OCTET STRING
        MAX-ACCESS not-accessible
        STATUS current
        DESCRIPTION
            "This object indicates the parameter contents of the monitored long-parameter data performance object."
        DEFVAL{ "" }
        ::= { optixDataPerEntry 4 }

    -- 1.3.6.1.4.1.2011.2.25.4.30.22.1.2.1.5
    optixDataPerMonstate OBJECT-TYPE
        SYNTAX INTEGER
        {
            enable(1),
            disable(0)
        }
        MAX-ACCESS read-write
        STATUS current
        DESCRIPTION
            "Thisobject indicates themonitoring status of long-parameter data performance events. 0: disable, 1: enable"
        DEFVAL{ 0 }
        ::= { optixDataPerEntry 5 }

    -- 1.3.6.1.4.1.2011.2.25.4.30.22.1.2.1.6
    optixDataPerAutoRep OBJECT-TYPE
        SYNTAX INTEGER
        {
            enable(1),
            disable(0)
        }
        MAX-ACCESS read-write
        STATUS current
        DESCRIPTION
            "This object indicates theauto-reporting status of long-parameter data performance events. 0: disable, 1: enable"
        DEFVAL{ 0 }
        ::= { optixDataPerEntry 6 }

    -- 1.3.6.1.4.1.2011.2.25.4.30.22.1.3
    optixDataPer2Table OBJECT-TYPE
        SYNTAX SEQUENCE OF OptixDataPer2Entry
        MAX-ACCESS not-accessible
        STATUS current
        DESCRIPTION
            "This table describes long-parameter data performance event management."
        ::= { optixPerCfg 3 }

    -- 1.3.6.1.4.1.2011.2.25.4.30.22.1.3.1
    optixDataPer2Entry OBJECT-TYPE
        SYNTAX OptixDataPer2Entry
        MAX-ACCESS not-accessible
        STATUS current
        DESCRIPTION
            "Thisentry describes long-parameter data performance event management."
        INDEX{ optixDataPerIdIndex,optixDataPerObjtype,optixDataPerObjpara }
        ::= { optixDataPer2Table 1 }

    OptixDataPer2Entry ::=
        SEQUENCE {
            optixDataPerReMode
                INTEGER,
            optixDataPerHthr
                Unsigned32,
            optixDataPerLthr
                Unsigned32,
            optixDataPerTrstate
                INTEGER
        }

    -- 1.3.6.1.4.1.2011.2.25.4.30.22.1.3.1.1
    optixDataPerReMode OBJECT-TYPE
        SYNTAX INTEGER
        {
            both(0),
            high(1),
            low(2)
        }
        MAX-ACCESS read-write
        STATUS current
        DESCRIPTION
            "This object indicates the reportingmode of long-parameter data performance threshold-crossing events. 0: both, 1: high, 2: low"
        DEFVAL{ 0 }
        ::= { optixDataPer2Entry 1 }

    -- 1.3.6.1.4.1.2011.2.25.4.30.22.1.3.1.2
    optixDataPerHthr OBJECT-TYPE
        SYNTAX Unsigned32
        MAX-ACCESS read-write
        STATUS current
        DESCRIPTION
            "This object indicates the upper threshold of long-parameter data performance events, which is associated with the lower threshold of long-parameter data performance events."
        ::= { optixDataPer2Entry 2 }

    -- 1.3.6.1.4.1.2011.2.25.4.30.22.1.3.1.3
    optixDataPerLthr OBJECT-TYPE
        SYNTAX Unsigned32
        MAX-ACCESS read-write
        STATUS current
        DESCRIPTION
            "This object indicates the lower threshold of long-parameter data performance events, which is associated with the upper threshold of long-parameter data performance events."
        ::= { optixDataPer2Entry 3 }

    -- 1.3.6.1.4.1.2011.2.25.4.30.22.1.3.1.4
    optixDataPerTrstate OBJECT-TYPE
        SYNTAX INTEGER
        {
            enable(1),
            disable(0)
        }
        MAX-ACCESS read-write
        STATUS current
        DESCRIPTION
            "This object indicates the enable status of the alarm group thresholds for long-parameter data performance events. 0: disable, 1: enable"
        DEFVAL{ 0 }
        ::= { optixDataPer2Entry 4 }

END
