-- OPTIX-NE-ALM-AIS-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-NE-ALM-AIS-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        ;

    optixNeAlmAisMng MODULE-IDENTITY
        LAST-UPDATED "201204270000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "ThisMIB describes the enable status of inserting AIS for NE alarms."
        REVISION "201204270000Z"
        DESCRIPTION
            "The initial revision of this MIB module."
        REVISION "201204270000Z"
        DESCRIPTION
            "The initial revision of this MIB module."
        ::={ optixProvisionEqpt 12 }

    -- 1.3.6.1.4.1.2011.2.25.4.30.12.1
    optixNeAlmAisGroup OBJECT IDENTIFIER ::= { optixNeAlmAisMng 1 }

    -- 1.3.6.1.4.1.2011.2.25.4.30.12.1.1
    optixNeAlmAisTable OBJECT-TYPE
        SYNTAX SEQUENCE OF OptixNeAlmAisEntry
        MAX-ACCESS not-accessible
        STATUS current
        DESCRIPTION
            "This table describes the enable status of inserting AIS for NE alarms."
        ::= { optixNeAlmAisGroup 1 }

    -- 1.3.6.1.4.1.2011.2.25.4.30.12.1.1.1
    optixNeAlmAisEntry OBJECT-TYPE
        SYNTAX OptixNeAlmAisEntry
        MAX-ACCESS not-accessible
        STATUS current
        DESCRIPTION
            "Thisentry describes the enable status of inserting AIS for NE alarms."
        INDEX{ optixAlmEid }
        ::= { optixNeAlmAisTable 1 }

    OptixNeAlmAisEntry ::=
        SEQUENCE {
            optixAlmEid
                INTEGER,
            optixAisState
                INTEGER
        }

    -- 1.3.6.1.4.1.2011.2.25.4.30.12.1.1.1.1
    optixAlmEid OBJECT-TYPE
        SYNTAX INTEGER
        {
            none(0),
            rlos(1),
            roof(5),
            rlof(8),
            b1exc(12),
            msais(33),
            msrdi(34),
            b2exc(35),
            b2sd(36),
            aulop(42),
            b3sd(70),
            b3exc(71),
            auais(72),
            hpuneq(75),
            hptim(76),
            hpslm(77),
            hplom(81),
            j0mm(87),
            lpuneq(90),
            lptim(91),
            lpslm(92),
            talos(107),
            plos(134),
            tcltc(160),
            tcuneq(161),
            tcincais(162),
            tctim(165),
            b1sd(175),
            bipsd(182),
            bipexc(183),
            linkerr(261),
            lpslmvc12(63594),
            lptimvc12(63596),
            lpuneqvc12(63598)
        }
        MAX-ACCESS not-accessible
        STATUS current
        DESCRIPTION
            "This object indicates the alarm EID. 0: none, 1: rlos, 5: roof, 8: rlof, 12: b1exc, 33: msais, 34: msrdi, 35: b2exc, 36: b2sd, 42: aulop, 70: b3sd, 71: b3exc, 72: auais, 75: hpuneq, 76: hptim, 77: hpslm, 81: hplom, 87: j0mm, 90: lpuneq, 91: lptim, 92: lpslm, 107: talos, 134: plos, 160: tcltc, 161: tcuneq, 162: tcincais, 165: tctim, 175: b1sd, 182: bipsd, 183: bipexc, 261: linkerr, 63594: lpslmvc12, 63596: lptimvc12, 63598: lpuneqvc12"
        ::= { optixNeAlmAisEntry 1 }

    -- 1.3.6.1.4.1.2011.2.25.4.30.12.1.1.1.2
    optixAisState OBJECT-TYPE
        SYNTAX INTEGER
        {
            enable(1),
            disable(0)
        }
        MAX-ACCESS read-write
        STATUS current
        DESCRIPTION
            "This object indicates the enable status of AIS. 0: disable, 1: enable"
        ::= { optixNeAlmAisEntry 2 }

END
