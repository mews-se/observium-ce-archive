-- OPTIX-ALM-CFG-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-ALM-CFG-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        AlarmEventType,ObjType
            FROM OPTIX-GLOBAL-TC-MIB
        RowStatus
            FROM SNMPv2-TC
        ;

    optixAlmCfgManage MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB specifies the alarm configuration"
        REVISION "201204170000Z"
        DESCRIPTION
            "The initial revision of this MIB module."
        REVISION "201204170000Z"
        DESCRIPTION
            "The initial revision of this MIB module."
        ::={ optixProvisionEqpt 1 }

    -- 1.3.6.1.4.1.2011.2.25.4.30.1.1
    optixAlmMng OBJECT IDENTIFIER ::= { optixAlmCfgManage 1 }

    -- 1.3.6.1.4.1.2011.2.25.4.30.1.1.1
    optixAlmInhistate OBJECT-TYPE
        SYNTAX INTEGER
        {
            disable(0),
            enable(1)
        }
        MAX-ACCESS read-write
        STATUS current
        DESCRIPTION
            "This object indicates theenable status of suppressing inter-board alarms. 0: disable, 1: enable"
        ::= { optixAlmMng 1 }

    -- 1.3.6.1.4.1.2011.2.25.4.30.1.1.2
    optixAlmLongMngTable OBJECT-TYPE
        SYNTAX SEQUENCE OF OptixAlmLongMngEntry
        MAX-ACCESS not-accessible
        STATUS current
        DESCRIPTION
            "This table describeslong-parameter alarm management."
        ::= { optixAlmMng 2 }

    -- 1.3.6.1.4.1.2011.2.25.4.30.1.1.2.1
    optixAlmLongMngEntry OBJECT-TYPE
        SYNTAX OptixAlmLongMngEntry
        MAX-ACCESS not-accessible
        STATUS current
        DESCRIPTION
            "Thisentry describeslong-parameter alarm management."
        INDEX{ optixAlmIdIndex,optixAlmobjtype,optixAlmobjpara }
        ::= { optixAlmLongMngTable 1 }

    OptixAlmLongMngEntry ::=
        SEQUENCE {
            optixAlmIdIndex
                Unsigned32,
            optixAlmobjtype
                Unsigned32,
            optixAlmobjpara
                OCTET STRING,
            optixAlmLevel
                INTEGER,
            optixAlmMonState
                INTEGER,
            optixAlmInsertState
                INTEGER,
            optixAlmInsertMothed
                INTEGER
        }

    -- 1.3.6.1.4.1.2011.2.25.4.30.1.1.2.1.1
    optixAlmIdIndex OBJECT-TYPE
        SYNTAX Unsigned32
        MAX-ACCESS not-accessible
        STATUS current
        DESCRIPTION
            "This object indicates the alarm ID defined by Huawei Software System Team. 0: long-parameter alarm"
        ::= { optixAlmLongMngEntry 1 }

    -- 1.3.6.1.4.1.2011.2.25.4.30.1.1.2.1.2
    optixAlmobjtype OBJECT-TYPE
        SYNTAX Unsigned32
        MAX-ACCESS not-accessible
        STATUS current
        DESCRIPTION
            "This object indicates the alarm object type. Alarm severity: 1: critical 2: major 3: minor 4: warning"
        ::= { optixAlmLongMngEntry 2 }

    -- 1.3.6.1.4.1.2011.2.25.4.30.1.1.2.1.3
    optixAlmobjpara OBJECT-TYPE
        SYNTAX OCTET STRING
        MAX-ACCESS not-accessible
        STATUS current
        DESCRIPTION
            "This object indicates the contents of the alarm object parameters."
        ::= { optixAlmLongMngEntry 3 }

    -- 1.3.6.1.4.1.2011.2.25.4.30.1.1.2.1.4
    optixAlmLevel OBJECT-TYPE
        SYNTAX INTEGER
        {
            cr(1),
            mj(2),
            mn(3),
            ig(4),
            nr(5)
        }
        MAX-ACCESS read-write
        STATUS current
        DESCRIPTION
            "This object indicates the alarm severity. Alarm severity: 1: critical, 2: major, 3: minor, 4: warning, 5: not reported"
        ::= { optixAlmLongMngEntry 4 }

    -- 1.3.6.1.4.1.2011.2.25.4.30.1.1.2.1.5
    optixAlmMonState OBJECT-TYPE
        SYNTAX INTEGER
        {
            disable(0),
            enable(1)
        }
        MAX-ACCESS read-write
        STATUS current
        DESCRIPTION
            "This object indicates the alarm monitoring status. 0: disable, 1: enable"
        ::= { optixAlmLongMngEntry 5 }

    -- 1.3.6.1.4.1.2011.2.25.4.30.1.1.2.1.6
    optixAlmInsertState OBJECT-TYPE
        SYNTAX INTEGER
        {
            start(1),
            end(3),
            invalid(255)
        }
        MAX-ACCESS read-write
        STATUS current
        DESCRIPTION
            "This object indicates the alarm insert state. 1: start 3: end 255: invalid"
        ::= { optixAlmLongMngEntry 6 }

    -- 1.3.6.1.4.1.2011.2.25.4.30.1.1.2.1.7
    optixAlmInsertMothed OBJECT-TYPE
        SYNTAX INTEGER
        {
            ne(1),
            bd(2),
            chip(3),
            invalid(255)
        }
        MAX-ACCESS read-write
        STATUS current
        DESCRIPTION
            "This object indicates the alarm insert mothed. 1: ne, 2: bd, 3: chip, 255: invalid"
        ::= { optixAlmLongMngEntry 7 }

    -- 1.3.6.1.4.1.2011.2.25.4.30.1.1.3
    optixAlmInverseStateTable OBJECT-TYPE
        SYNTAX SEQUENCE OF OptixAlmInverseStateEntry
        MAX-ACCESS not-accessible
        STATUS current
        DESCRIPTION
            "This table describes Alm Inverse State"
        ::= { optixAlmMng 3 }

    -- 1.3.6.1.4.1.2011.2.25.4.30.1.1.3.1
    optixAlmInverseStateEntry OBJECT-TYPE
        SYNTAX OptixAlmInverseStateEntry
        MAX-ACCESS not-accessible
        STATUS current
        DESCRIPTION
            "This&nbsp;entry describes Alm Inverse State"
        INDEX{ optixInverseAlmIdIndex,optixInverseAlmobjtype,optixInverseAlmobjpara }
        ::= { optixAlmInverseStateTable 1 }

    OptixAlmInverseStateEntry ::=
        SEQUENCE {
            optixInverseAlmIdIndex
                Unsigned32,
            optixInverseAlmobjtype
                Unsigned32,
            optixInverseAlmobjpara
                OCTET STRING,
            optixAlmInverseState
                INTEGER
        }

    -- 1.3.6.1.4.1.2011.2.25.4.30.1.1.3.1.1
    optixInverseAlmIdIndex OBJECT-TYPE
        SYNTAX Unsigned32
        MAX-ACCESS not-accessible
        STATUS current
        DESCRIPTION
            "This object indicates the alarm ID."
        ::= { optixAlmInverseStateEntry 1 }

    -- 1.3.6.1.4.1.2011.2.25.4.30.1.1.3.1.2
    optixInverseAlmobjtype OBJECT-TYPE
        SYNTAX Unsigned32
        MAX-ACCESS not-accessible
        STATUS current
        DESCRIPTION
            "This object indicates the alarm object type."
        ::= { optixAlmInverseStateEntry 2 }

    -- 1.3.6.1.4.1.2011.2.25.4.30.1.1.3.1.3
    optixInverseAlmobjpara OBJECT-TYPE
        SYNTAX OCTET STRING
        MAX-ACCESS not-accessible
        STATUS current
        DESCRIPTION
            "This object indicates the contents of the alarm object parameters."
        ::= { optixAlmInverseStateEntry 3 }

    -- 1.3.6.1.4.1.2011.2.25.4.30.1.1.3.1.4
    optixAlmInverseState OBJECT-TYPE
        SYNTAX INTEGER
        {
            disable(0),
            enable(1)
        }
        MAX-ACCESS read-write
        STATUS current
        DESCRIPTION
            "This object indicates the enablestatus of alarm inversion. 0: disable, 1: enable"
        ::= { optixAlmInverseStateEntry 4 }

    -- 1.3.6.1.4.1.2011.2.25.4.30.1.1.4
    optixAlmInhipairTable OBJECT-TYPE
        SYNTAX SEQUENCE OF OptixAlmInhipairEntry
        MAX-ACCESS not-accessible
        STATUS current
        DESCRIPTION
            "This table describes inhipair"
        ::= { optixAlmMng 4 }

    -- 1.3.6.1.4.1.2011.2.25.4.30.1.1.4.1
    optixAlmInhipairEntry OBJECT-TYPE
        SYNTAX OptixAlmInhipairEntry
        MAX-ACCESS not-accessible
        STATUS current
        DESCRIPTION
            "This entry describes inhipair"
        INDEX{ optixAlmInhipairObjType,optixAlmInhipairEid,optixAlmInhipairObjTypeED,optixAlmInhipairEidED }
        ::= { optixAlmInhipairTable 1 }

    OptixAlmInhipairEntry ::=
        SEQUENCE {
            optixAlmInhipairObjType
                ObjType,
            optixAlmInhipairEid
                AlarmEventType,
            optixAlmInhipairObjTypeED
                ObjType,
            optixAlmInhipairEidED
                AlarmEventType,
            optixAlmInhipairRowStatus
                RowStatus
        }

    -- 1.3.6.1.4.1.2011.2.25.4.30.1.1.4.1.1
    optixAlmInhipairObjType OBJECT-TYPE
        SYNTAX ObjType
        MAX-ACCESS read-only
        STATUS current
        DESCRIPTION
            "This object indicates an alarm object."
        ::= { optixAlmInhipairEntry 1 }

    -- 1.3.6.1.4.1.2011.2.25.4.30.1.1.4.1.2
    optixAlmInhipairEid OBJECT-TYPE
        SYNTAX AlarmEventType
        MAX-ACCESS read-only
        STATUS current
        DESCRIPTION
            "This object indicates an alarm ID."
        ::= { optixAlmInhipairEntry 2 }

    -- 1.3.6.1.4.1.2011.2.25.4.30.1.1.4.1.3
    optixAlmInhipairObjTypeED OBJECT-TYPE
        SYNTAX ObjType
        MAX-ACCESS read-only
        STATUS current
        DESCRIPTION
            "This object indicates a suppressed alarm object."
        ::= { optixAlmInhipairEntry 3 }

    -- 1.3.6.1.4.1.2011.2.25.4.30.1.1.4.1.4
    optixAlmInhipairEidED OBJECT-TYPE
        SYNTAX AlarmEventType
        MAX-ACCESS read-only
        STATUS current
        DESCRIPTION
            "This object indicates the ID of a suppressed alarm."
        ::= { optixAlmInhipairEntry 4 }

    -- 1.3.6.1.4.1.2011.2.25.4.30.1.1.4.1.255
    optixAlmInhipairRowStatus OBJECT-TYPE
        SYNTAX RowStatus
        MAX-ACCESS read-create
        STATUS current
        DESCRIPTION
            "This object indicates row status."
        ::= { optixAlmInhipairEntry 255 }

END
