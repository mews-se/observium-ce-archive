-- OPTIX-GLOBAL-SM-TRAPS-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-SM-TRAPS-MIB DEFINITIONS ::= BEGIN
    IMPORTS
        optixCommonGlobal
            FROM OPTIX-OID-MIB
        DisplayString,TEXTUAL-CONVENTION
            FROM SNMPv2-TC
        Unsigned32,MODULE-IDENTITY,OBJECT-TYPE,NOTIFICATION-TYPE
            FROM SNMPv2-SMI
        ;

    optixGlobalSMTrap MODULE-IDENTITY
        LAST-UPDATED "201607041630Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Information about SM TRAP nodes"
        REVISION "201607041630Z"
        DESCRIPTION
            "The initial version"
        ::={ optixCommonGlobal 5 }

    QuitType ::= TEXTUAL-CONVENTION
        STATUS current
        DESCRIPTION
            "QuitType"
        SYNTAX INTEGER
        {
            cmdQuit(1),
            forceQuit(2),
            agingQuit(3),
            autoQuit(4),
            logtimeQuit(5),
            encrykeychangeQuit(6)
        }

    IllegalType ::= TEXTUAL-CONVENTION
        STATUS current
        DESCRIPTION
            "IllegalType"
        SYNTAX INTEGER
        {
            pass(1),
            aging(2),
            disable(3),
            priority(4)
        }

    AddrType ::= TEXTUAL-CONVENTION
        STATUS current
        DESCRIPTION
            "AddrType"
        SYNTAX INTEGER
        {
            ipv4(1),
            neid(2),
            nsap(3),
            ipv6(4)
        }

    TeiType ::= TEXTUAL-CONVENTION
        STATUS current
        DESCRIPTION
            "TeiType"
        SYNTAX INTEGER
        {
            unlog(0),
            ems(1),
            lct(2),
            tm(3),
            tl1(4),
            snmp(5),
            web(6),
            lcd(7),
            toolkit(8),
            shell(9),
            ftp(10),
            ssh(11),
            usb(12),
            sdn(13)
        }

    -- 1.3.6.1.4.1.2011.2.25.3.40.5.1
    optixTrapsSMCommon OBJECT IDENTIFIER ::= { optixGlobalSMTrap 1 }

    -- 1.3.6.1.4.1.2011.2.25.3.40.5.1.1
    rptEvtDstName OBJECT-TYPE
        SYNTAX DisplayString
        MAX-ACCESS accessible-for-notify
        STATUS current
        DESCRIPTION
            "rptEvtDstName"
        ::= { optixTrapsSMCommon 1 }

    -- 1.3.6.1.4.1.2011.2.25.3.40.5.1.2
    rptEvtDstIP OBJECT-TYPE
        SYNTAX OCTET STRING
        MAX-ACCESS accessible-for-notify
        STATUS current
        DESCRIPTION
            "rptEvtDstIP"
        ::= { optixTrapsSMCommon 2 }

    -- 1.3.6.1.4.1.2011.2.25.3.40.5.1.3
    rptEvtSrcName OBJECT-TYPE
        SYNTAX DisplayString
        MAX-ACCESS accessible-for-notify
        STATUS current
        DESCRIPTION
            "rptEvtSrcName"
        ::= { optixTrapsSMCommon 3 }

    -- 1.3.6.1.4.1.2011.2.25.3.40.5.1.4
    rptEvtSrcIP OBJECT-TYPE
        SYNTAX OCTET STRING
        MAX-ACCESS accessible-for-notify
        STATUS current
        DESCRIPTION
            "rptEvtSrcIP"
        ::= { optixTrapsSMCommon 4 }

    -- 1.3.6.1.4.1.2011.2.25.3.40.5.1.5
    rptEvtQuitType OBJECT-TYPE
        SYNTAX QuitType
        MAX-ACCESS accessible-for-notify
        STATUS current
        DESCRIPTION
            "rptEvtQuitType"
        ::= { optixTrapsSMCommon 5 }

    -- 1.3.6.1.4.1.2011.2.25.3.40.5.1.6
    rptEvtUserID OBJECT-TYPE
        SYNTAX Unsigned32
        MAX-ACCESS accessible-for-notify
        STATUS current
        DESCRIPTION
            "rptEvtUserID"
        ::= { optixTrapsSMCommon 6 }

    -- 1.3.6.1.4.1.2011.2.25.3.40.5.1.7
    rptEvtIllegalType OBJECT-TYPE
        SYNTAX IllegalType
        MAX-ACCESS accessible-for-notify
        STATUS current
        DESCRIPTION
            "rptEvtIllegalType"
        ::= { optixTrapsSMCommon 7 }

    -- 1.3.6.1.4.1.2011.2.25.3.40.5.1.8
    rptEvtUserName OBJECT-TYPE
        SYNTAX OCTET STRING (SIZE(4..16))
        MAX-ACCESS accessible-for-notify
        STATUS current
        DESCRIPTION
            "rptEvtUserName"
        ::= { optixTrapsSMCommon 8 }

    -- 1.3.6.1.4.1.2011.2.25.3.40.5.1.9
    rptEvtTeiType OBJECT-TYPE
        SYNTAX TeiType
        MAX-ACCESS accessible-for-notify
        STATUS current
        DESCRIPTION
            "rptEvtTeiType"
        ::= { optixTrapsSMCommon 9 }

    -- 1.3.6.1.4.1.2011.2.25.3.40.5.1.10
    rptEvtAddrType OBJECT-TYPE
        SYNTAX AddrType
        MAX-ACCESS accessible-for-notify
        STATUS current
        DESCRIPTION
            "rptEvtAddrType"
        ::= { optixTrapsSMCommon 10 }

    -- 1.3.6.1.4.1.2011.2.25.3.40.5.1.11
    rptEvtLoginAddr OBJECT-TYPE
        SYNTAX Unsigned32
        MAX-ACCESS accessible-for-notify
        STATUS current
        DESCRIPTION
            "rptEvtLoginAddr"
        ::= { optixTrapsSMCommon 11 }

    -- 1.3.6.1.4.1.2011.2.25.3.40.5.1.12
    rptEvtOverdueDays OBJECT-TYPE
        SYNTAX Unsigned32
        MAX-ACCESS accessible-for-notify
        STATUS current
        DESCRIPTION
            "rptEvtOverdueDays"
        ::= { optixTrapsSMCommon 12 }

    -- 1.3.6.1.4.1.2011.2.25.3.40.5.2
    optixTrapsSM OBJECT IDENTIFIER ::= { optixGlobalSMTrap 2 }

    -- 1.3.6.1.4.1.2011.2.25.3.40.5.2.1
    smLogout NOTIFICATION-TYPE
        STATUS current
        DESCRIPTION
            "Trap of SM: User logout."
        ::= { optixTrapsSM 1 }

    -- 1.3.6.1.4.1.2011.2.25.3.40.5.2.2
    smUploadSeculog NOTIFICATION-TYPE
        STATUS current
        DESCRIPTION
            "Trap of SM: Seculog need upload."
        ::= { optixTrapsSM 2 }

    -- 1.3.6.1.4.1.2011.2.25.3.40.5.2.3
    smCircleSeculog NOTIFICATION-TYPE
        STATUS current
        DESCRIPTION
            "Trap of SM: Seculog already circle."
        ::= { optixTrapsSM 3 }

    -- 1.3.6.1.4.1.2011.2.25.3.40.5.2.4
    smAccessIllegal NOTIFICATION-TYPE
        STATUS current
        DESCRIPTION
            "Trap of SM: Illegal access."
        ::= { optixTrapsSM 4 }

    -- 1.3.6.1.4.1.2011.2.25.3.40.5.2.5
    smForceout NOTIFICATION-TYPE
        STATUS current
        DESCRIPTION
            "Trap of SM: User force logout."
        ::= { optixTrapsSM 5 }

    -- 1.3.6.1.4.1.2011.2.25.3.40.5.2.6
    smUploadOplog NOTIFICATION-TYPE
        STATUS current
        DESCRIPTION
            "Trap of SM: Oplog need upload."
        ::= { optixTrapsSM 6 }

    -- 1.3.6.1.4.1.2011.2.25.3.40.5.2.7
    smCircleOplog NOTIFICATION-TYPE
        STATUS current
        DESCRIPTION
            "Trap of SM: Oplog already circle."
        ::= { optixTrapsSM 7 }

    -- 1.3.6.1.4.1.2011.2.25.3.40.5.2.8
    smLogin NOTIFICATION-TYPE
        STATUS current
        DESCRIPTION
            "Trap of SM: User login."
        ::= { optixTrapsSM 8 }

    -- 1.3.6.1.4.1.2011.2.25.3.40.5.2.9
    smPwdOverdue NOTIFICATION-TYPE
        STATUS current
        DESCRIPTION
            "Trap of SM: Password will overdue."
        ::= { optixTrapsSM 9 }

END
