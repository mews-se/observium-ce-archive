-- OPTIX-EFMOAM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-EFMOAM-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        optixPortId
            FROM OPTIX-PORT-MANAGE-MIB
        ;

    optixEfmoam MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the 802.3ah configuration information of device"
        REVISION "201204200000Z"
        DESCRIPTION
            "The initial revision of this MIB module1."
        ::={ optixProvisionPtn 17 }

    -- 1.3.6.1.4.1.2011.2.25.4.50.17.1
    optixEfmoamGroup OBJECT IDENTIFIER ::= { optixEfmoam 1 }

    -- 1.3.6.1.4.1.2011.2.25.4.50.17.1.1
    optixEfmoamTable OBJECT-TYPE
        SYNTAX SEQUENCE OF OptixEfmoamEntry
        MAX-ACCESS not-accessible
        STATUS current
        DESCRIPTION
            "This table describes the basic configuration information of the Layer 2 802.3ah protocol."
        ::= { optixEfmoamGroup 1 }

    -- 1.3.6.1.4.1.2011.2.25.4.50.17.1.1.1
    optixEfmoamEntry OBJECT-TYPE
        SYNTAX OptixEfmoamEntry
        MAX-ACCESS not-accessible
        STATUS current
        DESCRIPTION
            "This entry describes the basic configuration information of the Layer 2 802.3ah protocol."
        INDEX{ optixLogBoardId,optixLogSubCardId,optixPortId }
        ::= { optixEfmoamTable 1 }

    OptixEfmoamEntry ::=
        SEQUENCE {
            optixEfmoamEnable
                INTEGER,
            optixEfmoamMode
                INTEGER,
            optixEfmoamRsplbEn
                INTEGER,
            optixEfmoamLinkevtEn
                INTEGER,
            optixEfmoamRMode
                INTEGER,
            optixEfmoamMaxPduSize
                Unsigned32,
            optixEfmoamLoopStatus
                INTEGER,
            optixEfmoamSendStatus
                INTEGER,
            optixEfmoamReceiveStatus
                INTEGER,
            optixEfmoamLocalDiscoverState
                INTEGER,
            optixEfmoamRemoteDiscoverState
                INTEGER,
            optixEfmoamErrFrmWin
                Unsigned32,
            optixEfmoamErrFrmThr
                Unsigned32,
            optixEfmoamErrFrmPerWin
                Unsigned32,
            optixEfmoamErrFrmPerThr
                Unsigned32,
            optixEfmoamErrFrmSecWin
                Unsigned32,
            optixEfmoamErrFrmSecThr
                Unsigned32,
            optixEfmoamErrFrmSymWin
                Unsigned32,
            optixEfmoamErrFrmSymThr
                OCTET STRING,
            optixEfmoamUnidirectional
                INTEGER,
            optixEfmoamRmtlbEn
                INTEGER,
            optixEfmoamRlinkevtEn
                INTEGER,
            optixEfmoamRmtRsplbEn
                INTEGER
        }

    -- 1.3.6.1.4.1.2011.2.25.4.50.17.1.1.1.1
    optixEfmoamEnable OBJECT-TYPE
        SYNTAX INTEGER
        {
            disable(0),
            enable(1)
        }
        MAX-ACCESS read-write
        STATUS current
        DESCRIPTION
            "This object indicates the enable status of the 802.3ah protocol. 0: disable, 1: enable"
        ::= { optixEfmoamEntry 1 }

    -- 1.3.6.1.4.1.2011.2.25.4.50.17.1.1.1.2
    optixEfmoamMode OBJECT-TYPE
        SYNTAX INTEGER
        {
            passive(1),
            active(2)
        }
        MAX-ACCESS read-write
        STATUS current
        DESCRIPTION
            "This object indicates the OAM modeof the 802.3ah protocol. 1: passive, 2: active"
        ::= { optixEfmoamEntry 2 }

    -- 1.3.6.1.4.1.2011.2.25.4.50.17.1.1.1.3
    optixEfmoamRsplbEn OBJECT-TYPE
        SYNTAX INTEGER
        {
            disable(0),
            enable(1)
        }
        MAX-ACCESS read-write
        STATUS current
        DESCRIPTION
            "This object indicates the capability of the 802.3ah protocol to respond to the remote loopback. 0: disable, 1: enable"
        ::= { optixEfmoamEntry 3 }

    -- 1.3.6.1.4.1.2011.2.25.4.50.17.1.1.1.4
    optixEfmoamLinkevtEn OBJECT-TYPE
        SYNTAX INTEGER
        {
            disable(0),
            enable(1)
        }
        MAX-ACCESS read-write
        STATUS current
        DESCRIPTION
            "This object indicates whether link event reporting is enabled for the 802.3ah protocol. 0: disable, 1: enable"
        ::= { optixEfmoamEntry 4 }

    -- 1.3.6.1.4.1.2011.2.25.4.50.17.1.1.1.5
    optixEfmoamRMode OBJECT-TYPE
        SYNTAX INTEGER
        {
            passive(1),
            active(2)
        }
        MAX-ACCESS read-only
        STATUS current
        DESCRIPTION
            "This object indicates the unidirectional operability of the 802.3ah protocol. 1: passive, 2: active"
        ::= { optixEfmoamEntry 5 }

    -- 1.3.6.1.4.1.2011.2.25.4.50.17.1.1.1.6
    optixEfmoamMaxPduSize OBJECT-TYPE
        SYNTAX Unsigned32
        MAX-ACCESS read-only
        STATUS current
        DESCRIPTION
            "This object indicates the maximum OAM packet length of the 802.3ah protocol. Value range: 0 to 65535."
        ::= { optixEfmoamEntry 6 }

    -- 1.3.6.1.4.1.2011.2.25.4.50.17.1.1.1.7
    optixEfmoamLoopStatus OBJECT-TYPE
        SYNTAX INTEGER
        {
            notLb(0),
            lclInitiate(1),
            lclRsp(2)
        }
        MAX-ACCESS read-only
        STATUS current
        DESCRIPTION
            "This object indicates the loopback status of the 802.3ah protocol. 0: notLb, 1: lclInitiate, 2: lclRsp"
        ::= { optixEfmoamEntry 7 }

    -- 1.3.6.1.4.1.2011.2.25.4.50.17.1.1.1.8
    optixEfmoamSendStatus OBJECT-TYPE
        SYNTAX INTEGER
        {
            fwd(1),
            lb(2),
            discard(3)
        }
        MAX-ACCESS read-only
        STATUS current
        DESCRIPTION
            "This object indicates the transmit status of the 802.3ah protocol. 1: fwd, 2: lb, 3: discard"
        ::= { optixEfmoamEntry 8 }

    -- 1.3.6.1.4.1.2011.2.25.4.50.17.1.1.1.9
    optixEfmoamReceiveStatus OBJECT-TYPE
        SYNTAX INTEGER
        {
            fwd(1),
            lb(2),
            discard(3)
        }
        MAX-ACCESS read-only
        STATUS current
        DESCRIPTION
            "This object indicates the receive status of the 802.3ah protocol. 1: fwd, 2: lb, 3: discard"
        ::= { optixEfmoamEntry 9 }

    -- 1.3.6.1.4.1.2011.2.25.4.50.17.1.1.1.10
    optixEfmoamLocalDiscoverState OBJECT-TYPE
        SYNTAX INTEGER
        {
            fault(1),
            activeSendLocal(2),
            passiveWait(3),
            sendLocalRemote(4),
            sendLocalRemoteOk(5),
            sendAny(6)
        }
        MAX-ACCESS read-only
        STATUS current
        DESCRIPTION
            "This object indicates the local discovery status of the 802.3ah protocol. 1: fault, 2: activeSendLocal, 3: passiveWait, 4: sendLocalRemote, 5: sendLocalRemoteOk, 6: sendAny"
        ::= { optixEfmoamEntry 10 }

    -- 1.3.6.1.4.1.2011.2.25.4.50.17.1.1.1.11
    optixEfmoamRemoteDiscoverState OBJECT-TYPE
        SYNTAX INTEGER
        {
            unsatified(0),
            unfinished(1),
            finished(2)
        }
        MAX-ACCESS read-only
        STATUS current
        DESCRIPTION
            "This object indicates the remote discovery status of the 802.3ah protocol. 0: unsatified, 1: unfinished, 2: finished"
        ::= { optixEfmoamEntry 11 }

    -- 1.3.6.1.4.1.2011.2.25.4.50.17.1.1.1.12
    optixEfmoamErrFrmWin OBJECT-TYPE
        SYNTAX Unsigned32
        MAX-ACCESS read-write
        STATUS current
        DESCRIPTION
            "This object indicates the timewindow for monitoring error frames for the 802.3ah protocol. Value range: 1000 to 60000 (unit: ms). The default value is 1000 and the step length is 100."
        ::= { optixEfmoamEntry 12 }

    -- 1.3.6.1.4.1.2011.2.25.4.50.17.1.1.1.13
    optixEfmoamErrFrmThr OBJECT-TYPE
        SYNTAX Unsigned32
        MAX-ACCESS read-write
        STATUS current
        DESCRIPTION
            "This object indicates the threshold of monitored error frames for the 802.3ah protocol. Value range: 1 to 0xffffffff (unit: frame). The default value is 1 and the step length is 1."
        ::= { optixEfmoamEntry 13 }

    -- 1.3.6.1.4.1.2011.2.25.4.50.17.1.1.1.14
    optixEfmoamErrFrmPerWin OBJECT-TYPE
        SYNTAX Unsigned32
        MAX-ACCESS read-write
        STATUS current
        DESCRIPTION
            "This object indicates the monitoring window for the periodically monitored error frames forthe 802.3ah protocol. Value range: 0 to 0xffffffff."
        ::= { optixEfmoamEntry 14 }

    -- 1.3.6.1.4.1.2011.2.25.4.50.17.1.1.1.15
    optixEfmoamErrFrmPerThr OBJECT-TYPE
        SYNTAX Unsigned32
        MAX-ACCESS read-write
        STATUS current
        DESCRIPTION
            "This object indicates the threshold of periodically monitored error frames for the 802.3ah protocol. Value range: 0 to 0xffffffff."
        ::= { optixEfmoamEntry 15 }

    -- 1.3.6.1.4.1.2011.2.25.4.50.17.1.1.1.16
    optixEfmoamErrFrmSecWin OBJECT-TYPE
        SYNTAX Unsigned32
        MAX-ACCESS read-write
        STATUS current
        DESCRIPTION
            "This object indicates the time range of monitored error frame seconds for the 802.3ah protocol. Value range: 10 to 900 (unit: s). The default value is 60."
        ::= { optixEfmoamEntry 16 }

    -- 1.3.6.1.4.1.2011.2.25.4.50.17.1.1.1.17
    optixEfmoamErrFrmSecThr OBJECT-TYPE
        SYNTAX Unsigned32
        MAX-ACCESS read-write
        STATUS current
        DESCRIPTION
            "This object indicates the threshold of monitored error frame seconds for the 802.3ah protocol. Value range: 1 to 65535 (unit: s)."
        ::= { optixEfmoamEntry 17 }

    -- 1.3.6.1.4.1.2011.2.25.4.50.17.1.1.1.18
    optixEfmoamErrFrmSymWin OBJECT-TYPE
        SYNTAX Unsigned32
        MAX-ACCESS read-write
        STATUS current
        DESCRIPTION
            "This object indicates the monitoring window for monitored error frame signals for the 802.3ah protocol. Value range: 1 to 60 (unit: s)."
        ::= { optixEfmoamEntry 18 }

    -- 1.3.6.1.4.1.2011.2.25.4.50.17.1.1.1.19
    optixEfmoamErrFrmSymThr OBJECT-TYPE
        SYNTAX OCTET STRING (SIZE(0..24))
        MAX-ACCESS read-write
        STATUS current
        DESCRIPTION
            "This object indicates the threshold of monitored error frame signals for the 802.3ah protocol. Value range: 1 to 0xffffffffffffffff. 64-bit data is in string format."
        ::= { optixEfmoamEntry 19 }

    -- 1.3.6.1.4.1.2011.2.25.4.50.17.1.1.1.20
    optixEfmoamUnidirectional OBJECT-TYPE
        SYNTAX INTEGER
        {
            disable(0),
            enable(1)
        }
        MAX-ACCESS read-only
        STATUS current
        DESCRIPTION
            "This object indicates the unidirectional operability of the 802.3ah protocol. 0: disable, 1: enable"
        ::= { optixEfmoamEntry 20 }

    -- 1.3.6.1.4.1.2011.2.25.4.50.17.1.1.1.21
    optixEfmoamRmtlbEn OBJECT-TYPE
        SYNTAX INTEGER
        {
            disable(0),
            enable(1)
        }
        MAX-ACCESS read-write
        STATUS current
        DESCRIPTION
            "This object indicates the remote loop back support of the 802.3ah protocol. 0: disable, 1: enable"
        ::= { optixEfmoamEntry 21 }

    -- 1.3.6.1.4.1.2011.2.25.4.50.17.1.1.1.22
    optixEfmoamRlinkevtEn OBJECT-TYPE
        SYNTAX INTEGER
        {
            disable(0),
            enable(1)
        }
        MAX-ACCESS read-only
        STATUS current
        DESCRIPTION
            "This object indicates the link event enable of the 802.3ah protocol. 0: disable, 1: enable"
        ::= { optixEfmoamEntry 22 }

    -- 1.3.6.1.4.1.2011.2.25.4.50.17.1.1.1.23
    optixEfmoamRmtRsplbEn OBJECT-TYPE
        SYNTAX INTEGER
        {
            disable(0),
            enable(1)
        }
        MAX-ACCESS read-only
        STATUS current
        DESCRIPTION
            "This object indicates the remote capability of the 802.3ah protocol to respond to the loopback. 0: disable, 1: enable"
        ::= { optixEfmoamEntry 23 }

END
