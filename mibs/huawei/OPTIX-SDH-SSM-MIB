-- OPTIX-SDH-SSM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-SSM-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        optixLogBoardId
            FROM OPTIX-BOARD-MANAGE-MIB
        ;

    optixSdhSsm MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations ofSSM protocolmanagement."
        REVISION "201204200000Z"
        DESCRIPTION
            "The initial revision of this MIB module1."
        ::={ optixProvisionSdh 47 }

    -- 1.3.6.1.4.1.2011.2.25.4.10.47.1
    optixSdhSsmGroup OBJECT IDENTIFIER ::= { optixSdhSsm 1 }

    -- 1.3.6.1.4.1.2011.2.25.4.10.47.1.1
    optixSsmS1ModeTable OBJECT-TYPE
        SYNTAX SEQUENCE OF OptixSsmS1ModeEntry
        MAX-ACCESS not-accessible
        STATUS current
        DESCRIPTION
            "This table describes the basic configurations of SSM protocol S1 mode management."
        ::= { optixSdhSsmGroup 1 }

    -- 1.3.6.1.4.1.2011.2.25.4.10.47.1.1.1
    optixSsmS1ModeEntry OBJECT-TYPE
        SYNTAX OptixSsmS1ModeEntry
        MAX-ACCESS not-accessible
        STATUS current
        DESCRIPTION
            "Thisentry describes the basic configurations of SSM protocol S1 mode management."
        INDEX{ optixLogBoardId }
        ::= { optixSsmS1ModeTable 1 }

    OptixSsmS1ModeEntry ::=
        SEQUENCE {
            optixSsmS1Mode
                INTEGER,
            optixSsmSynClkIdOut
                OCTET STRING
        }

    -- 1.3.6.1.4.1.2011.2.25.4.10.47.1.1.1.1
    optixSsmS1Mode OBJECT-TYPE
        SYNTAX INTEGER
        {
            disables1(0),
            expands1(1),
            standards1(2),
            asonssm(3)
        }
        MAX-ACCESS read-write
        STATUS current
        DESCRIPTION
            "This object indicates the working mode of the SSM protocol. 0: disables1, 1: expands1, 2: standards1, 3: asonssm"
        ::= { optixSsmS1ModeEntry 1 }

    -- 1.3.6.1.4.1.2011.2.25.4.10.47.1.1.1.2
    optixSsmSynClkIdOut OBJECT-TYPE
        SYNTAX OCTET STRING (SIZE(0..256))
        MAX-ACCESS read-only
        STATUS current
        DESCRIPTION
            "This object indicates that the output of SSM protocol clock ID cannot be disabled."
        ::= { optixSsmS1ModeEntry 2 }

    -- 1.3.6.1.4.1.2011.2.25.4.10.47.1.2
    optixS1ExportModeTable OBJECT-TYPE
        SYNTAX SEQUENCE OF OptixS1ExportModeEntry
        MAX-ACCESS not-accessible
        STATUS current
        DESCRIPTION
            "This table describes the basic configurations ofenabling the S1 mode."
        ::= { optixSdhSsmGroup 2 }

    -- 1.3.6.1.4.1.2011.2.25.4.10.47.1.2.1
    optixS1ExportModeEntry OBJECT-TYPE
        SYNTAX OptixS1ExportModeEntry
        MAX-ACCESS not-accessible
        STATUS current
        DESCRIPTION
            "Thisentry describes the basic configurations of enabling the S1 mode."
        INDEX{ optixLogBoardId,optixS1ExportMode }
        ::= { optixS1ExportModeTable 1 }

    OptixS1ExportModeEntry ::=
        SEQUENCE {
            optixS1ExportMode
                Unsigned32,
            optixSsmEnableFlag
                INTEGER,
            optixSsmSynClkIdMode
                INTEGER
        }

    -- 1.3.6.1.4.1.2011.2.25.4.10.47.1.2.1.1
    optixS1ExportMode OBJECT-TYPE
        SYNTAX Unsigned32
        MAX-ACCESS not-accessible
        STATUS current
        DESCRIPTION
            "This object indicates the clock source code of the SSM protocol. For example, 0x01ff0001 or 06ff0006."
        ::= { optixS1ExportModeEntry 1 }

    -- 1.3.6.1.4.1.2011.2.25.4.10.47.1.2.1.2
    optixSsmEnableFlag OBJECT-TYPE
        SYNTAX INTEGER
        {
            permit(1),
            forbid(0)
        }
        MAX-ACCESS read-write
        STATUS current
        DESCRIPTION
            "This object indicates the enable status of the SSM protocol. 1: permit, 0: forbid"
        ::= { optixS1ExportModeEntry 2 }

    -- 1.3.6.1.4.1.2011.2.25.4.10.47.1.2.1.3
    optixSsmSynClkIdMode OBJECT-TYPE
        SYNTAX INTEGER
        {
            permit(1),
            forbid(0)
        }
        MAX-ACCESS read-write
        STATUS current
        DESCRIPTION
            "This object indicates that the output of SSM protocol clock ID cannot be disabled. 1: permit, 0: forbid"
        ::= { optixS1ExportModeEntry 3 }

END
