-- OPTIX-PKT-PTPCLOCK-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-PTPCLOCK-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,IpAddress,NOTIFICATION-TYPE
            FROM SNMPv2-SMI
        optixLogBoardId,optixLogSubCardId
            FROM OPTIX-BOARD-MANAGE-MIB
        optixEthSrvIndex
            FROM OPTIX-L2VPN-MIB
        optixPortId
            FROM OPTIX-PORT-MANAGE-MIB
        ;

    optixPktptpclock MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "this mib describes configuration of 1588 clock mode"
        REVISION "201204200000Z"
        DESCRIPTION
            "The initial revision of this MIB module1."
        ::={ optixProvisionPtn 13 }

    -- 1.3.6.1.4.1.2011.2.25.4.50.13.1
    optixPktPtpClockGroup OBJECT IDENTIFIER ::= { optixPktptpclock 1 }

    -- 1.3.6.1.4.1.2011.2.25.4.50.13.1.1
    optixPktPtpStaticBMCState OBJECT-TYPE
        SYNTAX INTEGER
        {
            disable(0),
            enable(1)
        }
        MAX-ACCESS read-write
        STATUS current
        DESCRIPTION
            "this parameter describes static BMCs enabled status. 0 disable, 1 enable"
        ::= { optixPktPtpClockGroup 1 }

    -- 1.3.6.1.4.1.2011.2.25.4.50.13.1.2
    optixPktPtpMode OBJECT-TYPE
        SYNTAX INTEGER
        {
            oc(1),
            bc(2),
            tc(3),
            tcBc(5),
            tbc(6)
        }
        MAX-ACCESS read-write
        STATUS current
        DESCRIPTION
            "This parameter describes the PTP working mode of an NE. 1: oc; 2: bc; 3: tc; 5: tcBc; 6: tbc"
        ::= { optixPktPtpClockGroup 2 }

    -- 1.3.6.1.4.1.2011.2.25.4.50.13.1.3
    optixPktPtpDomain OBJECT-TYPE
        SYNTAX Unsigned32
        MAX-ACCESS read-write
        STATUS current
        DESCRIPTION
            "this parameter describes the PTP Domain of NE. Value range 0 to 255. The default value is 0."
        ::= { optixPktPtpClockGroup 3 }

    -- 1.3.6.1.4.1.2011.2.25.4.50.13.1.4
    optixPktPtpTimeSrcIdHigh OBJECT-TYPE
        SYNTAX Unsigned32
        MAX-ACCESS read-only
        STATUS current
        DESCRIPTION
            "this parameter describes the PTPs source IDs high part. Clock source ID generation rule The first three bytes are the OUI code. The following four bytes are the NE ID. The last byte is 0x10. For example, if the OUI code is 0X001E10 and the NE ID is 10.1.1.1, the clock source ID is 0X001E100A01010110."
        ::= { optixPktPtpClockGroup 4 }

    -- 1.3.6.1.4.1.2011.2.25.4.50.13.1.5
    optixPktPtpTimeSrcIdLow OBJECT-TYPE
        SYNTAX Unsigned32
        MAX-ACCESS read-only
        STATUS current
        DESCRIPTION
            "this parameter describes the PTPs source IDs low part. Clock source ID generation rule The first three bytes are the OUI code. The following four bytes are the NE ID. The last byte is 0x10. For example, if the OUI code is 0X001E10 and the NE ID is 10.1.1.1, the clock source ID is 0X001E100A01010110."
        ::= { optixPktPtpClockGroup 5 }

    -- 1.3.6.1.4.1.2011.2.25.4.50.13.1.6
    optixPktPtpSrcMode OBJECT-TYPE
        SYNTAX INTEGER
        {
            phyClock(1),
            ptp(2),
            ptpAcrUni(3)
        }
        MAX-ACCESS read-write
        STATUS current
        DESCRIPTION
            "This parameter describes the mode of selecting system frequency sources. 1 Physical clock, 2 PTP, 3 PTP ACR UNI"
        ::= { optixPktPtpClockGroup 6 }

    -- 1.3.6.1.4.1.2011.2.25.4.50.13.1.7
    optixPktPtpSrcTimeYear OBJECT-TYPE
        SYNTAX Unsigned32
        MAX-ACCESS read-write
        STATUS current
        DESCRIPTION
            "this parameter describes the PTPs system year. Value range 2000 to 2099."
        ::= { optixPktPtpClockGroup 7 }

    -- 1.3.6.1.4.1.2011.2.25.4.50.13.1.8
    optixPktPtpSrcTimeMonth OBJECT-TYPE
        SYNTAX Unsigned32
        MAX-ACCESS read-write
        STATUS current
        DESCRIPTION
            "this parameter describes the PTPs system month. Value range 1 to 12."
        ::= { optixPktPtpClockGroup 8 }

    -- 1.3.6.1.4.1.2011.2.25.4.50.13.1.9
    optixPktPtpSrcTimeDay OBJECT-TYPE
        SYNTAX Unsigned32
        MAX-ACCESS read-write
        STATUS current
        DESCRIPTION
            "this parameter describes the PTPs system day. Value range 1 to 31."
        ::= { optixPktPtpClockGroup 9 }

    -- 1.3.6.1.4.1.2011.2.25.4.50.13.1.10
    optixPktPtpSrcTimeHour OBJECT-TYPE
        SYNTAX Unsigned32
        MAX-ACCESS read-write
        STATUS current
        DESCRIPTION
            "this parameter describes the PTPs system hour. Value range 0 to 59."
        ::= { optixPktPtpClockGroup 10 }

    -- 1.3.6.1.4.1.2011.2.25.4.50.13.1.11
    optixPktPtpSrcTimeMinute OBJECT-TYPE
        SYNTAX Unsigned32
        MAX-ACCESS read-write
        STATUS current
        DESCRIPTION
            "this parameter describes the PTPs system minute. Value range 0 to 59."
        ::= { optixPktPtpClockGroup 11 }

    -- 1.3.6.1.4.1.2011.2.25.4.50.13.1.12
    optixPktPtpSrcTimeSecond OBJECT-TYPE
        SYNTAX Unsigned32
        MAX-ACCESS read-write
        STATUS current
        DESCRIPTION
            "this parameter describes the PTPs system second. Value range 0 to 64."
        ::= { optixPktPtpClockGroup 12 }

    -- 1.3.6.1.4.1.2011.2.25.4.50.13.1.13
    optixPktPtpSlaveOnlyMode OBJECT-TYPE
        SYNTAX INTEGER
        {
            slaveOnly(1),
            nonSlaveOnly(2)
        }
        MAX-ACCESS read-write
        STATUS current
        DESCRIPTION
            "this parameter describes the NEs mode of SLAVEONLY. 1 slaveOnly, 2 nonSlaveOnly"
        ::= { optixPktPtpClockGroup 13 }

    -- 1.3.6.1.4.1.2011.2.25.4.50.13.1.14
    optixPktPtpGrandMasterBid OBJECT-TYPE
        SYNTAX Unsigned32
        MAX-ACCESS read-only
        STATUS current
        DESCRIPTION
            "this parameter describes the main clocks board ID that being tailed. Value range 1 to all Fs."
        ::= { optixPktPtpClockGroup 14 }

    -- 1.3.6.1.4.1.2011.2.25.4.50.13.1.15
    optixPktPtpGrandMasterSbid OBJECT-TYPE
        SYNTAX Unsigned32
        MAX-ACCESS read-only
        STATUS current
        DESCRIPTION
            "this parameter describes the main clocks subcard ID that being tailed. Value range 1 to all Fs."
        ::= { optixPktPtpClockGroup 15 }

    -- 1.3.6.1.4.1.2011.2.25.4.50.13.1.16
    optixPktPtpGrandMasterPid OBJECT-TYPE
        SYNTAX Unsigned32
        MAX-ACCESS read-only
        STATUS current
        DESCRIPTION
            "this parameter describes the main clocks port ID that being tailed. Value range 1 to all Fs."
        ::= { optixPktPtpClockGroup 16 }

    -- 1.3.6.1.4.1.2011.2.25.4.50.13.1.17
    optixPktPtpGrandMasterGrandmasterID1 OBJECT-TYPE
        SYNTAX Unsigned32
        MAX-ACCESS read-only
        STATUS current
        DESCRIPTION
            "this parameter describes the main clocks low randmaster ID1. Clock source ID generation rule The first three bytes are the OUI code. The following four bytes are the NE ID. The last byte is 0x10. For example, if the OUI code is 0X001E10 and the NE ID is 10.1.1.1, the clock source ID is 0X001E100A01010110."
        ::= { optixPktPtpClockGroup 17 }

    -- 1.3.6.1.4.1.2011.2.25.4.50.13.1.18
    optixPktPtpGrandMasterGrandmasterID2 OBJECT-TYPE
        SYNTAX Unsigned32
        MAX-ACCESS read-only
        STATUS current
        DESCRIPTION
            "this parameter describes the main clocks high randmaster ID2. Clock source ID generation rule The first three bytes are the OUI code. The following four bytes are the NE ID. The last byte is 0x10. For example, if the OUI code is 0X001E10 and the NE ID is 10.1.1.1, the clock source ID is 0X001E100A01010110."
        ::= { optixPktPtpClockGroup 18 }

    -- 1.3.6.1.4.1.2011.2.25.4.50.13.1.19
    optixPktPtpWTR OBJECT-TYPE
        SYNTAX Unsigned32
        MAX-ACCESS read-write
        STATUS current
        DESCRIPTION
            "this parameter describes the time of 1588 WTR. Value range 0 to 12 (unit minute). The default value is 5 and the step length is 1."
        ::= { optixPktPtpClockGroup 19 }

    -- 1.3.6.1.4.1.2011.2.25.4.50.13.1.20
    optixPktPtpTimeEnableState OBJECT-TYPE
        SYNTAX INTEGER
        {
            close(0),
            open(1)
        }
        MAX-ACCESS read-write
        STATUS current
        DESCRIPTION
            "this parameter describes the NEs time adjusting enable state. 0 close, 1 open"
        ::= { optixPktPtpClockGroup 20 }

    -- 1.3.6.1.4.1.2011.2.25.4.50.13.1.21
    optixPktPtpInfoMode OBJECT-TYPE
        SYNTAX INTEGER
        {
            multicast(1),
            partlyMulticast(2)
        }
        MAX-ACCESS read-write
        STATUS current
        DESCRIPTION
            "This parameter describes the NE PTP message multicast mode. 1 multicast, 2 partlyMulticast"
        ::= { optixPktPtpClockGroup 21 }

    -- 1.3.6.1.4.1.2011.2.25.4.50.13.1.22
    optixPktPtpClockTable OBJECT-TYPE
        SYNTAX SEQUENCE OF OptixPktPtpClockEntry
        MAX-ACCESS not-accessible
        STATUS current
        DESCRIPTION
            "this table describes the configuration message of 1588 clock mode"
        ::= { optixPktPtpClockGroup 22 }

    -- 1.3.6.1.4.1.2011.2.25.4.50.13.1.22.1
    optixPktPtpClockEntry OBJECT-TYPE
        SYNTAX OptixPktPtpClockEntry
        MAX-ACCESS not-accessible
        STATUS current
        DESCRIPTION
            "this entry describes the configuration message of 1588 clock mode"
        INDEX{ optixLogBoardId,optixLogSubCardId,optixPktPtpClockPhyPortId }
        ::= { optixPktPtpClockTable 1 }

    OptixPktPtpClockEntry ::=
        SEQUENCE {
            optixPktPtpClockPhyPortId
                Unsigned32,
            optixPktPtpClockPortManState
                INTEGER,
            optixPktPtpClockPortState
                INTEGER,
            optixPktPtpClockAnnounceCycle
                Unsigned32,
            optixPktPtpClockSyncCycle
                Unsigned32,
            optixPktPtpClockDelayCycle
                Unsigned32,
            optixPktPtpClockPdelayCycle
                Unsigned32,
            optixPktPtpClockAnnounceTimeout
                Unsigned32,
            optixPktPtpClockVlan
                Unsigned32,
            optixPktPtpClockPrewiredPortState
                INTEGER,
            optixPktPtpClockPEMode
                INTEGER,
            optixPktPtpClockHighBit
                Unsigned32,
            optixPktPtpClockLowBit
                Unsigned32,
            optixPktPtpClockInterfaceNo
                Unsigned32,
            optixPktPtpClockLinkState
                INTEGER,
            optixPktPtpClockMsgFormat
                INTEGER,
            optixPktPtpClockRefClkIDHigh
                Unsigned32,
            optixPktPtpClockRefClkIDLow
                Unsigned32,
            optixPktPtpClockRecClkNo
                Unsigned32,
            optixPktPtpClockExtInterfaceMode
                INTEGER,
            optixPktPtpClockINorOUT
                INTEGER,
            optixPktPtpClockTimeProtocolType
                INTEGER,
            optixPktPtpClockElectricalLevel
                INTEGER,
            optixPktPtpClockQulityOfTime
                Unsigned32,
            optixPktPtpClockPrecision
                Unsigned32,
            optixPktPtpClockSrcType
                INTEGER,
            optixPktPtpClockPriority1
                Unsigned32,
            optixPktPtpClockPriority2
                Unsigned32,
            optixPktPtpClockRealState
                INTEGER,
            optixPktPtpClockWarpMode
                INTEGER,
            optixPktPtpClockWarpDirection
                INTEGER,
            optixPktPtpClockWarpValue
                Unsigned32,
            optixPktPtpClockStep
                INTEGER,
            optixPktPtpClockPortMode
                INTEGER,
            optixPktPtpClockAcrState
                INTEGER,
            optixPktPtpClockTimeLevelMode
                INTEGER,
            optixPktPtpCableLengthDirRec
                INTEGER,
            optixPktPtpCableLengthModeRec
                INTEGER,
            optixPktPtpCableLengthValueRec
                Unsigned32,
            optixPktPtpCableLengthDirSend
                INTEGER,
            optixPktPtpCableLengthModeSend
                INTEGER,
            optixPktPtpCableLengthValueSend
                Unsigned32,
            optixPktPtpPortVlanPri
                Unsigned32,
            optixPktPtpClockLocalPriority
                Unsigned32,
            optixPktPtpClockNotSlave
                INTEGER,
            optixPktPtpClockPortDmac
                INTEGER
        }

    -- 1.3.6.1.4.1.2011.2.25.4.50.13.1.22.1.1
    optixPktPtpClockPhyPortId OBJECT-TYPE
        SYNTAX Unsigned32
        MAX-ACCESS not-accessible
        STATUS current
        DESCRIPTION
            "this parameter describes the physical ports ID of 1588 mode"
        ::= { optixPktPtpClockEntry 1 }

    -- 1.3.6.1.4.1.2011.2.25.4.50.13.1.22.1.2
    optixPktPtpClockPortManState OBJECT-TYPE
        SYNTAX INTEGER
        {
            initializing(1),
            faulty(2),
            disabled(3),
            listening(4),
            preMaster(5),
            master(6),
            passive(7),
            uncalibrated(8),
            slave(9),
            snmp(255)
        }
        MAX-ACCESS read-write
        STATUS current
        DESCRIPTION
            "this parameter describes the state of PTP port. 1 initializing, 2 faulty, 3 disabled, 4 listening, 5 preMaster, 6 master, 7 passive, 8 uncalibrated, 9 slave, 255 snmp"
        ::= { optixPktPtpClockEntry 2 }

    -- 1.3.6.1.4.1.2011.2.25.4.50.13.1.22.1.3
    optixPktPtpClockPortState OBJECT-TYPE
        SYNTAX INTEGER
        {
            disable(0),
            enable(1)
        }
        MAX-ACCESS read-write
        STATUS current
        DESCRIPTION
            "this parameter describes the enabled state of PTP clock port. 0 disable, 1 enable"
        ::= { optixPktPtpClockEntry 3 }

    -- 1.3.6.1.4.1.2011.2.25.4.50.13.1.22.1.4
    optixPktPtpClockAnnounceCycle OBJECT-TYPE
        SYNTAX Unsigned32
        MAX-ACCESS read-write
        STATUS current
        DESCRIPTION
            "this parameter describes the announce packet period of PTP clock port. Value range 0 to 20. The mapping relationship is as follows 0 1/1024s 1 2/1024s (1/512s) 2 4/1024s (1/256s) 3 8/1024s (1/128s) 4 16/1024s (1/64s) 5 32/1024s (1/32s) 6 64/1024s (1/16s) 7 128/1024s (1/8s) 8 256/1024s (1/4s) 9 512/1024s (1/2s) 10 1s 11 2s 12 4s 13 8s 14 16s 15 32s 16 64s 17 128s 18 256s 19 512s 20 1024s"
        ::= { optixPktPtpClockEntry 4 }

    -- 1.3.6.1.4.1.2011.2.25.4.50.13.1.22.1.5
    optixPktPtpClockSyncCycle OBJECT-TYPE
        SYNTAX Unsigned32
        MAX-ACCESS read-write
        STATUS current
        DESCRIPTION
            "this parameter describes the SYNC packet period of PTP clock port. Value range 0 to 20. The mapping relationship is as follows 0 1/1024s 1 2/1024s (1/512s) 2 4/1024s (1/256s) 3 8/1024s (1/128s) 4 16/1024s (1/64s) 5 32/1024s (1/32s) 6 64/1024s (1/16s) 7 128/1024s (1/8s) 8 256/1024s (1/4s) 9 512/1024s (1/2s) 10 1s 11 2s 12 4s 13 8s 14 16s 15 32s 16 64s 17 128s 18 256s 19 512s 20 1024s"
        ::= { optixPktPtpClockEntry 5 }

    -- 1.3.6.1.4.1.2011.2.25.4.50.13.1.22.1.6
    optixPktPtpClockDelayCycle OBJECT-TYPE
        SYNTAX Unsigned32
        MAX-ACCESS read-write
        STATUS current
        DESCRIPTION
            "this parameter describes the DELAY packet period of PTP clock port. Value range 0 to 20. The mapping relationship is as follows 0 1/1024s 1 2/1024s (1/512s) 2 4/1024s (1/256s) 3 8/1024s (1/128s) 4 16/1024s (1/64s) 5 32/1024s (1/32s) 6 64/1024s (1/16s) 7 128/1024s (1/8s) 8 256/1024s (1/4s) 9 512/1024s (1/2s) 10 1s 11 2s 12 4s 13 8s 14 16s 15 32s 16 64s 17 128s 18 256s 19 512s 20 1024s"
        ::= { optixPktPtpClockEntry 6 }

    -- 1.3.6.1.4.1.2011.2.25.4.50.13.1.22.1.7
    optixPktPtpClockPdelayCycle OBJECT-TYPE
        SYNTAX Unsigned32
        MAX-ACCESS read-write
        STATUS current
        DESCRIPTION
            "this parameter describes the PDELAY packet period of PTP clock port. Value range 0 to 20. The mapping relationship is as follows 0 1/1024s 1 2/1024s (1/512s) 2 4/1024s (1/256s) 3 8/1024s (1/128s) 4 16/1024s (1/64s) 5 32/1024s (1/32s) 6 64/1024s (1/16s) 7 128/1024s (1/8s) 8 256/1024s (1/4s) 9 512/1024s (1/2s) 10 1s 11 2s 12 4s 13 8s 14 16s 15 32s 16 64s 17 128s 18 256s 19 512s 20 1024s"
        ::= { optixPktPtpClockEntry 7 }

    -- 1.3.6.1.4.1.2011.2.25.4.50.13.1.22.1.8
    optixPktPtpClockAnnounceTimeout OBJECT-TYPE
        SYNTAX Unsigned32
        MAX-ACCESS read-write
        STATUS current
        DESCRIPTION
            "This parameter describes the timeout interval of port announce diagram."
        ::= { optixPktPtpClockEntry 8 }

    -- 1.3.6.1.4.1.2011.2.25.4.50.13.1.22.1.9
    optixPktPtpClockVlan OBJECT-TYPE
        SYNTAX Unsigned32
        MAX-ACCESS read-write
        STATUS current
        DESCRIPTION
            "this parameter describes the VLAN value of PTP packet"
        ::= { optixPktPtpClockEntry 9 }

    -- 1.3.6.1.4.1.2011.2.25.4.50.13.1.22.1.10
    optixPktPtpClockPrewiredPortState OBJECT-TYPE
        SYNTAX INTEGER
        {
            masterSlave(0),
            master(1),
            slave(2)
        }
        MAX-ACCESS read-write
        STATUS current
        DESCRIPTION
            "this parameter describes the preselection status of PTP clock. 0 masterSlave, 1 master, 2 slave"
        ::= { optixPktPtpClockEntry 10 }

    -- 1.3.6.1.4.1.2011.2.25.4.50.13.1.22.1.11
    optixPktPtpClockPEMode OBJECT-TYPE
        SYNTAX INTEGER
        {
            p2p(1),
            e2e(2)
        }
        MAX-ACCESS read-write
        STATUS current
        DESCRIPTION
            "this parameter describes the P/E mode of PTP clock. 1 p2p, 2 e2e"
        ::= { optixPktPtpClockEntry 11 }

    -- 1.3.6.1.4.1.2011.2.25.4.50.13.1.22.1.12
    optixPktPtpClockHighBit OBJECT-TYPE
        SYNTAX Unsigned32
        MAX-ACCESS read-only
        STATUS current
        DESCRIPTION
            "this parameter describes the high bit of received source PTP clock. Value range 1 to 0xfffffff. The defaut value is all Fs."
        ::= { optixPktPtpClockEntry 12 }

    -- 1.3.6.1.4.1.2011.2.25.4.50.13.1.22.1.13
    optixPktPtpClockLowBit OBJECT-TYPE
        SYNTAX Unsigned32
        MAX-ACCESS read-only
        STATUS current
        DESCRIPTION
            "this parameter describes the low bit of received source PTP clock"
        ::= { optixPktPtpClockEntry 13 }

    -- 1.3.6.1.4.1.2011.2.25.4.50.13.1.22.1.14
    optixPktPtpClockInterfaceNo OBJECT-TYPE
        SYNTAX Unsigned32
        MAX-ACCESS read-only
        STATUS current
        DESCRIPTION
            "this parameter describes the interface NO of the PTP port that receive source clock. Value range 1 to 0xfffffff. The defaut value is all Fs."
        ::= { optixPktPtpClockEntry 14 }

    -- 1.3.6.1.4.1.2011.2.25.4.50.13.1.22.1.15
    optixPktPtpClockLinkState OBJECT-TYPE
        SYNTAX INTEGER
        {
            up(1),
            down(0)
        }
        MAX-ACCESS read-only
        STATUS current
        DESCRIPTION
            "this parameter describes the link state of the PTP port that receive source clock. 1 up, 0 down"
        ::= { optixPktPtpClockEntry 15 }

    -- 1.3.6.1.4.1.2011.2.25.4.50.13.1.22.1.16
    optixPktPtpClockMsgFormat OBJECT-TYPE
        SYNTAX INTEGER
        {
            ptpeth(1),
            ptpip(2)
        }
        MAX-ACCESS read-write
        STATUS current
        DESCRIPTION
            "this parameter describes the encapsulated format of PTP packeting. 1 ptpeth, 2 ptpip"
        ::= { optixPktPtpClockEntry 16 }

    -- 1.3.6.1.4.1.2011.2.25.4.50.13.1.22.1.17
    optixPktPtpClockRefClkIDHigh OBJECT-TYPE
        SYNTAX Unsigned32
        MAX-ACCESS read-write
        STATUS current
        DESCRIPTION
            "this parameter describes the high bit of higher priority of PTP clock that for reference. Value range 1 to 0xffffffff. The default value is all Fs."
        ::= { optixPktPtpClockEntry 17 }

    -- 1.3.6.1.4.1.2011.2.25.4.50.13.1.22.1.18
    optixPktPtpClockRefClkIDLow OBJECT-TYPE
        SYNTAX Unsigned32
        MAX-ACCESS read-write
        STATUS current
        DESCRIPTION
            "this parameter describes the high bit of lower priority of PTP clock that for reference. Value range 1 to 0xffffffff. The default value is all Fs."
        ::= { optixPktPtpClockEntry 18 }

    -- 1.3.6.1.4.1.2011.2.25.4.50.13.1.22.1.19
    optixPktPtpClockRecClkNo OBJECT-TYPE
        SYNTAX Unsigned32
        MAX-ACCESS read-write
        STATUS current
        DESCRIPTION
            "this parameter describes the interface NO of port that reveive clock. Value range 1 to 0xffff. The default value is all Fs."
        ::= { optixPktPtpClockEntry 19 }

    -- 1.3.6.1.4.1.2011.2.25.4.50.13.1.22.1.20
    optixPktPtpClockExtInterfaceMode OBJECT-TYPE
        SYNTAX INTEGER
        {
            extclock(1),
            exttime(2)
        }
        MAX-ACCESS read-write
        STATUS current
        DESCRIPTION
            "this parameter describes the PTP ports mode of external interface. 1 extClock, 2 extTime"
        ::= { optixPktPtpClockEntry 20 }

    -- 1.3.6.1.4.1.2011.2.25.4.50.13.1.22.1.21
    optixPktPtpClockINorOUT OBJECT-TYPE
        SYNTAX INTEGER
        {
            in(1),
            out(2)
        }
        MAX-ACCESS read-write
        STATUS current
        DESCRIPTION
            "this parameter describes the direction(IN or OUT) of PTP clock port. 1 in, 2 out"
        ::= { optixPktPtpClockEntry 21 }

    -- 1.3.6.1.4.1.2011.2.25.4.50.13.1.22.1.22
    optixPktPtpClockTimeProtocolType OBJECT-TYPE
        SYNTAX INTEGER
        {
            dcls(1),
            oneppsTime(2),
            j211(3)
        }
        MAX-ACCESS read-write
        STATUS current
        DESCRIPTION
            "this parameter describes the protocol style of PTP clock. 1 dcls, 2 oneppsTime, 3 j211"
        ::= { optixPktPtpClockEntry 22 }

    -- 1.3.6.1.4.1.2011.2.25.4.50.13.1.22.1.23
    optixPktPtpClockElectricalLevel OBJECT-TYPE
        SYNTAX INTEGER
        {
            rs422(3),
            snmpnull(255)
        }
        MAX-ACCESS read-write
        STATUS current
        DESCRIPTION
            "this parameter describes the electrical level of PTP clock. 3 rs422, 255 snmpnull"
        ::= { optixPktPtpClockEntry 23 }

    -- 1.3.6.1.4.1.2011.2.25.4.50.13.1.22.1.24
    optixPktPtpClockQulityOfTime OBJECT-TYPE
        SYNTAX Unsigned32
        MAX-ACCESS read-write
        STATUS current
        DESCRIPTION
            "This parameter describes the time quality degree of a PTP clock."
        ::= { optixPktPtpClockEntry 24 }

    -- 1.3.6.1.4.1.2011.2.25.4.50.13.1.22.1.25
    optixPktPtpClockPrecision OBJECT-TYPE
        SYNTAX Unsigned32
        MAX-ACCESS read-write
        STATUS current
        DESCRIPTION
            "This parameter describes the time precision accuracy of a PTP clock."
        ::= { optixPktPtpClockEntry 25 }

    -- 1.3.6.1.4.1.2011.2.25.4.50.13.1.22.1.26
    optixPktPtpClockSrcType OBJECT-TYPE
        SYNTAX INTEGER
        {
            atomicClock(1),
            gps(2),
            terrestrialRadio(3),
            ptp(4),
            ntp(5),
            handSet(6),
            other(7),
            internalOscillator(8)
        }
        MAX-ACCESS read-write
        STATUS current
        DESCRIPTION
            "This parameter describes the type of the source PTP clock. 1 ATOMICCLOCK, 2 GPS, 3 TerrestrialRadio, 4 PTP, 5 NTP, 6 HANDSET, 7 OTHER, 8 Internaloscillator"
        ::= { optixPktPtpClockEntry 26 }

    -- 1.3.6.1.4.1.2011.2.25.4.50.13.1.22.1.27
    optixPktPtpClockPriority1 OBJECT-TYPE
        SYNTAX Unsigned32
        MAX-ACCESS read-write
        STATUS current
        DESCRIPTION
            "This parameter describes priority 1 of a PTP port. Value range: 0 to 255."
        ::= { optixPktPtpClockEntry 27 }

    -- 1.3.6.1.4.1.2011.2.25.4.50.13.1.22.1.28
    optixPktPtpClockPriority2 OBJECT-TYPE
        SYNTAX Unsigned32
        MAX-ACCESS read-write
        STATUS current
        DESCRIPTION
            "This parameter describes priority 2 of a PTP port. Value range: 0 to 255."
        ::= { optixPktPtpClockEntry 28 }

    -- 1.3.6.1.4.1.2011.2.25.4.50.13.1.22.1.29
    optixPktPtpClockRealState OBJECT-TYPE
        SYNTAX INTEGER
        {
            initializing(1),
            faulty(2),
            disabled(3),
            listening(4),
            preMaster(5),
            master(6),
            passive(7),
            uncalibrated(8),
            slave(9),
            snmp(255)
        }
        MAX-ACCESS read-only
        STATUS current
        DESCRIPTION
            "this parameter describes the real state of PTP port. 1 initializing, 2 faulty, 3 disabled, 4 listening, 4 preMaster, 6 master, 7 passive, 8 uncalibrated, 9 slave, 255 snmp"
        ::= { optixPktPtpClockEntry 29 }

    -- 1.3.6.1.4.1.2011.2.25.4.50.13.1.22.1.30
    optixPktPtpClockWarpMode OBJECT-TYPE
        SYNTAX INTEGER
        {
            length(0),
            time(1)
        }
        MAX-ACCESS read-write
        STATUS current
        DESCRIPTION
            "This parameter describes the divergence mode of a PTP port. 0: length; 1: time. The default value is length."
        ::= { optixPktPtpClockEntry 30 }

    -- 1.3.6.1.4.1.2011.2.25.4.50.13.1.22.1.31
    optixPktPtpClockWarpDirection OBJECT-TYPE
        SYNTAX INTEGER
        {
            positive(0),
            negative(1)
        }
        MAX-ACCESS read-write
        STATUS current
        DESCRIPTION
            "This parameter describes the divergence direction of a PTP port. 0: positive; 1: negative. The default value is positive."
        ::= { optixPktPtpClockEntry 31 }

    -- 1.3.6.1.4.1.2011.2.25.4.50.13.1.22.1.32
    optixPktPtpClockWarpValue OBJECT-TYPE
        SYNTAX Unsigned32
        MAX-ACCESS read-write
        STATUS current
        DESCRIPTION
            "This parameter describes the divergence value of a PTP port. Value range for the length mode: 0 to 54000 (unit m).The default value is 0. Value range for the time mode 0 to 262143 (unit ns). The default value is 0."
        ::= { optixPktPtpClockEntry 32 }

    -- 1.3.6.1.4.1.2011.2.25.4.50.13.1.22.1.33
    optixPktPtpClockStep OBJECT-TYPE
        SYNTAX INTEGER
        {
            one(1),
            two(2)
        }
        MAX-ACCESS read-write
        STATUS current
        DESCRIPTION
            "this parameter describes the ports PTP STEP mode. 1 ONESTEP, 2 TWOSTEP. The default value is ONESTEP. Note The FO supports only ONESTEP. That is, the GSP supports both modes. TWOSTEP returned by the product PSU fails."
        ::= { optixPktPtpClockEntry 33 }

    -- 1.3.6.1.4.1.2011.2.25.4.50.13.1.22.1.34
    optixPktPtpClockPortMode OBJECT-TYPE
        SYNTAX INTEGER
        {
            oc(1),
            bc(2),
            tc(3),
            tcBc(5)
        }
        MAX-ACCESS read-write
        STATUS current
        DESCRIPTION
            "this parameter describes the ports 1588 mode. 1 oc, 2 bc, 3 tc, 5 tcBc"
        ::= { optixPktPtpClockEntry 34 }

    -- 1.3.6.1.4.1.2011.2.25.4.50.13.1.22.1.35
    optixPktPtpClockAcrState OBJECT-TYPE
        SYNTAX INTEGER
        {
            disable(0),
            enable(1)
        }
        MAX-ACCESS read-write
        STATUS current
        DESCRIPTION
            "this parameter describes the ports enable status of 1588 ACR. 0 disable, 1 enable"
        ::= { optixPktPtpClockEntry 35 }

    -- 1.3.6.1.4.1.2011.2.25.4.50.13.1.22.1.36
    optixPktPtpClockTimeLevelMode OBJECT-TYPE
        SYNTAX INTEGER
        {
            manual(1),
            auto(2)
        }
        MAX-ACCESS read-write
        STATUS current
        DESCRIPTION
            "this parameter describes the time level of external time interface. 1 manual, 2 auto"
        ::= { optixPktPtpClockEntry 36 }

    -- 1.3.6.1.4.1.2011.2.25.4.50.13.1.22.1.37
    optixPktPtpCableLengthDirRec OBJECT-TYPE
        SYNTAX INTEGER
        {
            receive(0),
            send(1)
        }
        MAX-ACCESS read-write
        STATUS current
        DESCRIPTION
            "this parameter describes the received direction(IN or OUT) of external cable. 0 receive, 1 send"
        ::= { optixPktPtpClockEntry 37 }

    -- 1.3.6.1.4.1.2011.2.25.4.50.13.1.22.1.38
    optixPktPtpCableLengthModeRec OBJECT-TYPE
        SYNTAX INTEGER
        {
            length(0),
            time(1)
        }
        MAX-ACCESS read-write
        STATUS current
        DESCRIPTION
            "this parameter describes the received direction(IN or OUT) of external cable in in transmission length mode. 0 length, 1 time"
        ::= { optixPktPtpClockEntry 38 }

    -- 1.3.6.1.4.1.2011.2.25.4.50.13.1.22.1.39
    optixPktPtpCableLengthValueRec OBJECT-TYPE
        SYNTAX Unsigned32
        MAX-ACCESS read-write
        STATUS current
        DESCRIPTION
            "this parameter describes the received direction(IN or OUT) of external cable in length value"
        ::= { optixPktPtpClockEntry 39 }

    -- 1.3.6.1.4.1.2011.2.25.4.50.13.1.22.1.40
    optixPktPtpCableLengthDirSend OBJECT-TYPE
        SYNTAX INTEGER
        {
            receive(0),
            send(1)
        }
        MAX-ACCESS read-write
        STATUS current
        DESCRIPTION
            "this parameter describes the sent direction(IN or OUT) of external cable. 0 receive, 1 send"
        ::= { optixPktPtpClockEntry 40 }

    -- 1.3.6.1.4.1.2011.2.25.4.50.13.1.22.1.41
    optixPktPtpCableLengthModeSend OBJECT-TYPE
        SYNTAX INTEGER
        {
            length(0),
            time(1)
        }
        MAX-ACCESS read-write
        STATUS current
        DESCRIPTION
            "this parameter describes the sent direction(IN or OUT) of external cable in transmission length mode. 0 length, 1 time"
        ::= { optixPktPtpClockEntry 41 }

    -- 1.3.6.1.4.1.2011.2.25.4.50.13.1.22.1.42
    optixPktPtpCableLengthValueSend OBJECT-TYPE
        SYNTAX Unsigned32
        MAX-ACCESS read-write
        STATUS current
        DESCRIPTION
            "this parameter describes the sent direction(IN or OUT) of external cable in transmission length mode"
        ::= { optixPktPtpClockEntry 42 }

    -- 1.3.6.1.4.1.2011.2.25.4.50.13.1.22.1.43
    optixPktPtpPortVlanPri OBJECT-TYPE
        SYNTAX Unsigned32
        MAX-ACCESS read-write
        STATUS current
        DESCRIPTION
            "this parameter describes Vlan Priority with the PTP message."
        ::= { optixPktPtpClockEntry 43 }

    -- 1.3.6.1.4.1.2011.2.25.4.50.13.1.22.1.44
    optixPktPtpClockLocalPriority OBJECT-TYPE
        SYNTAX Unsigned32
        MAX-ACCESS read-write
        STATUS current
        DESCRIPTION
            "This parameter describes the local priority of a PTP clock."
        ::= { optixPktPtpClockEntry 44 }

    -- 1.3.6.1.4.1.2011.2.25.4.50.13.1.22.1.45
    optixPktPtpClockNotSlave OBJECT-TYPE
        SYNTAX INTEGER
        {
            disable(0),
            enable(1)
        }
        MAX-ACCESS read-write
        STATUS current
        DESCRIPTION
            "This parameter describes the NotSlave status of a PTP clock. 0: disable, 1: enable."
        ::= { optixPktPtpClockEntry 45 }

    -- 1.3.6.1.4.1.2011.2.25.4.50.13.1.22.1.46
    optixPktPtpClockPortDmac OBJECT-TYPE
        SYNTAX INTEGER
        {
            mac011B19000000(0),
            mac0180C200000E(1)
        }
        MAX-ACCESS read-write
        STATUS current
        DESCRIPTION
            "This parameter describes the destination MAC address of a PTP clock. mac011B19000000:01-1B-19-00-00-00,mac0180C200000E:01-80-C2-00-00-0E."
        ::= { optixPktPtpClockEntry 46 }

    -- 1.3.6.1.4.1.2011.2.25.4.50.13.1.23
    optixPktSTGPtpSrcChangeEventMember OBJECT IDENTIFIER ::= { optixPktPtpClockGroup 23 }

    -- 1.3.6.1.4.1.2011.2.25.4.50.13.1.23.1
    optixPktPtpSrcBid OBJECT-TYPE
        SYNTAX Unsigned32
        MAX-ACCESS accessible-for-notify
        STATUS current
        DESCRIPTION
            "this parameter describes the main PTP bid before being switched"
        ::= { optixPktSTGPtpSrcChangeEventMember 1 }

    -- 1.3.6.1.4.1.2011.2.25.4.50.13.1.23.2
    optixPktPtpSrcSbid OBJECT-TYPE
        SYNTAX Unsigned32
        MAX-ACCESS accessible-for-notify
        STATUS current
        DESCRIPTION
            "this parameter describes the main PTP subcard ID before being switched"
        ::= { optixPktSTGPtpSrcChangeEventMember 2 }

    -- 1.3.6.1.4.1.2011.2.25.4.50.13.1.23.3
    optixPktPtpSrcPid OBJECT-TYPE
        SYNTAX Unsigned32
        MAX-ACCESS accessible-for-notify
        STATUS current
        DESCRIPTION
            "this parameter describes the main PTP port ID before being switched"
        ::= { optixPktSTGPtpSrcChangeEventMember 3 }

    -- 1.3.6.1.4.1.2011.2.25.4.50.13.1.23.4
    optixPktPtpSrcGrandmasterID1 OBJECT-TYPE
        SYNTAX Unsigned32
        MAX-ACCESS accessible-for-notify
        STATUS current
        DESCRIPTION
            "this parameter describes the high bit of Grandmaster ID1 of main clock before being switched"
        ::= { optixPktSTGPtpSrcChangeEventMember 4 }

    -- 1.3.6.1.4.1.2011.2.25.4.50.13.1.23.5
    optixPktPtpSrcGrandmasterID2 OBJECT-TYPE
        SYNTAX Unsigned32
        MAX-ACCESS accessible-for-notify
        STATUS current
        DESCRIPTION
            "this parameter describes the low bit of Grandmaster ID2 of main clock before being switched"
        ::= { optixPktSTGPtpSrcChangeEventMember 5 }

    -- 1.3.6.1.4.1.2011.2.25.4.50.13.1.23.6
    optixPktPtpDestBid OBJECT-TYPE
        SYNTAX Unsigned32
        MAX-ACCESS accessible-for-notify
        STATUS current
        DESCRIPTION
            "this parameter describes the main PTP bid after being switched"
        ::= { optixPktSTGPtpSrcChangeEventMember 6 }

    -- 1.3.6.1.4.1.2011.2.25.4.50.13.1.23.7
    optixPktPtpDestSbid OBJECT-TYPE
        SYNTAX Unsigned32
        MAX-ACCESS accessible-for-notify
        STATUS current
        DESCRIPTION
            "this parameter describes the main PTP subcard ID after being switched"
        ::= { optixPktSTGPtpSrcChangeEventMember 7 }

    -- 1.3.6.1.4.1.2011.2.25.4.50.13.1.23.8
    optixPktPtpDestPid OBJECT-TYPE
        SYNTAX Unsigned32
        MAX-ACCESS accessible-for-notify
        STATUS current
        DESCRIPTION
            "this parameter describes the main PTP port ID after being switched"
        ::= { optixPktSTGPtpSrcChangeEventMember 8 }

    -- 1.3.6.1.4.1.2011.2.25.4.50.13.1.23.9
    optixPktPtprDestGrandmasterID1 OBJECT-TYPE
        SYNTAX Unsigned32
        MAX-ACCESS accessible-for-notify
        STATUS current
        DESCRIPTION
            "this parameter describes the high bit of Grandmaster ID1 of main clock after being switched"
        ::= { optixPktSTGPtpSrcChangeEventMember 9 }

    -- 1.3.6.1.4.1.2011.2.25.4.50.13.1.23.10
    optixPktPtprDestGrandmasterID2 OBJECT-TYPE
        SYNTAX Unsigned32
        MAX-ACCESS accessible-for-notify
        STATUS current
        DESCRIPTION
            "this parameter describes the low bit of Grandmaster ID2 of main clock after being switched"
        ::= { optixPktSTGPtpSrcChangeEventMember 10 }

    -- 1.3.6.1.4.1.2011.2.25.4.50.13.1.23.11
    optixPktPtpSwitchMode OBJECT-TYPE
        SYNTAX INTEGER
        {
            auto(1),
            man(2),
            force(3)
        }
        MAX-ACCESS accessible-for-notify
        STATUS current
        DESCRIPTION
            "this parameter describes the style of switching. 1 auto, 2 man, 3 force"
        ::= { optixPktSTGPtpSrcChangeEventMember 11 }

    -- 1.3.6.1.4.1.2011.2.25.4.50.13.1.24
    optixPktSTGPtpSrcChangeEvent OBJECT IDENTIFIER ::= { optixPktPtpClockGroup 24 }

    -- 1.3.6.1.4.1.2011.2.25.4.50.13.1.24.1
    optixPktSTGPtpSrcChange NOTIFICATION-TYPE
        OBJECTS{ optixPktPtpSrcBid,optixPktPtpSrcSbid,optixPktPtpSrcPid,optixPktPtpSrcGrandmasterID1,optixPktPtpSrcGrandmasterID2,optixPktPtpDestBid,optixPktPtpDestSbid,optixPktPtpDestPid,optixPktPtprDestGrandmasterID1,optixPktPtprDestGrandmasterID2,optixPktPtpSwitchMode }
        STATUS current
        DESCRIPTION
            "this parameter describes the feature of 1588 clock switching"
        ::= { optixPktSTGPtpSrcChangeEvent 1 }

    -- 1.3.6.1.4.1.2011.2.25.4.50.13.1.25
    optixPktPtpClockPLTable OBJECT-TYPE
        SYNTAX SEQUENCE OF OptixPktPtpClockPLEntry
        MAX-ACCESS not-accessible
        STATUS current
        DESCRIPTION
            "This table describes the configurations of the TC+OC port reference source priority list."
        ::= { optixPktPtpClockGroup 25 }

    -- 1.3.6.1.4.1.2011.2.25.4.50.13.1.25.1
    optixPktPtpClockPLEntry OBJECT-TYPE
        SYNTAX OptixPktPtpClockPLEntry
        MAX-ACCESS not-accessible
        STATUS current
        DESCRIPTION
            "This entry describes the configurations of the TC+OC port reference source priority list."
        INDEX{ optixPktPtpClockPLNum,optixLogBoardId,optixLogSubCardId,optixPortId }
        ::= { optixPktPtpClockPLTable 1 }

    OptixPktPtpClockPLEntry ::=
        SEQUENCE {
            optixPktPtpClockPLNum
                Unsigned32,
            optixPktPtpClockPLRefClkIDHigh
                Unsigned32,
            optixPktPtpClockPLRefClkIDLow
                Unsigned32,
            optixPktPtpClockPLRecClkNo
                Unsigned32
        }

    -- 1.3.6.1.4.1.2011.2.25.4.50.13.1.25.1.1
    optixPktPtpClockPLNum OBJECT-TYPE
        SYNTAX Unsigned32
        MAX-ACCESS not-accessible
        STATUS current
        DESCRIPTION
            "This object indicates the number of reference sources in the priority list."
        ::= { optixPktPtpClockPLEntry 1 }

    -- 1.3.6.1.4.1.2011.2.25.4.50.13.1.25.1.2
    optixPktPtpClockPLRefClkIDHigh OBJECT-TYPE
        SYNTAX Unsigned32
        MAX-ACCESS read-write
        STATUS current
        DESCRIPTION
            "This object indicates the high order of the port reference clock source number (with the highest priority)."
        ::= { optixPktPtpClockPLEntry 2 }

    -- 1.3.6.1.4.1.2011.2.25.4.50.13.1.25.1.3
    optixPktPtpClockPLRefClkIDLow OBJECT-TYPE
        SYNTAX Unsigned32
        MAX-ACCESS read-write
        STATUS current
        DESCRIPTION
            "This object indicates the low order of the port reference clock source number (with the highest priority)."
        ::= { optixPktPtpClockPLEntry 3 }

    -- 1.3.6.1.4.1.2011.2.25.4.50.13.1.25.1.4
    optixPktPtpClockPLRecClkNo OBJECT-TYPE
        SYNTAX Unsigned32
        MAX-ACCESS not-accessible
        STATUS current
        DESCRIPTION
            "This object indicates the receive clock source interface ID of a port."
        ::= { optixPktPtpClockPLEntry 4 }

    -- 1.3.6.1.4.1.2011.2.25.4.50.13.1.26
    optixPktSTGPtpPdvOverTHResEvent OBJECT IDENTIFIER ::= { optixPktPtpClockGroup 26 }

    -- 1.3.6.1.4.1.2011.2.25.4.50.13.1.26.1
    optixPktSTGPtpPdvOverTHRes NOTIFICATION-TYPE
        STATUS current
        DESCRIPTION
            "this parameter describes the event of 1588 ACR PDV over."
        ::= { optixPktSTGPtpPdvOverTHResEvent 1 }

    -- 1.3.6.1.4.1.2011.2.25.4.50.13.1.27
    optixPktClockSrvInfoTable OBJECT-TYPE
        SYNTAX SEQUENCE OF OptixPktClockSrvInfoEntry
        MAX-ACCESS not-accessible
        STATUS current
        DESCRIPTION
            "This table describes the configurations of clock services."
        ::= { optixPktPtpClockGroup 27 }

    -- 1.3.6.1.4.1.2011.2.25.4.50.13.1.27.1
    optixPktClockSrvInfoEntry OBJECT-TYPE
        SYNTAX OptixPktClockSrvInfoEntry
        MAX-ACCESS not-accessible
        STATUS current
        DESCRIPTION
            "This entry describes the configurations of clock services."
        INDEX{ optixEthSrvIndex }
        ::= { optixPktClockSrvInfoTable 1 }

    OptixPktClockSrvInfoEntry ::=
        SEQUENCE {
            optixPktClockEsrvID
                Unsigned32,
            optixPktClockEsrName
                OCTET STRING,
            optixPktClockL2pTnl
                INTEGER,
            optixPktClockLgcIFnum
                Unsigned32,
            optixPktClockTypeID
                OCTET STRING
        }

    -- 1.3.6.1.4.1.2011.2.25.4.50.13.1.27.1.1
    optixPktClockEsrvID OBJECT-TYPE
        SYNTAX Unsigned32
        MAX-ACCESS read-only
        STATUS current
        DESCRIPTION
            "This object indicates the service index."
        ::= { optixPktClockSrvInfoEntry 1 }

    -- 1.3.6.1.4.1.2011.2.25.4.50.13.1.27.1.2
    optixPktClockEsrName OBJECT-TYPE
        SYNTAX OCTET STRING
        MAX-ACCESS read-only
        STATUS current
        DESCRIPTION
            "This object indicates the clock service name, which is a string of 64 characters."
        ::= { optixPktClockSrvInfoEntry 2 }

    -- 1.3.6.1.4.1.2011.2.25.4.50.13.1.27.1.3
    optixPktClockL2pTnl OBJECT-TYPE
        SYNTAX INTEGER
        {
            disable(0),
            bpdu(1)
        }
        MAX-ACCESS read-only
        STATUS current
        DESCRIPTION
            "This object indicates the flag for transparent transmission of L2 protocol packets. 0: No transparent transmission; 1: BPDU transparent transmission"
        ::= { optixPktClockSrvInfoEntry 3 }

    -- 1.3.6.1.4.1.2011.2.25.4.50.13.1.27.1.4
    optixPktClockLgcIFnum OBJECT-TYPE
        SYNTAX Unsigned32
        MAX-ACCESS read-only
        STATUS current
        DESCRIPTION
            "This object indicates the number of logical interfaces."
        ::= { optixPktClockSrvInfoEntry 4 }

    -- 1.3.6.1.4.1.2011.2.25.4.50.13.1.27.1.5
    optixPktClockTypeID OBJECT-TYPE
        SYNTAX OCTET STRING
        MAX-ACCESS read-only
        STATUS current
        DESCRIPTION
            "This object indicates the type of a logical interface (1: V-UNI; 2: V-NNI) and the list of logical interface IDs."
        ::= { optixPktClockSrvInfoEntry 5 }

    -- 1.3.6.1.4.1.2011.2.25.4.50.13.2
    optixPktPtpClockGroupEx OBJECT IDENTIFIER ::= { optixPktptpclock 2 }

    -- 1.3.6.1.4.1.2011.2.25.4.50.13.2.1
    optixPktPtpProtFormat OBJECT-TYPE
        SYNTAX INTEGER
        {
            nmea(0),
            ubx(1)
        }
        MAX-ACCESS read-write
        STATUS current
        DESCRIPTION
            "this parameter describes the message format of 1588 protcol. 0 nmea, 1 ubx"
        ::= { optixPktPtpClockGroupEx 1 }

    -- 1.3.6.1.4.1.2011.2.25.4.50.13.2.2
    optixPktPtpLockState OBJECT-TYPE
        SYNTAX INTEGER
        {
            unlock(0),
            lock(1)
        }
        MAX-ACCESS read-only
        STATUS current
        DESCRIPTION
            "This parameter describes the clock lock state of the 1588 protcol."
        ::= { optixPktPtpClockGroupEx 2 }

    -- 1.3.6.1.4.1.2011.2.25.4.50.13.2.3
    optixPktPtpTimeLockState OBJECT-TYPE
        SYNTAX INTEGER
        {
            unlock(0),
            lock(1)
        }
        MAX-ACCESS read-only
        STATUS current
        DESCRIPTION
            "This parameter describes the time lock state of the 1588 protcol."
        ::= { optixPktPtpClockGroupEx 3 }

    -- 1.3.6.1.4.1.2011.2.25.4.50.13.2.4
    optixPktPtpProfile OBJECT-TYPE
        SYNTAX INTEGER
        {
            ieee1588v2(0),
            g82751(1)
        }
        MAX-ACCESS read-write
        STATUS current
        DESCRIPTION
            "This parameter describes the PTP clock protocol type of an NE. 0: IEEE-1588v2, 1: G8275-1."
        ::= { optixPktPtpClockGroupEx 4 }

    -- 1.3.6.1.4.1.2011.2.25.4.50.13.2.5
    optixPktPtpClockState OBJECT-TYPE
        SYNTAX INTEGER
        {
            freerun(0),
            locked(1),
            holdoutofspec(2)
        }
        MAX-ACCESS read-only
        STATUS current
        DESCRIPTION
            "This parameter describes the PTP clock tracking state of an NE. 0: Free-Run,1: Locked,2: Holdover-Out-Of-Specification."
        ::= { optixPktPtpClockGroupEx 5 }

    -- 1.3.6.1.4.1.2011.2.25.4.50.13.3
    optixPktPtpAcrUniGroup OBJECT IDENTIFIER ::= { optixPktptpclock 3 }

    -- 1.3.6.1.4.1.2011.2.25.4.50.13.3.1
    optixPktPtpAcrUniTable OBJECT-TYPE
        SYNTAX SEQUENCE OF OptixPktPtpAcrUniEntry
        MAX-ACCESS not-accessible
        STATUS current
        DESCRIPTION
            "This table describes the configuration message of IEEE 1588 ACR unicast."
        ::= { optixPktPtpAcrUniGroup 1 }

    -- 1.3.6.1.4.1.2011.2.25.4.50.13.3.1.1
    optixPktPtpAcrUniEntry OBJECT-TYPE
        SYNTAX OptixPktPtpAcrUniEntry
        MAX-ACCESS not-accessible
        STATUS current
        DESCRIPTION
            "This entry describes the configuration message of IEEE 1588 ACR unicast."
        INDEX{ optixPtpAcrUniId }
        ::= { optixPktPtpAcrUniTable 1 }

    OptixPktPtpAcrUniEntry ::=
        SEQUENCE {
            optixPtpAcrUniId
                Unsigned32,
            optixPtpAcrUniNegEnable
                INTEGER,
            optixPtpAcrUniMasterIPAddr
                IpAddress,
            optixPtpAcrUniMasterIPMask
                IpAddress,
            optixPtpAcrUniSrcPri
                Unsigned32,
            optixPtpAcrUniMasterState
                INTEGER,
            optixPtpAcrUniBoardId
                Unsigned32,
            optixPtpAcrUniSubBoardId
                Unsigned32,
            optixPtpAcrUniPortId
                Unsigned32,
            optixPtpAcrUniDMAC
                OCTET STRING,
            optixPtpAcrUniTnlInLabel
                Unsigned32,
            optixPtpAcrUniTnlOutLabel
                Unsigned32,
            optixPtpAcrUniPwInLabel
                Unsigned32,
            optixPtpAcrUniPwOutLabel
                Unsigned32,
            optixPtpAcrUniTnlExp
                Unsigned32,
            optixPtpAcrUniTnlVlanId
                Unsigned32,
            optixPtpAcrUniTnlVlanPri
                Unsigned32,
            optixPtpAcrUniPwTpid
                Unsigned32,
            optixPtpAcrUniPwVlan
                Unsigned32,
            optixPtpAcrUniVrfName
                OCTET STRING
        }

    -- 1.3.6.1.4.1.2011.2.25.4.50.13.3.1.1.1
    optixPtpAcrUniId OBJECT-TYPE
        SYNTAX Unsigned32
        MAX-ACCESS not-accessible
        STATUS current
        DESCRIPTION
            "This parameter describes the 1588acr unicast ID."
        ::= { optixPktPtpAcrUniEntry 1 }

    -- 1.3.6.1.4.1.2011.2.25.4.50.13.3.1.1.2
    optixPtpAcrUniNegEnable OBJECT-TYPE
        SYNTAX INTEGER
        {
            disable(0),
            enable(1)
        }
        MAX-ACCESS read-write
        STATUS current
        DESCRIPTION
            "This parameter describes the negotiation enable state. 0 disable, 1 enable"
        ::= { optixPktPtpAcrUniEntry 2 }

    -- 1.3.6.1.4.1.2011.2.25.4.50.13.3.1.1.3
    optixPtpAcrUniMasterIPAddr OBJECT-TYPE
        SYNTAX IpAddress
        MAX-ACCESS read-write
        STATUS current
        DESCRIPTION
            "This parameter describes the master IP address."
        ::= { optixPktPtpAcrUniEntry 3 }

    -- 1.3.6.1.4.1.2011.2.25.4.50.13.3.1.1.4
    optixPtpAcrUniMasterIPMask OBJECT-TYPE
        SYNTAX IpAddress
        MAX-ACCESS read-write
        STATUS current
        DESCRIPTION
            "This parameter describes the subnet mask corresponding to the master IP address."
        ::= { optixPktPtpAcrUniEntry 4 }

    -- 1.3.6.1.4.1.2011.2.25.4.50.13.3.1.1.5
    optixPtpAcrUniSrcPri OBJECT-TYPE
        SYNTAX Unsigned32
        MAX-ACCESS read-write
        STATUS current
        DESCRIPTION
            "This parameter describes the clock source priority. Value range: 1 to 2. The default value is 1."
        ::= { optixPktPtpAcrUniEntry 5 }

    -- 1.3.6.1.4.1.2011.2.25.4.50.13.3.1.1.6
    optixPtpAcrUniMasterState OBJECT-TYPE
        SYNTAX INTEGER
        {
            up(1),
            down(2)
        }
        MAX-ACCESS read-only
        STATUS current
        DESCRIPTION
            "This parameter describes the status of the 1588acr unicast source. 1 up, 2 down"
        ::= { optixPktPtpAcrUniEntry 6 }

    -- 1.3.6.1.4.1.2011.2.25.4.50.13.3.1.1.7
    optixPtpAcrUniBoardId OBJECT-TYPE
        SYNTAX Unsigned32
        MAX-ACCESS read-write
        STATUS current
        DESCRIPTION
            "This parameter describes the board slot ID."
        ::= { optixPktPtpAcrUniEntry 7 }

    -- 1.3.6.1.4.1.2011.2.25.4.50.13.3.1.1.8
    optixPtpAcrUniSubBoardId OBJECT-TYPE
        SYNTAX Unsigned32
        MAX-ACCESS read-write
        STATUS current
        DESCRIPTION
            "This parameter describes the subboard ID."
        ::= { optixPktPtpAcrUniEntry 8 }

    -- 1.3.6.1.4.1.2011.2.25.4.50.13.3.1.1.9
    optixPtpAcrUniPortId OBJECT-TYPE
        SYNTAX Unsigned32
        MAX-ACCESS read-write
        STATUS current
        DESCRIPTION
            "This parameter describes the port number."
        ::= { optixPktPtpAcrUniEntry 9 }

    -- 1.3.6.1.4.1.2011.2.25.4.50.13.3.1.1.10
    optixPtpAcrUniDMAC OBJECT-TYPE
        SYNTAX OCTET STRING
        MAX-ACCESS read-write
        STATUS current
        DESCRIPTION
            "This parameter describes the destination MAC address."
        ::= { optixPktPtpAcrUniEntry 10 }

    -- 1.3.6.1.4.1.2011.2.25.4.50.13.3.1.1.11
    optixPtpAcrUniTnlInLabel OBJECT-TYPE
        SYNTAX Unsigned32
        MAX-ACCESS read-write
        STATUS current
        DESCRIPTION
            "This parameter describes the ingress lable of a tunnel. Value range: 16 to 1048575, 4294967295."
        ::= { optixPktPtpAcrUniEntry 11 }

    -- 1.3.6.1.4.1.2011.2.25.4.50.13.3.1.1.12
    optixPtpAcrUniTnlOutLabel OBJECT-TYPE
        SYNTAX Unsigned32
        MAX-ACCESS read-write
        STATUS current
        DESCRIPTION
            "This parameter describes the egress label of a tunnel. Value range: 16 to 1048575, 4294967295."
        ::= { optixPktPtpAcrUniEntry 12 }

    -- 1.3.6.1.4.1.2011.2.25.4.50.13.3.1.1.13
    optixPtpAcrUniPwInLabel OBJECT-TYPE
        SYNTAX Unsigned32
        MAX-ACCESS read-write
        STATUS current
        DESCRIPTION
            "This parameter describes the ingress label of a PW. Value range: 16 to 1048575, 4294967295."
        ::= { optixPktPtpAcrUniEntry 13 }

    -- 1.3.6.1.4.1.2011.2.25.4.50.13.3.1.1.14
    optixPtpAcrUniPwOutLabel OBJECT-TYPE
        SYNTAX Unsigned32
        MAX-ACCESS read-write
        STATUS current
        DESCRIPTION
            "This parameter describes the egress label of a PW. Value range: 16 to 1048575, 4294967295."
        ::= { optixPktPtpAcrUniEntry 14 }

    -- 1.3.6.1.4.1.2011.2.25.4.50.13.3.1.1.15
    optixPtpAcrUniTnlExp OBJECT-TYPE
        SYNTAX Unsigned32
        MAX-ACCESS read-write
        STATUS current
        DESCRIPTION
            "This parameter describes the tunnel EXP. Value range: 0 to 7. The default value is 6."
        ::= { optixPktPtpAcrUniEntry 15 }

    -- 1.3.6.1.4.1.2011.2.25.4.50.13.3.1.1.16
    optixPtpAcrUniTnlVlanId OBJECT-TYPE
        SYNTAX Unsigned32
        MAX-ACCESS read-write
        STATUS current
        DESCRIPTION
            "This parameter describes the tunnel VLAN. Value range: 1 to 4094, 65535."
        ::= { optixPktPtpAcrUniEntry 16 }

    -- 1.3.6.1.4.1.2011.2.25.4.50.13.3.1.1.17
    optixPtpAcrUniTnlVlanPri OBJECT-TYPE
        SYNTAX Unsigned32
        MAX-ACCESS read-write
        STATUS current
        DESCRIPTION
            "This parameter describes the tunnel VLAN priority. Value range: 0 to 7. The default value is 6."
        ::= { optixPktPtpAcrUniEntry 17 }

    -- 1.3.6.1.4.1.2011.2.25.4.50.13.3.1.1.18
    optixPtpAcrUniPwTpid OBJECT-TYPE
        SYNTAX Unsigned32
        MAX-ACCESS read-write
        STATUS current
        DESCRIPTION
            "This parameter describes the PW TPID. Value range: 1536 to 65535. The default value is 34984."
        ::= { optixPktPtpAcrUniEntry 18 }

    -- 1.3.6.1.4.1.2011.2.25.4.50.13.3.1.1.19
    optixPtpAcrUniPwVlan OBJECT-TYPE
        SYNTAX Unsigned32
        MAX-ACCESS read-write
        STATUS current
        DESCRIPTION
            "This parameter describes the PW VLAN. Value range: 1 to 4094, 65535."
        ::= { optixPktPtpAcrUniEntry 19 }

    -- 1.3.6.1.4.1.2011.2.25.4.50.13.3.1.1.20
    optixPtpAcrUniVrfName OBJECT-TYPE
        SYNTAX OCTET STRING (SIZE(0..31))
        MAX-ACCESS read-write
        STATUS current
        DESCRIPTION
            "This parameter describes the VRF name."
        ::= { optixPktPtpAcrUniEntry 20 }

    -- 1.3.6.1.4.1.2011.2.25.4.50.13.3.2
    optixPktPtpAcrUniPktTable OBJECT-TYPE
        SYNTAX SEQUENCE OF OptixPktPtpAcrUniPktEntry
        MAX-ACCESS not-accessible
        STATUS current
        DESCRIPTION
            "This table describes the configuration message of IEEE 1588 ACR unicast packets."
        ::= { optixPktPtpAcrUniGroup 2 }

    -- 1.3.6.1.4.1.2011.2.25.4.50.13.3.2.1
    optixPktPtpAcrUniPktEntry OBJECT-TYPE
        SYNTAX OptixPktPtpAcrUniPktEntry
        MAX-ACCESS not-accessible
        STATUS current
        DESCRIPTION
            "This entry describes the configuration message of IEEE 1588 ACR unicast packets."
        INDEX{ optixPtpAcrUniPktType }
        ::= { optixPktPtpAcrUniPktTable 1 }

    OptixPktPtpAcrUniPktEntry ::=
        SEQUENCE {
            optixPtpAcrUniPktType
                INTEGER,
            optixPtpAcrUniDurationField
                Unsigned32,
            optixPtpAcrUniSendCycle
                Unsigned32
        }

    -- 1.3.6.1.4.1.2011.2.25.4.50.13.3.2.1.1
    optixPtpAcrUniPktType OBJECT-TYPE
        SYNTAX INTEGER
        {
            sync(1),
            announce(2),
            delay(3)
        }
        MAX-ACCESS not-accessible
        STATUS current
        DESCRIPTION
            "This parameter describes the packet type. 1 sync, 2 announce, 3 delay"
        ::= { optixPktPtpAcrUniPktEntry 1 }

    -- 1.3.6.1.4.1.2011.2.25.4.50.13.3.2.1.2
    optixPtpAcrUniDurationField OBJECT-TYPE
        SYNTAX Unsigned32
        MAX-ACCESS read-write
        STATUS current
        DESCRIPTION
            "This parameter describes the duration field. Value range: 6 to 1000. The default value is 300."
        ::= { optixPktPtpAcrUniPktEntry 2 }

    -- 1.3.6.1.4.1.2011.2.25.4.50.13.3.2.1.3
    optixPtpAcrUniSendCycle OBJECT-TYPE
        SYNTAX Unsigned32
        MAX-ACCESS read-write
        STATUS current
        DESCRIPTION
            "This parameter describes the send cycle. Value range: sync: 3 to 14, announce: 7 to 14, delay: 3 to 14"
        ::= { optixPktPtpAcrUniPktEntry 3 }

    -- 1.3.6.1.4.1.2011.2.25.4.50.13.3.3
    optixPktPtpAcrUniNegStatTable OBJECT-TYPE
        SYNTAX SEQUENCE OF OptixPktPtpAcrUniNegStatEntry
        MAX-ACCESS not-accessible
        STATUS current
        DESCRIPTION
            "This table describes the negotiation state of IEEE 1588 ACR unicast."
        ::= { optixPktPtpAcrUniGroup 3 }

    -- 1.3.6.1.4.1.2011.2.25.4.50.13.3.3.1
    optixPktPtpAcrUniNegStatEntry OBJECT-TYPE
        SYNTAX OptixPktPtpAcrUniNegStatEntry
        MAX-ACCESS not-accessible
        STATUS current
        DESCRIPTION
            "This entry describes the negotiation state of IEEE 1588 ACR unicast."
        INDEX{ optixPtpAcrUniId,optixPtpAcrUniPktType }
        ::= { optixPktPtpAcrUniNegStatTable 1 }

    OptixPktPtpAcrUniNegStatEntry ::=
        SEQUENCE {
            optixPtpAcrUniNegState
                INTEGER
        }

    -- 1.3.6.1.4.1.2011.2.25.4.50.13.3.3.1.1
    optixPtpAcrUniNegState OBJECT-TYPE
        SYNTAX INTEGER
        {
            up(1),
            down(2),
            nouse(3)
        }
        MAX-ACCESS read-only
        STATUS current
        DESCRIPTION
            "This parameter describes the negotiation state. 1 up, 2 down, 3 no-use"
        ::= { optixPktPtpAcrUniNegStatEntry 1 }

    -- 1.3.6.1.4.1.2011.2.25.4.50.13.4
    optixPktPtpAcrUniNeGroup OBJECT IDENTIFIER ::= { optixPktptpclock 4 }

    -- 1.3.6.1.4.1.2011.2.25.4.50.13.4.1
    optixPtpAcrUniDomain OBJECT-TYPE
        SYNTAX Unsigned32
        MAX-ACCESS read-write
        STATUS current
        DESCRIPTION
            "This parameter describes the domain value. Value range: 4 to 23. The default value is 4."
        ::= { optixPktPtpAcrUniNeGroup 1 }

    -- 1.3.6.1.4.1.2011.2.25.4.50.13.4.2
    optixPtpAcrUniSlaveIPAddr OBJECT-TYPE
        SYNTAX IpAddress
        MAX-ACCESS read-write
        STATUS current
        DESCRIPTION
            "This parameter describes the IP address at the local end."
        ::= { optixPktPtpAcrUniNeGroup 2 }

    -- 1.3.6.1.4.1.2011.2.25.4.50.13.4.3
    optixPtpAcrUniSlaveIPMask OBJECT-TYPE
        SYNTAX IpAddress
        MAX-ACCESS read-write
        STATUS current
        DESCRIPTION
            "This parameter describes the subnet mask at the local end."
        ::= { optixPktPtpAcrUniNeGroup 3 }

    -- 1.3.6.1.4.1.2011.2.25.4.50.13.4.4
    optixPtpAcrUniOneTwoWay OBJECT-TYPE
        SYNTAX INTEGER
        {
            oneway(1),
            twoway(2)
        }
        MAX-ACCESS read-write
        STATUS current
        DESCRIPTION
            "This parameter describes the one-way or two-way synchronization mode. 1 one-way, 2 two-way"
        ::= { optixPktPtpAcrUniNeGroup 4 }

    -- 1.3.6.1.4.1.2011.2.25.4.50.13.4.5
    optixPtpAcrUniAnnTimeout OBJECT-TYPE
        SYNTAX Unsigned32
        MAX-ACCESS read-write
        STATUS current
        DESCRIPTION
            "This parameter describes the announce packet timeout period. Value range: 2 to 10. The default value is 3."
        ::= { optixPktPtpAcrUniNeGroup 5 }

    -- 1.3.6.1.4.1.2011.2.25.4.50.13.4.6
    optixPtpAcrUniDSCPPri OBJECT-TYPE
        SYNTAX Unsigned32
        MAX-ACCESS read-write
        STATUS current
        DESCRIPTION
            "This parameter describes the DSCP priority. Value range: 0 to 63. The default value is 56."
        ::= { optixPktPtpAcrUniNeGroup 6 }

    -- 1.3.6.1.4.1.2011.2.25.4.50.13.4.7
    optixPtpAcrUniTrackSource OBJECT-TYPE
        SYNTAX Unsigned32
        MAX-ACCESS read-only
        STATUS current
        DESCRIPTION
            "This parameter describes the track source."
        ::= { optixPktPtpAcrUniNeGroup 7 }

    -- 1.3.6.1.4.1.2011.2.25.4.50.13.4.8
    optixPtpAcrUniTrackState OBJECT-TYPE
        SYNTAX INTEGER
        {
            track(1),
            keep(2),
            free(3)
        }
        MAX-ACCESS read-only
        STATUS current
        DESCRIPTION
            "This parameter describes the track state. 1 track, 2 keep, 3 free"
        ::= { optixPktPtpAcrUniNeGroup 8 }

    -- 1.3.6.1.4.1.2011.2.25.4.50.13.4.9
    optixPtpAcrUniLockState OBJECT-TYPE
        SYNTAX INTEGER
        {
            lock(1),
            unlock(2)
        }
        MAX-ACCESS read-only
        STATUS current
        DESCRIPTION
            "This parameter describes the lock state. 1 lock, 2 unlock"
        ::= { optixPktPtpAcrUniNeGroup 9 }

    -- 1.3.6.1.4.1.2011.2.25.4.50.13.4.10
    optixPtpAcrUniCarryMode OBJECT-TYPE
        SYNTAX INTEGER
        {
            l3vpn(1),
            vlan(2),
            qinq(3),
            l2vpn(4),
            l3(5)
        }
        MAX-ACCESS read-write
        STATUS current
        DESCRIPTION
            "This parameter describes the carry mode. 1 L3VPN, 2 VLAN, 3 QINQ, 4 L2VPN, 5 L3"
        ::= { optixPktPtpAcrUniNeGroup 10 }

    -- 1.3.6.1.4.1.2011.2.25.4.50.13.4.11
    optixPtpAcrUniUserVlanId OBJECT-TYPE
        SYNTAX Unsigned32
        MAX-ACCESS read-write
        STATUS current
        DESCRIPTION
            "This parameter describes the user VLAN ID. Value range: 1 to 4094, 65535."
        ::= { optixPktPtpAcrUniNeGroup 11 }

    -- 1.3.6.1.4.1.2011.2.25.4.50.13.4.12
    optixPtpAcrUniUserVlanPri OBJECT-TYPE
        SYNTAX Unsigned32
        MAX-ACCESS read-write
        STATUS current
        DESCRIPTION
            "This parameter describes the user VLAN priority. Value range: 0 to 7. The default value is 6."
        ::= { optixPktPtpAcrUniNeGroup 12 }

    -- 1.3.6.1.4.1.2011.2.25.4.50.13.4.13
    optixPtpAcrUniTpid OBJECT-TYPE
        SYNTAX Unsigned32
        MAX-ACCESS read-write
        STATUS current
        DESCRIPTION
            "This parameter describes the TPID. Value range: 1536 to 65535. The default value is 34984."
        ::= { optixPktPtpAcrUniNeGroup 13 }

    -- 1.3.6.1.4.1.2011.2.25.4.50.13.4.14
    optixPtpAcrUniSVlanId OBJECT-TYPE
        SYNTAX Unsigned32
        MAX-ACCESS read-write
        STATUS current
        DESCRIPTION
            "This parameter describes the SVLAN ID. Value range: 1 to 4094, 65535."
        ::= { optixPktPtpAcrUniNeGroup 14 }

    -- 1.3.6.1.4.1.2011.2.25.4.50.13.4.15
    optixPtpAcrUniSVlanPri OBJECT-TYPE
        SYNTAX Unsigned32
        MAX-ACCESS read-write
        STATUS current
        DESCRIPTION
            "This parameter describes the SVLAN priority. Value range: 0 to 7. The default value is 6."
        ::= { optixPktPtpAcrUniNeGroup 15 }

    -- 1.3.6.1.4.1.2011.2.25.4.50.13.4.16
    optixPtpAcrUniPwCW OBJECT-TYPE
        SYNTAX INTEGER
        {
            notuse(1),
            use(2)
        }
        MAX-ACCESS read-write
        STATUS current
        DESCRIPTION
            "This parameter describes the control word. 1 not-use, 2 use"
        ::= { optixPktPtpAcrUniNeGroup 16 }

    -- 1.3.6.1.4.1.2011.2.25.4.50.13.4.17
    optixPtpAcrUniPwType OBJECT-TYPE
        SYNTAX INTEGER
        {
            ethtag(4),
            ethraw(5)
        }
        MAX-ACCESS read-write
        STATUS current
        DESCRIPTION
            "This parameter describes the PW type. 4 ethtag, 5 ethraw"
        ::= { optixPktPtpAcrUniNeGroup 17 }

END
