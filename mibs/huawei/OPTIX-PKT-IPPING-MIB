-- OPTIX-PKT-IPPING-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-IPPING-MIB DEFINITIONS ::= BEGIN
    IMPORTS
        optixProvisionPtn
            FROM OPTIX-OID-MIB
        OBJECT-GROUP,MODULE-COMPLIANCE
            FROM SNMPv2-CONF
        optixLogBoardId,optixLogSubCardId
            FROM OPTIX-BOARD-MANAGE-MIB
        optixPortId
            FROM OPTIX-PORT-MANAGE-MIB
        Unsigned32,OBJECT-TYPE,MODULE-IDENTITY,NOTIFICATION-TYPE,IpAddress
            FROM SNMPv2-SMI
        MacAddress,RowStatus
            FROM SNMPv2-TC
        ;

    optixPktIPPING MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the IP information of device"
        REVISION "201204200000Z"
        DESCRIPTION
            "The initial revision of this MIB module1."
        ::={ optixProvisionPtn 53 }

    -- 1.3.6.1.4.1.2011.2.25.4.50.53.1
    optixPktIPPINGGroup OBJECT IDENTIFIER ::= { optixPktIPPING 1 }

    -- 1.3.6.1.4.1.2011.2.25.4.50.53.1.1
    optixPKTIPPingTable OBJECT-TYPE
        SYNTAX SEQUENCE OF OptixPKTIPPingEntry
        MAX-ACCESS not-accessible
        STATUS current
        DESCRIPTION
            "This table describes the basic IPPing port information configurations."
        ::= { optixPktIPPINGGroup 1 }

    -- 1.3.6.1.4.1.2011.2.25.4.50.53.1.1.1
    optixPKTIPPingEntry OBJECT-TYPE
        SYNTAX OptixPKTIPPingEntry
        MAX-ACCESS not-accessible
        STATUS current
        DESCRIPTION
            "This entry describes the basic IPPing port information configurations."
        INDEX{ optixLogBoardId,optixLogSubCardId,optixPortId }
        ::= { optixPKTIPPingTable 1 }

    OptixPKTIPPingEntry ::=
        SEQUENCE {
            optixPKTIPPingenable
                INTEGER,
            optixPKTIPPingPortIP
                IpAddress,
            optixPKTIPPingPortMask
                IpAddress,
            optixPKTIPPingNextopIP
                IpAddress,
            optixPKTIPPingNextopMask
                IpAddress,
            optixPKTIPPingIplistNum
                Unsigned32,
            optixPKTIPPingIplist
                OCTET STRING,
            optixPKTIPPingRoutelist
                Unsigned32,
            optixPKTIPPingIPAddr
                IpAddress,
            optixPKTIPPingIPMac
                OCTET STRING,
            optixPKTIPPingArpPort
                Unsigned32,
            optixPKTIPPingArpIP
                OCTET STRING,
            optixPKTIPPingArpIPMac
                OCTET STRING
        }

    -- 1.3.6.1.4.1.2011.2.25.4.50.53.1.1.1.1
    optixPKTIPPingenable OBJECT-TYPE
        SYNTAX INTEGER
        {
            disable(0),
            enable(1)
        }
        MAX-ACCESS read-write
        STATUS current
        DESCRIPTION
            "This objectis used to reportthe enable status of the IPPing port. 0: disable, 1: enable"
        ::= { optixPKTIPPingEntry 1 }

    -- 1.3.6.1.4.1.2011.2.25.4.50.53.1.1.1.2
    optixPKTIPPingPortIP OBJECT-TYPE
        SYNTAX IpAddress
        MAX-ACCESS read-write
        STATUS current
        DESCRIPTION
            "This objectis used to reportthe IP Adress of the IPPing port."
        ::= { optixPKTIPPingEntry 2 }

    -- 1.3.6.1.4.1.2011.2.25.4.50.53.1.1.1.3
    optixPKTIPPingPortMask OBJECT-TYPE
        SYNTAX IpAddress
        MAX-ACCESS read-write
        STATUS current
        DESCRIPTION
            "This objectis used to reportthe IP MASK of the IPPing port."
        ::= { optixPKTIPPingEntry 3 }

    -- 1.3.6.1.4.1.2011.2.25.4.50.53.1.1.1.4
    optixPKTIPPingNextopIP OBJECT-TYPE
        SYNTAX IpAddress
        MAX-ACCESS read-write
        STATUS current
        DESCRIPTION
            "This objectis used to reportthe IP Adress of the Next IPPing port."
        ::= { optixPKTIPPingEntry 4 }

    -- 1.3.6.1.4.1.2011.2.25.4.50.53.1.1.1.5
    optixPKTIPPingNextopMask OBJECT-TYPE
        SYNTAX IpAddress
        MAX-ACCESS read-write
        STATUS current
        DESCRIPTION
            "This objectis used to reportthe IP MASK of the Next IPPing port."
        ::= { optixPKTIPPingEntry 5 }

    -- 1.3.6.1.4.1.2011.2.25.4.50.53.1.1.1.6
    optixPKTIPPingIplistNum OBJECT-TYPE
        SYNTAX Unsigned32
        MAX-ACCESS read-write
        STATUS current
        DESCRIPTION
            "This objectis used to reportthe IP List Num of the IPPing port."
        ::= { optixPKTIPPingEntry 6 }

    -- 1.3.6.1.4.1.2011.2.25.4.50.53.1.1.1.7
    optixPKTIPPingIplist OBJECT-TYPE
        SYNTAX OCTET STRING
        MAX-ACCESS read-write
        STATUS current
        DESCRIPTION
            "This objectis used to reportthe IP List of the IPPing port."
        ::= { optixPKTIPPingEntry 7 }

    -- 1.3.6.1.4.1.2011.2.25.4.50.53.1.1.1.8
    optixPKTIPPingRoutelist OBJECT-TYPE
        SYNTAX Unsigned32
        MAX-ACCESS read-write
        STATUS current
        DESCRIPTION
            "This objectis used to report the Static Route Num of the IP PING PORT ."
        ::= { optixPKTIPPingEntry 8 }

    -- 1.3.6.1.4.1.2011.2.25.4.50.53.1.1.1.9
    optixPKTIPPingIPAddr OBJECT-TYPE
        SYNTAX IpAddress
        MAX-ACCESS read-write
        STATUS current
        DESCRIPTION
            "This objectis used to report the Static Route IP Addr List of the IP PING PORT ."
        ::= { optixPKTIPPingEntry 9 }

    -- 1.3.6.1.4.1.2011.2.25.4.50.53.1.1.1.10
    optixPKTIPPingIPMac OBJECT-TYPE
        SYNTAX OCTET STRING
        MAX-ACCESS read-write
        STATUS current
        DESCRIPTION
            "This objectis used to report the MAC Addr List of the IP PING PORT ."
        ::= { optixPKTIPPingEntry 10 }

    -- 1.3.6.1.4.1.2011.2.25.4.50.53.1.1.1.11
    optixPKTIPPingArpPort OBJECT-TYPE
        SYNTAX Unsigned32
        MAX-ACCESS read-only
        STATUS current
        DESCRIPTION
            "This objectis used to report the port which learn the arp table"
        ::= { optixPKTIPPingEntry 11 }

    -- 1.3.6.1.4.1.2011.2.25.4.50.53.1.1.1.12
    optixPKTIPPingArpIP OBJECT-TYPE
        SYNTAX OCTET STRING
        MAX-ACCESS read-only
        STATUS current
        DESCRIPTION
            "This objectis used to report the IP Addr in the arp table,have a one-to-one correspondence between report the IP Addr in the arp table and report the MAC Addr in the arp table."
        ::= { optixPKTIPPingEntry 12 }

    -- 1.3.6.1.4.1.2011.2.25.4.50.53.1.1.1.13
    optixPKTIPPingArpIPMac OBJECT-TYPE
        SYNTAX OCTET STRING
        MAX-ACCESS read-only
        STATUS current
        DESCRIPTION
            "This objectis used to report the MAC Addr in the arp table"
        ::= { optixPKTIPPingEntry 13 }

    -- 1.3.6.1.4.1.2011.2.25.4.50.53.1.2
    optixPKTIPPingVlanTable OBJECT-TYPE
        SYNTAX SEQUENCE OF OptixPKTIPPingVlanEntry
        MAX-ACCESS not-accessible
        STATUS current
        DESCRIPTION
            "This table describes the basic IPPing port VLAN information configurations."
        ::= { optixPktIPPINGGroup 2 }

    -- 1.3.6.1.4.1.2011.2.25.4.50.53.1.2.1
    optixPKTIPPingVlanEntry OBJECT-TYPE
        SYNTAX OptixPKTIPPingVlanEntry
        MAX-ACCESS not-accessible
        STATUS current
        DESCRIPTION
            "This entry describes the basic IPPing port VLAN information configurations."
        INDEX{ optixLogBoardId,optixLogSubCardId,optixPortId,optixPKTIPPingProtolType }
        ::= { optixPKTIPPingVlanTable 1 }

    OptixPKTIPPingVlanEntry ::=
        SEQUENCE {
            optixPKTIPPingProtolType
                INTEGER,
            optixPKTIPPingVlanID
                Unsigned32,
            optixPKTIPPingVlanPrio
                Unsigned32
        }

    -- 1.3.6.1.4.1.2011.2.25.4.50.53.1.2.1.1
    optixPKTIPPingProtolType OBJECT-TYPE
        SYNTAX INTEGER
        {
            ipPing(1),
            ipPingEx(2)
        }
        MAX-ACCESS not-accessible
        STATUS current
        DESCRIPTION
            "This objectis used to reportthe type of the IPPing port. 1: IPPing"
        ::= { optixPKTIPPingVlanEntry 1 }

    -- 1.3.6.1.4.1.2011.2.25.4.50.53.1.2.1.2
    optixPKTIPPingVlanID OBJECT-TYPE
        SYNTAX Unsigned32
        MAX-ACCESS read-write
        STATUS current
        DESCRIPTION
            "This objectis used to reportthe Vlan ID of the IPPING message."
        ::= { optixPKTIPPingVlanEntry 2 }

    -- 1.3.6.1.4.1.2011.2.25.4.50.53.1.2.1.3
    optixPKTIPPingVlanPrio OBJECT-TYPE
        SYNTAX Unsigned32
        MAX-ACCESS read-write
        STATUS current
        DESCRIPTION
            "This objectis used to reportthe VLAN prio of the IPPing port. Value range: 0 to 7."
        ::= { optixPKTIPPingVlanEntry 3 }

    -- 1.3.6.1.4.1.2011.2.25.4.50.53.1.3
    optixPKTIPPingArpTrap OBJECT IDENTIFIER ::= { optixPktIPPINGGroup 3 }

    -- 1.3.6.1.4.1.2011.2.25.4.50.53.1.3.1
    optixPKTIPPingArpEvent NOTIFICATION-TYPE
        OBJECTS{ optixPktIPPingBoardId,optixPktIPPingSubBoardId,optixPktIPPingPortId,optixPktIPPingDMAC,optixPktIPPingSMAC,optixPktIPPingVlanID,optixPktIPPingVlanPri,optixPktIPPingArpType,optixPktIPPingArpSMAC,optixPktIPPingArpSIP,optixPktIPPingArpDMAC,optixPktIPPingArpDIP }
        STATUS current
        DESCRIPTION
            "This objectis used to report the ARP Event information of the IP Ping port."
        ::= { optixPKTIPPingArpTrap 1 }

    -- 1.3.6.1.4.1.2011.2.25.4.50.53.1.4
    optixPKTIPPingPingTrap OBJECT IDENTIFIER ::= { optixPktIPPINGGroup 4 }

    -- 1.3.6.1.4.1.2011.2.25.4.50.53.1.4.1
    optixPKTIPPingPingEvent NOTIFICATION-TYPE
        OBJECTS{ optixPktIPPingBoardId,optixPktIPPingSubBoardId,optixPktIPPingPortId,optixPktIPPingDMAC,optixPktIPPingSMAC,optixPktIPPingVlanID,optixPktIPPingVlanPri,optixPktIPPingProType,optixPktIPPingPingSIP,optixPktIPPingPingDIP,optixPktIPPingPingType }
        STATUS current
        DESCRIPTION
            "This objectis used to report the Ping Event information of the IP Ping port."
        ::= { optixPKTIPPingPingTrap 1 }

    -- 1.3.6.1.4.1.2011.2.25.4.50.53.1.5
    optixPKTIPPingTrapMember OBJECT IDENTIFIER ::= { optixPktIPPINGGroup 5 }

    -- 1.3.6.1.4.1.2011.2.25.4.50.53.1.5.1
    optixPktIPPingBoardId OBJECT-TYPE
        SYNTAX Unsigned32
        MAX-ACCESS accessible-for-notify
        STATUS current
        DESCRIPTION
            "This object indicates the slot ID of the IPPING port."
        ::= { optixPKTIPPingTrapMember 1 }

    -- 1.3.6.1.4.1.2011.2.25.4.50.53.1.5.2
    optixPktIPPingSubBoardId OBJECT-TYPE
        SYNTAX Unsigned32
        MAX-ACCESS accessible-for-notify
        STATUS current
        DESCRIPTION
            "This object indicates the sbuboard ID of the IPPING port."
        ::= { optixPKTIPPingTrapMember 2 }

    -- 1.3.6.1.4.1.2011.2.25.4.50.53.1.5.3
    optixPktIPPingPortId OBJECT-TYPE
        SYNTAX Unsigned32
        MAX-ACCESS accessible-for-notify
        STATUS current
        DESCRIPTION
            "This object indicates the port ID of the IPPING port."
        ::= { optixPKTIPPingTrapMember 3 }

    -- 1.3.6.1.4.1.2011.2.25.4.50.53.1.5.4
    optixPktIPPingDMAC OBJECT-TYPE
        SYNTAX OCTET STRING
        MAX-ACCESS accessible-for-notify
        STATUS current
        DESCRIPTION
            "This objectis used to reportthe dest MAC of the IPPING message."
        ::= { optixPKTIPPingTrapMember 4 }

    -- 1.3.6.1.4.1.2011.2.25.4.50.53.1.5.5
    optixPktIPPingSMAC OBJECT-TYPE
        SYNTAX OCTET STRING
        MAX-ACCESS accessible-for-notify
        STATUS current
        DESCRIPTION
            "This objectis used to reportthe source MAC of the IPPING message."
        ::= { optixPKTIPPingTrapMember 5 }

    -- 1.3.6.1.4.1.2011.2.25.4.50.53.1.5.6
    optixPktIPPingVlanID OBJECT-TYPE
        SYNTAX Unsigned32
        MAX-ACCESS accessible-for-notify
        STATUS current
        DESCRIPTION
            "This objectis used to reportthe Vlan ID of the IPPING message."
        ::= { optixPKTIPPingTrapMember 6 }

    -- 1.3.6.1.4.1.2011.2.25.4.50.53.1.5.7
    optixPktIPPingVlanPri OBJECT-TYPE
        SYNTAX Unsigned32
        MAX-ACCESS accessible-for-notify
        STATUS current
        DESCRIPTION
            "This objectis used to report the Vlan priority of the IPPING message."
        ::= { optixPKTIPPingTrapMember 7 }

    -- 1.3.6.1.4.1.2011.2.25.4.50.53.1.5.8
    optixPktIPPingArpType OBJECT-TYPE
        SYNTAX INTEGER
        {
            txarpreq(1),
            rxarpreply(2),
            rxarpreq(3),
            txarpreply(4)
        }
        MAX-ACCESS accessible-for-notify
        STATUS current
        DESCRIPTION
            "This objectis used to reportthe type of the IPPING protocol."
        ::= { optixPKTIPPingTrapMember 8 }

    -- 1.3.6.1.4.1.2011.2.25.4.50.53.1.5.9
    optixPktIPPingArpSMAC OBJECT-TYPE
        SYNTAX OCTET STRING
        MAX-ACCESS accessible-for-notify
        STATUS current
        DESCRIPTION
            "This objectis used to reportthe source MAC of the Arp protocol message."
        ::= { optixPKTIPPingTrapMember 9 }

    -- 1.3.6.1.4.1.2011.2.25.4.50.53.1.5.10
    optixPktIPPingArpSIP OBJECT-TYPE
        SYNTAX OCTET STRING
        MAX-ACCESS accessible-for-notify
        STATUS current
        DESCRIPTION
            "This objectis used to reportthe source IP of the Arp protocol message."
        ::= { optixPKTIPPingTrapMember 10 }

    -- 1.3.6.1.4.1.2011.2.25.4.50.53.1.5.11
    optixPktIPPingArpDMAC OBJECT-TYPE
        SYNTAX OCTET STRING
        MAX-ACCESS accessible-for-notify
        STATUS current
        DESCRIPTION
            "This objectis used to reportthe dest MAC of the Arp protocol message."
        ::= { optixPKTIPPingTrapMember 11 }

    -- 1.3.6.1.4.1.2011.2.25.4.50.53.1.5.12
    optixPktIPPingArpDIP OBJECT-TYPE
        SYNTAX OCTET STRING
        MAX-ACCESS accessible-for-notify
        STATUS current
        DESCRIPTION
            "This objectis used to reportthe dest IP of the Arp protocol message."
        ::= { optixPKTIPPingTrapMember 12 }

    -- 1.3.6.1.4.1.2011.2.25.4.50.53.1.5.13
    optixPktIPPingProType OBJECT-TYPE
        SYNTAX INTEGER
        {
            icmp(1)
        }
        MAX-ACCESS accessible-for-notify
        STATUS current
        DESCRIPTION
            "This objectis used to reportthe IP title type of the IPPING message."
        ::= { optixPKTIPPingTrapMember 13 }

    -- 1.3.6.1.4.1.2011.2.25.4.50.53.1.5.14
    optixPktIPPingPingSIP OBJECT-TYPE
        SYNTAX OCTET STRING
        MAX-ACCESS accessible-for-notify
        STATUS current
        DESCRIPTION
            "This objectis used to reportthe source IP of the IPPING protocol message."
        ::= { optixPKTIPPingTrapMember 14 }

    -- 1.3.6.1.4.1.2011.2.25.4.50.53.1.5.15
    optixPktIPPingPingDIP OBJECT-TYPE
        SYNTAX OCTET STRING
        MAX-ACCESS accessible-for-notify
        STATUS current
        DESCRIPTION
            "This objectis used to reportthe dest MAC of the IPPING protocol message."
        ::= { optixPKTIPPingTrapMember 15 }

    -- 1.3.6.1.4.1.2011.2.25.4.50.53.1.5.16
    optixPktIPPingPingType OBJECT-TYPE
        SYNTAX INTEGER
        {
            reply(0),
            request(8)
        }
        MAX-ACCESS accessible-for-notify
        STATUS current
        DESCRIPTION
            "This objectis used to reportthe respond type of the IPPING message."
        ::= { optixPKTIPPingTrapMember 16 }

    -- 1.3.6.1.4.1.2011.2.25.4.50.53.1.5.18
    optixPktIPPingState OBJECT-TYPE
        SYNTAX Unsigned32
        MAX-ACCESS accessible-for-notify
        STATUS current
        DESCRIPTION
            "This parameter specifies whether the local ping or remote ping reports the IP ping event."
        ::= { optixPKTIPPingTrapMember 18 }

    -- 1.3.6.1.4.1.2011.2.25.4.50.53.1.5.19
    optixPktIPPingPktLen OBJECT-TYPE
        SYNTAX Unsigned32
        MAX-ACCESS accessible-for-notify
        STATUS current
        DESCRIPTION
            "This parameter specifies the number of bytes in a packet."
        ::= { optixPKTIPPingTrapMember 19 }

    -- 1.3.6.1.4.1.2011.2.25.4.50.53.1.5.20
    optixPktIPPingPktSeq OBJECT-TYPE
        SYNTAX Unsigned32
        MAX-ACCESS accessible-for-notify
        STATUS current
        DESCRIPTION
            "This parameter specifies the sequence number of a packet."
        ::= { optixPKTIPPingTrapMember 20 }

    -- 1.3.6.1.4.1.2011.2.25.4.50.53.1.5.21
    optixPktIPPingDelay OBJECT-TYPE
        SYNTAX Unsigned32
        MAX-ACCESS accessible-for-notify
        STATUS current
        DESCRIPTION
            "This parameter specifies the response time."
        ::= { optixPKTIPPingTrapMember 21 }

    -- 1.3.6.1.4.1.2011.2.25.4.50.53.1.5.22
    optixPktIPPingTxNum OBJECT-TYPE
        SYNTAX Unsigned32
        MAX-ACCESS accessible-for-notify
        STATUS current
        DESCRIPTION
            "This parameter specifies the number of sent packets."
        ::= { optixPKTIPPingTrapMember 22 }

    -- 1.3.6.1.4.1.2011.2.25.4.50.53.1.5.23
    optixPktIPPingRxNum OBJECT-TYPE
        SYNTAX Unsigned32
        MAX-ACCESS accessible-for-notify
        STATUS current
        DESCRIPTION
            "This parameter specifies the number of received packets."
        ::= { optixPKTIPPingTrapMember 23 }

    -- 1.3.6.1.4.1.2011.2.25.4.50.53.1.5.24
    optixPktIPPingLOSERATE OBJECT-TYPE
        SYNTAX Unsigned32
        MAX-ACCESS accessible-for-notify
        STATUS current
        DESCRIPTION
            "This parameter specifies the packet loss rate."
        ::= { optixPKTIPPingTrapMember 24 }

    -- 1.3.6.1.4.1.2011.2.25.4.50.53.1.6
    optixPKTIPPingStateTable OBJECT-TYPE
        SYNTAX SEQUENCE OF OptixPKTIPPingStateEntry
        MAX-ACCESS not-accessible
        STATUS current
        DESCRIPTION
            "This table describes the basic information to support the start of the IP PING"
        ::= { optixPktIPPINGGroup 6 }

    -- 1.3.6.1.4.1.2011.2.25.4.50.53.1.6.1
    optixPKTIPPingStateEntry OBJECT-TYPE
        SYNTAX OptixPKTIPPingStateEntry
        MAX-ACCESS not-accessible
        STATUS current
        DESCRIPTION
            "This entry describes the basic key information to support the start of the IP Ping"
        INDEX{ optixCurtPingNum }
        ::= { optixPKTIPPingStateTable 1 }

    OptixPKTIPPingStateEntry ::=
        SEQUENCE {
            optixCurtPingNum
                Unsigned32,
            optixCurtPingDstIPAddr
                IpAddress,
            optixCurtPingPostion
                INTEGER,
            optixCurtPingInBid
                Unsigned32,
            optixCurtPingInSubid
                Unsigned32,
            optixCurtPingInPid
                Unsigned32,
            optixCurtPingTos
                Unsigned32,
            optixCurtPingtime
                INTEGER,
            optixCurtPingCnt
                Unsigned32,
            optixCurtPingLength
                Unsigned32,
            opitxCurtPingoptixRowStatus
                RowStatus
        }

    -- 1.3.6.1.4.1.2011.2.25.4.50.53.1.6.1.1
    optixCurtPingNum OBJECT-TYPE
        SYNTAX Unsigned32
        MAX-ACCESS not-accessible
        STATUS current
        DESCRIPTION
            "This entry describes the number of IP PING object(only support one)"
        ::= { optixPKTIPPingStateEntry 1 }

    -- 1.3.6.1.4.1.2011.2.25.4.50.53.1.6.1.2
    optixCurtPingDstIPAddr OBJECT-TYPE
        SYNTAX IpAddress
        MAX-ACCESS read-create
        STATUS current
        DESCRIPTION
            "This entry describes the destination addr of IP ping operation"
        ::= { optixPKTIPPingStateEntry 2 }

    -- 1.3.6.1.4.1.2011.2.25.4.50.53.1.6.1.3
    optixCurtPingPostion OBJECT-TYPE
        SYNTAX INTEGER
        {
            near(0),
            far(1)
        }
        MAX-ACCESS read-create
        STATUS current
        DESCRIPTION
            "This entry describes the type of IP PING, 0 means near-end IP PING,1 means far-end IP PING"
        ::= { optixPKTIPPingStateEntry 3 }

    -- 1.3.6.1.4.1.2011.2.25.4.50.53.1.6.1.4
    optixCurtPingInBid OBJECT-TYPE
        SYNTAX Unsigned32
        MAX-ACCESS read-create
        STATUS current
        DESCRIPTION
            "This entry describes the entrance-board,the value must be the oxffff if the operation is the near-end IP ping"
        ::= { optixPKTIPPingStateEntry 4 }

    -- 1.3.6.1.4.1.2011.2.25.4.50.53.1.6.1.5
    optixCurtPingInSubid OBJECT-TYPE
        SYNTAX Unsigned32
        MAX-ACCESS read-create
        STATUS current
        DESCRIPTION
            "This entry describes the entrance-subcard t,the value must be the oxff if the operation is the near-end IP ping"
        ::= { optixPKTIPPingStateEntry 5 }

    -- 1.3.6.1.4.1.2011.2.25.4.50.53.1.6.1.6
    optixCurtPingInPid OBJECT-TYPE
        SYNTAX Unsigned32
        MAX-ACCESS read-create
        STATUS current
        DESCRIPTION
            "This entry describes the entrance-port,the value must be the oxffff if the operation is the near-end IP ping"
        ::= { optixPKTIPPingStateEntry 6 }

    -- 1.3.6.1.4.1.2011.2.25.4.50.53.1.6.1.7
    optixCurtPingTos OBJECT-TYPE
        SYNTAX Unsigned32
        MAX-ACCESS read-create
        STATUS current
        DESCRIPTION
            "This entry decribes the TOS value of the ECHO-REQUEST packet,range 0~255,default 0"
        ::= { optixPKTIPPingStateEntry 7 }

    -- 1.3.6.1.4.1.2011.2.25.4.50.53.1.6.1.8
    optixCurtPingtime OBJECT-TYPE
        SYNTAX INTEGER
        {
            twoSecond(0),
            tenSecond(1)
        }
        MAX-ACCESS read-create
        STATUS current
        DESCRIPTION
            "This entry decribes the timeout value,range 0~1,default 0,0 means 1sec,1 means 10sec"
        ::= { optixPKTIPPingStateEntry 8 }

    -- 1.3.6.1.4.1.2011.2.25.4.50.53.1.6.1.9
    optixCurtPingCnt OBJECT-TYPE
        SYNTAX Unsigned32
        MAX-ACCESS read-create
        STATUS current
        DESCRIPTION
            "This entry decribes the retry times of the ECHO-REQUEST packet,range 0~65535,default 3"
        ::= { optixPKTIPPingStateEntry 9 }

    -- 1.3.6.1.4.1.2011.2.25.4.50.53.1.6.1.10
    optixCurtPingLength OBJECT-TYPE
        SYNTAX Unsigned32
        MAX-ACCESS read-create
        STATUS current
        DESCRIPTION
            "This entry decribes the length of the ECHO-REQUEST packet"
        ::= { optixPKTIPPingStateEntry 10 }

    -- 1.3.6.1.4.1.2011.2.25.4.50.53.1.6.1.255
    opitxCurtPingoptixRowStatus OBJECT-TYPE
        SYNTAX RowStatus
        MAX-ACCESS read-create
        STATUS current
        DESCRIPTION
            "This object indicates the row status of IP PING."
        ::= { optixPKTIPPingStateEntry 255 }

    -- 1.3.6.1.4.1.2011.2.25.4.50.53.1.7
    optixPKTIPPingResponseTrap OBJECT IDENTIFIER ::= { optixPktIPPINGGroup 7 }

    -- 1.3.6.1.4.1.2011.2.25.4.50.53.1.7.1
    optixPKTIPPingResponse NOTIFICATION-TYPE
        OBJECTS{ optixPktIPPingDstIP,optixPktIPPingPacketSize,optixPktIPPingPacketSEQ,optixPktIPPingResponseTime }
        STATUS current
        DESCRIPTION
            "This objectis used to report the Response Event information of the IP Ping port."
        ::= { optixPKTIPPingResponseTrap 1 }

    -- 1.3.6.1.4.1.2011.2.25.4.50.53.1.8
    optixPKTIPPingTimeOutTrap OBJECT IDENTIFIER ::= { optixPktIPPINGGroup 8 }

    -- 1.3.6.1.4.1.2011.2.25.4.50.53.1.8.1
    optixPKTIPPingTimeOut NOTIFICATION-TYPE
        OBJECTS{ optixPktIPPingDstIP,optixPktIPPingPacketSize,optixPktIPPingPacketSEQ }
        STATUS current
        DESCRIPTION
            "This objectis used to report the Ping Timeout Event information of the IP Ping port."
        ::= { optixPKTIPPingTimeOutTrap 1 }

    -- 1.3.6.1.4.1.2011.2.25.4.50.53.1.9
    optixPKTIPPingStatTrap OBJECT IDENTIFIER ::= { optixPktIPPINGGroup 9 }

    -- 1.3.6.1.4.1.2011.2.25.4.50.53.1.9.1
    optixPKTIPPingStat NOTIFICATION-TYPE
        OBJECTS{ optixPktIPPingDstIP,optixPktIPPingTXNUM,optixPktIPPingRXNUM,optixPktIPPingLoseRate }
        STATUS current
        DESCRIPTION
            "This objectis used to report the Stat Event information of the IP Ping port."
        ::= { optixPKTIPPingStatTrap 1 }

    -- 1.3.6.1.4.1.2011.2.25.4.50.53.1.10
    optixPKTIPPingLaunchTrapMember OBJECT IDENTIFIER ::= { optixPktIPPINGGroup 10 }

    -- 1.3.6.1.4.1.2011.2.25.4.50.53.1.10.1
    optixPktIPPingDstIP OBJECT-TYPE
        SYNTAX IpAddress
        MAX-ACCESS accessible-for-notify
        STATUS current
        DESCRIPTION
            "This objectis used to report the .dst IP addr"
        ::= { optixPKTIPPingLaunchTrapMember 1 }

    -- 1.3.6.1.4.1.2011.2.25.4.50.53.1.10.2
    optixPktIPPingPacketSize OBJECT-TYPE
        SYNTAX Unsigned32
        MAX-ACCESS accessible-for-notify
        STATUS current
        DESCRIPTION
            "This objectis used to report the .size of packet"
        ::= { optixPKTIPPingLaunchTrapMember 2 }

    -- 1.3.6.1.4.1.2011.2.25.4.50.53.1.10.3
    optixPktIPPingPacketSEQ OBJECT-TYPE
        SYNTAX Unsigned32
        MAX-ACCESS accessible-for-notify
        STATUS current
        DESCRIPTION
            "This objectis used to report the sequence of packet"
        ::= { optixPKTIPPingLaunchTrapMember 3 }

    -- 1.3.6.1.4.1.2011.2.25.4.50.53.1.10.4
    optixPktIPPingResponseTime OBJECT-TYPE
        SYNTAX Unsigned32
        MAX-ACCESS accessible-for-notify
        STATUS current
        DESCRIPTION
            "This objectis used to report the response time of packet,0xFFFF means Timeout"
        ::= { optixPKTIPPingLaunchTrapMember 4 }

    -- 1.3.6.1.4.1.2011.2.25.4.50.53.1.10.5
    optixPktIPPingTXNUM OBJECT-TYPE
        SYNTAX Unsigned32
        MAX-ACCESS accessible-for-notify
        STATUS current
        DESCRIPTION
            "This objectis used to report the total number of sending packet"
        ::= { optixPKTIPPingLaunchTrapMember 5 }

    -- 1.3.6.1.4.1.2011.2.25.4.50.53.1.10.6
    optixPktIPPingRXNUM OBJECT-TYPE
        SYNTAX Unsigned32
        MAX-ACCESS accessible-for-notify
        STATUS current
        DESCRIPTION
            "This objectis used to report the total number of receiving packet"
        ::= { optixPKTIPPingLaunchTrapMember 6 }

    -- 1.3.6.1.4.1.2011.2.25.4.50.53.1.10.7
    optixPktIPPingLoseRate OBJECT-TYPE
        SYNTAX Unsigned32
        MAX-ACCESS accessible-for-notify
        STATUS current
        DESCRIPTION
            "This objectis used to report lose packet ratio"
        ::= { optixPKTIPPingLaunchTrapMember 7 }

    -- 1.3.6.1.4.1.2011.2.25.4.50.53.1.11
    optixPktIPPingTrap OBJECT IDENTIFIER ::= { optixPktIPPINGGroup 11 }

    -- 1.3.6.1.4.1.2011.2.25.4.50.53.1.11.1
    optixPktIPPingByIpResponse NOTIFICATION-TYPE
        OBJECTS{ optixPktIPPingPingDIP,optixPktIPPingState,optixPktIPPingBoardId,optixPktIPPingSubBoardId,optixPktIPPingPortId,optixPktIPPingPktLen,optixPktIPPingPktSeq,optixPktIPPingDelay }
        STATUS current
        DESCRIPTION
            "This object describes the event that pinging the IP address of a port is successful."
        ::= { optixPktIPPingTrap 1 }

    -- 1.3.6.1.4.1.2011.2.25.4.50.53.1.11.2
    optixPktIPPingByIpTimeOut NOTIFICATION-TYPE
        OBJECTS{ optixPktIPPingPingDIP,optixPktIPPingState,optixPktIPPingBoardId,optixPktIPPingSubBoardId,optixPktIPPingPortId,optixPktIPPingPktLen,optixPktIPPingPktSeq }
        STATUS current
        DESCRIPTION
            "This object describes the event that pinging the IP address of a port times out."
        ::= { optixPktIPPingTrap 2 }

    -- 1.3.6.1.4.1.2011.2.25.4.50.53.1.11.3
    optixPktIPPingByIpStat NOTIFICATION-TYPE
        OBJECTS{ optixPktIPPingPingDIP,optixPktIPPingState,optixPktIPPingBoardId,optixPktIPPingSubBoardId,optixPktIPPingPortId,optixPktIPPingTxNum,optixPktIPPingRxNum,optixPktIPPingLOSERATE }
        STATUS current
        DESCRIPTION
            "This object provides statistics about an IP ping event."
        ::= { optixPktIPPingTrap 3 }

END
