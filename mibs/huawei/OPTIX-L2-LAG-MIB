-- OPTIX-L2-LAG-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-L2-LAG-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        RowStatus
            FROM SNMPv2-TC
        optixLogBoardId,optixLogSubCardId
            FROM OPTIX-BOARD-MANAGE-MIB
        ;

    optixL2Lag MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of L2 lag"
        REVISION "201204200000Z"
        DESCRIPTION
            "The initial revision of this MIB module1."
        ::={ optixProvisionPtn 19 }

    -- 1.3.6.1.4.1.2011.2.25.4.50.19.1
    optixL2LagGroup OBJECT IDENTIFIER ::= { optixL2Lag 1 }

    -- 1.3.6.1.4.1.2011.2.25.4.50.19.1.1
    optixL2LagLinkAggreTable OBJECT-TYPE
        SYNTAX SEQUENCE OF OptixL2LagLinkAggreEntry
        MAX-ACCESS not-accessible
        STATUS current
        DESCRIPTION
            "This table describes the L2 LAG configurations."
        ::= { optixL2LagGroup 1 }

    -- 1.3.6.1.4.1.2011.2.25.4.50.19.1.1.1
    optixL2LagLinkAggreEntry OBJECT-TYPE
        SYNTAX OptixL2LagLinkAggreEntry
        MAX-ACCESS not-accessible
        STATUS current
        DESCRIPTION
            "This entry describes the L2 LAG configurations."
        INDEX{ optixL2LagLinkAggreId }
        ::= { optixL2LagLinkAggreTable 1 }

    OptixL2LagLinkAggreEntry ::=
        SEQUENCE {
            optixL2LagLinkAggreId
                Unsigned32,
            optixL2LagLinkAggreName
                OCTET STRING,
            optixL2LagLinkAggreGroupSysPri
                Unsigned32,
            optixL2LagLinkAggreGroupType
                INTEGER,
            optixL2LagLinkAggreRvtMode
                INTEGER,
            optixL2LagLinkAggreLoadType
                INTEGER,
            optixL2LagLinkAggreLoadAlg
                INTEGER,
            optixL2LagLinkAggreMainBid
                Unsigned32,
            optixL2LagLinkAggreMainSubId
                Unsigned32,
            optixL2LagLinkAggreMainPid
                Unsigned32,
            optixL2LagLinkAggrMainPortPri
                Unsigned32,
            optixL2LagLinkAggreWtrTime
                Unsigned32,
            optixL2LagLinkAggreSdEn
                INTEGER,
            optixL2LagLinkAggrSlvPortlist
                OCTET STRING,
            optixL2LagLinkAggrWorkPortlist
                OCTET STRING,
            optixL2LagLinkAggreLDProtocol
                INTEGER,
            optixL2LagLinkAggrePeriod
                INTEGER,
            optixL2LagLinkAggreMinActLinkth
                Unsigned32,
            optixL2LagLinkAggreSlavePortNum
                Unsigned32,
            optixL2LagLinkAggreSlavePortInfo
                OCTET STRING,
            optixL2LagLinkAggreWtrTimeEx
                Unsigned32,
            optixL2LagLinkAggreRowStatus
                RowStatus
        }

    -- 1.3.6.1.4.1.2011.2.25.4.50.19.1.1.1.1
    optixL2LagLinkAggreId OBJECT-TYPE
        SYNTAX Unsigned32
        MAX-ACCESS not-accessible
        STATUS current
        DESCRIPTION
            "This object indicates the L2 LAG ID."
        ::= { optixL2LagLinkAggreEntry 1 }

    -- 1.3.6.1.4.1.2011.2.25.4.50.19.1.1.1.2
    optixL2LagLinkAggreName OBJECT-TYPE
        SYNTAX OCTET STRING (SIZE(0..64))
        MAX-ACCESS read-create
        STATUS current
        DESCRIPTION
            "This object indicates the L2 LAG name."
        ::= { optixL2LagLinkAggreEntry 2 }

    -- 1.3.6.1.4.1.2011.2.25.4.50.19.1.1.1.3
    optixL2LagLinkAggreGroupSysPri OBJECT-TYPE
        SYNTAX Unsigned32
        MAX-ACCESS read-create
        STATUS current
        DESCRIPTION
            "This object indicates the system priority of the L2 LAG. Value range: 0 to 65535. The default value is 32768."
        ::= { optixL2LagLinkAggreEntry 3 }

    -- 1.3.6.1.4.1.2011.2.25.4.50.19.1.1.1.4
    optixL2LagLinkAggreGroupType OBJECT-TYPE
        SYNTAX INTEGER
        {
            manual(0),
            static(1)
        }
        MAX-ACCESS read-create
        STATUS current
        DESCRIPTION
            "This object indicates the L2 LAG type. 0: manual, 1: static"
        ::= { optixL2LagLinkAggreEntry 4 }

    -- 1.3.6.1.4.1.2011.2.25.4.50.19.1.1.1.5
    optixL2LagLinkAggreRvtMode OBJECT-TYPE
        SYNTAX INTEGER
        {
            disable(0),
            enable(1)
        }
        MAX-ACCESS read-create
        STATUS current
        DESCRIPTION
            "This object indicates the revetive mode of the L2 LAG. 0: disable, 1: enable"
        ::= { optixL2LagLinkAggreEntry 5 }

    -- 1.3.6.1.4.1.2011.2.25.4.50.19.1.1.1.6
    optixL2LagLinkAggreLoadType OBJECT-TYPE
        SYNTAX INTEGER
        {
            share(0),
            noShare(1)
        }
        MAX-ACCESS read-create
        STATUS current
        DESCRIPTION
            "This object indicates the load-sharing type of the L2 LAG. 0: share, 1: noShare"
        ::= { optixL2LagLinkAggreEntry 6 }

    -- 1.3.6.1.4.1.2011.2.25.4.50.19.1.1.1.7
    optixL2LagLinkAggreLoadAlg OBJECT-TYPE
        SYNTAX INTEGER
        {
            auto(0),
            srcMac(1),
            dstMac(2),
            srcDstMac(3),
            srcIp(4),
            dstIp(5),
            srcDstIp(6),
            srcPort(7),
            dstPort(8),
            srcDstPort(9),
            label(10)
        }
        MAX-ACCESS read-only
        STATUS current
        DESCRIPTION
            "This object indicates the load-sharingalgorithm of the L2 LAG. 0: auto, 1: srcMac, 2: dstMac, 3: srcDstMac, 4: srcIp, 5: dstIp, 6: srcDstIp, 7: srcPort, 8: dstPort, 9: srcDstPort, 10: label"
        ::= { optixL2LagLinkAggreEntry 7 }

    -- 1.3.6.1.4.1.2011.2.25.4.50.19.1.1.1.8
    optixL2LagLinkAggreMainBid OBJECT-TYPE
        SYNTAX Unsigned32
        MAX-ACCESS read-create
        STATUS current
        DESCRIPTION
            "This object indicates the master slot ID of the L2 LAG."
        ::= { optixL2LagLinkAggreEntry 8 }

    -- 1.3.6.1.4.1.2011.2.25.4.50.19.1.1.1.9
    optixL2LagLinkAggreMainSubId OBJECT-TYPE
        SYNTAX Unsigned32
        MAX-ACCESS read-create
        STATUS current
        DESCRIPTION
            "This object indicates the master subboard ID of the L2 LAG."
        ::= { optixL2LagLinkAggreEntry 9 }

    -- 1.3.6.1.4.1.2011.2.25.4.50.19.1.1.1.10
    optixL2LagLinkAggreMainPid OBJECT-TYPE
        SYNTAX Unsigned32
        MAX-ACCESS read-create
        STATUS current
        DESCRIPTION
            "This object indicates the master port number of the L2 LAG."
        ::= { optixL2LagLinkAggreEntry 10 }

    -- 1.3.6.1.4.1.2011.2.25.4.50.19.1.1.1.11
    optixL2LagLinkAggrMainPortPri OBJECT-TYPE
        SYNTAX Unsigned32
        MAX-ACCESS read-only
        STATUS current
        DESCRIPTION
            "This object indicates the master port priority of the L2 LAG. Value range: 0 to 65535. The default value is 32768."
        ::= { optixL2LagLinkAggreEntry 11 }

    -- 1.3.6.1.4.1.2011.2.25.4.50.19.1.1.1.12
    optixL2LagLinkAggreWtrTime OBJECT-TYPE
        SYNTAX Unsigned32
        MAX-ACCESS read-create
        STATUS current
        DESCRIPTION
            "This object indicates the WTR time of the L2 LAG. Value range: 0 to 30 (unit: minute). The default value is 10."
        ::= { optixL2LagLinkAggreEntry 12 }

    -- 1.3.6.1.4.1.2011.2.25.4.50.19.1.1.1.13
    optixL2LagLinkAggreSdEn OBJECT-TYPE
        SYNTAX INTEGER
        {
            disable(0),
            enable(1)
        }
        MAX-ACCESS read-create
        STATUS current
        DESCRIPTION
            "This object indicates the enable status of the LAG switching due to air interface bit errors. 0: disable, 1: enable"
        ::= { optixL2LagLinkAggreEntry 13 }

    -- 1.3.6.1.4.1.2011.2.25.4.50.19.1.1.1.14
    optixL2LagLinkAggrSlvPortlist OBJECT-TYPE
        SYNTAX OCTET STRING (SIZE(0..128))
        MAX-ACCESS read-create
        STATUS current
        DESCRIPTION
            "This object indicates the slave port list of the L2 LAG."
        ::= { optixL2LagLinkAggreEntry 14 }

    -- 1.3.6.1.4.1.2011.2.25.4.50.19.1.1.1.15
    optixL2LagLinkAggrWorkPortlist OBJECT-TYPE
        SYNTAX OCTET STRING (SIZE(0..128))
        MAX-ACCESS read-only
        STATUS current
        DESCRIPTION
            "This object indicates the working port list of the L2 LAG."
        ::= { optixL2LagLinkAggreEntry 15 }

    -- 1.3.6.1.4.1.2011.2.25.4.50.19.1.1.1.16
    optixL2LagLinkAggreLDProtocol OBJECT-TYPE
        SYNTAX INTEGER
        {
            snmpNull(0),
            snmp3ah(1)
        }
        MAX-ACCESS read-create
        STATUS current
        DESCRIPTION
            "This object indicates the LD protocol of the L2 LAG. 0: null, 1: 3ah"
        ::= { optixL2LagLinkAggreEntry 16 }

    -- 1.3.6.1.4.1.2011.2.25.4.50.19.1.1.1.17
    optixL2LagLinkAggrePeriod OBJECT-TYPE
        SYNTAX INTEGER
        {
            long(0),
            short(1)
        }
        MAX-ACCESS read-create
        STATUS current
        DESCRIPTION
            "This object indicates the master port priority of the L2 LAG. 0: long, 1: short"
        ::= { optixL2LagLinkAggreEntry 17 }

    -- 1.3.6.1.4.1.2011.2.25.4.50.19.1.1.1.18
    optixL2LagLinkAggreMinActLinkth OBJECT-TYPE
        SYNTAX Unsigned32
        MAX-ACCESS read-create
        STATUS current
        DESCRIPTION
            "This object indicates the minimum number of active links of the L2 LAG. Value range: 1 to the total number of main and slave ports in a LAG group. The default value is 1."
        ::= { optixL2LagLinkAggreEntry 18 }

    -- 1.3.6.1.4.1.2011.2.25.4.50.19.1.1.1.19
    optixL2LagLinkAggreSlavePortNum OBJECT-TYPE
        SYNTAX Unsigned32
        MAX-ACCESS read-create
        STATUS current
        DESCRIPTION
            "This parameter indicates the number of slave ports in the L2 LAG."
        ::= { optixL2LagLinkAggreEntry 19 }

    -- 1.3.6.1.4.1.2011.2.25.4.50.19.1.1.1.20
    optixL2LagLinkAggreSlavePortInfo OBJECT-TYPE
        SYNTAX OCTET STRING (SIZE(0..1024))
        MAX-ACCESS read-only
        STATUS current
        DESCRIPTION
            "This object indicates the slave port info of active links of the L2 LAG."
        ::= { optixL2LagLinkAggreEntry 20 }

    -- 1.3.6.1.4.1.2011.2.25.4.50.19.1.1.1.21
    optixL2LagLinkAggreWtrTimeEx OBJECT-TYPE
        SYNTAX Unsigned32
        MAX-ACCESS read-create
        STATUS current
        DESCRIPTION
            "This parameter indicates the WTR of the L2 LAG."
        ::= { optixL2LagLinkAggreEntry 21 }

    -- 1.3.6.1.4.1.2011.2.25.4.50.19.1.1.1.255
    optixL2LagLinkAggreRowStatus OBJECT-TYPE
        SYNTAX RowStatus
        MAX-ACCESS read-create
        STATUS current
        DESCRIPTION
            "This object indicates the row status of the L2 LAG."
        ::= { optixL2LagLinkAggreEntry 255 }

    -- 1.3.6.1.4.1.2011.2.25.4.50.19.1.2
    optixL2LagLinkAggrePortTable OBJECT-TYPE
        SYNTAX SEQUENCE OF OptixL2LagLinkAggrePortEntry
        MAX-ACCESS not-accessible
        STATUS current
        DESCRIPTION
            "This table describes the L2 LAG port configurations."
        ::= { optixL2LagGroup 2 }

    -- 1.3.6.1.4.1.2011.2.25.4.50.19.1.2.1
    optixL2LagLinkAggrePortEntry OBJECT-TYPE
        SYNTAX OptixL2LagLinkAggrePortEntry
        MAX-ACCESS not-accessible
        STATUS current
        DESCRIPTION
            "This entry describes the L2 LAG port configurations."
        INDEX{ optixL2LagLinkAggreSlvBid,optixL2LagLinkAggreSlvSbid,optixL2LagLinkAggreSlvPortId }
        ::= { optixL2LagLinkAggrePortTable 1 }

    OptixL2LagLinkAggrePortEntry ::=
        SEQUENCE {
            optixL2LagLinkAggreSlvBid
                Unsigned32,
            optixL2LagLinkAggreSlvSbid
                Unsigned32,
            optixL2LagLinkAggreSlvPortId
                Unsigned32,
            optixL2LagLinkAggreInfoLocalSysId
                OCTET STRING,
            optixL2LagLinkAggreInfoLocalPid
                Unsigned32,
            optixL2LagLinkAggreInfoLocalPortPri
                Unsigned32,
            optixL2LagLinkAggreInfoLocalPortOpKey
                Unsigned32,
            optixL2LagLinkAggreInfoLocalPortLacpFlag
                Unsigned32,
            optixL2LagLinkAggrInfoRemoteSysId
                OCTET STRING,
            optixL2LagLinkAggrInfoRemotePid
                Unsigned32,
            optixL2LagLinkAggrInfoRemotePortPri
                Unsigned32,
            optixL2LagLinkAggrInfoRemoteOpKey
                Unsigned32,
            optixL2LagLinkAggrInfoRemotePortLacpFlag
                Unsigned32,
            optixL2LagLinkAggreRcvPdu
                Unsigned32,
            optixL2LagLinkAggreRcvIllPdu
                Unsigned32,
            optixL2LagLinkAggreSendPdu
                Unsigned32,
            optixL2LagLinkAggreRcvMarkPdu
                Unsigned32,
            optixL2LagLinkAggreRcvIllMarkPdu
                Unsigned32,
            optixL2LagLinkAggreSendMarkPdu
                Unsigned32,
            optixL2LagLinkAggrePortPri
                Unsigned32,
            optixL2LagLinkAggrePortSelected
                INTEGER,
            optixL2LagLinkAggrePortInuse
                INTEGER,
            optixL2LagLinkAggrePortRef
                INTEGER,
            optixL2LagLinkAggreLagId
                Unsigned32,
            optixL2LagLinkAggrePdutype
                INTEGER,
            optixL2LagLinkAggrePortRowStatus
                RowStatus
        }

    -- 1.3.6.1.4.1.2011.2.25.4.50.19.1.2.1.1
    optixL2LagLinkAggreSlvBid OBJECT-TYPE
        SYNTAX Unsigned32
        MAX-ACCESS not-accessible
        STATUS current
        DESCRIPTION
            "This object indicates the slot ID of the L2 LAG port."
        ::= { optixL2LagLinkAggrePortEntry 1 }

    -- 1.3.6.1.4.1.2011.2.25.4.50.19.1.2.1.2
    optixL2LagLinkAggreSlvSbid OBJECT-TYPE
        SYNTAX Unsigned32
        MAX-ACCESS not-accessible
        STATUS current
        DESCRIPTION
            "This object indicates the subboard ID of the L2 LAG port."
        ::= { optixL2LagLinkAggrePortEntry 2 }

    -- 1.3.6.1.4.1.2011.2.25.4.50.19.1.2.1.3
    optixL2LagLinkAggreSlvPortId OBJECT-TYPE
        SYNTAX Unsigned32
        MAX-ACCESS not-accessible
        STATUS current
        DESCRIPTION
            "This object indicates the logical port number of the L2 LAG port."
        ::= { optixL2LagLinkAggrePortEntry 3 }

    -- 1.3.6.1.4.1.2011.2.25.4.50.19.1.2.1.4
    optixL2LagLinkAggreInfoLocalSysId OBJECT-TYPE
        SYNTAX OCTET STRING (SIZE(0..32))
        MAX-ACCESS read-only
        STATUS current
        DESCRIPTION
            "This object indicates the local system ID of the L2 LAG. System priority+MAC address"
        ::= { optixL2LagLinkAggrePortEntry 4 }

    -- 1.3.6.1.4.1.2011.2.25.4.50.19.1.2.1.5
    optixL2LagLinkAggreInfoLocalPid OBJECT-TYPE
        SYNTAX Unsigned32
        MAX-ACCESS read-only
        STATUS current
        DESCRIPTION
            "This object indicates the logical port number of the L2 LAG localport."
        ::= { optixL2LagLinkAggrePortEntry 5 }

    -- 1.3.6.1.4.1.2011.2.25.4.50.19.1.2.1.6
    optixL2LagLinkAggreInfoLocalPortPri OBJECT-TYPE
        SYNTAX Unsigned32
        MAX-ACCESS read-only
        STATUS current
        DESCRIPTION
            "This object indicates the priority of the L2 LAG local port. Value range: 0 to 65535. The default value is 32768."
        ::= { optixL2LagLinkAggrePortEntry 6 }

    -- 1.3.6.1.4.1.2011.2.25.4.50.19.1.2.1.7
    optixL2LagLinkAggreInfoLocalPortOpKey OBJECT-TYPE
        SYNTAX Unsigned32
        MAX-ACCESS read-only
        STATUS current
        DESCRIPTION
            "This object indicates the operation key of the L2 LAG local port. The default value is 0."
        ::= { optixL2LagLinkAggrePortEntry 7 }

    -- 1.3.6.1.4.1.2011.2.25.4.50.19.1.2.1.8
    optixL2LagLinkAggreInfoLocalPortLacpFlag OBJECT-TYPE
        SYNTAX Unsigned32
        MAX-ACCESS read-only
        STATUS current
        DESCRIPTION
            "This object indicates the LACP flag of the L2 LAG local port. The default value is 125. Packets are sent in a long period."
        ::= { optixL2LagLinkAggrePortEntry 8 }

    -- 1.3.6.1.4.1.2011.2.25.4.50.19.1.2.1.9
    optixL2LagLinkAggrInfoRemoteSysId OBJECT-TYPE
        SYNTAX OCTET STRING (SIZE(0..32))
        MAX-ACCESS read-only
        STATUS current
        DESCRIPTION
            "This object indicates the remote system ID of the L2 LAG. System priority+MAC address"
        ::= { optixL2LagLinkAggrePortEntry 9 }

    -- 1.3.6.1.4.1.2011.2.25.4.50.19.1.2.1.10
    optixL2LagLinkAggrInfoRemotePid OBJECT-TYPE
        SYNTAX Unsigned32
        MAX-ACCESS read-only
        STATUS current
        DESCRIPTION
            "This object indicates the logical port number of the L2 LAG remote port."
        ::= { optixL2LagLinkAggrePortEntry 10 }

    -- 1.3.6.1.4.1.2011.2.25.4.50.19.1.2.1.11
    optixL2LagLinkAggrInfoRemotePortPri OBJECT-TYPE
        SYNTAX Unsigned32
        MAX-ACCESS read-only
        STATUS current
        DESCRIPTION
            "This object indicates the priority of the L2 LAG remote port. Value range: 0 to 65535. The default value is 32768."
        ::= { optixL2LagLinkAggrePortEntry 11 }

    -- 1.3.6.1.4.1.2011.2.25.4.50.19.1.2.1.12
    optixL2LagLinkAggrInfoRemoteOpKey OBJECT-TYPE
        SYNTAX Unsigned32
        MAX-ACCESS read-only
        STATUS current
        DESCRIPTION
            "This object indicates the operation key of the L2 LAG remote port. The default value is 0."
        ::= { optixL2LagLinkAggrePortEntry 12 }

    -- 1.3.6.1.4.1.2011.2.25.4.50.19.1.2.1.13
    optixL2LagLinkAggrInfoRemotePortLacpFlag OBJECT-TYPE
        SYNTAX Unsigned32
        MAX-ACCESS read-only
        STATUS current
        DESCRIPTION
            "This object indicates the LACP status of the L2 LAG remote port. The default value is 125. Packets are sent in a long period."
        ::= { optixL2LagLinkAggrePortEntry 13 }

    -- 1.3.6.1.4.1.2011.2.25.4.50.19.1.2.1.14
    optixL2LagLinkAggreRcvPdu OBJECT-TYPE
        SYNTAX Unsigned32
        MAX-ACCESS read-only
        STATUS current
        DESCRIPTION
            "This object indicates the packets received by the L2 LAG. Value range: 0 to 0xffffffff."
        ::= { optixL2LagLinkAggrePortEntry 14 }

    -- 1.3.6.1.4.1.2011.2.25.4.50.19.1.2.1.15
    optixL2LagLinkAggreRcvIllPdu OBJECT-TYPE
        SYNTAX Unsigned32
        MAX-ACCESS read-only
        STATUS current
        DESCRIPTION
            "This object indicates the error packets received by the L2 LAG. Value range: 0 to 0xffffffff."
        ::= { optixL2LagLinkAggrePortEntry 15 }

    -- 1.3.6.1.4.1.2011.2.25.4.50.19.1.2.1.16
    optixL2LagLinkAggreSendPdu OBJECT-TYPE
        SYNTAX Unsigned32
        MAX-ACCESS read-only
        STATUS current
        DESCRIPTION
            "This object indicates the packets transmitted by the L2 LAG. Value range: 0 to 0xffffffff."
        ::= { optixL2LagLinkAggrePortEntry 16 }

    -- 1.3.6.1.4.1.2011.2.25.4.50.19.1.2.1.17
    optixL2LagLinkAggreRcvMarkPdu OBJECT-TYPE
        SYNTAX Unsigned32
        MAX-ACCESS read-only
        STATUS current
        DESCRIPTION
            "This object indicates the marked packets received by the L2 LAG. Value range: 0 to 0xffffffff."
        ::= { optixL2LagLinkAggrePortEntry 17 }

    -- 1.3.6.1.4.1.2011.2.25.4.50.19.1.2.1.18
    optixL2LagLinkAggreRcvIllMarkPdu OBJECT-TYPE
        SYNTAX Unsigned32
        MAX-ACCESS read-only
        STATUS current
        DESCRIPTION
            "This object indicates the marked error packets received by the L2 LAG. Value range: 0 to 0xffffffff."
        ::= { optixL2LagLinkAggrePortEntry 18 }

    -- 1.3.6.1.4.1.2011.2.25.4.50.19.1.2.1.19
    optixL2LagLinkAggreSendMarkPdu OBJECT-TYPE
        SYNTAX Unsigned32
        MAX-ACCESS read-only
        STATUS current
        DESCRIPTION
            "This object indicates the marked packets transmitted by the L2 LAG. Value range: 0 to 0xffffffff."
        ::= { optixL2LagLinkAggrePortEntry 19 }

    -- 1.3.6.1.4.1.2011.2.25.4.50.19.1.2.1.20
    optixL2LagLinkAggrePortPri OBJECT-TYPE
        SYNTAX Unsigned32
        MAX-ACCESS read-create
        STATUS current
        DESCRIPTION
            "This object indicates the priority of the L2 LAG slave port. Value range: 0 to 0xffffffff."
        ::= { optixL2LagLinkAggrePortEntry 20 }

    -- 1.3.6.1.4.1.2011.2.25.4.50.19.1.2.1.21
    optixL2LagLinkAggrePortSelected OBJECT-TYPE
        SYNTAX INTEGER
        {
            selected(0),
            standby(1),
            unselected(2)
        }
        MAX-ACCESS read-only
        STATUS current
        DESCRIPTION
            "This object indicates the selected status of the L2 LAG port. 0: selected, 1: standby, 2: unselected"
        ::= { optixL2LagLinkAggrePortEntry 21 }

    -- 1.3.6.1.4.1.2011.2.25.4.50.19.1.2.1.22
    optixL2LagLinkAggrePortInuse OBJECT-TYPE
        SYNTAX INTEGER
        {
            false(0),
            true(1)
        }
        MAX-ACCESS read-only
        STATUS current
        DESCRIPTION
            "This object indicates the used status of the L2 LAG port. 0: false, 1: true"
        ::= { optixL2LagLinkAggrePortEntry 22 }

    -- 1.3.6.1.4.1.2011.2.25.4.50.19.1.2.1.23
    optixL2LagLinkAggrePortRef OBJECT-TYPE
        SYNTAX INTEGER
        {
            false(0),
            true(1)
        }
        MAX-ACCESS read-only
        STATUS current
        DESCRIPTION
            "This object indicates the referenced status of the L2 LAG port. 0: false, 1: true"
        ::= { optixL2LagLinkAggrePortEntry 23 }

    -- 1.3.6.1.4.1.2011.2.25.4.50.19.1.2.1.24
    optixL2LagLinkAggreLagId OBJECT-TYPE
        SYNTAX Unsigned32
        MAX-ACCESS read-create
        STATUS current
        DESCRIPTION
            "This entry describes the L2 LAG configurations. Value range: 1 to 16."
        ::= { optixL2LagLinkAggrePortEntry 24 }

    -- 1.3.6.1.4.1.2011.2.25.4.50.19.1.2.1.25
    optixL2LagLinkAggrePdutype OBJECT-TYPE
        SYNTAX INTEGER
        {
            all(0),
            lacpdurcv(1),
            lacpdurcvill(2),
            lacpdusend(3),
            markerpdurcv(4),
            markerpdurcvill(5),
            markerrsppdusend(6),
            invalid(7)
        }
        MAX-ACCESS read-create
        STATUS current
        DESCRIPTION
            "This object indicates the cleartype of packets by the L2 LAG. 1: lacpdurcv, 2: lacpdurcvill, 3: lacpdusend, 4: markerpdurcv, 5: markerpdurcvill, 6: markerrsppdusend, 7: invalid"
        ::= { optixL2LagLinkAggrePortEntry 25 }

    -- 1.3.6.1.4.1.2011.2.25.4.50.19.1.2.1.255
    optixL2LagLinkAggrePortRowStatus OBJECT-TYPE
        SYNTAX RowStatus
        MAX-ACCESS read-create
        STATUS current
        DESCRIPTION
            "This object indicates the row status of the L2 LAG logical port."
        ::= { optixL2LagLinkAggrePortEntry 255 }

    -- 1.3.6.1.4.1.2011.2.25.4.50.19.1.3
    optixL2LagPortFsmTable OBJECT-TYPE
        SYNTAX SEQUENCE OF OptixL2LagPortFsmEntry
        MAX-ACCESS not-accessible
        STATUS current
        DESCRIPTION
            "This table describes the L2 LAG history state configurations."
        ::= { optixL2LagGroup 3 }

    -- 1.3.6.1.4.1.2011.2.25.4.50.19.1.3.1
    optixL2LagPortFsmEntry OBJECT-TYPE
        SYNTAX OptixL2LagPortFsmEntry
        MAX-ACCESS not-accessible
        STATUS current
        DESCRIPTION
            "This entry describes the L2 LAG history state configurations."
        INDEX{ optixL2LagLinkAggreId,optixL2LagLinkAggreSlvBid,optixL2LagLinkAggreSlvSbid,optixL2LagLinkAggreSlvPortId,optixL2LagPortFsmType }
        ::= { optixL2LagPortFsmTable 1 }

    OptixL2LagPortFsmEntry ::=
        SEQUENCE {
            optixL2LagPortFsmType
                INTEGER,
            optixL2LagPortFsmInfoNum
                Unsigned32,
            optixL2LagPortFsmCause
                OCTET STRING,
            optixL2LagPortFsmLacpState
                OCTET STRING,
            optixL2LagPortFsmTimeStamp
                OCTET STRING,
            optixL2LagPortFsmTimeCentiSec
                OCTET STRING
        }

    -- 1.3.6.1.4.1.2011.2.25.4.50.19.1.3.1.1
    optixL2LagPortFsmType OBJECT-TYPE
        SYNTAX INTEGER
        {
            rx(1),
            ptx(2),
            mux(3),
            actor(4),
            partner(5)
        }
        MAX-ACCESS not-accessible
        STATUS current
        DESCRIPTION
            "This object indicates the type of the L2 LAG Finite State Machine. 1: rx, 2: ptx, 3: mux, 4: actor, 5: partner"
        ::= { optixL2LagPortFsmEntry 1 }

    -- 1.3.6.1.4.1.2011.2.25.4.50.19.1.3.1.2
    optixL2LagPortFsmInfoNum OBJECT-TYPE
        SYNTAX Unsigned32
        MAX-ACCESS read-only
        STATUS current
        DESCRIPTION
            "This object indicates the number of the L2 LAG Finite State Machine. Value range: 1 to 10."
        ::= { optixL2LagPortFsmEntry 2 }

    -- 1.3.6.1.4.1.2011.2.25.4.50.19.1.3.1.3
    optixL2LagPortFsmCause OBJECT-TYPE
        SYNTAX OCTET STRING (SIZE(0..256))
        MAX-ACCESS read-only
        STATUS current
        DESCRIPTION
            "This object indicates the transferential reason of the L2 LAG Finite State Machine. '&amp;' is used to separate multiple records. For example, PORTENLACPEN &amp; PARTNERSYNCTRUE."
        ::= { optixL2LagPortFsmEntry 3 }

    -- 1.3.6.1.4.1.2011.2.25.4.50.19.1.3.1.4
    optixL2LagPortFsmLacpState OBJECT-TYPE
        SYNTAX OCTET STRING (SIZE(0..256))
        MAX-ACCESS read-only
        STATUS current
        DESCRIPTION
            "This object indicates the state of the L2 LAG Finite State Machine. '&amp;' is used to separate multiple records. For example, MUXWAITING &amp; MUXDETACHED."
        ::= { optixL2LagPortFsmEntry 4 }

    -- 1.3.6.1.4.1.2011.2.25.4.50.19.1.3.1.5
    optixL2LagPortFsmTimeStamp OBJECT-TYPE
        SYNTAX OCTET STRING (SIZE(0..512))
        MAX-ACCESS read-only
        STATUS current
        DESCRIPTION
            "This object indicates the timestamp of the L2 LAG Finite State Machine."
        ::= { optixL2LagPortFsmEntry 5 }

    -- 1.3.6.1.4.1.2011.2.25.4.50.19.1.3.1.6
    optixL2LagPortFsmTimeCentiSec OBJECT-TYPE
        SYNTAX OCTET STRING (SIZE(0..256))
        MAX-ACCESS read-only
        STATUS current
        DESCRIPTION
            "This object indicates the CentiSec of the L2 LAG Finite State Machine."
        ::= { optixL2LagPortFsmEntry 6 }

    -- 1.3.6.1.4.1.2011.2.25.4.50.19.2
    optixL2LagLoadGroup OBJECT IDENTIFIER ::= { optixL2Lag 2 }

    -- 1.3.6.1.4.1.2011.2.25.4.50.19.2.1
    optixL2LagTtllagloadalg OBJECT-TYPE
        SYNTAX INTEGER
        {
            auto(0),
            srcMac(1),
            dstMac(2),
            srcDstMac(3),
            srcIp(4),
            dstIp(5),
            srcDstIp(6),
            srcPort(7),
            dstPort(8),
            srcDstPort(9),
            label(10)
        }
        MAX-ACCESS read-write
        STATUS current
        DESCRIPTION
            "This object indicates the TTL Load alg of the L2 LAG."
        ::= { optixL2LagLoadGroup 1 }

END
