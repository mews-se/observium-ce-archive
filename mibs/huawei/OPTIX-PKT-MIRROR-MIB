-- OPTIX-PKT-MIRROR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-MIRROR-MIB DEFINITIONS ::= BEGIN
    IMPORTS
        optixProvisionPtn
            FROM OPTIX-OID-MIB
        OBJECT-GROUP,MODULE-COMPLIANCE
            FROM SNMPv2-CONF
        Unsigned32,MODULE-IDENTITY,OBJECT-TYPE,NOTIFICATION-TYPE
            FROM SNMPv2-SMI
        RowStatus
            FROM SNMPv2-TC
        ;

    optixPktMirror MODULE-IDENTITY
        LAST-UPDATED "201307091027Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB specifies the port mirroring configuration information of the device"
        REVISION "201307091027Z"
        DESCRIPTION
            "The initial revision of this MIB module."
        ::={ optixProvisionPtn 22 }

    -- 1.3.6.1.4.1.2011.2.25.4.50.22.1
    optixPktMirrorGroup OBJECT IDENTIFIER ::= { optixPktMirror 1 }

    -- 1.3.6.1.4.1.2011.2.25.4.50.22.1.1
    optixPktMirrorTable OBJECT-TYPE
        SYNTAX SEQUENCE OF OptixPktMirrorEntry
        MAX-ACCESS not-accessible
        STATUS current
        DESCRIPTION
            "This table describes the basic configuration informationin of the port mirror."
        ::= { optixPktMirrorGroup 1 }

    -- 1.3.6.1.4.1.2011.2.25.4.50.22.1.1.1
    optixPktMirrorEntry OBJECT-TYPE
        SYNTAX OptixPktMirrorEntry
        MAX-ACCESS not-accessible
        STATUS current
        DESCRIPTION
            "This entry describes the basic configuration information of the port mirror."
        INDEX{ optixPktMirrorID }
        ::= { optixPktMirrorTable 1 }

    OptixPktMirrorEntry ::=
        SEQUENCE {
            optixPktMirrorID
                Unsigned32,
            optixPktMirrorType
                INTEGER,
            optixPktMirrorName
                OCTET STRING,
            optixPktMirrorSrcType
                INTEGER,
            optixPktMirrorSrcDir
                INTEGER,
            optixPktMirrorSrcPoint1
                Unsigned32,
            optixPktMirrorSrcPoint2
                Unsigned32,
            optixPktMirrorSrcPoint3
                Unsigned32,
            optixPktMirrorDestPoint1
                Unsigned32,
            optixPktMirrorDestPoint2
                Unsigned32,
            optixPktMirrorDestPoint3
                Unsigned32,
            optixPktMirrorCarrierType
                INTEGER,
            optixPktMirrorCarrierIndex
                Unsigned32,
            optixPktMirrorRules
                OCTET STRING,
            optixPktMirrorRowStatus
                RowStatus
        }

    -- 1.3.6.1.4.1.2011.2.25.4.50.22.1.1.1.1
    optixPktMirrorID OBJECT-TYPE
        SYNTAX Unsigned32
        MAX-ACCESS not-accessible
        STATUS current
        DESCRIPTION
            "Port mirroring ID. Value range: 1 to 4294967295. 0 means auto."
        ::= { optixPktMirrorEntry 1 }

    -- 1.3.6.1.4.1.2011.2.25.4.50.22.1.1.1.2
    optixPktMirrorType OBJECT-TYPE
        SYNTAX INTEGER
        {
            local(0),
            remote(1),
            observe(2),
            localClassifier(3)
        }
        MAX-ACCESS read-create
        STATUS current
        DESCRIPTION
            "Type of port mirror. 0: local, 1: remote, 2: observe, 3:localClassifier"
        ::= { optixPktMirrorEntry 2 }

    -- 1.3.6.1.4.1.2011.2.25.4.50.22.1.1.1.3
    optixPktMirrorName OBJECT-TYPE
        SYNTAX OCTET STRING
        MAX-ACCESS read-create
        STATUS current
        DESCRIPTION
            "name of port mirror"
        ::= { optixPktMirrorEntry 3 }

    -- 1.3.6.1.4.1.2011.2.25.4.50.22.1.1.1.4
    optixPktMirrorSrcType OBJECT-TYPE
        SYNTAX INTEGER
        {
            phyport(0),
            vuni(1),
            vnni(2),
            flow(3)
        }
        MAX-ACCESS read-create
        STATUS current
        DESCRIPTION
            "Type of source point of port mirror. 0: phyport, 1: V-UNI, 2: V-NNI, 3: flow"
        ::= { optixPktMirrorEntry 4 }

    -- 1.3.6.1.4.1.2011.2.25.4.50.22.1.1.1.5
    optixPktMirrorSrcDir OBJECT-TYPE
        SYNTAX INTEGER
        {
            ingress(1),
            egress(2)
        }
        MAX-ACCESS read-create
        STATUS current
        DESCRIPTION
            "Direction of source point of port mirror. 1: ingress, 2: egress"
        ::= { optixPktMirrorEntry 5 }

    -- 1.3.6.1.4.1.2011.2.25.4.50.22.1.1.1.6
    optixPktMirrorSrcPoint1 OBJECT-TYPE
        SYNTAX Unsigned32
        MAX-ACCESS read-create
        STATUS current
        DESCRIPTION
            "Source point1 of port mirror. Value range: 1 to 65535 (based on the number of boards supported by the NE)."
        ::= { optixPktMirrorEntry 6 }

    -- 1.3.6.1.4.1.2011.2.25.4.50.22.1.1.1.7
    optixPktMirrorSrcPoint2 OBJECT-TYPE
        SYNTAX Unsigned32
        MAX-ACCESS read-create
        STATUS current
        DESCRIPTION
            "Source point2 of port mirror. Value range: 1 to 255. If the NE does not support subboards, the value is 255."
        ::= { optixPktMirrorEntry 7 }

    -- 1.3.6.1.4.1.2011.2.25.4.50.22.1.1.1.8
    optixPktMirrorSrcPoint3 OBJECT-TYPE
        SYNTAX Unsigned32
        MAX-ACCESS read-create
        STATUS current
        DESCRIPTION
            "Source point3 of port mirror. Value range: 1 to 65535 (based on the number of ports supported by the board)."
        ::= { optixPktMirrorEntry 8 }

    -- 1.3.6.1.4.1.2011.2.25.4.50.22.1.1.1.9
    optixPktMirrorDestPoint1 OBJECT-TYPE
        SYNTAX Unsigned32
        MAX-ACCESS read-create
        STATUS current
        DESCRIPTION
            "Dest point1 of port mirror. Value range: 1 to 65535 (based on the number of boards supported by the NE)."
        ::= { optixPktMirrorEntry 9 }

    -- 1.3.6.1.4.1.2011.2.25.4.50.22.1.1.1.10
    optixPktMirrorDestPoint2 OBJECT-TYPE
        SYNTAX Unsigned32
        MAX-ACCESS read-create
        STATUS current
        DESCRIPTION
            "Dest point2 of port mirror. Value range: 1 to 255. If the NE does not support subboards, the value is 255."
        ::= { optixPktMirrorEntry 10 }

    -- 1.3.6.1.4.1.2011.2.25.4.50.22.1.1.1.11
    optixPktMirrorDestPoint3 OBJECT-TYPE
        SYNTAX Unsigned32
        MAX-ACCESS read-create
        STATUS current
        DESCRIPTION
            "Dest point3 of port mirror. Value range: 1 to 65535 (based on the number of ports supported by the board)."
        ::= { optixPktMirrorEntry 11 }

    -- 1.3.6.1.4.1.2011.2.25.4.50.22.1.1.1.12
    optixPktMirrorCarrierType OBJECT-TYPE
        SYNTAX INTEGER
        {
            pw(0),
            qinq(1),
            snmp255(255)
        }
        MAX-ACCESS read-only
        STATUS current
        DESCRIPTION
            "Carrier type of port mirror. 0: PW, 1: QinQ"
        ::= { optixPktMirrorEntry 12 }

    -- 1.3.6.1.4.1.2011.2.25.4.50.22.1.1.1.13
    optixPktMirrorCarrierIndex OBJECT-TYPE
        SYNTAX Unsigned32
        MAX-ACCESS read-only
        STATUS current
        DESCRIPTION
            "carrier index of port mirror"
        ::= { optixPktMirrorEntry 13 }

    -- 1.3.6.1.4.1.2011.2.25.4.50.22.1.1.1.14
    optixPktMirrorRules OBJECT-TYPE
        SYNTAX OCTET STRING
        MAX-ACCESS read-create
        STATUS current
        DESCRIPTION
            "This parameter indicates the matching rules for port traffic mirroring."
        ::= { optixPktMirrorEntry 14 }

    -- 1.3.6.1.4.1.2011.2.25.4.50.22.1.1.1.255
    optixPktMirrorRowStatus OBJECT-TYPE
        SYNTAX RowStatus
        MAX-ACCESS read-create
        STATUS current
        DESCRIPTION
            "the row status of port mirror"
        ::= { optixPktMirrorEntry 255 }

    -- 1.3.6.1.4.1.2011.2.25.4.50.22.1.2
    optixMirrorTrap OBJECT IDENTIFIER ::= { optixPktMirrorGroup 2 }

    -- 1.3.6.1.4.1.2011.2.25.4.50.22.1.2.1
    optixMirrorPortCfgEvtTrap NOTIFICATION-TYPE
        STATUS current
        DESCRIPTION
            "This node is used to report a port mirroring configuration event."
        ::= { optixMirrorTrap 1 }

    -- 1.3.6.1.4.1.2011.2.25.4.50.22.1.3
    optixMirrorTrapMember OBJECT IDENTIFIER ::= { optixPktMirrorGroup 3 }

    -- 1.3.6.1.4.1.2011.2.25.4.50.22.1.3.1
    optixMirrorEvtTrapID OBJECT-TYPE
        SYNTAX Unsigned32
        MAX-ACCESS accessible-for-notify
        STATUS current
        DESCRIPTION
            "Port mirroring ID. Value range: 1 to 4294967295."
        ::= { optixMirrorTrapMember 1 }

    -- 1.3.6.1.4.1.2011.2.25.4.50.22.1.3.2
    optixMirrorEvtTrapState OBJECT-TYPE
        SYNTAX INTEGER
        {
            delete(0),
            create(1)
        }
        MAX-ACCESS accessible-for-notify
        STATUS current
        DESCRIPTION
            "Configuration type of port mirroring. 0: delete, 1: create."
        ::= { optixMirrorTrapMember 2 }

    -- 1.3.6.1.4.1.2011.2.25.4.50.22.1.3.3
    optixMirrorEvtTrapSrcPointBoard OBJECT-TYPE
        SYNTAX Unsigned32
        MAX-ACCESS accessible-for-notify
        STATUS current
        DESCRIPTION
            "Slot ID of the board where the source port is located."
        ::= { optixMirrorTrapMember 3 }

    -- 1.3.6.1.4.1.2011.2.25.4.50.22.1.3.4
    optixMirrorEvtTrapSrcPointSubCard OBJECT-TYPE
        SYNTAX Unsigned32
        MAX-ACCESS accessible-for-notify
        STATUS current
        DESCRIPTION
            "Subboard ID of the source port."
        ::= { optixMirrorTrapMember 4 }

    -- 1.3.6.1.4.1.2011.2.25.4.50.22.1.3.5
    optixMirrorEvtTrapSrcPointPortID OBJECT-TYPE
        SYNTAX Unsigned32
        MAX-ACCESS accessible-for-notify
        STATUS current
        DESCRIPTION
            "Source port number."
        ::= { optixMirrorTrapMember 5 }

    -- 1.3.6.1.4.1.2011.2.25.4.50.22.1.3.6
    optixMirrorEvtTrapDestPointBoard OBJECT-TYPE
        SYNTAX Unsigned32
        MAX-ACCESS accessible-for-notify
        STATUS current
        DESCRIPTION
            "Slot ID of the board where the observation port is located."
        ::= { optixMirrorTrapMember 6 }

    -- 1.3.6.1.4.1.2011.2.25.4.50.22.1.3.7
    optixMirrorEvtTrapDestPointSubCard OBJECT-TYPE
        SYNTAX Unsigned32
        MAX-ACCESS accessible-for-notify
        STATUS current
        DESCRIPTION
            "Subboard ID of the observation port."
        ::= { optixMirrorTrapMember 7 }

    -- 1.3.6.1.4.1.2011.2.25.4.50.22.1.3.8
    optixMirrorEvtTrapDestPointPortID OBJECT-TYPE
        SYNTAX Unsigned32
        MAX-ACCESS accessible-for-notify
        STATUS current
        DESCRIPTION
            "Observation port number."
        ::= { optixMirrorTrapMember 8 }

    -- 1.3.6.1.4.1.2011.2.25.4.50.22.1.3.9
    optixMirrorEvtTrapDirection OBJECT-TYPE
        SYNTAX INTEGER
        {
            ingress(1),
            egress(2)
        }
        MAX-ACCESS accessible-for-notify
        STATUS current
        DESCRIPTION
            "Direction of traffic that is mirrored to the observation port. 1: ingress, 2: egress."
        ::= { optixMirrorTrapMember 9 }

END
