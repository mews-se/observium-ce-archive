-- OPTIX-SDH-OUTSYN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-OUTSYN-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        optixLogBoardId
            FROM OPTIX-BOARD-MANAGE-MIB
        ;

    optixSdhOutSyn MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations of external clock source management."
        REVISION "201204200000Z"
        DESCRIPTION
            "The initial revision of this MIB module1."
        ::={ optixProvisionSdh 43 }

    -- 1.3.6.1.4.1.2011.2.25.4.10.43.1
    optixSdhOutSynGroup OBJECT IDENTIFIER ::= { optixSdhOutSyn 1 }

    -- 1.3.6.1.4.1.2011.2.25.4.10.43.1.1
    optixSdhOutSynTable OBJECT-TYPE
        SYNTAX SEQUENCE OF OptixSdhOutSynEntry
        MAX-ACCESS not-accessible
        STATUS current
        DESCRIPTION
            "This table describes the configurations of the SDH external clock source."
        ::= { optixSdhOutSynGroup 1 }

    -- 1.3.6.1.4.1.2011.2.25.4.10.43.1.1.1
    optixSdhOutSynEntry OBJECT-TYPE
        SYNTAX OptixSdhOutSynEntry
        MAX-ACCESS not-accessible
        STATUS current
        DESCRIPTION
            "Thisentry describes the configurations of the SDH external clock source."
        INDEX{ optixLogBoardId,optixSdhOutSynOutSrcId }
        ::= { optixSdhOutSynTable 1 }

    OptixSdhOutSynEntry ::=
        SEQUENCE {
            optixSdhOutSynOutSrcId
                Unsigned32,
            optixSdhOutSynOutputTh
                INTEGER,
            optixSdhOutSynInMode
                INTEGER,
            optixSdhOutSynOutMode
                INTEGER,
            optixSSMExS1ByteInSlot
                Unsigned32,
            optixSSMExS1ByteOutSlot
                Unsigned32,
            optixSdhOutSynForceclose
                INTEGER
        }

    -- 1.3.6.1.4.1.2011.2.25.4.10.43.1.1.1.1
    optixSdhOutSynOutSrcId OBJECT-TYPE
        SYNTAX Unsigned32
        MAX-ACCESS not-accessible
        STATUS current
        DESCRIPTION
            "This object indicates the external clock source ID. 0xf001: external soure 1, 0xf002: external source 2"
        ::= { optixSdhOutSynEntry 1 }

    -- 1.3.6.1.4.1.2011.2.25.4.10.43.1.1.1.2
    optixSdhOutSynOutputTh OBJECT-TYPE
        SYNTAX INTEGER
        {
            qLDNU(0),
            qLSEC(1),
            qLSSUB(2),
            qLSSUA(3),
            qLPRC(4)
        }
        MAX-ACCESS read-write
        STATUS current
        DESCRIPTION
            "This object indicates the threshold of the external clock source. 0: qLDNU, 1: qLSEC, 2: qLSSUB, 3: qLSSUA, 4: qLPRC"
        ::= { optixSdhOutSynEntry 2 }

    -- 1.3.6.1.4.1.2011.2.25.4.10.43.1.1.1.3
    optixSdhOutSynInMode OBJECT-TYPE
        SYNTAX INTEGER
        {
            bit(0),
            hz(1)
        }
        MAX-ACCESS read-write
        STATUS current
        DESCRIPTION
            "This object indicates the input mode of the external clock source. 0: bit, 1: Hz"
        ::= { optixSdhOutSynEntry 3 }

    -- 1.3.6.1.4.1.2011.2.25.4.10.43.1.1.1.4
    optixSdhOutSynOutMode OBJECT-TYPE
        SYNTAX INTEGER
        {
            bit(0),
            hz(1)
        }
        MAX-ACCESS read-write
        STATUS current
        DESCRIPTION
            "This object indicates the output mode of the external clock source. 0: bit, 1: Hz"
        ::= { optixSdhOutSynEntry 4 }

    -- 1.3.6.1.4.1.2011.2.25.4.10.43.1.1.1.5
    optixSSMExS1ByteInSlot OBJECT-TYPE
        SYNTAX Unsigned32
        MAX-ACCESS read-write
        STATUS current
        DESCRIPTION
            "This object indicates the S1 byteinput timeslot of the SSM protocol. Value range: 0 to 5."
        ::= { optixSdhOutSynEntry 5 }

    -- 1.3.6.1.4.1.2011.2.25.4.10.43.1.1.1.6
    optixSSMExS1ByteOutSlot OBJECT-TYPE
        SYNTAX Unsigned32
        MAX-ACCESS read-write
        STATUS current
        DESCRIPTION
            "This object indicates the S1 byte output timeslot of the SSM protocol. Value range: 0 to 5."
        ::= { optixSdhOutSynEntry 6 }

    -- 1.3.6.1.4.1.2011.2.25.4.10.43.1.1.1.7
    optixSdhOutSynForceclose OBJECT-TYPE
        SYNTAX INTEGER
        {
            disable(0),
            enable(1)
        }
        MAX-ACCESS read-write
        STATUS current
        DESCRIPTION
            "This object indicates the force close enable of the external clock source ."
        ::= { optixSdhOutSynEntry 7 }

    -- 1.3.6.1.4.1.2011.2.25.4.10.43.1.2
    optixSdhLapseTermTable OBJECT-TYPE
        SYNTAX SEQUENCE OF OptixSdhLapseTermEntry
        MAX-ACCESS not-accessible
        STATUS current
        DESCRIPTION
            "This table describes the configurations of the external clock source invalidation"
        ::= { optixSdhOutSynGroup 2 }

    -- 1.3.6.1.4.1.2011.2.25.4.10.43.1.2.1
    optixSdhLapseTermEntry OBJECT-TYPE
        SYNTAX OptixSdhLapseTermEntry
        MAX-ACCESS not-accessible
        STATUS current
        DESCRIPTION
            "This entry describes the configurations of the external clock source invalidation"
        INDEX{ optixLogBoardId,optixSdhOutSynOutSrcId,optixSdhLapseTerm }
        ::= { optixSdhLapseTermTable 1 }

    OptixSdhLapseTermEntry ::=
        SEQUENCE {
            optixSdhLapseTerm
                INTEGER,
            optixSdhLapseTermEnable
                INTEGER
        }

    -- 1.3.6.1.4.1.2011.2.25.4.10.43.1.2.1.1
    optixSdhLapseTerm OBJECT-TYPE
        SYNTAX INTEGER
        {
            ais(1),
            lof(2)
        }
        MAX-ACCESS not-accessible
        STATUS current
        DESCRIPTION
            "This object indicates the external clock source invalidation. 1: ais, 2: lof"
        ::= { optixSdhLapseTermEntry 1 }

    -- 1.3.6.1.4.1.2011.2.25.4.10.43.1.2.1.2
    optixSdhLapseTermEnable OBJECT-TYPE
        SYNTAX INTEGER
        {
            disable(0),
            enable(1)
        }
        MAX-ACCESS read-write
        STATUS current
        DESCRIPTION
            "This object indicates the external clock source invalidation state. 0: disable, 1: enable"
        ::= { optixSdhLapseTermEntry 2 }

END
