-- OPTIX-GLOBAL-TRAPS-MIB
-- MIB generated by ExcelToMIB tool 1.0
-- 
-- =================================================================
--  Copyright (C) 2012 by HUAWEI TECHNOLOGIES. All rights reserved
--  
--  Description:This MIB describes the trap interface of Huawei microwave transmit
--  Reference:
--  Version: V1.00
--  History:
-- 	<author>,<date>,<contents>
-- =================================================================
--
OPTIX-GLOBAL-TRAPS-MIB DEFINITIONS ::= BEGIN
    IMPORTS
        optixCommonGlobal
            FROM OPTIX-OID-MIB
        PerformanceEventType,ValidflagType,ObjType,AlarmEventType,AlmDataSrvEffType,AlmDataNtfcnCdeType,DataPmEventType
            FROM OPTIX-GLOBAL-TC-MIB
        OBJECT-GROUP,MODULE-COMPLIANCE
            FROM SNMPv2-CONF
        Integer32,Unsigned32,OBJECT-TYPE,MODULE-IDENTITY,Counter64,Counter32,NOTIFICATION-TYPE
            FROM SNMPv2-SMI
        DateAndTime,DisplayString
	    FROM SNMPv2-TC;
	

    optixGlobalTrap MODULE-IDENTITY
        LAST-UPDATED "1003290000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
	    "The initial revision of this MIB module."
        ::={ optixCommonGlobal 40 }

    -- 1.3.6.1.4.1.2011.2.25.3.40.40.10
    optixTrapsCommon OBJECT IDENTIFIER ::= { optixGlobalTrap 10 }

    -- 1.3.6.1.4.1.2011.2.25.3.40.40.10.10
    rptAlmName OBJECT-TYPE
        SYNTAX AlarmEventType
        MAX-ACCESS accessible-for-notify
        STATUS current
        DESCRIPTION
            "Indicates the alarm name."
        ::= { optixTrapsCommon 10 }

    -- 1.3.6.1.4.1.2011.2.25.3.40.40.10.40
    rptEvtDateTime OBJECT-TYPE
        SYNTAX DateAndTime
        MAX-ACCESS accessible-for-notify
        STATUS current
        DESCRIPTION
            "Indicates the date and time when the alarm is reported."
        ::= { optixTrapsCommon 40 }

    -- 1.3.6.1.4.1.2011.2.25.3.40.40.10.50
    rptEvtSrvEff OBJECT-TYPE
        SYNTAX AlmDataSrvEffType
        MAX-ACCESS accessible-for-notify
        STATUS current
        DESCRIPTION
            "Indicates whether the alarm affect services. Only NSA(Nonservice-effecting)|SA(Service-effecting) will be represented here."
        ::= { optixTrapsCommon 50 }

    -- 1.3.6.1.4.1.2011.2.25.3.40.40.10.60
    rptEvtNtfcnCde OBJECT-TYPE
        SYNTAX AlmDataNtfcnCdeType
        MAX-ACCESS accessible-for-notify
        STATUS current
        DESCRIPTION
            "Indicates the alarm severity, which can be critical (CR), major (MJ), minor (MN), not alarmed (NA), or not reported (NR).
                Only CR|MJ|MN|NA|NR will be represented here."
        ::= { optixTrapsCommon 60 }

    -- 1.3.6.1.4.1.2011.2.25.3.40.40.10.90
    rptEvtMonValue OBJECT-TYPE
        SYNTAX Counter64
        MAX-ACCESS accessible-for-notify
        STATUS current
        DESCRIPTION
            "Indicates the performance value when a crossing event occurs."
        ::= { optixTrapsCommon 90 }

    -- 1.3.6.1.4.1.2011.2.25.3.40.40.10.100
    rptEvtThValue OBJECT-TYPE
        SYNTAX Counter64
        MAX-ACCESS accessible-for-notify
        STATUS current
        DESCRIPTION
            "Indicates the performance threshold."
        ::= { optixTrapsCommon 100 }

    -- 1.3.6.1.4.1.2011.2.25.3.40.40.10.110
    rptEvtDescription OBJECT-TYPE
        SYNTAX DisplayString
        MAX-ACCESS accessible-for-notify
        STATUS current
        DESCRIPTION
            "Indicates the description of the reported performance events."
        ::= { optixTrapsCommon 110 }

    -- 1.3.6.1.4.1.2011.2.25.3.40.40.10.120
    rptEvtNumber OBJECT-TYPE
        SYNTAX Unsigned32
        MAX-ACCESS accessible-for-notify
        STATUS current
        DESCRIPTION
            "Indicates the alarm number."
        ::= { optixTrapsCommon 120 }

    -- 1.3.6.1.4.1.2011.2.25.3.40.40.10.130
    rptEvtPeriod OBJECT-TYPE
        SYNTAX INTEGER
        {
            null(0),
            period15m(1),
            period1day(2)
        }
        MAX-ACCESS accessible-for-notify
        STATUS current
        DESCRIPTION
            "Specifies the accumulation time period for the PM information.
                Only period15m|period1day|NULL will be represented here."
        ::= { optixTrapsCommon 130 }

    -- 1.3.6.1.4.1.2011.2.25.3.40.40.10.140
    rptEvtVldty OBJECT-TYPE
        SYNTAX ValidflagType
        MAX-ACCESS accessible-for-notify
        STATUS current
        DESCRIPTION
            "It indicates whether the information 
                for the specified time period was 
                accumulated over the entire time period 
                or some portion of it.
                Only INVALID|VALID will be represented here."
        ::= { optixTrapsCommon 140 }

    -- 1.3.6.1.4.1.2011.2.25.3.40.40.10.150
    rptEvtEffect OBJECT-TYPE
        SYNTAX INTEGER
        {
            tc(6),
            sc(7),
            cl(8)
        }
        MAX-ACCESS accessible-for-notify
        STATUS current
        DESCRIPTION
            "indicates the effect of the event on the condition of the NE.
                Only TC(Transient Condition)|SC(Raised Condition)|CL(Cleared Condition) will be represented here."
        ::= { optixTrapsCommon 150 }

    -- 1.3.6.1.4.1.2011.2.25.3.40.40.10.160
    rptEvtState OBJECT-TYPE
        SYNTAX INTEGER
        {
            start(1),
            clear(3)
        }
        MAX-ACCESS accessible-for-notify
        STATUS current
        DESCRIPTION
	    "The state of alarm.Only START|CL(Cleared) will be represented here."
        ::= { optixTrapsCommon 160 }
        

    -- 1.3.6.1.4.1.2011.2.25.3.40.40.10.180
    rptEvtSeqNumber OBJECT-TYPE
        SYNTAX Unsigned32
        MAX-ACCESS accessible-for-notify
        STATUS current
        DESCRIPTION
            "Indicates the sequence number of the reported events."
        ::= { optixTrapsCommon 180 }

    -- 1.3.6.1.4.1.2011.2.25.3.40.40.10.190
    rptPmName OBJECT-TYPE
        SYNTAX PerformanceEventType
        MAX-ACCESS accessible-for-notify
        STATUS current
        DESCRIPTION
            "Indicates the name of a PM event."
        ::= { optixTrapsCommon 190 }

    -- 1.3.6.1.4.1.2011.2.25.3.40.40.10.210
    rptEvtValue OBJECT-TYPE
        SYNTAX DisplayString
        MAX-ACCESS accessible-for-notify
        STATUS current
        DESCRIPTION
            "Indicates the current PM event value."
        ::= { optixTrapsCommon 210 }

    -- 1.3.6.1.4.1.2011.2.25.3.40.40.10.220
    rptEvtObjType OBJECT-TYPE
        SYNTAX ObjType
        MAX-ACCESS accessible-for-notify
        STATUS current
        DESCRIPTION
            "Indicates the PM object type."
        ::= { optixTrapsCommon 220 }

    -- 1.3.6.1.4.1.2011.2.25.3.40.40.10.230
    rptEvtParaLen OBJECT-TYPE
        SYNTAX Counter32
        MAX-ACCESS accessible-for-notify
        STATUS current
        DESCRIPTION
            "Indicates the parameter length of the PM object."
        ::= { optixTrapsCommon 230 }

    -- 1.3.6.1.4.1.2011.2.25.3.40.40.10.240
    rptEvtPara OBJECT-TYPE
        SYNTAX DisplayString
        MAX-ACCESS accessible-for-notify
        STATUS current
        DESCRIPTION
            "Indicates the parameter of the PM object."
        ::= { optixTrapsCommon 240 }

    -- 1.3.6.1.4.1.2011.2.25.3.40.40.10.250
    rptEvtStartTime OBJECT-TYPE
        SYNTAX DateAndTime
        MAX-ACCESS accessible-for-notify
        STATUS current
        DESCRIPTION
            "Indicates the start date and time of the reported event."
        ::= { optixTrapsCommon 250 }

    -- 1.3.6.1.4.1.2011.2.25.3.40.40.10.260
    rptEvtEndTime OBJECT-TYPE
        SYNTAX DateAndTime
        MAX-ACCESS accessible-for-notify
        STATUS current
        DESCRIPTION
            "Indicates the end date and time of the reported event."
        ::= { optixTrapsCommon 260 }

    -- 1.3.6.1.4.1.2011.2.25.3.40.40.10.270
    rptEvtDataPmName OBJECT-TYPE
        SYNTAX DataPmEventType
        MAX-ACCESS accessible-for-notify
        STATUS current
        DESCRIPTION
            "Indicates the name of the reported data performance."
        ::= { optixTrapsCommon 270 }

    -- 1.3.6.1.4.1.2011.2.25.3.40.40.20
    optixTrapsPM OBJECT IDENTIFIER ::= { optixGlobalTrap 20 }

    -- 1.3.6.1.4.1.2011.2.25.3.40.40.20.1
    pmRisingAlarm NOTIFICATION-TYPE
        OBJECTS{ rptEvtObjType,rptEvtParaLen,rptEvtPara,rptEvtDataPmName,rptEvtMonValue,rptEvtThValue,rptEvtDateTime }
        STATUS current
        DESCRIPTION
            "Indicates the performance event whose value is above the upper threshold."
        ::= { optixTrapsPM 1 }

    -- 1.3.6.1.4.1.2011.2.25.3.40.40.20.2
    pmFallingAlarm NOTIFICATION-TYPE
        OBJECTS{ rptEvtObjType,rptEvtParaLen,rptEvtPara,rptEvtDataPmName,rptEvtMonValue,rptEvtThValue,rptEvtDateTime }
        STATUS current
        DESCRIPTION
            "Indicates the performance event whose value is below the lower threshold."
        ::= { optixTrapsPM 2 }
END
--
-- OPTIX-GLOBAL-TRAPS-MIB.mib
--
