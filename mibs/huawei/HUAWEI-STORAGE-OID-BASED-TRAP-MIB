--
-- HUAWEI-STORAGE-OID-BASED-TRAP-MIB.mib
-- MIB generated by MG-SOFT Visual MIB Builder Version 4.0 Build 347
-- Wednesday, March 02, 2016 at 22:48:04

    HUAWEI-STORAGE-OID-BASED-TRAP-MIB DEFINITIONS ::= BEGIN
        IMPORTS
            hwStorageAlarmReporting
                FROM HUAWEI-STORAGE-ALARM-MIB       
            MODULE-IDENTITY, NOTIFICATION-TYPE, enterprises  
                FROM SNMPv2-SMI;

        -- 1.3.6.1.4.1.2011.2.251.20.1.2.2
        storage MODULE-IDENTITY 
            LAST-UPDATED "202407301804Z"        -- July 30, 2024 at 18:04 GMT
            ORGANIZATION 
                "Huawei Technologies Co.,Ltd."
            CONTACT-INFO 
                "Huawei Industrial Base
                Bantian, Longgang
                Shenzhen 518129
                People's Republic of China
                Website: http://www.huawei.com
                Email: support@huawei.com"
            DESCRIPTION "Description."
            ::= { products 251 }

--
-- Node definitions
        -- 1.3.6.1.4.1.2011
        huawei OBJECT IDENTIFIER ::= { enterprises 2011 }

        -- 1.3.6.1.4.1.2011.2
        products OBJECT IDENTIFIER ::= { huawei 2 }

        -- 1.3.6.1.4.1.2011.2.251
        storage OBJECT IDENTIFIER ::= { products 251 }

        -- 1.3.6.1.4.1.2011.2.251.20
        alarm OBJECT IDENTIFIER ::= { storage 20 }

        -- 1.3.6.1.4.1.2011.2.251.20.1
        hwStorageNotification OBJECT IDENTIFIER ::= { alarm 1 }

        -- 1.3.6.1.4.1.2011.2.251.20.1.2
        hwStorageNotificationType OBJECT IDENTIFIER ::= { hwStorageNotification 2 }

        -- 1.3.6.1.4.1.2011.2.251.20.1.2.2
        hwStorageAlarmReportingPrecise NOTIFICATION-TYPE
            OBJECTS { hwStorageAlarmReporting }
            STATUS current
            DESCRIPTION "The node is used for reporting the parsed alarm. The ID of each alarm corresponds an independent OID, and different OIDs are used for alarm generation and clearance."
            ::= { hwStorageNotificationType 2 }

        -- 1.3.6.1.4.1.2011.2.251.20.1.2.2.15
        oidBasedTrap OBJECT IDENTIFIER ::= { hwStorageAlarmReportingPrecise 15 }
        -- 1.3.6.1.4.1.2011.2.251.20.1.2.2.15.6
        port OBJECT IDENTIFIER ::= { oidBasedTrap 6 }

        -- 1.3.6.1.4.1.2011.2.251.20.1.2.2.15.6.2
        expansionPortIsDisconnected OBJECT IDENTIFIER ::= { port 2 }

        -- 1.3.6.1.4.1.2011.2.251.20.1.2.2.15.6.2.1
        expansionPortIsDisconnected-Fault NOTIFICATION-TYPE
            OBJECTS { hwStorageAlarmReporting }
            STATUS current
            DESCRIPTION "Expansion Port Link Down"
            --#SEVERITY MAJOR
            ::= { expansionPortIsDisconnected 1 }

        -- 1.3.6.1.4.1.2011.2.251.20.1.2.2.15.6.2.2
        expansionPortIsDisconnected-Resume NOTIFICATION-TYPE
            OBJECTS { hwStorageAlarmReporting }
            STATUS current
            DESCRIPTION "Recover: Expansion Port Link Down"
            --#SEVERITY INFORMATIONAL
            ::= { expansionPortIsDisconnected 2 }

        -- 1.3.6.1.4.1.2011.2.251.20.1.2.2.15.6.4
        portIsDisconnected OBJECT IDENTIFIER ::= { port 4 }

        -- 1.3.6.1.4.1.2011.2.251.20.1.2.2.15.6.4.1
        portIsDisconnected-Fault NOTIFICATION-TYPE
            OBJECTS { hwStorageAlarmReporting }
            STATUS current
            DESCRIPTION "A Port Is Disconnected"
            --#SEVERITY MAJOR
            ::= { portIsDisconnected 1 }

        -- 1.3.6.1.4.1.2011.2.251.20.1.2.2.15.6.4.2
        portIsDisconnected-Resume NOTIFICATION-TYPE
            OBJECTS { hwStorageAlarmReporting }
            STATUS current
            DESCRIPTION "Recover: A Port Is Disconnected"
            --#SEVERITY INFORMATIONAL
            ::= { portIsDisconnected 2 }

        -- 1.3.6.1.4.1.2011.2.251.20.1.2.2.15.6.6
        expansionPortPartiallyDamaged OBJECT IDENTIFIER ::= { port 6 }

        -- 1.3.6.1.4.1.2011.2.251.20.1.2.2.15.6.6.1
        expansionPortPartiallyDamaged-Fault NOTIFICATION-TYPE
            OBJECTS { hwStorageAlarmReporting }
            STATUS current
            DESCRIPTION "Expansion Port Partially Damaged"
            --#SEVERITY MAJOR
            ::= { expansionPortPartiallyDamaged 1 }

        -- 1.3.6.1.4.1.2011.2.251.20.1.2.2.15.6.6.2
        expansionPortPartiallyDamaged-Resume NOTIFICATION-TYPE
            OBJECTS { hwStorageAlarmReporting }
            STATUS current
            DESCRIPTION "Recover: Expansion Port Partially Damaged"
            --#SEVERITY INFORMATIONAL
            ::= { expansionPortPartiallyDamaged 2 }

        -- 1.3.6.1.4.1.2011.2.251.20.1.2.2.15.6.12
        expansionPortIsFaulty OBJECT IDENTIFIER ::= { port 12 }

        -- 1.3.6.1.4.1.2011.2.251.20.1.2.2.15.6.12.1
        expansionPortIsFaulty-Fault NOTIFICATION-TYPE
            OBJECTS { hwStorageAlarmReporting }
            STATUS current
            DESCRIPTION "Expansion Port Is Faulty"
            --#SEVERITY MAJOR
            ::= { expansionPortIsFaulty 1 }

        -- 1.3.6.1.4.1.2011.2.251.20.1.2.2.15.6.12.2
        expansionPortIsFaulty-Resume NOTIFICATION-TYPE
            OBJECTS { hwStorageAlarmReporting }
            STATUS current
            DESCRIPTION "Recover: Expansion Port Is Faulty"
            --#SEVERITY INFORMATIONAL
            ::= { expansionPortIsFaulty 2 }

        -- 1.3.6.1.4.1.2011.2.251.20.1.2.2.15.6.16
        expansionPortIsolated OBJECT IDENTIFIER ::= { port 16 }

        -- 1.3.6.1.4.1.2011.2.251.20.1.2.2.15.6.16.1
        expansionPortIsolated-Fault NOTIFICATION-TYPE
            OBJECTS { hwStorageAlarmReporting }
            STATUS current
            DESCRIPTION "The Expansion Port Is Isolated"
            --#SEVERITY MAJOR
            ::= { expansionPortIsolated 1 }

        -- 1.3.6.1.4.1.2011.2.251.20.1.2.2.15.6.16.2
        expansionPortIsolated-Resume NOTIFICATION-TYPE
            OBJECTS { hwStorageAlarmReporting }
            STATUS current
            DESCRIPTION "Recover: The Expansion Port Is Isolated"
            --#SEVERITY INFORMATIONAL
            ::= { expansionPortIsolated 2 }

        -- 1.3.6.1.4.1.2011.2.251.20.1.2.2.15.6.17
        portIsWorkingInHalfDuplexMode OBJECT IDENTIFIER ::= { port 17 }

        -- 1.3.6.1.4.1.2011.2.251.20.1.2.2.15.6.17.1
        portIsWorkingInHalfDuplexMode-Fault NOTIFICATION-TYPE
            OBJECTS { hwStorageAlarmReporting }
            STATUS current
            DESCRIPTION "Network Port Is Working In HalfDuplex Mode"
            --#SEVERITY MAJOR
            ::= { portIsWorkingInHalfDuplexMode 1 }

        -- 1.3.6.1.4.1.2011.2.251.20.1.2.2.15.6.17.2
        portIsWorkingInHalfDuplexMode-Resume NOTIFICATION-TYPE
            OBJECTS { hwStorageAlarmReporting }
            STATUS current
            DESCRIPTION "Recover: Network Port Is Working In HalfDuplex Mode"
            --#SEVERITY INFORMATIONAL
            ::= { portIsWorkingInHalfDuplexMode 2 }

        -- 1.3.6.1.4.1.2011.2.251.20.1.2.2.15.6.21
        portHasTooManyBitErrors OBJECT IDENTIFIER ::= { port 21 }

        -- 1.3.6.1.4.1.2011.2.251.20.1.2.2.15.6.21.1
        portHasTooManyBitErrors-Fault NOTIFICATION-TYPE
            OBJECTS { hwStorageAlarmReporting }
            STATUS current
            DESCRIPTION "Port Has Too Many Bit Errors"
            --#SEVERITY MAJOR
            ::= { portHasTooManyBitErrors 1 }

        -- 1.3.6.1.4.1.2011.2.251.20.1.2.2.15.6.21.2
        portHasTooManyBitErrors-Resume NOTIFICATION-TYPE
            OBJECTS { hwStorageAlarmReporting }
            STATUS current
            DESCRIPTION "Recover: Port Has Too Many Bit Errors"
            --#SEVERITY INFORMATIONAL
            ::= { portHasTooManyBitErrors 2 }

        -- 1.3.6.1.4.1.2011.2.251.20.1.2.2.15.6.29
        rateIsSmallerThanAllowedMaximum OBJECT IDENTIFIER ::= { port 29 }

        -- 1.3.6.1.4.1.2011.2.251.20.1.2.2.15.6.29.1
        rateIsSmallerThanAllowedMaximum-Fault NOTIFICATION-TYPE
            OBJECTS { hwStorageAlarmReporting }
            STATUS current
            DESCRIPTION "Port Negotiated Rate Is Smaller Than The Allowed Maximum"
            --#SEVERITY MAJOR
            ::= { rateIsSmallerThanAllowedMaximum 1 }

        -- 1.3.6.1.4.1.2011.2.251.20.1.2.2.15.6.29.2
        rateIsSmallerThanAllowedMaximum-Resume NOTIFICATION-TYPE
            OBJECTS { hwStorageAlarmReporting }
            STATUS current
            DESCRIPTION "Recover: Port Negotiated Rate Is Smaller Than The Allowed Maximum"
            --#SEVERITY INFORMATIONAL
            ::= { rateIsSmallerThanAllowedMaximum 2 }

        -- 1.3.6.1.4.1.2011.2.251.20.1.2.2.15.6.49
        manageNetworkPortIsDisconnected OBJECT IDENTIFIER ::= { port 49 }

        -- 1.3.6.1.4.1.2011.2.251.20.1.2.2.15.6.49.1
        manageNetworkPortIsDisconnected-Fault NOTIFICATION-TYPE
            OBJECTS { hwStorageAlarmReporting }
            STATUS current
            DESCRIPTION "Management Network Port Is Disconnected"
            --#SEVERITY WARNING
            ::= { manageNetworkPortIsDisconnected 1 }

        -- 1.3.6.1.4.1.2011.2.251.20.1.2.2.15.6.49.2
        manageNetworkPortIsDisconnected-Resume NOTIFICATION-TYPE
            OBJECTS { hwStorageAlarmReporting }
            STATUS current
            DESCRIPTION "Recover: Management Network Port Is Disconnected"
            --#SEVERITY INFORMATIONAL
            ::= { manageNetworkPortIsDisconnected 2 }

        -- 1.3.6.1.4.1.2011.2.251.20.1.2.2.15.6.57
        theCableIsIncorrectlyConnectedToAPort OBJECT IDENTIFIER ::= { port 57 }

        -- 1.3.6.1.4.1.2011.2.251.20.1.2.2.15.6.57.1
        theCableIsIncorrectlyConnectedToAPort-Fault NOTIFICATION-TYPE
            OBJECTS { hwStorageAlarmReporting }
            STATUS current
            DESCRIPTION "The Cable Is Incorrectly Connected To A Port"
            --#SEVERITY MAJOR
            ::= { theCableIsIncorrectlyConnectedToAPort 1 }

        -- 1.3.6.1.4.1.2011.2.251.20.1.2.2.15.6.57.2
        theCableIsIncorrectlyConnectedToAPort-Resume NOTIFICATION-TYPE
            OBJECTS { hwStorageAlarmReporting }
            STATUS current
            DESCRIPTION "Recover: The Cable Is Incorrectly Connected To A Port"
            --#SEVERITY INFORMATIONAL
            ::= { theCableIsIncorrectlyConnectedToAPort 2 }

        -- 1.3.6.1.4.1.2011.2.251.20.1.2.2.15.6.58
        theCableBetweenTwoPortsIsIncorrectlyConnected1 OBJECT IDENTIFIER ::= { port 58 }

        -- 1.3.6.1.4.1.2011.2.251.20.1.2.2.15.6.58.1
        theCableBetweenTwoPortsIsIncorrectlyConnected1-Fault NOTIFICATION-TYPE
            OBJECTS { hwStorageAlarmReporting }
            STATUS current
            DESCRIPTION "The Cable Between Two Ports Is Incorrectly Connected"
            --#SEVERITY MAJOR
            ::= { theCableBetweenTwoPortsIsIncorrectlyConnected1 1 }

        -- 1.3.6.1.4.1.2011.2.251.20.1.2.2.15.6.58.2
        theCableBetweenTwoPortsIsIncorrectlyConnected1-Resume NOTIFICATION-TYPE
            OBJECTS { hwStorageAlarmReporting }
            STATUS current
            DESCRIPTION "Recover: The Cable Between Two Ports Is Incorrectly Connected"
            --#SEVERITY INFORMATIONAL
            ::= { theCableBetweenTwoPortsIsIncorrectlyConnected1 2 }

        -- 1.3.6.1.4.1.2011.2.251.20.1.2.2.15.6.59
        theCableBetweenTwoPortsIsNotConnectedAccordingToTheStandardNetwork1 OBJECT IDENTIFIER ::= { port 59 }

        -- 1.3.6.1.4.1.2011.2.251.20.1.2.2.15.6.59.1
        theCableBetweenTwoPortsIsNotConnectedAccordingToTheStandardNetwork1-Fault NOTIFICATION-TYPE
            OBJECTS { hwStorageAlarmReporting }
            STATUS current
            DESCRIPTION "The Cable Between Two Ports Is Not Connected According To The Standard Network"
            --#SEVERITY MAJOR
            ::= { theCableBetweenTwoPortsIsNotConnectedAccordingToTheStandardNetwork1 1 }

        -- 1.3.6.1.4.1.2011.2.251.20.1.2.2.15.6.59.2
        theCableBetweenTwoPortsIsNotConnectedAccordingToTheStandardNetwork1-Resume NOTIFICATION-TYPE
            OBJECTS { hwStorageAlarmReporting }
            STATUS current
            DESCRIPTION "Recover: The Cable Between Two Ports Is Not Connected According To The Standard Network"
            --#SEVERITY INFORMATIONAL
            ::= { theCableBetweenTwoPortsIsNotConnectedAccordingToTheStandardNetwork1 2 }

        -- 1.3.6.1.4.1.2011.2.251.20.1.2.2.15.6.60
        theCableIsNotConnectedToAPort OBJECT IDENTIFIER ::= { port 60 }

        -- 1.3.6.1.4.1.2011.2.251.20.1.2.2.15.6.60.1
        theCableIsNotConnectedToAPort-Fault NOTIFICATION-TYPE
            OBJECTS { hwStorageAlarmReporting }
            STATUS current
            DESCRIPTION "The Cable Is Not Connected To A Port"
            --#SEVERITY MAJOR
            ::= { theCableIsNotConnectedToAPort 1 }

        -- 1.3.6.1.4.1.2011.2.251.20.1.2.2.15.6.60.2
        theCableIsNotConnectedToAPort-Resume NOTIFICATION-TYPE
            OBJECTS { hwStorageAlarmReporting }
            STATUS current
            DESCRIPTION "Recover: The Cable Is Not Connected To A Port"
            --#SEVERITY INFORMATIONAL
            ::= { theCableIsNotConnectedToAPort 2 }

        -- 1.3.6.1.4.1.2011.2.251.20.1.2.2.15.6.61
        theCableBetweenTwoPortsIsNotConnected1 OBJECT IDENTIFIER ::= { port 61 }

        -- 1.3.6.1.4.1.2011.2.251.20.1.2.2.15.6.61.1
        theCableBetweenTwoPortsIsNotConnected1-Fault NOTIFICATION-TYPE
            OBJECTS { hwStorageAlarmReporting }
            STATUS current
            DESCRIPTION "The Cable Between Two Ports Is Not Connected"
            --#SEVERITY MAJOR
            ::= { theCableBetweenTwoPortsIsNotConnected1 1 }

        -- 1.3.6.1.4.1.2011.2.251.20.1.2.2.15.6.61.2
        theCableBetweenTwoPortsIsNotConnected1-Resume NOTIFICATION-TYPE
            OBJECTS { hwStorageAlarmReporting }
            STATUS current
            DESCRIPTION "Recover: The Cable Between Two Ports Is Not Connected"
            --#SEVERITY INFORMATIONAL
            ::= { theCableBetweenTwoPortsIsNotConnected1 2 }

        -- 1.3.6.1.4.1.2011.2.251.20.1.2.2.15.6.62
        cableLengthError OBJECT IDENTIFIER ::= { port 62 }

        -- 1.3.6.1.4.1.2011.2.251.20.1.2.2.15.6.62.1
        cableLengthError-Fault NOTIFICATION-TYPE
            OBJECTS { hwStorageAlarmReporting }
            STATUS current
            DESCRIPTION "Cable Length Does Not Meet Specifications"
            --#SEVERITY WARNING
            ::= { cableLengthError 1 }

        -- 1.3.6.1.4.1.2011.2.251.20.1.2.2.15.6.62.2
        cableLengthError-Resume NOTIFICATION-TYPE
            OBJECTS { hwStorageAlarmReporting }
            STATUS current
            DESCRIPTION "Recover: Cable Length Does Not Meet Specifications"
            --#SEVERITY INFORMATIONAL
            ::= { cableLengthError 2 }

        -- 1.3.6.1.4.1.2011.2.251.20.1.2.2.15.6.66
        theRDMALinksBetweenNodesAreAbnormal OBJECT IDENTIFIER ::= { port 66 }

        -- 1.3.6.1.4.1.2011.2.251.20.1.2.2.15.6.66.1
        theRDMALinksBetweenNodesAreAbnormal-Fault NOTIFICATION-TYPE
            OBJECTS { hwStorageAlarmReporting }
            STATUS current
            DESCRIPTION "The RDMA Links Between Nodes Are Abnormal"
            --#SEVERITY MAJOR
            ::= { theRDMALinksBetweenNodesAreAbnormal 1 }

        -- 1.3.6.1.4.1.2011.2.251.20.1.2.2.15.6.66.2
        theRDMALinksBetweenNodesAreAbnormal-Resume NOTIFICATION-TYPE
            OBJECTS { hwStorageAlarmReporting }
            STATUS current
            DESCRIPTION "Recover: The RDMA Links Between Nodes Are Abnormal"
            --#SEVERITY INFORMATIONAL
            ::= { theRDMALinksBetweenNodesAreAbnormal 2 }

        -- 1.3.6.1.4.1.2011.2.251.20.1.2.2.15.6.73
        manageNetworkPortIsDisconnected1 OBJECT IDENTIFIER ::= { port 73 }

        -- 1.3.6.1.4.1.2011.2.251.20.1.2.2.15.6.73.1
        manageNetworkPortIsDisconnected1-Fault NOTIFICATION-TYPE
            OBJECTS { hwStorageAlarmReporting }
            STATUS current
            DESCRIPTION "Management Network Port Is Disconnected"
            --#SEVERITY WARNING
            ::= { manageNetworkPortIsDisconnected1 1 }

        -- 1.3.6.1.4.1.2011.2.251.20.1.2.2.15.6.73.2
        manageNetworkPortIsDisconnected1-Resume NOTIFICATION-TYPE
            OBJECTS { hwStorageAlarmReporting }
            STATUS current
            DESCRIPTION "Recover: Management Network Port Is Disconnected"
            --#SEVERITY INFORMATIONAL
            ::= { manageNetworkPortIsDisconnected1 2 }

        -- 1.3.6.1.4.1.2011.2.251.20.1.2.2.15.6.74
        theCableBetweenTwoPortsIsIncorrectlyConnected OBJECT IDENTIFIER ::= { port 74 }

        -- 1.3.6.1.4.1.2011.2.251.20.1.2.2.15.6.74.1
        theCableBetweenTwoPortsIsIncorrectlyConnected-Fault NOTIFICATION-TYPE
            OBJECTS { hwStorageAlarmReporting }
            STATUS current
            DESCRIPTION "The Cable Between Two Ports Is Incorrectly Connected"
            --#SEVERITY MAJOR
            ::= { theCableBetweenTwoPortsIsIncorrectlyConnected 1 }

        -- 1.3.6.1.4.1.2011.2.251.20.1.2.2.15.6.74.2
        theCableBetweenTwoPortsIsIncorrectlyConnected-Resume NOTIFICATION-TYPE
            OBJECTS { hwStorageAlarmReporting }
            STATUS current
            DESCRIPTION "Recover: The Cable Between Two Ports Is Incorrectly Connected"
            --#SEVERITY INFORMATIONAL
            ::= { theCableBetweenTwoPortsIsIncorrectlyConnected 2 }

        -- 1.3.6.1.4.1.2011.2.251.20.1.2.2.15.6.75
        theCableBetweenTwoPortsIsNotConnectedAccordingToTheStandardNetwork OBJECT IDENTIFIER ::= { port 75 }

        -- 1.3.6.1.4.1.2011.2.251.20.1.2.2.15.6.75.1
        theCableBetweenTwoPortsIsNotConnectedAccordingToTheStandardNetwork-Fault NOTIFICATION-TYPE
            OBJECTS { hwStorageAlarmReporting }
            STATUS current
            DESCRIPTION "The Cable Between Two Ports Is Not Connected According To The Standard Network"
            --#SEVERITY MAJOR
            ::= { theCableBetweenTwoPortsIsNotConnectedAccordingToTheStandardNetwork 1 }

        -- 1.3.6.1.4.1.2011.2.251.20.1.2.2.15.6.75.2
        theCableBetweenTwoPortsIsNotConnectedAccordingToTheStandardNetwork-Resume NOTIFICATION-TYPE
            OBJECTS { hwStorageAlarmReporting }
            STATUS current
            DESCRIPTION "Recover: The Cable Between Two Ports Is Not Connected According To The Standard Network"
            --#SEVERITY INFORMATIONAL
            ::= { theCableBetweenTwoPortsIsNotConnectedAccordingToTheStandardNetwork 2 }

        -- 1.3.6.1.4.1.2011.2.251.20.1.2.2.15.6.76
        theCableBetweenTwoPortsIsNotConnected OBJECT IDENTIFIER ::= { port 76 }

        -- 1.3.6.1.4.1.2011.2.251.20.1.2.2.15.6.76.1
        theCableBetweenTwoPortsIsNotConnected-Fault NOTIFICATION-TYPE
            OBJECTS { hwStorageAlarmReporting }
            STATUS current
            DESCRIPTION "The Cable Between Two Ports Is Not Connected"
            --#SEVERITY MAJOR
            ::= { theCableBetweenTwoPortsIsNotConnected 1 }

        -- 1.3.6.1.4.1.2011.2.251.20.1.2.2.15.6.76.2
        theCableBetweenTwoPortsIsNotConnected-Resume NOTIFICATION-TYPE
            OBJECTS { hwStorageAlarmReporting }
            STATUS current
            DESCRIPTION "Recover: The Cable Between Two Ports Is Not Connected"
            --#SEVERITY INFORMATIONAL
            ::= { theCableBetweenTwoPortsIsNotConnected 2 }

        -- 1.3.6.1.4.1.2011.2.251.20.1.2.2.15.6.77
        theHeartbeatLinksBetweenControllersInTheControllerEnclosureAreAbnormal OBJECT IDENTIFIER ::= { port 77 }

        -- 1.3.6.1.4.1.2011.2.251.20.1.2.2.15.6.77.1
        theHeartbeatLinksBetweenControllersInTheControllerEnclosureAreAbnormal-Fault NOTIFICATION-TYPE
            OBJECTS { hwStorageAlarmReporting }
            STATUS current
            DESCRIPTION "The Heartbeat Links Between Controllers In The Controller Enclosure Are Abnormal"
            --#SEVERITY MAJOR
            ::= { theHeartbeatLinksBetweenControllersInTheControllerEnclosureAreAbnormal 1 }

        -- 1.3.6.1.4.1.2011.2.251.20.1.2.2.15.6.77.2
        theHeartbeatLinksBetweenControllersInTheControllerEnclosureAreAbnormal-Resume NOTIFICATION-TYPE
            OBJECTS { hwStorageAlarmReporting }
            STATUS current
            DESCRIPTION "Recover: The Heartbeat Links Between Controllers In The Controller Enclosure Are Abnormal"
            --#SEVERITY INFORMATIONAL
            ::= { theHeartbeatLinksBetweenControllersInTheControllerEnclosureAreAbnormal 2 }

        -- 1.3.6.1.4.1.2011.2.251.20.1.2.2.15.6.78
        theNetworkingOfTheDiskEnclosureDoesNotMeetTheRequirementsOfTheEnclosureLevelRedundancyPolicy OBJECT IDENTIFIER ::= { port 78 }

        -- 1.3.6.1.4.1.2011.2.251.20.1.2.2.15.6.78.1
        theNetworkingOfTheDiskEnclosureDoesNotMeetTheRequirementsOfTheEnclosureLevelRedundancyPolicy-Fault NOTIFICATION-TYPE
            OBJECTS { hwStorageAlarmReporting }
            STATUS current
            DESCRIPTION "The Networking Of The Disk Enclosure Does Not Meet The Requirements Of The EnclosureLevel Redundancy Policy"
            --#SEVERITY MAJOR
            ::= { theNetworkingOfTheDiskEnclosureDoesNotMeetTheRequirementsOfTheEnclosureLevelRedundancyPolicy 1 }

        -- 1.3.6.1.4.1.2011.2.251.20.1.2.2.15.6.78.2
        theNetworkingOfTheDiskEnclosureDoesNotMeetTheRequirementsOfTheEnclosureLevelRedundancyPolicy-Resume NOTIFICATION-TYPE
            OBJECTS { hwStorageAlarmReporting }
            STATUS current
            DESCRIPTION "Recover: The Networking Of The Disk Enclosure Does Not Meet The Requirements Of The EnclosureLevel Redundancy Policy"
            --#SEVERITY INFORMATIONAL
            ::= { theNetworkingOfTheDiskEnclosureDoesNotMeetTheRequirementsOfTheEnclosureLevelRedundancyPolicy 2 }

        -- 1.3.6.1.4.1.2011.2.251.20.1.2.2.15.6.85
        failedToSynchronizeThePortRouteConfigurationToTheSecondaryVStoreOfTheVStorePair OBJECT IDENTIFIER ::= { port 85 }

        -- 1.3.6.1.4.1.2011.2.251.20.1.2.2.15.6.85.1
        failedToSynchronizeThePortRouteConfigurationToTheSecondaryVStoreOfTheVStorePair-Fault NOTIFICATION-TYPE
            OBJECTS { hwStorageAlarmReporting }
            STATUS current
            DESCRIPTION "Failed To Synchronize The Port Route Configuration To The Secondary VStore Of The VStore Pair"
            --#SEVERITY MAJOR
            ::= { failedToSynchronizeThePortRouteConfigurationToTheSecondaryVStoreOfTheVStorePair 1 }

        -- 1.3.6.1.4.1.2011.2.251.20.1.2.2.15.6.85.2
        failedToSynchronizeThePortRouteConfigurationToTheSecondaryVStoreOfTheVStorePair-Resume NOTIFICATION-TYPE
            OBJECTS { hwStorageAlarmReporting }
            STATUS current
            DESCRIPTION "Recover: Failed To Synchronize The Port Route Configuration To The Secondary VStore Of The VStore Pair"
            --#SEVERITY INFORMATIONAL
            ::= { failedToSynchronizeThePortRouteConfigurationToTheSecondaryVStoreOfTheVStorePair 2 }

        -- 1.3.6.1.4.1.2011.2.251.20.1.2.2.15.6.92
        theManagementNetworkIsNotRedundant OBJECT IDENTIFIER ::= { port 92 }

        -- 1.3.6.1.4.1.2011.2.251.20.1.2.2.15.6.92.1
        theManagementNetworkIsNotRedundant-Fault NOTIFICATION-TYPE
            OBJECTS { hwStorageAlarmReporting }
            STATUS current
            DESCRIPTION "The Management Network Is Not Redundant"
            --#SEVERITY WARNING
            ::= { theManagementNetworkIsNotRedundant 1 }

        -- 1.3.6.1.4.1.2011.2.251.20.1.2.2.15.6.92.2
        theManagementNetworkIsNotRedundant-Resume NOTIFICATION-TYPE
            OBJECTS { hwStorageAlarmReporting }
            STATUS current
            DESCRIPTION "Recover: The Management Network Is Not Redundant"
            --#SEVERITY INFORMATIONAL
            ::= { theManagementNetworkIsNotRedundant 2 }

        -- 1.3.6.1.4.1.2011.2.251.20.1.2.2.15.6.100
        theNumberOfIntermittentDisconnectionsOfTheLinkWhereThePortIsLocatedExceedsTheThreshold OBJECT IDENTIFIER ::= { port 100 }

        -- 1.3.6.1.4.1.2011.2.251.20.1.2.2.15.6.100.1
        theNumberOfIntermittentDisconnectionsOfTheLinkWhereThePortIsLocatedExceedsTheThreshold-Fault NOTIFICATION-TYPE
            OBJECTS { hwStorageAlarmReporting }
            STATUS current
            DESCRIPTION "The Number Of Intermittent Disconnections Of The Link Where The Port Is Located Exceeds The Threshold"
            --#SEVERITY WARNING
            ::= { theNumberOfIntermittentDisconnectionsOfTheLinkWhereThePortIsLocatedExceedsTheThreshold 1 }

        -- 1.3.6.1.4.1.2011.2.251.20.1.2.2.15.6.100.2
        theNumberOfIntermittentDisconnectionsOfTheLinkWhereThePortIsLocatedExceedsTheThreshold-Resume NOTIFICATION-TYPE
            OBJECTS { hwStorageAlarmReporting }
            STATUS current
            DESCRIPTION "Recover: The Number Of Intermittent Disconnections Of The Link Where The Port Is Located Exceeds The Threshold"
            --#SEVERITY INFORMATIONAL
            ::= { theNumberOfIntermittentDisconnectionsOfTheLinkWhereThePortIsLocatedExceedsTheThreshold 2 }

        -- 1.3.6.1.4.1.2011.2.251.20.1.2.2.15.6.171
        linkIsAbnormal OBJECT IDENTIFIER ::= { port 171 }

        -- 1.3.6.1.4.1.2011.2.251.20.1.2.2.15.6.171.1
        linkIsAbnormal-Fault NOTIFICATION-TYPE
            OBJECTS { hwStorageAlarmReporting }
            STATUS current
            DESCRIPTION "The RDMA Link Between Nodes Is Abnormal"
            --#SEVERITY MAJOR
            ::= { linkIsAbnormal 1 }

        -- 1.3.6.1.4.1.2011.2.251.20.1.2.2.15.6.171.2
        linkIsAbnormal-Resume NOTIFICATION-TYPE
            OBJECTS { hwStorageAlarmReporting }
            STATUS current
            DESCRIPTION "Recover: The RDMA Link Between Nodes Is Abnormal"
            --#SEVERITY INFORMATIONAL
            ::= { linkIsAbnormal 2 }

        -- 1.3.6.1.4.1.2011.2.251.20.1.2.2.15.10
        disk OBJECT IDENTIFIER ::= { oidBasedTrap 10 }

        -- 1.3.6.1.4.1.2011.2.251.20.1.2.2.15.10.1
        diskIsFaulty1 OBJECT IDENTIFIER ::= { disk 1 }

        -- 1.3.6.1.4.1.2011.2.251.20.1.2.2.15.10.1.1
        diskIsFaulty1-Fault NOTIFICATION-TYPE
            OBJECTS { hwStorageAlarmReporting }
            STATUS current
            DESCRIPTION "Disk Is Faulty"
            --#SEVERITY CRITICAL
            ::= { diskIsFaulty1 1 }

        -- 1.3.6.1.4.1.2011.2.251.20.1.2.2.15.10.1.2
        diskIsFaulty1-Resume NOTIFICATION-TYPE
            OBJECTS { hwStorageAlarmReporting }
            STATUS current
            DESCRIPTION "Recover: Disk Is Faulty"
            --#SEVERITY INFORMATIONAL
            ::= { diskIsFaulty1 2 }

        -- 1.3.6.1.4.1.2011.2.251.20.1.2.2.15.10.12
        hardDiskIsInSingleLinkState1 OBJECT IDENTIFIER ::= { disk 12 }

        -- 1.3.6.1.4.1.2011.2.251.20.1.2.2.15.10.12.1
        hardDiskIsInSingleLinkState1-Fault NOTIFICATION-TYPE
            OBJECTS { hwStorageAlarmReporting }
            STATUS current
            DESCRIPTION "A Disk Is In The SingleLink Status"
            --#SEVERITY MAJOR
            ::= { hardDiskIsInSingleLinkState1 1 }

        -- 1.3.6.1.4.1.2011.2.251.20.1.2.2.15.10.12.2
        hardDiskIsInSingleLinkState1-Resume NOTIFICATION-TYPE
            OBJECTS { hwStorageAlarmReporting }
            STATUS current
            DESCRIPTION "Recover: A Disk Is In The SingleLink Status"
            --#SEVERITY INFORMATIONAL
            ::= { hardDiskIsInSingleLinkState1 2 }

        -- 1.3.6.1.4.1.2011.2.251.20.1.2.2.15.10.21
        diskMonitoringFailed OBJECT IDENTIFIER ::= { disk 21 }

        -- 1.3.6.1.4.1.2011.2.251.20.1.2.2.15.10.21.1
        diskMonitoringFailed-Fault NOTIFICATION-TYPE
            OBJECTS { hwStorageAlarmReporting }
            STATUS current
            DESCRIPTION "The System Failed To Monitor A Disk In The Disk Enclosure"
            --#SEVERITY MAJOR
            ::= { diskMonitoringFailed 1 }

        -- 1.3.6.1.4.1.2011.2.251.20.1.2.2.15.10.21.2
        diskMonitoringFailed-Resume NOTIFICATION-TYPE
            OBJECTS { hwStorageAlarmReporting }
            STATUS current
            DESCRIPTION "Recover: The System Failed To Monitor A Disk In The Disk Enclosure"
            --#SEVERITY INFORMATIONAL
            ::= { diskMonitoringFailed 2 }

        -- 1.3.6.1.4.1.2011.2.251.20.1.2.2.15.10.45
        diskRepair OBJECT IDENTIFIER ::= { disk 45 }

        -- 1.3.6.1.4.1.2011.2.251.20.1.2.2.15.10.45.1
        diskRepair-Fault NOTIFICATION-TYPE
            OBJECTS { hwStorageAlarmReporting }
            STATUS current
            DESCRIPTION "Disk Repair"
            --#SEVERITY WARNING
            ::= { diskRepair 1 }

        -- 1.3.6.1.4.1.2011.2.251.20.1.2.2.15.10.45.2
        diskRepair-Resume NOTIFICATION-TYPE
            OBJECTS { hwStorageAlarmReporting }
            STATUS current
            DESCRIPTION "Recover: Disk Repair"
            --#SEVERITY INFORMATIONAL
            ::= { diskRepair 2 }

        -- 1.3.6.1.4.1.2011.2.251.20.1.2.2.15.10.147
        diskHasTooManyBitError OBJECT IDENTIFIER ::= { disk 147 }

        -- 1.3.6.1.4.1.2011.2.251.20.1.2.2.15.10.147.1
        diskHasTooManyBitError-Fault NOTIFICATION-TYPE
            OBJECTS { hwStorageAlarmReporting }
            STATUS current
            DESCRIPTION "A Disk Has Too Many Bit Errors"
            --#SEVERITY MAJOR
            ::= { diskHasTooManyBitError 1 }

        -- 1.3.6.1.4.1.2011.2.251.20.1.2.2.15.10.147.2
        diskHasTooManyBitError-Resume NOTIFICATION-TYPE
            OBJECTS { hwStorageAlarmReporting }
            STATUS current
            DESCRIPTION "Recover: A Disk Has Too Many Bit Errors"
            --#SEVERITY INFORMATIONAL
            ::= { diskHasTooManyBitError 2 }

        -- 1.3.6.1.4.1.2011.2.251.20.1.2.2.15.10.262
        unrecognizableDisk OBJECT IDENTIFIER ::= { disk 262 }

        -- 1.3.6.1.4.1.2011.2.251.20.1.2.2.15.10.262.1
        unrecognizableDisk-Fault NOTIFICATION-TYPE
            OBJECTS { hwStorageAlarmReporting }
            STATUS current
            DESCRIPTION "Unrecognizable Disk"
            --#SEVERITY MAJOR
            ::= { unrecognizableDisk 1 }

        -- 1.3.6.1.4.1.2011.2.251.20.1.2.2.15.10.262.2
        unrecognizableDisk-Resume NOTIFICATION-TYPE
            OBJECTS { hwStorageAlarmReporting }
            STATUS current
            DESCRIPTION "Recover: Unrecognizable Disk"
            --#SEVERITY INFORMATIONAL
            ::= { unrecognizableDisk 2 }

        -- 1.3.6.1.4.1.2011.2.251.20.1.2.2.15.10.263
        diskIsAboutToFail OBJECT IDENTIFIER ::= { disk 263 }

        -- 1.3.6.1.4.1.2011.2.251.20.1.2.2.15.10.263.1
        diskIsAboutToFail-Fault NOTIFICATION-TYPE
            OBJECTS { hwStorageAlarmReporting }
            STATUS current
            DESCRIPTION "Disk Is About To Fail"
            --#SEVERITY MAJOR
            ::= { diskIsAboutToFail 1 }

        -- 1.3.6.1.4.1.2011.2.251.20.1.2.2.15.10.263.2
        diskIsAboutToFail-Resume NOTIFICATION-TYPE
            OBJECTS { hwStorageAlarmReporting }
            STATUS current
            DESCRIPTION "Recover: Disk Is About To Fail"
            --#SEVERITY INFORMATIONAL
            ::= { diskIsAboutToFail 2 }

        -- 1.3.6.1.4.1.2011.2.251.20.1.2.2.15.10.280
        diskInEngineMonitoringFailed OBJECT IDENTIFIER ::= { disk 280 }

        -- 1.3.6.1.4.1.2011.2.251.20.1.2.2.15.10.280.1
        diskInEngineMonitoringFailed-Fault NOTIFICATION-TYPE
            OBJECTS { hwStorageAlarmReporting }
            STATUS current
            DESCRIPTION "The System Failed To Monitor A Disk In The Controller Enclosure"
            --#SEVERITY MAJOR
            ::= { diskInEngineMonitoringFailed 1 }

        -- 1.3.6.1.4.1.2011.2.251.20.1.2.2.15.10.280.2
        diskInEngineMonitoringFailed-Resume NOTIFICATION-TYPE
            OBJECTS { hwStorageAlarmReporting }
            STATUS current
            DESCRIPTION "Recover: The System Failed To Monitor A Disk In The Controller Enclosure"
            --#SEVERITY INFORMATIONAL
            ::= { diskInEngineMonitoringFailed 2 }

        -- 1.3.6.1.4.1.2011.2.251.20.1.2.2.15.10.281
        diskWorkingRateAbnormal OBJECT IDENTIFIER ::= { disk 281 }

        -- 1.3.6.1.4.1.2011.2.251.20.1.2.2.15.10.281.1
        diskWorkingRateAbnormal-Fault NOTIFICATION-TYPE
            OBJECTS { hwStorageAlarmReporting }
            STATUS current
            DESCRIPTION "Working Rate Of A Disk Is Abnormal"
            --#SEVERITY MAJOR
            ::= { diskWorkingRateAbnormal 1 }

        -- 1.3.6.1.4.1.2011.2.251.20.1.2.2.15.10.281.2
        diskWorkingRateAbnormal-Resume NOTIFICATION-TYPE
            OBJECTS { hwStorageAlarmReporting }
            STATUS current
            DESCRIPTION "Recover: Working Rate Of A Disk Is Abnormal"
            --#SEVERITY INFORMATIONAL
            ::= { diskWorkingRateAbnormal 2 }

        -- 1.3.6.1.4.1.2011.2.251.20.1.2.2.15.10.283
        theNumberOfConnectedDisksExceedsTheUpperLimitOfTheSystem OBJECT IDENTIFIER ::= { disk 283 }

        -- 1.3.6.1.4.1.2011.2.251.20.1.2.2.15.10.283.1
        theNumberOfConnectedDisksExceedsTheUpperLimitOfTheSystem-Fault NOTIFICATION-TYPE
            OBJECTS { hwStorageAlarmReporting }
            STATUS current
            DESCRIPTION "The Number Of Connected Disks Exceeds The Upper Limit Of The System"
            --#SEVERITY WARNING
            ::= { theNumberOfConnectedDisksExceedsTheUpperLimitOfTheSystem 1 }

        -- 1.3.6.1.4.1.2011.2.251.20.1.2.2.15.10.283.2
        theNumberOfConnectedDisksExceedsTheUpperLimitOfTheSystem-Resume NOTIFICATION-TYPE
            OBJECTS { hwStorageAlarmReporting }
            STATUS current
            DESCRIPTION "Recover: The Number Of Connected Disks Exceeds The Upper Limit Of The System"
            --#SEVERITY INFORMATIONAL
            ::= { theNumberOfConnectedDisksExceedsTheUpperLimitOfTheSystem 2 }

        -- 1.3.6.1.4.1.2011.2.251.20.1.2.2.15.10.288
        diskTemperatureExceedsUpperLimit1 OBJECT IDENTIFIER ::= { disk 288 }

        -- 1.3.6.1.4.1.2011.2.251.20.1.2.2.15.10.288.1
        diskTemperatureExceedsUpperLimit1-Fault NOTIFICATION-TYPE
            OBJECTS { hwStorageAlarmReporting }
            STATUS current
            DESCRIPTION "Disk Temperature Exceeds The Upper Limit"
            --#SEVERITY WARNING
            ::= { diskTemperatureExceedsUpperLimit1 1 }

        -- 1.3.6.1.4.1.2011.2.251.20.1.2.2.15.10.288.2
        diskTemperatureExceedsUpperLimit1-Resume NOTIFICATION-TYPE
            OBJECTS { hwStorageAlarmReporting }
            STATUS current
            DESCRIPTION "Recover: Disk Temperature Exceeds The Upper Limit"
            --#SEVERITY INFORMATIONAL
            ::= { diskTemperatureExceedsUpperLimit1 2 }

        -- 1.3.6.1.4.1.2011.2.251.20.1.2.2.15.10.289
        slowDiskResponse1 OBJECT IDENTIFIER ::= { disk 289 }

        -- 1.3.6.1.4.1.2011.2.251.20.1.2.2.15.10.289.1
        slowDiskResponse1-Fault NOTIFICATION-TYPE
            OBJECTS { hwStorageAlarmReporting }
            STATUS current
            DESCRIPTION "Slow Disk Response"
            --#SEVERITY MAJOR
            ::= { slowDiskResponse1 1 }

        -- 1.3.6.1.4.1.2011.2.251.20.1.2.2.15.10.289.2
        slowDiskResponse1-Resume NOTIFICATION-TYPE
            OBJECTS { hwStorageAlarmReporting }
            STATUS current
            DESCRIPTION "Recover: Slow Disk Response"
            --#SEVERITY INFORMATIONAL
            ::= { slowDiskResponse1 2 }

        -- 1.3.6.1.4.1.2011.2.251.20.1.2.2.15.10.291
        diskModelIsIncompatible1 OBJECT IDENTIFIER ::= { disk 291 }

        -- 1.3.6.1.4.1.2011.2.251.20.1.2.2.15.10.291.1
        diskModelIsIncompatible1-Fault NOTIFICATION-TYPE
            OBJECTS { hwStorageAlarmReporting }
            STATUS current
            DESCRIPTION "Incompatible Disk Model"
            --#SEVERITY MAJOR
            ::= { diskModelIsIncompatible1 1 }

        -- 1.3.6.1.4.1.2011.2.251.20.1.2.2.15.10.291.2
        diskModelIsIncompatible1-Resume NOTIFICATION-TYPE
            OBJECTS { hwStorageAlarmReporting }
            STATUS current
            DESCRIPTION "Recover: Incompatible Disk Model"
            --#SEVERITY INFORMATIONAL
            ::= { diskModelIsIncompatible1 2 }

        -- 1.3.6.1.4.1.2011.2.251.20.1.2.2.15.10.296
        authenticationOfSEDAccessFails1 OBJECT IDENTIFIER ::= { disk 296 }

        -- 1.3.6.1.4.1.2011.2.251.20.1.2.2.15.10.296.1
        authenticationOfSEDAccessFails1-Fault NOTIFICATION-TYPE
            OBJECTS { hwStorageAlarmReporting }
            STATUS current
            DESCRIPTION "Failed To Authenticate SelfEncrypting Disk Access"
            --#SEVERITY MAJOR
            ::= { authenticationOfSEDAccessFails1 1 }

        -- 1.3.6.1.4.1.2011.2.251.20.1.2.2.15.10.296.2
        authenticationOfSEDAccessFails1-Resume NOTIFICATION-TYPE
            OBJECTS { hwStorageAlarmReporting }
            STATUS current
            DESCRIPTION "Recover: Failed To Authenticate SelfEncrypting Disk Access"
            --#SEVERITY INFORMATIONAL
            ::= { authenticationOfSEDAccessFails1 2 }

        -- 1.3.6.1.4.1.2011.2.251.20.1.2.2.15.10.297
        authenticationOfSEDKeyFails1 OBJECT IDENTIFIER ::= { disk 297 }

        -- 1.3.6.1.4.1.2011.2.251.20.1.2.2.15.10.297.1
        authenticationOfSEDKeyFails1-Fault NOTIFICATION-TYPE
            OBJECTS { hwStorageAlarmReporting }
            STATUS current
            DESCRIPTION "Failed To Authenticate A SelfEncrypting Disk Key"
            --#SEVERITY MAJOR
            ::= { authenticationOfSEDKeyFails1 1 }

        -- 1.3.6.1.4.1.2011.2.251.20.1.2.2.15.10.297.2
        authenticationOfSEDKeyFails1-Resume NOTIFICATION-TYPE
            OBJECTS { hwStorageAlarmReporting }
            STATUS current
            DESCRIPTION "Recover: Failed To Authenticate A SelfEncrypting Disk Key"
            --#SEVERITY INFORMATIONAL
            ::= { authenticationOfSEDKeyFails1 2 }

        -- 1.3.6.1.4.1.2011.2.251.20.1.2.2.15.10.318
        theDiskIsIsolated OBJECT IDENTIFIER ::= { disk 318 }

        -- 1.3.6.1.4.1.2011.2.251.20.1.2.2.15.10.318.1
        theDiskIsIsolated-Fault NOTIFICATION-TYPE
            OBJECTS { hwStorageAlarmReporting }
            STATUS current
            DESCRIPTION "The Disk Is Isolated"
            --#SEVERITY MAJOR
            ::= { theDiskIsIsolated 1 }

        -- 1.3.6.1.4.1.2011.2.251.20.1.2.2.15.10.318.2
        theDiskIsIsolated-Resume NOTIFICATION-TYPE
            OBJECTS { hwStorageAlarmReporting }
            STATUS current
            DESCRIPTION "Recover: The Disk Is Isolated"
            --#SEVERITY INFORMATIONAL
            ::= { theDiskIsIsolated 2 }

        -- 1.3.6.1.4.1.2011.2.251.20.1.2.2.15.10.368
        theAmountOfDataWrittenToTheSystemDiskIsAbnormal OBJECT IDENTIFIER ::= { disk 368 }

        -- 1.3.6.1.4.1.2011.2.251.20.1.2.2.15.10.368.1
        theAmountOfDataWrittenToTheSystemDiskIsAbnormal-Fault NOTIFICATION-TYPE
            OBJECTS { hwStorageAlarmReporting }
            STATUS current
            DESCRIPTION "The Amount Of Data Written To The System Disk Is Abnormal"
            --#SEVERITY WARNING
            ::= { theAmountOfDataWrittenToTheSystemDiskIsAbnormal 1 }

        -- 1.3.6.1.4.1.2011.2.251.20.1.2.2.15.10.368.2
        theAmountOfDataWrittenToTheSystemDiskIsAbnormal-Resume NOTIFICATION-TYPE
            OBJECTS { hwStorageAlarmReporting }
            STATUS current
            DESCRIPTION "Recover: The Amount Of Data Written To The System Disk Is Abnormal"
            --#SEVERITY INFORMATIONAL
            ::= { theAmountOfDataWrittenToTheSystemDiskIsAbnormal 2 }

        -- 1.3.6.1.4.1.2011.2.251.20.1.2.2.15.10.565
        theEstimatedLifespanOfADiskIsAboutToBeReached OBJECT IDENTIFIER ::= { disk 565 }

        -- 1.3.6.1.4.1.2011.2.251.20.1.2.2.15.10.565.1
        theEstimatedLifespanOfADiskIsAboutToBeReached-Fault NOTIFICATION-TYPE
            OBJECTS { hwStorageAlarmReporting }
            STATUS current
            DESCRIPTION "The Estimated Lifespan Of A Disk Is About To Be Reached"
            --#SEVERITY MAJOR
            ::= { theEstimatedLifespanOfADiskIsAboutToBeReached 1 }

        -- 1.3.6.1.4.1.2011.2.251.20.1.2.2.15.10.565.2
        theEstimatedLifespanOfADiskIsAboutToBeReached-Resume NOTIFICATION-TYPE
            OBJECTS { hwStorageAlarmReporting }
            STATUS current
            DESCRIPTION "Recover: The Estimated Lifespan Of A Disk Is About To Be Reached"
            --#SEVERITY INFORMATIONAL
            ::= { theEstimatedLifespanOfADiskIsAboutToBeReached 2 }

        -- 1.3.6.1.4.1.2011.2.251.20.1.2.2.15.10.567
        theNumberOfConnectedDisksExceedsTheUpperLimitOfASingleEngine OBJECT IDENTIFIER ::= { disk 567 }

        -- 1.3.6.1.4.1.2011.2.251.20.1.2.2.15.10.567.1
        theNumberOfConnectedDisksExceedsTheUpperLimitOfASingleEngine-Fault NOTIFICATION-TYPE
            OBJECTS { hwStorageAlarmReporting }
            STATUS current
            DESCRIPTION "The Number Of Connected Disks Exceeds The Upper Limit Of A Single Engine"
            --#SEVERITY WARNING
            ::= { theNumberOfConnectedDisksExceedsTheUpperLimitOfASingleEngine 1 }

        -- 1.3.6.1.4.1.2011.2.251.20.1.2.2.15.10.567.2
        theNumberOfConnectedDisksExceedsTheUpperLimitOfASingleEngine-Resume NOTIFICATION-TYPE
            OBJECTS { hwStorageAlarmReporting }
            STATUS current
            DESCRIPTION "Recover: The Number Of Connected Disks Exceeds The Upper Limit Of A Single Engine"
            --#SEVERITY INFORMATIONAL
            ::= { theNumberOfConnectedDisksExceedsTheUpperLimitOfASingleEngine 2 }

        -- 1.3.6.1.4.1.2011.2.251.20.1.2.2.15.10.568
        theDiskIsInsertedIntoAnIncorrectSlot OBJECT IDENTIFIER ::= { disk 568 }

        -- 1.3.6.1.4.1.2011.2.251.20.1.2.2.15.10.568.1
        theDiskIsInsertedIntoAnIncorrectSlot-Fault NOTIFICATION-TYPE
            OBJECTS { hwStorageAlarmReporting }
            STATUS current
            DESCRIPTION "The Disk Is Inserted Into An Incorrect Slot"
            --#SEVERITY MAJOR
            ::= { theDiskIsInsertedIntoAnIncorrectSlot 1 }

        -- 1.3.6.1.4.1.2011.2.251.20.1.2.2.15.10.568.2
        theDiskIsInsertedIntoAnIncorrectSlot-Resume NOTIFICATION-TYPE
            OBJECTS { hwStorageAlarmReporting }
            STATUS current
            DESCRIPTION "Recover: The Disk Is Inserted Into An Incorrect Slot"
            --#SEVERITY INFORMATIONAL
            ::= { theDiskIsInsertedIntoAnIncorrectSlot 2 }

        -- 1.3.6.1.4.1.2011.2.251.20.1.2.2.15.10.573
        authenticationOfSEDKeyFails OBJECT IDENTIFIER ::= { disk 573 }

        -- 1.3.6.1.4.1.2011.2.251.20.1.2.2.15.10.573.1
        authenticationOfSEDKeyFails-Fault NOTIFICATION-TYPE
            OBJECTS { hwStorageAlarmReporting }
            STATUS current
            DESCRIPTION "Failed To Authenticate The Key Of The SelfEncrypting Drive"
            --#SEVERITY MAJOR
            ::= { authenticationOfSEDKeyFails 1 }

        -- 1.3.6.1.4.1.2011.2.251.20.1.2.2.15.10.573.2
        authenticationOfSEDKeyFails-Resume NOTIFICATION-TYPE
            OBJECTS { hwStorageAlarmReporting }
            STATUS current
            DESCRIPTION "Recover: Failed To Authenticate The Key Of The SelfEncrypting Drive"
            --#SEVERITY INFORMATIONAL
            ::= { authenticationOfSEDKeyFails 2 }

        -- 1.3.6.1.4.1.2011.2.251.20.1.2.2.15.10.574
        authenticationOfSEDAccessFails OBJECT IDENTIFIER ::= { disk 574 }

        -- 1.3.6.1.4.1.2011.2.251.20.1.2.2.15.10.574.1
        authenticationOfSEDAccessFails-Fault NOTIFICATION-TYPE
            OBJECTS { hwStorageAlarmReporting }
            STATUS current
            DESCRIPTION "Access Authentication Of The SelfEncrypting Drive Failed"
            --#SEVERITY MAJOR
            ::= { authenticationOfSEDAccessFails 1 }

        -- 1.3.6.1.4.1.2011.2.251.20.1.2.2.15.10.574.2
        authenticationOfSEDAccessFails-Resume NOTIFICATION-TYPE
            OBJECTS { hwStorageAlarmReporting }
            STATUS current
            DESCRIPTION "Recover: Access Authentication Of The SelfEncrypting Drive Failed"
            --#SEVERITY INFORMATIONAL
            ::= { authenticationOfSEDAccessFails 2 }

        -- 1.3.6.1.4.1.2011.2.251.20.1.2.2.15.10.577
        diskModelIsIncompatible OBJECT IDENTIFIER ::= { disk 577 }

        -- 1.3.6.1.4.1.2011.2.251.20.1.2.2.15.10.577.1
        diskModelIsIncompatible-Fault NOTIFICATION-TYPE
            OBJECTS { hwStorageAlarmReporting }
            STATUS current
            DESCRIPTION "The Disk Model Is Incompatible With The Device"
            --#SEVERITY MAJOR
            ::= { diskModelIsIncompatible 1 }

        -- 1.3.6.1.4.1.2011.2.251.20.1.2.2.15.10.577.2
        diskModelIsIncompatible-Resume NOTIFICATION-TYPE
            OBJECTS { hwStorageAlarmReporting }
            STATUS current
            DESCRIPTION "Recover: The Disk Model Is Incompatible With The Device"
            --#SEVERITY INFORMATIONAL
            ::= { diskModelIsIncompatible 2 }

        -- 1.3.6.1.4.1.2011.2.251.20.1.2.2.15.10.579
        slowDiskResponse OBJECT IDENTIFIER ::= { disk 579 }

        -- 1.3.6.1.4.1.2011.2.251.20.1.2.2.15.10.579.1
        slowDiskResponse-Fault NOTIFICATION-TYPE
            OBJECTS { hwStorageAlarmReporting }
            STATUS current
            DESCRIPTION "Slow Disk Response"
            --#SEVERITY MAJOR
            ::= { slowDiskResponse 1 }

        -- 1.3.6.1.4.1.2011.2.251.20.1.2.2.15.10.579.2
        slowDiskResponse-Resume NOTIFICATION-TYPE
            OBJECTS { hwStorageAlarmReporting }
            STATUS current
            DESCRIPTION "Recover: Slow Disk Response"
            --#SEVERITY INFORMATIONAL
            ::= { slowDiskResponse 2 }

        -- 1.3.6.1.4.1.2011.2.251.20.1.2.2.15.10.580
        hardDiskIsInSingleLinkState OBJECT IDENTIFIER ::= { disk 580 }

        -- 1.3.6.1.4.1.2011.2.251.20.1.2.2.15.10.580.1
        hardDiskIsInSingleLinkState-Fault NOTIFICATION-TYPE
            OBJECTS { hwStorageAlarmReporting }
            STATUS current
            DESCRIPTION "The Disk Is In The SingleLink Status"
            --#SEVERITY MAJOR
            ::= { hardDiskIsInSingleLinkState 1 }

        -- 1.3.6.1.4.1.2011.2.251.20.1.2.2.15.10.580.2
        hardDiskIsInSingleLinkState-Resume NOTIFICATION-TYPE
            OBJECTS { hwStorageAlarmReporting }
            STATUS current
            DESCRIPTION "Recover: The Disk Is In The SingleLink Status"
            --#SEVERITY INFORMATIONAL
            ::= { hardDiskIsInSingleLinkState 2 }

        -- 1.3.6.1.4.1.2011.2.251.20.1.2.2.15.10.581
        diskFaulty OBJECT IDENTIFIER ::= { disk 581 }

        -- 1.3.6.1.4.1.2011.2.251.20.1.2.2.15.10.581.1
        diskFaulty-Fault NOTIFICATION-TYPE
            OBJECTS { hwStorageAlarmReporting }
            STATUS current
            DESCRIPTION "The Disk Is About To Fail"
            --#SEVERITY MAJOR
            ::= { diskFaulty 1 }

        -- 1.3.6.1.4.1.2011.2.251.20.1.2.2.15.10.581.2
        diskFaulty-Resume NOTIFICATION-TYPE
            OBJECTS { hwStorageAlarmReporting }
            STATUS current
            DESCRIPTION "Recover: The Disk Is About To Fail"
            --#SEVERITY INFORMATIONAL
            ::= { diskFaulty 2 }

        -- 1.3.6.1.4.1.2011.2.251.20.1.2.2.15.10.582
        diskTemperatureExceedsUpperLimit OBJECT IDENTIFIER ::= { disk 582 }

        -- 1.3.6.1.4.1.2011.2.251.20.1.2.2.15.10.582.1
        diskTemperatureExceedsUpperLimit-Fault NOTIFICATION-TYPE
            OBJECTS { hwStorageAlarmReporting }
            STATUS current
            DESCRIPTION "The Temperature Of The Disk Exceeds The Upper Limit"
            --#SEVERITY WARNING
            ::= { diskTemperatureExceedsUpperLimit 1 }

        -- 1.3.6.1.4.1.2011.2.251.20.1.2.2.15.10.582.2
        diskTemperatureExceedsUpperLimit-Resume NOTIFICATION-TYPE
            OBJECTS { hwStorageAlarmReporting }
            STATUS current
            DESCRIPTION "Recover: The Temperature Of The Disk Exceeds The Upper Limit"
            --#SEVERITY INFORMATIONAL
            ::= { diskTemperatureExceedsUpperLimit 2 }

        -- 1.3.6.1.4.1.2011.2.251.20.1.2.2.15.10.583
        theDiskCannotBeIdentified OBJECT IDENTIFIER ::= { disk 583 }

        -- 1.3.6.1.4.1.2011.2.251.20.1.2.2.15.10.583.1
        theDiskCannotBeIdentified-Fault NOTIFICATION-TYPE
            OBJECTS { hwStorageAlarmReporting }
            STATUS current
            DESCRIPTION "The Disk Cannot Be Identified"
            --#SEVERITY MAJOR
            ::= { theDiskCannotBeIdentified 1 }

        -- 1.3.6.1.4.1.2011.2.251.20.1.2.2.15.10.583.2
        theDiskCannotBeIdentified-Resume NOTIFICATION-TYPE
            OBJECTS { hwStorageAlarmReporting }
            STATUS current
            DESCRIPTION "Recover: The Disk Cannot Be Identified"
            --#SEVERITY INFORMATIONAL
            ::= { theDiskCannotBeIdentified 2 }

        -- 1.3.6.1.4.1.2011.2.251.20.1.2.2.15.10.584
        diskIsFaulty OBJECT IDENTIFIER ::= { disk 584 }

        -- 1.3.6.1.4.1.2011.2.251.20.1.2.2.15.10.584.1
        diskIsFaulty-Fault NOTIFICATION-TYPE
            OBJECTS { hwStorageAlarmReporting }
            STATUS current
            DESCRIPTION "The Disk Is Faulty"
            --#SEVERITY CRITICAL
            ::= { diskIsFaulty 1 }

        -- 1.3.6.1.4.1.2011.2.251.20.1.2.2.15.10.584.2
        diskIsFaulty-Resume NOTIFICATION-TYPE
            OBJECTS { hwStorageAlarmReporting }
            STATUS current
            DESCRIPTION "Recover: The Disk Is Faulty"
            --#SEVERITY INFORMATIONAL
            ::= { diskIsFaulty 2 }

        -- 1.3.6.1.4.1.2011.2.251.20.1.2.2.15.10.585
        theTemperatureOfMultipleDisksSeriouslyExceedsTheUpperLimit OBJECT IDENTIFIER ::= { disk 585 }

        -- 1.3.6.1.4.1.2011.2.251.20.1.2.2.15.10.585.1
        theTemperatureOfMultipleDisksSeriouslyExceedsTheUpperLimit-Fault NOTIFICATION-TYPE
            OBJECTS { hwStorageAlarmReporting }
            STATUS current
            DESCRIPTION "The Temperature Of Multiple Disks Seriously Exceeds The Upper Limit"
            --#SEVERITY CRITICAL
            ::= { theTemperatureOfMultipleDisksSeriouslyExceedsTheUpperLimit 1 }

        -- 1.3.6.1.4.1.2011.2.251.20.1.2.2.15.10.585.2
        theTemperatureOfMultipleDisksSeriouslyExceedsTheUpperLimit-Resume NOTIFICATION-TYPE
            OBJECTS { hwStorageAlarmReporting }
            STATUS current
            DESCRIPTION "Recover: The Temperature Of Multiple Disks Seriously Exceeds The Upper Limit"
            --#SEVERITY INFORMATIONAL
            ::= { theTemperatureOfMultipleDisksSeriouslyExceedsTheUpperLimit 2 }

        -- 1.3.6.1.4.1.2011.2.251.20.1.2.2.15.10.650
        theTemperatureOfMultipleDisksExceedsTheUpperLimit OBJECT IDENTIFIER ::= { disk 650 }

        -- 1.3.6.1.4.1.2011.2.251.20.1.2.2.15.10.650.1
        theTemperatureOfMultipleDisksExceedsTheUpperLimit-Fault NOTIFICATION-TYPE
            OBJECTS { hwStorageAlarmReporting }
            STATUS current
            DESCRIPTION "The Temperature Of Multiple Disks Exceeds The Upper Limit"
            --#SEVERITY MAJOR
            ::= { theTemperatureOfMultipleDisksExceedsTheUpperLimit 1 }

        -- 1.3.6.1.4.1.2011.2.251.20.1.2.2.15.10.650.2
        theTemperatureOfMultipleDisksExceedsTheUpperLimit-Resume NOTIFICATION-TYPE
            OBJECTS { hwStorageAlarmReporting }
            STATUS current
            DESCRIPTION "Recover: The Temperature Of Multiple Disks Exceeds The Upper Limit"
            --#SEVERITY INFORMATIONAL
            ::= { theTemperatureOfMultipleDisksExceedsTheUpperLimit 2 }

        -- 1.3.6.1.4.1.2011.2.251.20.1.2.2.15.10.656
        theSystemDiskOfTheControllerIsFaulty OBJECT IDENTIFIER ::= { disk 656 }

        -- 1.3.6.1.4.1.2011.2.251.20.1.2.2.15.10.656.1
        theSystemDiskOfTheControllerIsFaulty-Fault NOTIFICATION-TYPE
            OBJECTS { hwStorageAlarmReporting }
            STATUS current
            DESCRIPTION "The System Disk Of The Controller Is Faulty"
            --#SEVERITY MAJOR
            ::= { theSystemDiskOfTheControllerIsFaulty 1 }

        -- 1.3.6.1.4.1.2011.2.251.20.1.2.2.15.10.656.2
        theSystemDiskOfTheControllerIsFaulty-Resume NOTIFICATION-TYPE
            OBJECTS { hwStorageAlarmReporting }
            STATUS current
            DESCRIPTION "Recover: The System Disk Of The Controller Is Faulty"
            --#SEVERITY INFORMATIONAL
            ::= { theSystemDiskOfTheControllerIsFaulty 2 }

        -- 1.3.6.1.4.1.2011.2.251.20.1.2.2.15.10.658
        theSystemDiskOfTheExpansionModuleIsFaulty OBJECT IDENTIFIER ::= { disk 658 }

        -- 1.3.6.1.4.1.2011.2.251.20.1.2.2.15.10.658.1
        theSystemDiskOfTheExpansionModuleIsFaulty-Fault NOTIFICATION-TYPE
            OBJECTS { hwStorageAlarmReporting }
            STATUS current
            DESCRIPTION "The System Disk Of The Expansion Module Is Faulty"
            --#SEVERITY MAJOR
            ::= { theSystemDiskOfTheExpansionModuleIsFaulty 1 }

        -- 1.3.6.1.4.1.2011.2.251.20.1.2.2.15.10.658.2
        theSystemDiskOfTheExpansionModuleIsFaulty-Resume NOTIFICATION-TYPE
            OBJECTS { hwStorageAlarmReporting }
            STATUS current
            DESCRIPTION "Recover: The System Disk Of The Expansion Module Is Faulty"
            --#SEVERITY INFORMATIONAL
            ::= { theSystemDiskOfTheExpansionModuleIsFaulty 2 }

        -- 1.3.6.1.4.1.2011.2.251.20.1.2.2.15.10.659
        theNumberOfConnectedDisksExceedsTheUpperLimitOfASingleControllerEnclosure OBJECT IDENTIFIER ::= { disk 659 }

        -- 1.3.6.1.4.1.2011.2.251.20.1.2.2.15.10.659.1
        theNumberOfConnectedDisksExceedsTheUpperLimitOfASingleControllerEnclosure-Fault NOTIFICATION-TYPE
            OBJECTS { hwStorageAlarmReporting }
            STATUS current
            DESCRIPTION "The Number Of Connected Disks Exceeds The Upper Limit Of A Single Controller Enclosure"
            --#SEVERITY WARNING
            ::= { theNumberOfConnectedDisksExceedsTheUpperLimitOfASingleControllerEnclosure 1 }

        -- 1.3.6.1.4.1.2011.2.251.20.1.2.2.15.10.659.2
        theNumberOfConnectedDisksExceedsTheUpperLimitOfASingleControllerEnclosure-Resume NOTIFICATION-TYPE
            OBJECTS { hwStorageAlarmReporting }
            STATUS current
            DESCRIPTION "Recover: The Number Of Connected Disks Exceeds The Upper Limit Of A Single Controller Enclosure"
            --#SEVERITY INFORMATIONAL
            ::= { theNumberOfConnectedDisksExceedsTheUpperLimitOfASingleControllerEnclosure 2 }

        -- 1.3.6.1.4.1.2011.2.251.20.1.2.2.15.10.831
        diskIsRiskyLifeCritial OBJECT IDENTIFIER ::= { disk 831 }

        -- 1.3.6.1.4.1.2011.2.251.20.1.2.2.15.10.831.1
        diskIsRiskyLifeCritial-Fault NOTIFICATION-TYPE
            OBJECTS { hwStorageAlarmReporting }
            STATUS current
            DESCRIPTION "The Disk In The Device Is About To Fail"
            --#SEVERITY CRITICAL
            ::= { diskIsRiskyLifeCritial 1 }

        -- 1.3.6.1.4.1.2011.2.251.20.1.2.2.15.10.831.2
        diskIsRiskyLifeCritial-Resume NOTIFICATION-TYPE
            OBJECTS { hwStorageAlarmReporting }
            STATUS current
            DESCRIPTION "Recover: The Disk In The Device Is About To Fail"
            --#SEVERITY INFORMATIONAL
            ::= { diskIsRiskyLifeCritial 2 }

        -- 1.3.6.1.4.1.2011.2.251.20.1.2.2.15.10.832
        diskIsRiskyLifeMajor OBJECT IDENTIFIER ::= { disk 832 }

        -- 1.3.6.1.4.1.2011.2.251.20.1.2.2.15.10.832.1
        diskIsRiskyLifeMajor-Fault NOTIFICATION-TYPE
            OBJECTS { hwStorageAlarmReporting }
            STATUS current
            DESCRIPTION "The Firmware Version Of The Disk In The Device Is Too Early"
            --#SEVERITY MAJOR
            ::= { diskIsRiskyLifeMajor 1 }

        -- 1.3.6.1.4.1.2011.2.251.20.1.2.2.15.10.832.2
        diskIsRiskyLifeMajor-Resume NOTIFICATION-TYPE
            OBJECTS { hwStorageAlarmReporting }
            STATUS current
            DESCRIPTION "Recover: The Firmware Version Of The Disk In The Device Is Too Early"
            --#SEVERITY INFORMATIONAL
            ::= { diskIsRiskyLifeMajor 2 }

        -- 1.3.6.1.4.1.2011.2.251.20.1.2.2.15.10.833
        systemDiskIsFaulty OBJECT IDENTIFIER ::= { disk 833 }

        -- 1.3.6.1.4.1.2011.2.251.20.1.2.2.15.10.833.1
        systemDiskIsFaulty-Fault NOTIFICATION-TYPE
            OBJECTS { hwStorageAlarmReporting }
            STATUS current
            DESCRIPTION "The System Disk Of The Controller Is Faulty"
            --#SEVERITY MAJOR
            ::= { systemDiskIsFaulty 1 }

        -- 1.3.6.1.4.1.2011.2.251.20.1.2.2.15.10.833.2
        systemDiskIsFaulty-Resume NOTIFICATION-TYPE
            OBJECTS { hwStorageAlarmReporting }
            STATUS current
            DESCRIPTION "Recover: The System Disk Of The Controller Is Faulty"
            --#SEVERITY INFORMATIONAL
            ::= { systemDiskIsFaulty 2 }

        -- 1.3.6.1.4.1.2011.2.251.20.1.2.2.15.10.846
        expansionModuleSystemDiskIsFaulty OBJECT IDENTIFIER ::= { disk 846 }

        -- 1.3.6.1.4.1.2011.2.251.20.1.2.2.15.10.846.1
        expansionModuleSystemDiskIsFaulty-Fault NOTIFICATION-TYPE
            OBJECTS { hwStorageAlarmReporting }
            STATUS current
            DESCRIPTION "A System Disk Is Faulty"
            --#SEVERITY MAJOR
            ::= { expansionModuleSystemDiskIsFaulty 1 }

        -- 1.3.6.1.4.1.2011.2.251.20.1.2.2.15.10.846.2
        expansionModuleSystemDiskIsFaulty-Resume NOTIFICATION-TYPE
            OBJECTS { hwStorageAlarmReporting }
            STATUS current
            DESCRIPTION "Recover: A System Disk Is Faulty"
            --#SEVERITY INFORMATIONAL
            ::= { expansionModuleSystemDiskIsFaulty 2 }

        -- 1.3.6.1.4.1.2011.2.251.20.1.2.2.15.10.847
        diskLowTemperature OBJECT IDENTIFIER ::= { disk 847 }

        -- 1.3.6.1.4.1.2011.2.251.20.1.2.2.15.10.847.1
        diskLowTemperature-Fault NOTIFICATION-TYPE
            OBJECTS { hwStorageAlarmReporting }
            STATUS current
            DESCRIPTION "Disk Temperature Is Below The Lower Limit"
            --#SEVERITY MAJOR
            ::= { diskLowTemperature 1 }

        -- 1.3.6.1.4.1.2011.2.251.20.1.2.2.15.10.847.2
        diskLowTemperature-Resume NOTIFICATION-TYPE
            OBJECTS { hwStorageAlarmReporting }
            STATUS current
            DESCRIPTION "Recover: Disk Temperature Is Below The Lower Limit"
            --#SEVERITY INFORMATIONAL
            ::= { diskLowTemperature 2 }

        -- 1.3.6.1.4.1.2011.2.251.20.1.2.2.15.10.851
        controllerSystemDiskIsFaulty OBJECT IDENTIFIER ::= { disk 851 }

        -- 1.3.6.1.4.1.2011.2.251.20.1.2.2.15.10.851.1
        controllerSystemDiskIsFaulty-Fault NOTIFICATION-TYPE
            OBJECTS { hwStorageAlarmReporting }
            STATUS current
            DESCRIPTION "A System Disk Is Faulty"
            --#SEVERITY MAJOR
            ::= { controllerSystemDiskIsFaulty 1 }

        -- 1.3.6.1.4.1.2011.2.251.20.1.2.2.15.10.851.2
        controllerSystemDiskIsFaulty-Resume NOTIFICATION-TYPE
            OBJECTS { hwStorageAlarmReporting }
            STATUS current
            DESCRIPTION "Recover: A System Disk Is Faulty"
            --#SEVERITY INFORMATIONAL
            ::= { controllerSystemDiskIsFaulty 2 }

        -- 1.3.6.1.4.1.2011.2.251.20.1.2.2.15.11
        lun OBJECT IDENTIFIER ::= { oidBasedTrap 11 }

        -- 1.3.6.1.4.1.2011.2.251.20.1.2.2.15.11.1
        theLUNIsFault OBJECT IDENTIFIER ::= { lun 1 }

        -- 1.3.6.1.4.1.2011.2.251.20.1.2.2.15.11.1.1
        theLUNIsFault-Fault NOTIFICATION-TYPE
            OBJECTS { hwStorageAlarmReporting }
            STATUS current
            DESCRIPTION "LUN Is Faulty"
            --#SEVERITY CRITICAL
            ::= { theLUNIsFault 1 }

        -- 1.3.6.1.4.1.2011.2.251.20.1.2.2.15.11.1.2
        theLUNIsFault-Resume NOTIFICATION-TYPE
            OBJECTS { hwStorageAlarmReporting }
            STATUS current
            DESCRIPTION "Recover: LUN Is Faulty"
            --#SEVERITY INFORMATIONAL
            ::= { theLUNIsFault 2 }

        -- 1.3.6.1.4.1.2011.2.251.20.1.2.2.15.11.2
        theLUNHasMediumError OBJECT IDENTIFIER ::= { lun 2 }

        -- 1.3.6.1.4.1.2011.2.251.20.1.2.2.15.11.2.1
        theLUNHasMediumError-Fault NOTIFICATION-TYPE
            OBJECTS { hwStorageAlarmReporting }
            STATUS current
            DESCRIPTION "A Medium Error Occurred On A LUN"
            --#SEVERITY CRITICAL
            ::= { theLUNHasMediumError 1 }

        -- 1.3.6.1.4.1.2011.2.251.20.1.2.2.15.11.2.2
        theLUNHasMediumError-Resume NOTIFICATION-TYPE
            OBJECTS { hwStorageAlarmReporting }
            STATUS current
            DESCRIPTION "Recover: A Medium Error Occurred On A LUN"
            --#SEVERITY INFORMATIONAL
            ::= { theLUNHasMediumError 2 }

        -- 1.3.6.1.4.1.2011.2.251.20.1.2.2.15.11.61
        snapshotLUNIsFault OBJECT IDENTIFIER ::= { lun 61 }

        -- 1.3.6.1.4.1.2011.2.251.20.1.2.2.15.11.61.1
        snapshotLUNIsFault-Fault NOTIFICATION-TYPE
            OBJECTS { hwStorageAlarmReporting }
            STATUS current
            DESCRIPTION "Snapshot LUN Is Faulty"
            --#SEVERITY CRITICAL
            ::= { snapshotLUNIsFault 1 }

        -- 1.3.6.1.4.1.2011.2.251.20.1.2.2.15.11.61.2
        snapshotLUNIsFault-Resume NOTIFICATION-TYPE
            OBJECTS { hwStorageAlarmReporting }
            STATUS current
            DESCRIPTION "Recover: Snapshot LUN Is Faulty"
            --#SEVERITY INFORMATIONAL
            ::= { snapshotLUNIsFault 2 }

        -- 1.3.6.1.4.1.2011.2.251.20.1.2.2.15.11.82
        incompatibleArrayConnected OBJECT IDENTIFIER ::= { lun 82 }

        -- 1.3.6.1.4.1.2011.2.251.20.1.2.2.15.11.82.1
        incompatibleArrayConnected-Fault NOTIFICATION-TYPE
            OBJECTS { hwStorageAlarmReporting }
            STATUS current
            DESCRIPTION "Incompatible Heterogeneous Array Connected To The System"
            --#SEVERITY WARNING
            ::= { incompatibleArrayConnected 1 }

        -- 1.3.6.1.4.1.2011.2.251.20.1.2.2.15.11.82.2
        incompatibleArrayConnected-Resume NOTIFICATION-TYPE
            OBJECTS { hwStorageAlarmReporting }
            STATUS current
            DESCRIPTION "Recover: Incompatible Heterogeneous Array Connected To The System"
            --#SEVERITY INFORMATIONAL
            ::= { incompatibleArrayConnected 2 }

        -- 1.3.6.1.4.1.2011.2.251.20.1.2.2.15.11.99
        externalLUNToOnlyOneController OBJECT IDENTIFIER ::= { lun 99 }

        -- 1.3.6.1.4.1.2011.2.251.20.1.2.2.15.11.99.1
        externalLUNToOnlyOneController-Fault NOTIFICATION-TYPE
            OBJECTS { hwStorageAlarmReporting }
            STATUS current
            DESCRIPTION "An External LUN Has A Link To Only One Controller"
            --#SEVERITY MAJOR
            ::= { externalLUNToOnlyOneController 1 }

        -- 1.3.6.1.4.1.2011.2.251.20.1.2.2.15.11.99.2
        externalLUNToOnlyOneController-Resume NOTIFICATION-TYPE
            OBJECTS { hwStorageAlarmReporting }
            STATUS current
            DESCRIPTION "Recover: An External LUN Has A Link To Only One Controller"
            --#SEVERITY INFORMATIONAL
            ::= { externalLUNToOnlyOneController 2 }

        -- 1.3.6.1.4.1.2011.2.251.20.1.2.2.15.11.100
        externalLUNOffline OBJECT IDENTIFIER ::= { lun 100 }

        -- 1.3.6.1.4.1.2011.2.251.20.1.2.2.15.11.100.1
        externalLUNOffline-Fault NOTIFICATION-TYPE
            OBJECTS { hwStorageAlarmReporting }
            STATUS current
            DESCRIPTION "External LUN Offline"
            --#SEVERITY MAJOR
            ::= { externalLUNOffline 1 }

        -- 1.3.6.1.4.1.2011.2.251.20.1.2.2.15.11.100.2
        externalLUNOffline-Resume NOTIFICATION-TYPE
            OBJECTS { hwStorageAlarmReporting }
            STATUS current
            DESCRIPTION "Recover: External LUN Offline"
            --#SEVERITY INFORMATIONAL
            ::= { externalLUNOffline 2 }

        -- 1.3.6.1.4.1.2011.2.251.20.1.2.2.15.11.101
        externalLUNFault OBJECT IDENTIFIER ::= { lun 101 }

        -- 1.3.6.1.4.1.2011.2.251.20.1.2.2.15.11.101.1
        externalLUNFault-Fault NOTIFICATION-TYPE
            OBJECTS { hwStorageAlarmReporting }
            STATUS current
            DESCRIPTION "External LUN Faulty"
            --#SEVERITY MAJOR
            ::= { externalLUNFault 1 }

        -- 1.3.6.1.4.1.2011.2.251.20.1.2.2.15.11.101.2
        externalLUNFault-Resume NOTIFICATION-TYPE
            OBJECTS { hwStorageAlarmReporting }
            STATUS current
            DESCRIPTION "Recover: External LUN Faulty"
            --#SEVERITY INFORMATIONAL
            ::= { externalLUNFault 2 }

        -- 1.3.6.1.4.1.2011.2.251.20.1.2.2.15.11.102
        externalLUNIsDownsized OBJECT IDENTIFIER ::= { lun 102 }

        -- 1.3.6.1.4.1.2011.2.251.20.1.2.2.15.11.102.1
        externalLUNIsDownsized-Fault NOTIFICATION-TYPE
            OBJECTS { hwStorageAlarmReporting }
            STATUS current
            DESCRIPTION "External LUN Downsized"
            --#SEVERITY MAJOR
            ::= { externalLUNIsDownsized 1 }

        -- 1.3.6.1.4.1.2011.2.251.20.1.2.2.15.11.102.2
        externalLUNIsDownsized-Resume NOTIFICATION-TYPE
            OBJECTS { hwStorageAlarmReporting }
            STATUS current
            DESCRIPTION "Recover: External LUN Downsized"
            --#SEVERITY INFORMATIONAL
            ::= { externalLUNIsDownsized 2 }

        -- 1.3.6.1.4.1.2011.2.251.20.1.2.2.15.11.258
        externalLunTypeChanged OBJECT IDENTIFIER ::= { lun 258 }

        -- 1.3.6.1.4.1.2011.2.251.20.1.2.2.15.11.258.1
        externalLunTypeChanged-Fault NOTIFICATION-TYPE
            OBJECTS { hwStorageAlarmReporting }
            STATUS current
            DESCRIPTION "External LUN Is Changed To Command Device"
            --#SEVERITY MAJOR
            ::= { externalLunTypeChanged 1 }

        -- 1.3.6.1.4.1.2011.2.251.20.1.2.2.15.11.258.2
        externalLunTypeChanged-Resume NOTIFICATION-TYPE
            OBJECTS { hwStorageAlarmReporting }
            STATUS current
            DESCRIPTION "Recover: External LUN Is Changed To Command Device"
            --#SEVERITY INFORMATIONAL
            ::= { externalLunTypeChanged 2 }

        -- 1.3.6.1.4.1.2011.2.251.20.1.2.2.15.11.264
        remoteLinkExceedUpperLimit OBJECT IDENTIFIER ::= { lun 264 }

        -- 1.3.6.1.4.1.2011.2.251.20.1.2.2.15.11.264.1
        remoteLinkExceedUpperLimit-Fault NOTIFICATION-TYPE
            OBJECTS { hwStorageAlarmReporting }
            STATUS current
            DESCRIPTION "Number Of The Connected Remote Links Has Exceeded The Upper Limit"
            --#SEVERITY WARNING
            ::= { remoteLinkExceedUpperLimit 1 }

        -- 1.3.6.1.4.1.2011.2.251.20.1.2.2.15.11.264.2
        remoteLinkExceedUpperLimit-Resume NOTIFICATION-TYPE
            OBJECTS { hwStorageAlarmReporting }
            STATUS current
            DESCRIPTION "Recover: Number Of The Connected Remote Links Has Exceeded The Upper Limit"
            --#SEVERITY INFORMATIONAL
            ::= { remoteLinkExceedUpperLimit 2 }

        -- 1.3.6.1.4.1.2011.2.251.20.1.2.2.15.11.265
        remoteArrayExceedUpperLimit OBJECT IDENTIFIER ::= { lun 265 }

        -- 1.3.6.1.4.1.2011.2.251.20.1.2.2.15.11.265.1
        remoteArrayExceedUpperLimit-Fault NOTIFICATION-TYPE
            OBJECTS { hwStorageAlarmReporting }
            STATUS current
            DESCRIPTION "Number Of The Connected Remote Arrays Has Exceeded The Upper Limit"
            --#SEVERITY WARNING
            ::= { remoteArrayExceedUpperLimit 1 }

        -- 1.3.6.1.4.1.2011.2.251.20.1.2.2.15.11.265.2
        remoteArrayExceedUpperLimit-Resume NOTIFICATION-TYPE
            OBJECTS { hwStorageAlarmReporting }
            STATUS current
            DESCRIPTION "Recover: Number Of The Connected Remote Arrays Has Exceeded The Upper Limit"
            --#SEVERITY INFORMATIONAL
            ::= { remoteArrayExceedUpperLimit 2 }

        -- 1.3.6.1.4.1.2011.2.251.20.1.2.2.15.11.266
        lunHasAMediumError OBJECT IDENTIFIER ::= { lun 266 }

        -- 1.3.6.1.4.1.2011.2.251.20.1.2.2.15.11.266.1
        lunHasAMediumError-Fault NOTIFICATION-TYPE
            OBJECTS { hwStorageAlarmReporting }
            STATUS current
            DESCRIPTION "LUN Has A Medium Error"
            --#SEVERITY CRITICAL
            ::= { lunHasAMediumError 1 }

        -- 1.3.6.1.4.1.2011.2.251.20.1.2.2.15.11.266.2
        lunHasAMediumError-Resume NOTIFICATION-TYPE
            OBJECTS { hwStorageAlarmReporting }
            STATUS current
            DESCRIPTION "Recover: LUN Has A Medium Error"
            --#SEVERITY INFORMATIONAL
            ::= { lunHasAMediumError 2 }

        -- 1.3.6.1.4.1.2011.2.251.20.1.2.2.15.11.267
        localArrayRegPathToHeteroFailed OBJECT IDENTIFIER ::= { lun 267 }

        -- 1.3.6.1.4.1.2011.2.251.20.1.2.2.15.11.267.1
        localArrayRegPathToHeteroFailed-Fault NOTIFICATION-TYPE
            OBJECTS { hwStorageAlarmReporting }
            STATUS current
            DESCRIPTION "Failed To Register Paths From The Local Storage Array To Heterogeneous Storage Array"
            --#SEVERITY WARNING
            ::= { localArrayRegPathToHeteroFailed 1 }

        -- 1.3.6.1.4.1.2011.2.251.20.1.2.2.15.11.267.2
        localArrayRegPathToHeteroFailed-Resume NOTIFICATION-TYPE
            OBJECTS { hwStorageAlarmReporting }
            STATUS current
            DESCRIPTION "Recover: Failed To Register Paths From The Local Storage Array To Heterogeneous Storage Array"
            --#SEVERITY INFORMATIONAL
            ::= { localArrayRegPathToHeteroFailed 2 }

        -- 1.3.6.1.4.1.2011.2.251.20.1.2.2.15.11.268
        lunStartBgrTaskFailed OBJECT IDENTIFIER ::= { lun 268 }

        -- 1.3.6.1.4.1.2011.2.251.20.1.2.2.15.11.268.1
        lunStartBgrTaskFailed-Fault NOTIFICATION-TYPE
            OBJECTS { hwStorageAlarmReporting }
            STATUS current
            DESCRIPTION "Failed To Start LUN Background Task"
            --#SEVERITY WARNING
            ::= { lunStartBgrTaskFailed 1 }

        -- 1.3.6.1.4.1.2011.2.251.20.1.2.2.15.11.268.2
        lunStartBgrTaskFailed-Resume NOTIFICATION-TYPE
            OBJECTS { hwStorageAlarmReporting }
            STATUS current
            DESCRIPTION "Recover: Failed To Start LUN Background Task"
            --#SEVERITY INFORMATIONAL
            ::= { lunStartBgrTaskFailed 2 }

        -- 1.3.6.1.4.1.2011.2.251.20.1.2.2.15.11.271
        snapshotStartBgrTaskFailed OBJECT IDENTIFIER ::= { lun 271 }

        -- 1.3.6.1.4.1.2011.2.251.20.1.2.2.15.11.271.1
        snapshotStartBgrTaskFailed-Fault NOTIFICATION-TYPE
            OBJECTS { hwStorageAlarmReporting }
            STATUS current
            DESCRIPTION "Snapshot Start Bgr Task Failed"
            --#SEVERITY WARNING
            ::= { snapshotStartBgrTaskFailed 1 }

        -- 1.3.6.1.4.1.2011.2.251.20.1.2.2.15.11.271.2
        snapshotStartBgrTaskFailed-Resume NOTIFICATION-TYPE
            OBJECTS { hwStorageAlarmReporting }
            STATUS current
            DESCRIPTION "Recover: Snapshot Start Bgr Task Failed"
            --#SEVERITY INFORMATIONAL
            ::= { snapshotStartBgrTaskFailed 2 }

        -- 1.3.6.1.4.1.2011.2.251.20.1.2.2.15.11.273
        theLUNWriteProtect OBJECT IDENTIFIER ::= { lun 273 }

        -- 1.3.6.1.4.1.2011.2.251.20.1.2.2.15.11.273.1
        theLUNWriteProtect-Fault NOTIFICATION-TYPE
            OBJECTS { hwStorageAlarmReporting }
            STATUS current
            DESCRIPTION "LUN Write Protection"
            --#SEVERITY MAJOR
            ::= { theLUNWriteProtect 1 }

        -- 1.3.6.1.4.1.2011.2.251.20.1.2.2.15.11.273.2
        theLUNWriteProtect-Resume NOTIFICATION-TYPE
            OBJECTS { hwStorageAlarmReporting }
            STATUS current
            DESCRIPTION "Recover: LUN Write Protection"
            --#SEVERITY INFORMATIONAL
            ::= { theLUNWriteProtect 2 }

        -- 1.3.6.1.4.1.2011.2.251.20.1.2.2.15.11.292
        iscsiLinkDisconnected OBJECT IDENTIFIER ::= { lun 292 }

        -- 1.3.6.1.4.1.2011.2.251.20.1.2.2.15.11.292.1
        iscsiLinkDisconnected-Fault NOTIFICATION-TYPE
            OBJECTS { hwStorageAlarmReporting }
            STATUS current
            DESCRIPTION "ISCSI Link Of Heterogeneous Array Disconnected"
            --#SEVERITY INFORMATIONAL
            ::= { iscsiLinkDisconnected 1 }

        -- 1.3.6.1.4.1.2011.2.251.20.1.2.2.15.11.292.2
        iscsiLinkDisconnected-Resume NOTIFICATION-TYPE
            OBJECTS { hwStorageAlarmReporting }
            STATUS current
            DESCRIPTION "Recover: ISCSI Link Of Heterogeneous Array Disconnected"
            --#SEVERITY INFORMATIONAL
            ::= { iscsiLinkDisconnected 2 }

        -- 1.3.6.1.4.1.2011.2.251.20.1.2.2.15.11.323
        lunCapacityNotEnough OBJECT IDENTIFIER ::= { lun 323 }

        -- 1.3.6.1.4.1.2011.2.251.20.1.2.2.15.11.323.1
        lunCapacityNotEnough-Fault NOTIFICATION-TYPE
            OBJECTS { hwStorageAlarmReporting }
            STATUS current
            DESCRIPTION "The Remaining LUN Capacity Is Insufficient"
            --#SEVERITY MAJOR
            ::= { lunCapacityNotEnough 1 }

        -- 1.3.6.1.4.1.2011.2.251.20.1.2.2.15.11.323.2
        lunCapacityNotEnough-Resume NOTIFICATION-TYPE
            OBJECTS { hwStorageAlarmReporting }
            STATUS current
            DESCRIPTION "Recover: The Remaining LUN Capacity Is Insufficient"
            --#SEVERITY INFORMATIONAL
            ::= { lunCapacityNotEnough 2 }

        -- 1.3.6.1.4.1.2011.2.251.20.1.2.2.15.21
        host OBJECT IDENTIFIER ::= { oidBasedTrap 21 }

        -- 1.3.6.1.4.1.2011.2.251.20.1.2.2.15.21.4
        pathsBetweenTheHostAndStorageArrayDoNotMeetRedundancyRequirements OBJECT IDENTIFIER ::= { host 4 }

        -- 1.3.6.1.4.1.2011.2.251.20.1.2.2.15.21.4.1
        pathsBetweenTheHostAndStorageArrayDoNotMeetRedundancyRequirements-Fault NOTIFICATION-TYPE
            OBJECTS { hwStorageAlarmReporting }
            STATUS current
            DESCRIPTION "Paths Between The Host And Storage Array Do Not Meet Redundancy Requirements"
            --#SEVERITY WARNING
            ::= { pathsBetweenTheHostAndStorageArrayDoNotMeetRedundancyRequirements 1 }

        -- 1.3.6.1.4.1.2011.2.251.20.1.2.2.15.21.4.2
        pathsBetweenTheHostAndStorageArrayDoNotMeetRedundancyRequirements-Resume NOTIFICATION-TYPE
            OBJECTS { hwStorageAlarmReporting }
            STATUS current
            DESCRIPTION "Recover: Paths Between The Host And Storage Array Do Not Meet Redundancy Requirements"
            --#SEVERITY INFORMATIONAL
            ::= { pathsBetweenTheHostAndStorageArrayDoNotMeetRedundancyRequirements 2 }

        -- 1.3.6.1.4.1.2011.2.251.20.1.2.2.15.21.25
        noRedundantConnectionToHost OBJECT IDENTIFIER ::= { host 25 }

        -- 1.3.6.1.4.1.2011.2.251.20.1.2.2.15.21.25.1
        noRedundantConnectionToHost-Fault NOTIFICATION-TYPE
            OBJECTS { hwStorageAlarmReporting }
            STATUS current
            DESCRIPTION "Host Is Not Redundantly Connected To Storage Arrays"
            --#SEVERITY MAJOR
            ::= { noRedundantConnectionToHost 1 }

        -- 1.3.6.1.4.1.2011.2.251.20.1.2.2.15.21.25.2
        noRedundantConnectionToHost-Resume NOTIFICATION-TYPE
            OBJECTS { hwStorageAlarmReporting }
            STATUS current
            DESCRIPTION "Recover: Host Is Not Redundantly Connected To Storage Arrays"
            --#SEVERITY INFORMATIONAL
            ::= { noRedundantConnectionToHost 2 }

        -- 1.3.6.1.4.1.2011.2.251.20.1.2.2.15.21.26
        aLinkToHostIsDown OBJECT IDENTIFIER ::= { host 26 }

        -- 1.3.6.1.4.1.2011.2.251.20.1.2.2.15.21.26.1
        aLinkToHostIsDown-Fault NOTIFICATION-TYPE
            OBJECTS { hwStorageAlarmReporting }
            STATUS current
            DESCRIPTION "Link Between A Host And Storage Array Is Down"
            --#SEVERITY MAJOR
            ::= { aLinkToHostIsDown 1 }

        -- 1.3.6.1.4.1.2011.2.251.20.1.2.2.15.21.26.2
        aLinkToHostIsDown-Resume NOTIFICATION-TYPE
            OBJECTS { hwStorageAlarmReporting }
            STATUS current
            DESCRIPTION "Recover: Link Between A Host And Storage Array Is Down"
            --#SEVERITY INFORMATIONAL
            ::= { aLinkToHostIsDown 2 }

        -- 1.3.6.1.4.1.2011.2.251.20.1.2.2.15.21.29
        ultrapathIncompatibleWithStorage OBJECT IDENTIFIER ::= { host 29 }

        -- 1.3.6.1.4.1.2011.2.251.20.1.2.2.15.21.29.1
        ultrapathIncompatibleWithStorage-Fault NOTIFICATION-TYPE
            OBJECTS { hwStorageAlarmReporting }
            STATUS current
            DESCRIPTION "Ultrapath Incompatible With Storage Array Software"
            --#SEVERITY MAJOR
            ::= { ultrapathIncompatibleWithStorage 1 }

        -- 1.3.6.1.4.1.2011.2.251.20.1.2.2.15.21.29.2
        ultrapathIncompatibleWithStorage-Resume NOTIFICATION-TYPE
            OBJECTS { hwStorageAlarmReporting }
            STATUS current
            DESCRIPTION "Recover: Ultrapath Incompatible With Storage Array Software"
            --#SEVERITY INFORMATIONAL
            ::= { ultrapathIncompatibleWithStorage 2 }

        -- 1.3.6.1.4.1.2011.2.251.20.1.2.2.15.21.30
        theOperatingSystemTypeOfTheArrayHostIsInconsistentWithThatOfTheAssociatedPhysicalHost OBJECT IDENTIFIER ::= { host 30 }

        -- 1.3.6.1.4.1.2011.2.251.20.1.2.2.15.21.30.1
        theOperatingSystemTypeOfTheArrayHostIsInconsistentWithThatOfTheAssociatedPhysicalHost-Fault NOTIFICATION-TYPE
            OBJECTS { hwStorageAlarmReporting }
            STATUS current
            DESCRIPTION "The Operating System Type Of The Array Host Is Inconsistent With That Of The Associated Physical Host"
            --#SEVERITY WARNING
            ::= { theOperatingSystemTypeOfTheArrayHostIsInconsistentWithThatOfTheAssociatedPhysicalHost 1 }

        -- 1.3.6.1.4.1.2011.2.251.20.1.2.2.15.21.30.2
        theOperatingSystemTypeOfTheArrayHostIsInconsistentWithThatOfTheAssociatedPhysicalHost-Resume NOTIFICATION-TYPE
            OBJECTS { hwStorageAlarmReporting }
            STATUS current
            DESCRIPTION "Recover: The Operating System Type Of The Array Host Is Inconsistent With That Of The Associated Physical Host"
            --#SEVERITY INFORMATIONAL
            ::= { theOperatingSystemTypeOfTheArrayHostIsInconsistentWithThatOfTheAssociatedPhysicalHost 2 }

        -- 1.3.6.1.4.1.2011.2.251.20.1.2.2.15.21.35
        theUniversalMultipathingSoftwareAndUltraPathJointlyTakeOverTheLUNs OBJECT IDENTIFIER ::= { host 35 }

        -- 1.3.6.1.4.1.2011.2.251.20.1.2.2.15.21.35.1
        theUniversalMultipathingSoftwareAndUltraPathJointlyTakeOverTheLUNs-Fault NOTIFICATION-TYPE
            OBJECTS { hwStorageAlarmReporting }
            STATUS current
            DESCRIPTION "The Universal Multipathing Software And UltraPath Jointly Take Over The LUNs"
            --#SEVERITY MAJOR
            ::= { theUniversalMultipathingSoftwareAndUltraPathJointlyTakeOverTheLUNs 1 }

        -- 1.3.6.1.4.1.2011.2.251.20.1.2.2.15.21.35.2
        theUniversalMultipathingSoftwareAndUltraPathJointlyTakeOverTheLUNs-Resume NOTIFICATION-TYPE
            OBJECTS { hwStorageAlarmReporting }
            STATUS current
            DESCRIPTION "Recover: The Universal Multipathing Software And UltraPath Jointly Take Over The LUNs"
            --#SEVERITY INFORMATIONAL
            ::= { theUniversalMultipathingSoftwareAndUltraPathJointlyTakeOverTheLUNs 2 }

        -- 1.3.6.1.4.1.2011.2.251.20.1.2.2.15.21.37
        ultraPathIncompatibleWithOperatingSystemKernel OBJECT IDENTIFIER ::= { host 37 }

        -- 1.3.6.1.4.1.2011.2.251.20.1.2.2.15.21.37.1
        ultraPathIncompatibleWithOperatingSystemKernel-Fault NOTIFICATION-TYPE
            OBJECTS { hwStorageAlarmReporting }
            STATUS current
            DESCRIPTION "UltraPath Incompatible With Operating System Kernel"
            --#SEVERITY MAJOR
            ::= { ultraPathIncompatibleWithOperatingSystemKernel 1 }

        -- 1.3.6.1.4.1.2011.2.251.20.1.2.2.15.21.37.2
        ultraPathIncompatibleWithOperatingSystemKernel-Resume NOTIFICATION-TYPE
            OBJECTS { hwStorageAlarmReporting }
            STATUS current
            DESCRIPTION "Recover: UltraPath Incompatible With Operating System Kernel"
            --#SEVERITY INFORMATIONAL
            ::= { ultraPathIncompatibleWithOperatingSystemKernel 2 }

        -- 1.3.6.1.4.1.2011.2.251.20.1.2.2.15.21.39
        lUNsMappedToTheHostHaveNoRedundantLinksToTheStorageArray OBJECT IDENTIFIER ::= { host 39 }

        -- 1.3.6.1.4.1.2011.2.251.20.1.2.2.15.21.39.1
        lUNsMappedToTheHostHaveNoRedundantLinksToTheStorageArray-Fault NOTIFICATION-TYPE
            OBJECTS { hwStorageAlarmReporting }
            STATUS current
            DESCRIPTION "LUNs Mapped To The Host Have No Redundant Links To The Storage Array"
            --#SEVERITY MAJOR
            ::= { lUNsMappedToTheHostHaveNoRedundantLinksToTheStorageArray 1 }

        -- 1.3.6.1.4.1.2011.2.251.20.1.2.2.15.21.39.2
        lUNsMappedToTheHostHaveNoRedundantLinksToTheStorageArray-Resume NOTIFICATION-TYPE
            OBJECTS { hwStorageAlarmReporting }
            STATUS current
            DESCRIPTION "Recover: LUNs Mapped To The Host Have No Redundant Links To The Storage Array"
            --#SEVERITY INFORMATIONAL
            ::= { lUNsMappedToTheHostHaveNoRedundantLinksToTheStorageArray 2 }

        -- 1.3.6.1.4.1.2011.2.251.20.1.2.2.15.21.40
        lUNsMappedToTheHostHaveNoRedundantLinksToControllers OBJECT IDENTIFIER ::= { host 40 }

        -- 1.3.6.1.4.1.2011.2.251.20.1.2.2.15.21.40.1
        lUNsMappedToTheHostHaveNoRedundantLinksToControllers-Fault NOTIFICATION-TYPE
            OBJECTS { hwStorageAlarmReporting }
            STATUS current
            DESCRIPTION "LUNs Mapped To The Host Have No Redundant Links To Controllers"
            --#SEVERITY MAJOR
            ::= { lUNsMappedToTheHostHaveNoRedundantLinksToControllers 1 }

        -- 1.3.6.1.4.1.2011.2.251.20.1.2.2.15.21.40.2
        lUNsMappedToTheHostHaveNoRedundantLinksToControllers-Resume NOTIFICATION-TYPE
            OBJECTS { hwStorageAlarmReporting }
            STATUS current
            DESCRIPTION "Recover: LUNs Mapped To The Host Have No Redundant Links To Controllers"
            --#SEVERITY INFORMATIONAL
            ::= { lUNsMappedToTheHostHaveNoRedundantLinksToControllers 2 }

        -- 1.3.6.1.4.1.2011.2.251.20.1.2.2.15.21.54
        theHostLUNIDOfALUNMappedToTheHostIs0 OBJECT IDENTIFIER ::= { host 54 }

        -- 1.3.6.1.4.1.2011.2.251.20.1.2.2.15.21.54.1
        theHostLUNIDOfALUNMappedToTheHostIs0-Fault NOTIFICATION-TYPE
            OBJECTS { hwStorageAlarmReporting }
            STATUS current
            DESCRIPTION "The Host LUN ID Of A LUN Mapped To The Host Is 0"
            --#SEVERITY WARNING
            ::= { theHostLUNIDOfALUNMappedToTheHostIs0 1 }

        -- 1.3.6.1.4.1.2011.2.251.20.1.2.2.15.21.54.2
        theHostLUNIDOfALUNMappedToTheHostIs0-Resume NOTIFICATION-TYPE
            OBJECTS { hwStorageAlarmReporting }
            STATUS current
            DESCRIPTION "Recover: The Host LUN ID Of A LUN Mapped To The Host Is 0"
            --#SEVERITY INFORMATIONAL
            ::= { theHostLUNIDOfALUNMappedToTheHostIs0 2 }

        -- 1.3.6.1.4.1.2011.2.251.20.1.2.2.15.21.55
        hyperMetroLUNsAreNotSupportedDueToNVMeUsedByTheHost OBJECT IDENTIFIER ::= { host 55 }

        -- 1.3.6.1.4.1.2011.2.251.20.1.2.2.15.21.55.1
        hyperMetroLUNsAreNotSupportedDueToNVMeUsedByTheHost-Fault NOTIFICATION-TYPE
            OBJECTS { hwStorageAlarmReporting }
            STATUS current
            DESCRIPTION "HyperMetro LUNs Are Not Supported Due To NVMe Used By The Host"
            --#SEVERITY WARNING
            ::= { hyperMetroLUNsAreNotSupportedDueToNVMeUsedByTheHost 1 }

        -- 1.3.6.1.4.1.2011.2.251.20.1.2.2.15.21.55.2
        hyperMetroLUNsAreNotSupportedDueToNVMeUsedByTheHost-Resume NOTIFICATION-TYPE
            OBJECTS { hwStorageAlarmReporting }
            STATUS current
            DESCRIPTION "Recover: HyperMetro LUNs Are Not Supported Due To NVMe Used By The Host"
            --#SEVERITY INFORMATIONAL
            ::= { hyperMetroLUNsAreNotSupportedDueToNVMeUsedByTheHost 2 }

        -- 1.3.6.1.4.1.2011.2.251.20.1.2.2.15.21.56
        theInBandManagementCertificateOfTheHostIsAboutToExpire OBJECT IDENTIFIER ::= { host 56 }

        -- 1.3.6.1.4.1.2011.2.251.20.1.2.2.15.21.56.1
        theInBandManagementCertificateOfTheHostIsAboutToExpire-Fault NOTIFICATION-TYPE
            OBJECTS { hwStorageAlarmReporting }
            STATUS current
            DESCRIPTION "The InBand Management Certificate Of The Host Is About To Expire"
            --#SEVERITY WARNING
            ::= { theInBandManagementCertificateOfTheHostIsAboutToExpire 1 }

        -- 1.3.6.1.4.1.2011.2.251.20.1.2.2.15.21.56.2
        theInBandManagementCertificateOfTheHostIsAboutToExpire-Resume NOTIFICATION-TYPE
            OBJECTS { hwStorageAlarmReporting }
            STATUS current
            DESCRIPTION "Recover: The InBand Management Certificate Of The Host Is About To Expire"
            --#SEVERITY INFORMATIONAL
            ::= { theInBandManagementCertificateOfTheHostIsAboutToExpire 2 }

        -- 1.3.6.1.4.1.2011.2.251.20.1.2.2.15.21.57
        theInBandManagementCertificateOfTheHostHasExpired OBJECT IDENTIFIER ::= { host 57 }

        -- 1.3.6.1.4.1.2011.2.251.20.1.2.2.15.21.57.1
        theInBandManagementCertificateOfTheHostHasExpired-Fault NOTIFICATION-TYPE
            OBJECTS { hwStorageAlarmReporting }
            STATUS current
            DESCRIPTION "The InBand Management Certificate Of The Host Has Expired"
            --#SEVERITY MAJOR
            ::= { theInBandManagementCertificateOfTheHostHasExpired 1 }

        -- 1.3.6.1.4.1.2011.2.251.20.1.2.2.15.21.57.2
        theInBandManagementCertificateOfTheHostHasExpired-Resume NOTIFICATION-TYPE
            OBJECTS { hwStorageAlarmReporting }
            STATUS current
            DESCRIPTION "Recover: The InBand Management Certificate Of The Host Has Expired"
            --#SEVERITY INFORMATIONAL
            ::= { theInBandManagementCertificateOfTheHostHasExpired 2 }

        -- 1.3.6.1.4.1.2011.2.251.20.1.2.2.15.23
        powermodule OBJECT IDENTIFIER ::= { oidBasedTrap 23 }

        -- 1.3.6.1.4.1.2011.2.251.20.1.2.2.15.23.2
        powerModuleIsRemoved OBJECT IDENTIFIER ::= { powermodule 2 }

        -- 1.3.6.1.4.1.2011.2.251.20.1.2.2.15.23.2.1
        powerModuleIsRemoved-Fault NOTIFICATION-TYPE
            OBJECTS { hwStorageAlarmReporting }
            STATUS current
            DESCRIPTION "Power Module Is Removed"
            --#SEVERITY MAJOR
            ::= { powerModuleIsRemoved 1 }

        -- 1.3.6.1.4.1.2011.2.251.20.1.2.2.15.23.2.2
        powerModuleIsRemoved-Resume NOTIFICATION-TYPE
            OBJECTS { hwStorageAlarmReporting }
            STATUS current
            DESCRIPTION "Recover: Power Module Is Removed"
            --#SEVERITY INFORMATIONAL
            ::= { powerModuleIsRemoved 2 }

        -- 1.3.6.1.4.1.2011.2.251.20.1.2.2.15.23.4
        powerModuleTempExceedsLimit OBJECT IDENTIFIER ::= { powermodule 4 }

        -- 1.3.6.1.4.1.2011.2.251.20.1.2.2.15.23.4.1
        powerModuleTempExceedsLimit-Fault NOTIFICATION-TYPE
            OBJECTS { hwStorageAlarmReporting }
            STATUS current
            DESCRIPTION "Power Module Temperature Exceeds The Upper Limit"
            --#SEVERITY WARNING
            ::= { powerModuleTempExceedsLimit 1 }

        -- 1.3.6.1.4.1.2011.2.251.20.1.2.2.15.23.4.2
        powerModuleTempExceedsLimit-Resume NOTIFICATION-TYPE
            OBJECTS { hwStorageAlarmReporting }
            STATUS current
            DESCRIPTION "Recover: Power Module Temperature Exceeds The Upper Limit"
            --#SEVERITY INFORMATIONAL
            ::= { powerModuleTempExceedsLimit 2 }

        -- 1.3.6.1.4.1.2011.2.251.20.1.2.2.15.23.5
        powerModuleInputIsAbnormal1 OBJECT IDENTIFIER ::= { powermodule 5 }

        -- 1.3.6.1.4.1.2011.2.251.20.1.2.2.15.23.5.1
        powerModuleInputIsAbnormal1-Fault NOTIFICATION-TYPE
            OBJECTS { hwStorageAlarmReporting }
            STATUS current
            DESCRIPTION "Power Module Input Is Abnormal"
            --#SEVERITY MAJOR
            ::= { powerModuleInputIsAbnormal1 1 }

        -- 1.3.6.1.4.1.2011.2.251.20.1.2.2.15.23.5.2
        powerModuleInputIsAbnormal1-Resume NOTIFICATION-TYPE
            OBJECTS { hwStorageAlarmReporting }
            STATUS current
            DESCRIPTION "Recover: Power Module Input Is Abnormal"
            --#SEVERITY INFORMATIONAL
            ::= { powerModuleInputIsAbnormal1 2 }

        -- 1.3.6.1.4.1.2011.2.251.20.1.2.2.15.23.20
        powerModuleHasNoInput1 OBJECT IDENTIFIER ::= { powermodule 20 }

        -- 1.3.6.1.4.1.2011.2.251.20.1.2.2.15.23.20.1
        powerModuleHasNoInput1-Fault NOTIFICATION-TYPE
            OBJECTS { hwStorageAlarmReporting }
            STATUS current
            DESCRIPTION "Power Module Has No Input"
            --#SEVERITY MAJOR
            ::= { powerModuleHasNoInput1 1 }

        -- 1.3.6.1.4.1.2011.2.251.20.1.2.2.15.23.20.2
        powerModuleHasNoInput1-Resume NOTIFICATION-TYPE
            OBJECTS { hwStorageAlarmReporting }
            STATUS current
            DESCRIPTION "Recover: Power Module Has No Input"
            --#SEVERITY INFORMATIONAL
            ::= { powerModuleHasNoInput1 2 }

        -- 1.3.6.1.4.1.2011.2.251.20.1.2.2.15.23.21
        powerModulesTypesDifferent OBJECT IDENTIFIER ::= { powermodule 21 }

        -- 1.3.6.1.4.1.2011.2.251.20.1.2.2.15.23.21.1
        powerModulesTypesDifferent-Fault NOTIFICATION-TYPE
            OBJECTS { hwStorageAlarmReporting }
            STATUS current
            DESCRIPTION "Power Modules Of Different Types Are Used In A Disk Enclosure"
            --#SEVERITY MAJOR
            ::= { powerModulesTypesDifferent 1 }

        -- 1.3.6.1.4.1.2011.2.251.20.1.2.2.15.23.21.2
        powerModulesTypesDifferent-Resume NOTIFICATION-TYPE
            OBJECTS { hwStorageAlarmReporting }
            STATUS current
            DESCRIPTION "Recover: Power Modules Of Different Types Are Used In A Disk Enclosure"
            --#SEVERITY INFORMATIONAL
            ::= { powerModulesTypesDifferent 2 }

        -- 1.3.6.1.4.1.2011.2.251.20.1.2.2.15.23.23
        failedToMonitorAPowerModule OBJECT IDENTIFIER ::= { powermodule 23 }

        -- 1.3.6.1.4.1.2011.2.251.20.1.2.2.15.23.23.1
        failedToMonitorAPowerModule-Fault NOTIFICATION-TYPE
            OBJECTS { hwStorageAlarmReporting }
            STATUS current
            DESCRIPTION "The System Failed To Monitor A Power Module"
            --#SEVERITY MAJOR
            ::= { failedToMonitorAPowerModule 1 }

        -- 1.3.6.1.4.1.2011.2.251.20.1.2.2.15.23.23.2
        failedToMonitorAPowerModule-Resume NOTIFICATION-TYPE
            OBJECTS { hwStorageAlarmReporting }
            STATUS current
            DESCRIPTION "Recover: The System Failed To Monitor A Power Module"
            --#SEVERITY INFORMATIONAL
            ::= { failedToMonitorAPowerModule 2 }

        -- 1.3.6.1.4.1.2011.2.251.20.1.2.2.15.23.24
        powerModuleIsIncompatible OBJECT IDENTIFIER ::= { powermodule 24 }

        -- 1.3.6.1.4.1.2011.2.251.20.1.2.2.15.23.24.1
        powerModuleIsIncompatible-Fault NOTIFICATION-TYPE
            OBJECTS { hwStorageAlarmReporting }
            STATUS current
            DESCRIPTION "Power Module Type Is Mismatched"
            --#SEVERITY MAJOR
            ::= { powerModuleIsIncompatible 1 }

        -- 1.3.6.1.4.1.2011.2.251.20.1.2.2.15.23.24.2
        powerModuleIsIncompatible-Resume NOTIFICATION-TYPE
            OBJECTS { hwStorageAlarmReporting }
            STATUS current
            DESCRIPTION "Recover: Power Module Type Is Mismatched"
            --#SEVERITY INFORMATIONAL
            ::= { powerModuleIsIncompatible 2 }

        -- 1.3.6.1.4.1.2011.2.251.20.1.2.2.15.23.25
        powerModuleIsFaulty OBJECT IDENTIFIER ::= { powermodule 25 }

        -- 1.3.6.1.4.1.2011.2.251.20.1.2.2.15.23.25.1
        powerModuleIsFaulty-Fault NOTIFICATION-TYPE
            OBJECTS { hwStorageAlarmReporting }
            STATUS current
            DESCRIPTION "Power Module Is Faulty"
            --#SEVERITY MAJOR
            ::= { powerModuleIsFaulty 1 }

        -- 1.3.6.1.4.1.2011.2.251.20.1.2.2.15.23.25.2
        powerModuleIsFaulty-Resume NOTIFICATION-TYPE
            OBJECTS { hwStorageAlarmReporting }
            STATUS current
            DESCRIPTION "Recover: Power Module Is Faulty"
            --#SEVERITY INFORMATIONAL
            ::= { powerModuleIsFaulty 2 }

        -- 1.3.6.1.4.1.2011.2.251.20.1.2.2.15.23.26
        powerIsIncompatWithController OBJECT IDENTIFIER ::= { powermodule 26 }

        -- 1.3.6.1.4.1.2011.2.251.20.1.2.2.15.23.26.1
        powerIsIncompatWithController-Fault NOTIFICATION-TYPE
            OBJECTS { hwStorageAlarmReporting }
            STATUS current
            DESCRIPTION "The Power Module Is Incompatible With The Controller"
            --#SEVERITY MAJOR
            ::= { powerIsIncompatWithController 1 }

        -- 1.3.6.1.4.1.2011.2.251.20.1.2.2.15.23.26.2
        powerIsIncompatWithController-Resume NOTIFICATION-TYPE
            OBJECTS { hwStorageAlarmReporting }
            STATUS current
            DESCRIPTION "Recover: The Power Module Is Incompatible With The Controller"
            --#SEVERITY INFORMATIONAL
            ::= { powerIsIncompatWithController 2 }

        -- 1.3.6.1.4.1.2011.2.251.20.1.2.2.15.23.33
        powerModuleInputIsAbnormal OBJECT IDENTIFIER ::= { powermodule 33 }

        -- 1.3.6.1.4.1.2011.2.251.20.1.2.2.15.23.33.1
        powerModuleInputIsAbnormal-Fault NOTIFICATION-TYPE
            OBJECTS { hwStorageAlarmReporting }
            STATUS current
            DESCRIPTION "Power Module Input Is Abnormal"
            --#SEVERITY MAJOR
            ::= { powerModuleInputIsAbnormal 1 }

        -- 1.3.6.1.4.1.2011.2.251.20.1.2.2.15.23.33.2
        powerModuleInputIsAbnormal-Resume NOTIFICATION-TYPE
            OBJECTS { hwStorageAlarmReporting }
            STATUS current
            DESCRIPTION "Recover: Power Module Input Is Abnormal"
            --#SEVERITY INFORMATIONAL
            ::= { powerModuleInputIsAbnormal 2 }

        -- 1.3.6.1.4.1.2011.2.251.20.1.2.2.15.23.34
        powerModuleHasNoInput OBJECT IDENTIFIER ::= { powermodule 34 }

        -- 1.3.6.1.4.1.2011.2.251.20.1.2.2.15.23.34.1
        powerModuleHasNoInput-Fault NOTIFICATION-TYPE
            OBJECTS { hwStorageAlarmReporting }
            STATUS current
            DESCRIPTION "Power Module Has No Input"
            --#SEVERITY MAJOR
            ::= { powerModuleHasNoInput 1 }

        -- 1.3.6.1.4.1.2011.2.251.20.1.2.2.15.23.34.2
        powerModuleHasNoInput-Resume NOTIFICATION-TYPE
            OBJECTS { hwStorageAlarmReporting }
            STATUS current
            DESCRIPTION "Recover: Power Module Has No Input"
            --#SEVERITY INFORMATIONAL
            ::= { powerModuleHasNoInput 2 }

        -- 1.3.6.1.4.1.2011.2.251.20.1.2.2.15.23.36
        unbalancedPowerSupplyCurrentAlarm OBJECT IDENTIFIER ::= { powermodule 36 }

        -- 1.3.6.1.4.1.2011.2.251.20.1.2.2.15.23.36.1
        unbalancedPowerSupplyCurrentAlarm-Fault NOTIFICATION-TYPE
            OBJECTS { hwStorageAlarmReporting }
            STATUS current
            DESCRIPTION "Uneven Power Output"
            --#SEVERITY WARNING
            ::= { unbalancedPowerSupplyCurrentAlarm 1 }

        -- 1.3.6.1.4.1.2011.2.251.20.1.2.2.15.23.36.2
        unbalancedPowerSupplyCurrentAlarm-Resume NOTIFICATION-TYPE
            OBJECTS { hwStorageAlarmReporting }
            STATUS current
            DESCRIPTION "Recover: Uneven Power Output"
            --#SEVERITY INFORMATIONAL
            ::= { unbalancedPowerSupplyCurrentAlarm 2 }

        -- 1.3.6.1.4.1.2011.2.251.20.1.2.2.15.23.38
        powerIsIncompatWithExpModule OBJECT IDENTIFIER ::= { powermodule 38 }

        -- 1.3.6.1.4.1.2011.2.251.20.1.2.2.15.23.38.1
        powerIsIncompatWithExpModule-Fault NOTIFICATION-TYPE
            OBJECTS { hwStorageAlarmReporting }
            STATUS current
            DESCRIPTION "The Power Module Is Incompatible With The Expansion Module"
            --#SEVERITY MAJOR
            ::= { powerIsIncompatWithExpModule 1 }

        -- 1.3.6.1.4.1.2011.2.251.20.1.2.2.15.23.38.2
        powerIsIncompatWithExpModule-Resume NOTIFICATION-TYPE
            OBJECTS { hwStorageAlarmReporting }
            STATUS current
            DESCRIPTION "Recover: The Power Module Is Incompatible With The Expansion Module"
            --#SEVERITY INFORMATIONAL
            ::= { powerIsIncompatWithExpModule 2 }

        -- 1.3.6.1.4.1.2011.2.251.20.1.2.2.15.27
        snapshot OBJECT IDENTIFIER ::= { oidBasedTrap 27 }

        -- 1.3.6.1.4.1.2011.2.251.20.1.2.2.15.27.5
        faultsOccurDuringTheRollbackOfASnapshot OBJECT IDENTIFIER ::= { snapshot 5 }

        -- 1.3.6.1.4.1.2011.2.251.20.1.2.2.15.27.5.1
        faultsOccurDuringTheRollbackOfASnapshot-Fault NOTIFICATION-TYPE
            OBJECTS { hwStorageAlarmReporting }
            STATUS current
            DESCRIPTION "Faults Occur During The Rollback Of A Snapshot"
            --#SEVERITY MAJOR
            ::= { faultsOccurDuringTheRollbackOfASnapshot 1 }

        -- 1.3.6.1.4.1.2011.2.251.20.1.2.2.15.27.5.2
        faultsOccurDuringTheRollbackOfASnapshot-Resume NOTIFICATION-TYPE
            OBJECTS { hwStorageAlarmReporting }
            STATUS current
            DESCRIPTION "Recover: Faults Occur During The Rollback Of A Snapshot"
            --#SEVERITY INFORMATIONAL
            ::= { faultsOccurDuringTheRollbackOfASnapshot 2 }

        -- 1.3.6.1.4.1.2011.2.251.20.1.2.2.15.27.7
        hyperCDPSchedulesOfTheVStoreFailedToBeSynchronized OBJECT IDENTIFIER ::= { snapshot 7 }

        -- 1.3.6.1.4.1.2011.2.251.20.1.2.2.15.27.7.1
        hyperCDPSchedulesOfTheVStoreFailedToBeSynchronized-Fault NOTIFICATION-TYPE
            OBJECTS { hwStorageAlarmReporting }
            STATUS current
            DESCRIPTION "HyperCDP Schedules Of The VStore Failed To Be Synchronized"
            --#SEVERITY WARNING
            ::= { hyperCDPSchedulesOfTheVStoreFailedToBeSynchronized 1 }

        -- 1.3.6.1.4.1.2011.2.251.20.1.2.2.15.27.7.2
        hyperCDPSchedulesOfTheVStoreFailedToBeSynchronized-Resume NOTIFICATION-TYPE
            OBJECTS { hwStorageAlarmReporting }
            STATUS current
            DESCRIPTION "Recover: HyperCDP Schedules Of The VStore Failed To Be Synchronized"
            --#SEVERITY INFORMATIONAL
            ::= { hyperCDPSchedulesOfTheVStoreFailedToBeSynchronized 2 }

        -- 1.3.6.1.4.1.2011.2.251.20.1.2.2.15.27.8
        exceptionsOccurContinuouslyWhenFileSystemSnapshotsAreDeletedInTheBackground OBJECT IDENTIFIER ::= { snapshot 8 }

        -- 1.3.6.1.4.1.2011.2.251.20.1.2.2.15.27.8.1
        exceptionsOccurContinuouslyWhenFileSystemSnapshotsAreDeletedInTheBackground-Fault NOTIFICATION-TYPE
            OBJECTS { hwStorageAlarmReporting }
            STATUS current
            DESCRIPTION "Exceptions Occur Continuously When File System Snapshots Are Deleted In The Background"
            --#SEVERITY WARNING
            ::= { exceptionsOccurContinuouslyWhenFileSystemSnapshotsAreDeletedInTheBackground 1 }

        -- 1.3.6.1.4.1.2011.2.251.20.1.2.2.15.27.8.2
        exceptionsOccurContinuouslyWhenFileSystemSnapshotsAreDeletedInTheBackground-Resume NOTIFICATION-TYPE
            OBJECTS { hwStorageAlarmReporting }
            STATUS current
            DESCRIPTION "Recover: Exceptions Occur Continuously When File System Snapshots Are Deleted In The Background"
            --#SEVERITY INFORMATIONAL
            ::= { exceptionsOccurContinuouslyWhenFileSystemSnapshotsAreDeletedInTheBackground 2 }

        -- 1.3.6.1.4.1.2011.2.251.20.1.2.2.15.40
        filesystem OBJECT IDENTIFIER ::= { oidBasedTrap 40 }

        -- 1.3.6.1.4.1.2011.2.251.20.1.2.2.15.40.2
        theRatioOfTheTotalCapacityOfAllFileSystemsAndLUNsToTheCapacityOfTheStoragePoolExceedsTheOverprovisioningThreshold OBJECT IDENTIFIER ::= { filesystem 2 }

        -- 1.3.6.1.4.1.2011.2.251.20.1.2.2.15.40.2.1
        theRatioOfTheTotalCapacityOfAllFileSystemsAndLUNsToTheCapacityOfTheStoragePoolExceedsTheOverprovisioningThreshold-Fault NOTIFICATION-TYPE
            OBJECTS { hwStorageAlarmReporting }
            STATUS current
            DESCRIPTION "The Ratio Of The Total Capacity Of All File Systems And LUNs To The Capacity Of The Storage Pool Exceeds The Overprovisioning Threshold"
            --#SEVERITY WARNING
            ::= { theRatioOfTheTotalCapacityOfAllFileSystemsAndLUNsToTheCapacityOfTheStoragePoolExceedsTheOverprovisioningThreshold 1 }

        -- 1.3.6.1.4.1.2011.2.251.20.1.2.2.15.40.2.2
        theRatioOfTheTotalCapacityOfAllFileSystemsAndLUNsToTheCapacityOfTheStoragePoolExceedsTheOverprovisioningThreshold-Resume NOTIFICATION-TYPE
            OBJECTS { hwStorageAlarmReporting }
            STATUS current
            DESCRIPTION "Recover: The Ratio Of The Total Capacity Of All File Systems And LUNs To The Capacity Of The Storage Pool Exceeds The Overprovisioning Threshold"
            --#SEVERITY INFORMATIONAL
            ::= { theRatioOfTheTotalCapacityOfAllFileSystemsAndLUNsToTheCapacityOfTheStoragePoolExceedsTheOverprovisioningThreshold 2 }

        -- 1.3.6.1.4.1.2011.2.251.20.1.2.2.15.40.4
        directorySizeIsFaulty OBJECT IDENTIFIER ::= { filesystem 4 }

        -- 1.3.6.1.4.1.2011.2.251.20.1.2.2.15.40.4.1
        directorySizeIsFaulty-Fault NOTIFICATION-TYPE
            OBJECTS { hwStorageAlarmReporting }
            STATUS current
            DESCRIPTION "The Directory Contains Too Many Files And Subdirectories"
            --#SEVERITY WARNING
            ::= { directorySizeIsFaulty 1 }

        -- 1.3.6.1.4.1.2011.2.251.20.1.2.2.15.40.4.2
        directorySizeIsFaulty-Resume NOTIFICATION-TYPE
            OBJECTS { hwStorageAlarmReporting }
            STATUS current
            DESCRIPTION "Recover: The Directory Contains Too Many Files And Subdirectories"
            --#SEVERITY INFORMATIONAL
            ::= { directorySizeIsFaulty 2 }

        -- 1.3.6.1.4.1.2011.2.251.20.1.2.2.15.40.47
        nasHyperMetroFileSystemIsUnavailable OBJECT IDENTIFIER ::= { filesystem 47 }

        -- 1.3.6.1.4.1.2011.2.251.20.1.2.2.15.40.47.1
        nasHyperMetroFileSystemIsUnavailable-Fault NOTIFICATION-TYPE
            OBJECTS { hwStorageAlarmReporting }
            STATUS current
            DESCRIPTION "File System Data Is Incomplete"
            --#SEVERITY MAJOR
            ::= { nasHyperMetroFileSystemIsUnavailable 1 }

        -- 1.3.6.1.4.1.2011.2.251.20.1.2.2.15.40.47.2
        nasHyperMetroFileSystemIsUnavailable-Resume NOTIFICATION-TYPE
            OBJECTS { hwStorageAlarmReporting }
            STATUS current
            DESCRIPTION "Recover: File System Data Is Incomplete"
            --#SEVERITY INFORMATIONAL
            ::= { nasHyperMetroFileSystemIsUnavailable 2 }

        -- 1.3.6.1.4.1.2011.2.251.20.1.2.2.15.40.69
        fileSystemIsFaulty OBJECT IDENTIFIER ::= { filesystem 69 }

        -- 1.3.6.1.4.1.2011.2.251.20.1.2.2.15.40.69.1
        fileSystemIsFaulty-Fault NOTIFICATION-TYPE
            OBJECTS { hwStorageAlarmReporting }
            STATUS current
            DESCRIPTION "File System Is Faulty"
            --#SEVERITY CRITICAL
            ::= { fileSystemIsFaulty 1 }

        -- 1.3.6.1.4.1.2011.2.251.20.1.2.2.15.40.69.2
        fileSystemIsFaulty-Resume NOTIFICATION-TYPE
            OBJECTS { hwStorageAlarmReporting }
            STATUS current
            DESCRIPTION "Recover: File System Is Faulty"
            --#SEVERITY INFORMATIONAL
            ::= { fileSystemIsFaulty 2 }

        -- 1.3.6.1.4.1.2011.2.251.20.1.2.2.15.40.117
        writeProtectionIsEnabledForFS OBJECT IDENTIFIER ::= { filesystem 117 }

        -- 1.3.6.1.4.1.2011.2.251.20.1.2.2.15.40.117.1
        writeProtectionIsEnabledForFS-Fault NOTIFICATION-TYPE
            OBJECTS { hwStorageAlarmReporting }
            STATUS current
            DESCRIPTION "File System Under Write Protection"
            --#SEVERITY CRITICAL
            ::= { writeProtectionIsEnabledForFS 1 }

        -- 1.3.6.1.4.1.2011.2.251.20.1.2.2.15.40.117.2
        writeProtectionIsEnabledForFS-Resume NOTIFICATION-TYPE
            OBJECTS { hwStorageAlarmReporting }
            STATUS current
            DESCRIPTION "Recover: File System Under Write Protection"
            --#SEVERITY INFORMATIONAL
            ::= { writeProtectionIsEnabledForFS 2 }

        -- 1.3.6.1.4.1.2011.2.251.20.1.2.2.15.40.294
        theSpaceOfTheFileSystemIsUsedUp OBJECT IDENTIFIER ::= { filesystem 294 }

        -- 1.3.6.1.4.1.2011.2.251.20.1.2.2.15.40.294.1
        theSpaceOfTheFileSystemIsUsedUp-Fault NOTIFICATION-TYPE
            OBJECTS { hwStorageAlarmReporting }
            STATUS current
            DESCRIPTION "The Space Of The File System Is Used Up"
            --#SEVERITY MAJOR
            ::= { theSpaceOfTheFileSystemIsUsedUp 1 }

        -- 1.3.6.1.4.1.2011.2.251.20.1.2.2.15.40.294.2
        theSpaceOfTheFileSystemIsUsedUp-Resume NOTIFICATION-TYPE
            OBJECTS { hwStorageAlarmReporting }
            STATUS current
            DESCRIPTION "Recover: The Space Of The File System Is Used Up"
            --#SEVERITY INFORMATIONAL
            ::= { theSpaceOfTheFileSystemIsUsedUp 2 }

        -- 1.3.6.1.4.1.2011.2.251.20.1.2.2.15.40.296
        filesystemCapacityIsFull OBJECT IDENTIFIER ::= { filesystem 296 }

        -- 1.3.6.1.4.1.2011.2.251.20.1.2.2.15.40.296.1
        filesystemCapacityIsFull-Fault NOTIFICATION-TYPE
            OBJECTS { hwStorageAlarmReporting }
            STATUS current
            DESCRIPTION "Expand The Capacity In A Timely Manner Because The File System Capacity Reaches The Alarm Threshold"
            --#SEVERITY MAJOR
            ::= { filesystemCapacityIsFull 1 }

        -- 1.3.6.1.4.1.2011.2.251.20.1.2.2.15.40.296.2
        filesystemCapacityIsFull-Resume NOTIFICATION-TYPE
            OBJECTS { hwStorageAlarmReporting }
            STATUS current
            DESCRIPTION "Recover: Expand The Capacity In A Timely Manner Because The File System Capacity Reaches The Alarm Threshold"
            --#SEVERITY INFORMATIONAL
            ::= { filesystemCapacityIsFull 2 }

        -- 1.3.6.1.4.1.2011.2.251.20.1.2.2.15.40.300
        fileOrDirExistMediumError OBJECT IDENTIFIER ::= { filesystem 300 }

        -- 1.3.6.1.4.1.2011.2.251.20.1.2.2.15.40.300.1
        fileOrDirExistMediumError-Fault NOTIFICATION-TYPE
            OBJECTS { hwStorageAlarmReporting }
            STATUS current
            DESCRIPTION "A Metadata Medium Error Occurred To The File Or Directory"
            --#SEVERITY MAJOR
            ::= { fileOrDirExistMediumError 1 }

        -- 1.3.6.1.4.1.2011.2.251.20.1.2.2.15.40.300.2
        fileOrDirExistMediumError-Resume NOTIFICATION-TYPE
            OBJECTS { hwStorageAlarmReporting }
            STATUS current
            DESCRIPTION "Recover: A Metadata Medium Error Occurred To The File Or Directory"
            --#SEVERITY INFORMATIONAL
            ::= { fileOrDirExistMediumError 2 }

        -- 1.3.6.1.4.1.2011.2.251.20.1.2.2.15.40.301
        fileDataExistMediumError OBJECT IDENTIFIER ::= { filesystem 301 }

        -- 1.3.6.1.4.1.2011.2.251.20.1.2.2.15.40.301.1
        fileDataExistMediumError-Fault NOTIFICATION-TYPE
            OBJECTS { hwStorageAlarmReporting }
            STATUS current
            DESCRIPTION "A Medium Error Occurred To The File Data"
            --#SEVERITY MAJOR
            ::= { fileDataExistMediumError 1 }

        -- 1.3.6.1.4.1.2011.2.251.20.1.2.2.15.40.301.2
        fileDataExistMediumError-Resume NOTIFICATION-TYPE
            OBJECTS { hwStorageAlarmReporting }
            STATUS current
            DESCRIPTION "Recover: A Medium Error Occurred To The File Data"
            --#SEVERITY INFORMATIONAL
            ::= { fileDataExistMediumError 2 }

        -- 1.3.6.1.4.1.2011.2.251.20.1.2.2.15.40.303
        theRemainingCapacityOfTheAuditLogFileSystemIsInsufficient OBJECT IDENTIFIER ::= { filesystem 303 }

        -- 1.3.6.1.4.1.2011.2.251.20.1.2.2.15.40.303.1
        theRemainingCapacityOfTheAuditLogFileSystemIsInsufficient-Fault NOTIFICATION-TYPE
            OBJECTS { hwStorageAlarmReporting }
            STATUS current
            DESCRIPTION "The Remaining Capacity Of The Audit Log File System Is Insufficient"
            --#SEVERITY MAJOR
            ::= { theRemainingCapacityOfTheAuditLogFileSystemIsInsufficient 1 }

        -- 1.3.6.1.4.1.2011.2.251.20.1.2.2.15.40.303.2
        theRemainingCapacityOfTheAuditLogFileSystemIsInsufficient-Resume NOTIFICATION-TYPE
            OBJECTS { hwStorageAlarmReporting }
            STATUS current
            DESCRIPTION "Recover: The Remaining Capacity Of The Audit Log File System Is Insufficient"
            --#SEVERITY INFORMATIONAL
            ::= { theRemainingCapacityOfTheAuditLogFileSystemIsInsufficient 2 }

        -- 1.3.6.1.4.1.2011.2.251.20.1.2.2.15.40.304
        theSpaceOfTheAuditLogFileSystemIsUsedUp OBJECT IDENTIFIER ::= { filesystem 304 }

        -- 1.3.6.1.4.1.2011.2.251.20.1.2.2.15.40.304.1
        theSpaceOfTheAuditLogFileSystemIsUsedUp-Fault NOTIFICATION-TYPE
            OBJECTS { hwStorageAlarmReporting }
            STATUS current
            DESCRIPTION "The Space Of The Audit Log File System Is Used Up"
            --#SEVERITY MAJOR
            ::= { theSpaceOfTheAuditLogFileSystemIsUsedUp 1 }

        -- 1.3.6.1.4.1.2011.2.251.20.1.2.2.15.40.304.2
        theSpaceOfTheAuditLogFileSystemIsUsedUp-Resume NOTIFICATION-TYPE
            OBJECTS { hwStorageAlarmReporting }
            STATUS current
            DESCRIPTION "Recover: The Space Of The Audit Log File System Is Used Up"
            --#SEVERITY INFORMATIONAL
            ::= { theSpaceOfTheAuditLogFileSystemIsUsedUp 2 }

        -- 1.3.6.1.4.1.2011.2.251.20.1.2.2.15.40.306
        theClusterWriteCacheIsDegraded OBJECT IDENTIFIER ::= { filesystem 306 }

        -- 1.3.6.1.4.1.2011.2.251.20.1.2.2.15.40.306.1
        theClusterWriteCacheIsDegraded-Fault NOTIFICATION-TYPE
            OBJECTS { hwStorageAlarmReporting }
            STATUS current
            DESCRIPTION "The Cluster Write Cache Is Degraded"
            --#SEVERITY MAJOR
            ::= { theClusterWriteCacheIsDegraded 1 }

        -- 1.3.6.1.4.1.2011.2.251.20.1.2.2.15.40.306.2
        theClusterWriteCacheIsDegraded-Resume NOTIFICATION-TYPE
            OBJECTS { hwStorageAlarmReporting }
            STATUS current
            DESCRIPTION "Recover: The Cluster Write Cache Is Degraded"
            --#SEVERITY INFORMATIONAL
            ::= { theClusterWriteCacheIsDegraded 2 }

        -- 1.3.6.1.4.1.2011.2.251.20.1.2.2.15.40.308
        failedToCollectAuditLogFileSystemLogs OBJECT IDENTIFIER ::= { filesystem 308 }

        -- 1.3.6.1.4.1.2011.2.251.20.1.2.2.15.40.308.1
        failedToCollectAuditLogFileSystemLogs-Fault NOTIFICATION-TYPE
            OBJECTS { hwStorageAlarmReporting }
            STATUS current
            DESCRIPTION "Failed To Collect Audit Log File System Logs"
            --#SEVERITY WARNING
            ::= { failedToCollectAuditLogFileSystemLogs 1 }

        -- 1.3.6.1.4.1.2011.2.251.20.1.2.2.15.40.308.2
        failedToCollectAuditLogFileSystemLogs-Resume NOTIFICATION-TYPE
            OBJECTS { hwStorageAlarmReporting }
            STATUS current
            DESCRIPTION "Recover: Failed To Collect Audit Log File System Logs"
            --#SEVERITY INFORMATIONAL
            ::= { failedToCollectAuditLogFileSystemLogs 2 }

        -- 1.3.6.1.4.1.2011.2.251.20.1.2.2.15.40.309
        failedToUpdateTheAuditLogFileSystemTiming OBJECT IDENTIFIER ::= { filesystem 309 }

        -- 1.3.6.1.4.1.2011.2.251.20.1.2.2.15.40.309.1
        failedToUpdateTheAuditLogFileSystemTiming-Fault NOTIFICATION-TYPE
            OBJECTS { hwStorageAlarmReporting }
            STATUS current
            DESCRIPTION "Failed To Update The Audit Log File System Timing"
            --#SEVERITY WARNING
            ::= { failedToUpdateTheAuditLogFileSystemTiming 1 }

        -- 1.3.6.1.4.1.2011.2.251.20.1.2.2.15.40.309.2
        failedToUpdateTheAuditLogFileSystemTiming-Resume NOTIFICATION-TYPE
            OBJECTS { hwStorageAlarmReporting }
            STATUS current
            DESCRIPTION "Recover: Failed To Update The Audit Log File System Timing"
            --#SEVERITY INFORMATIONAL
            ::= { failedToUpdateTheAuditLogFileSystemTiming 2 }

        -- 1.3.6.1.4.1.2011.2.251.20.1.2.2.15.40.310
        theFileSystemTransactionPlaybackFailedContinuouslyOrHasBeenRunningForALongTime OBJECT IDENTIFIER ::= { filesystem 310 }

        -- 1.3.6.1.4.1.2011.2.251.20.1.2.2.15.40.310.1
        theFileSystemTransactionPlaybackFailedContinuouslyOrHasBeenRunningForALongTime-Fault NOTIFICATION-TYPE
            OBJECTS { hwStorageAlarmReporting }
            STATUS current
            DESCRIPTION "The File System Transaction Playback Failed Continuously Or Has Been Running For A Long Time"
            --#SEVERITY WARNING
            ::= { theFileSystemTransactionPlaybackFailedContinuouslyOrHasBeenRunningForALongTime 1 }

        -- 1.3.6.1.4.1.2011.2.251.20.1.2.2.15.40.310.2
        theFileSystemTransactionPlaybackFailedContinuouslyOrHasBeenRunningForALongTime-Resume NOTIFICATION-TYPE
            OBJECTS { hwStorageAlarmReporting }
            STATUS current
            DESCRIPTION "Recover: The File System Transaction Playback Failed Continuously Or Has Been Running For A Long Time"
            --#SEVERITY INFORMATIONAL
            ::= { theFileSystemTransactionPlaybackFailedContinuouslyOrHasBeenRunningForALongTime 2 }

        -- 1.3.6.1.4.1.2011.2.251.20.1.2.2.15.40.311
        tooMuchSpaceOfTheReservedVolumeOfTheFileSystemIsOccupied OBJECT IDENTIFIER ::= { filesystem 311 }

        -- 1.3.6.1.4.1.2011.2.251.20.1.2.2.15.40.311.1
        tooMuchSpaceOfTheReservedVolumeOfTheFileSystemIsOccupied-Fault NOTIFICATION-TYPE
            OBJECTS { hwStorageAlarmReporting }
            STATUS current
            DESCRIPTION "Too Much Space Of The Reserved Volume Of The File System Is Occupied"
            --#SEVERITY MAJOR
            ::= { tooMuchSpaceOfTheReservedVolumeOfTheFileSystemIsOccupied 1 }

        -- 1.3.6.1.4.1.2011.2.251.20.1.2.2.15.40.311.2
        tooMuchSpaceOfTheReservedVolumeOfTheFileSystemIsOccupied-Resume NOTIFICATION-TYPE
            OBJECTS { hwStorageAlarmReporting }
            STATUS current
            DESCRIPTION "Recover: Too Much Space Of The Reserved Volume Of The File System Is Occupied"
            --#SEVERITY INFORMATIONAL
            ::= { tooMuchSpaceOfTheReservedVolumeOfTheFileSystemIsOccupied 2 }

        -- 1.3.6.1.4.1.2011.2.251.20.1.2.2.15.40.312
        theFileSystemFailedToReclaimTransactionLogsContinuouslyOrTheOperationTakesALongTime1 OBJECT IDENTIFIER ::= { filesystem 312 }

        -- 1.3.6.1.4.1.2011.2.251.20.1.2.2.15.40.312.1
        theFileSystemFailedToReclaimTransactionLogsContinuouslyOrTheOperationTakesALongTime1-Fault NOTIFICATION-TYPE
            OBJECTS { hwStorageAlarmReporting }
            STATUS current
            DESCRIPTION "The File System Failed To Reclaim Transaction Logs Continuously Or The Operation Takes A Long Time"
            --#SEVERITY WARNING
            ::= { theFileSystemFailedToReclaimTransactionLogsContinuouslyOrTheOperationTakesALongTime1 1 }

        -- 1.3.6.1.4.1.2011.2.251.20.1.2.2.15.40.312.2
        theFileSystemFailedToReclaimTransactionLogsContinuouslyOrTheOperationTakesALongTime1-Resume NOTIFICATION-TYPE
            OBJECTS { hwStorageAlarmReporting }
            STATUS current
            DESCRIPTION "Recover: The File System Failed To Reclaim Transaction Logs Continuously Or The Operation Takes A Long Time"
            --#SEVERITY INFORMATIONAL
            ::= { theFileSystemFailedToReclaimTransactionLogsContinuouslyOrTheOperationTakesALongTime1 2 }

        -- 1.3.6.1.4.1.2011.2.251.20.1.2.2.15.40.313
        numberOfAllocatedObjectIDsInTheFileSystemExceedsTheThreshold OBJECT IDENTIFIER ::= { filesystem 313 }

        -- 1.3.6.1.4.1.2011.2.251.20.1.2.2.15.40.313.1
        numberOfAllocatedObjectIDsInTheFileSystemExceedsTheThreshold-Fault NOTIFICATION-TYPE
            OBJECTS { hwStorageAlarmReporting }
            STATUS current
            DESCRIPTION "Number Of Allocated Object IDs In The File System Exceeds The Threshold"
            --#SEVERITY WARNING
            ::= { numberOfAllocatedObjectIDsInTheFileSystemExceedsTheThreshold 1 }

        -- 1.3.6.1.4.1.2011.2.251.20.1.2.2.15.40.313.2
        numberOfAllocatedObjectIDsInTheFileSystemExceedsTheThreshold-Resume NOTIFICATION-TYPE
            OBJECTS { hwStorageAlarmReporting }
            STATUS current
            DESCRIPTION "Recover: Number Of Allocated Object IDs In The File System Exceeds The Threshold"
            --#SEVERITY INFORMATIONAL
            ::= { numberOfAllocatedObjectIDsInTheFileSystemExceedsTheThreshold 2 }

        -- 1.3.6.1.4.1.2011.2.251.20.1.2.2.15.40.316
        singleVnodeCapacityIsTooHigh OBJECT IDENTIFIER ::= { filesystem 316 }

        -- 1.3.6.1.4.1.2011.2.251.20.1.2.2.15.40.316.1
        singleVnodeCapacityIsTooHigh-Fault NOTIFICATION-TYPE
            OBJECTS { hwStorageAlarmReporting }
            STATUS current
            DESCRIPTION "Used Capacity Of A Single Vnode In The File System Is Too High"
            --#SEVERITY WARNING
            ::= { singleVnodeCapacityIsTooHigh 1 }

        -- 1.3.6.1.4.1.2011.2.251.20.1.2.2.15.40.316.2
        singleVnodeCapacityIsTooHigh-Resume NOTIFICATION-TYPE
            OBJECTS { hwStorageAlarmReporting }
            STATUS current
            DESCRIPTION "Recover: Used Capacity Of A Single Vnode In The File System Is Too High"
            --#SEVERITY INFORMATIONAL
            ::= { singleVnodeCapacityIsTooHigh 2 }

        -- 1.3.6.1.4.1.2011.2.251.20.1.2.2.15.40.317
        smartMobilityRemoteDeviceFault OBJECT IDENTIFIER ::= { filesystem 317 }

        -- 1.3.6.1.4.1.2011.2.251.20.1.2.2.15.40.317.1
        smartMobilityRemoteDeviceFault-Fault NOTIFICATION-TYPE
            OBJECTS { hwStorageAlarmReporting }
            STATUS current
            DESCRIPTION "SmartMobility Remote Device Fault"
            --#SEVERITY MAJOR
            ::= { smartMobilityRemoteDeviceFault 1 }

        -- 1.3.6.1.4.1.2011.2.251.20.1.2.2.15.40.317.2
        smartMobilityRemoteDeviceFault-Resume NOTIFICATION-TYPE
            OBJECTS { hwStorageAlarmReporting }
            STATUS current
            DESCRIPTION "Recover: SmartMobility Remote Device Fault"
            --#SEVERITY INFORMATIONAL
            ::= { smartMobilityRemoteDeviceFault 2 }

        -- 1.3.6.1.4.1.2011.2.251.20.1.2.2.15.40.318
        failedToRecallDataDueToInsufficientRemainingSpaceOfTheFileSystem OBJECT IDENTIFIER ::= { filesystem 318 }

        -- 1.3.6.1.4.1.2011.2.251.20.1.2.2.15.40.318.1
        failedToRecallDataDueToInsufficientRemainingSpaceOfTheFileSystem-Fault NOTIFICATION-TYPE
            OBJECTS { hwStorageAlarmReporting }
            STATUS current
            DESCRIPTION "Failed To Recall Data Due To Insufficient Remaining Space Of The File System"
            --#SEVERITY MAJOR
            ::= { failedToRecallDataDueToInsufficientRemainingSpaceOfTheFileSystem 1 }

        -- 1.3.6.1.4.1.2011.2.251.20.1.2.2.15.40.318.2
        failedToRecallDataDueToInsufficientRemainingSpaceOfTheFileSystem-Resume NOTIFICATION-TYPE
            OBJECTS { hwStorageAlarmReporting }
            STATUS current
            DESCRIPTION "Recover: Failed To Recall Data Due To Insufficient Remaining Space Of The File System"
            --#SEVERITY INFORMATIONAL
            ::= { failedToRecallDataDueToInsufficientRemainingSpaceOfTheFileSystem 2 }

        -- 1.3.6.1.4.1.2011.2.251.20.1.2.2.15.40.323
        insufficientCapacityReservedForFileSystemDataProtection OBJECT IDENTIFIER ::= { filesystem 323 }

        -- 1.3.6.1.4.1.2011.2.251.20.1.2.2.15.40.323.1
        insufficientCapacityReservedForFileSystemDataProtection-Fault NOTIFICATION-TYPE
            OBJECTS { hwStorageAlarmReporting }
            STATUS current
            DESCRIPTION "Insufficient Capacity Reserved For File System Data Protection"
            --#SEVERITY WARNING
            ::= { insufficientCapacityReservedForFileSystemDataProtection 1 }

        -- 1.3.6.1.4.1.2011.2.251.20.1.2.2.15.40.323.2
        insufficientCapacityReservedForFileSystemDataProtection-Resume NOTIFICATION-TYPE
            OBJECTS { hwStorageAlarmReporting }
            STATUS current
            DESCRIPTION "Recover: Insufficient Capacity Reserved For File System Data Protection"
            --#SEVERITY INFORMATIONAL
            ::= { insufficientCapacityReservedForFileSystemDataProtection 2 }

        -- 1.3.6.1.4.1.2011.2.251.20.1.2.2.15.40.325
        theFileSystemFailedToReclaimTransactionLogsContinuouslyOrTheOperationTakesALongTime OBJECT IDENTIFIER ::= { filesystem 325 }

        -- 1.3.6.1.4.1.2011.2.251.20.1.2.2.15.40.325.1
        theFileSystemFailedToReclaimTransactionLogsContinuouslyOrTheOperationTakesALongTime-Fault NOTIFICATION-TYPE
            OBJECTS { hwStorageAlarmReporting }
            STATUS current
            DESCRIPTION "The File System Failed To Reclaim Transaction Logs Continuously Or The Operation Takes A Long Time"
            --#SEVERITY WARNING
            ::= { theFileSystemFailedToReclaimTransactionLogsContinuouslyOrTheOperationTakesALongTime 1 }

        -- 1.3.6.1.4.1.2011.2.251.20.1.2.2.15.40.325.2
        theFileSystemFailedToReclaimTransactionLogsContinuouslyOrTheOperationTakesALongTime-Resume NOTIFICATION-TYPE
            OBJECTS { hwStorageAlarmReporting }
            STATUS current
            DESCRIPTION "Recover: The File System Failed To Reclaim Transaction Logs Continuously Or The Operation Takes A Long Time"
            --#SEVERITY INFORMATIONAL
            ::= { theFileSystemFailedToReclaimTransactionLogsContinuouslyOrTheOperationTakesALongTime 2 }

        -- 1.3.6.1.4.1.2011.2.251.20.1.2.2.15.40.327
        auditServerFault OBJECT IDENTIFIER ::= { filesystem 327 }

        -- 1.3.6.1.4.1.2011.2.251.20.1.2.2.15.40.327.1
        auditServerFault-Fault NOTIFICATION-TYPE
            OBJECTS { hwStorageAlarmReporting }
            STATUS current
            DESCRIPTION "The Syslog Server For Audit Logs Cannot Be Connected"
            --#SEVERITY MAJOR
            ::= { auditServerFault 1 }

        -- 1.3.6.1.4.1.2011.2.251.20.1.2.2.15.40.327.2
        auditServerFault-Resume NOTIFICATION-TYPE
            OBJECTS { hwStorageAlarmReporting }
            STATUS current
            DESCRIPTION "Recover: The Syslog Server For Audit Logs Cannot Be Connected"
            --#SEVERITY INFORMATIONAL
            ::= { auditServerFault 2 }

        -- 1.3.6.1.4.1.2011.2.251.20.1.2.2.15.40.329
        engineHighCapacityAndUneven OBJECT IDENTIFIER ::= { filesystem 329 }

        -- 1.3.6.1.4.1.2011.2.251.20.1.2.2.15.40.329.1
        engineHighCapacityAndUneven-Fault NOTIFICATION-TYPE
            OBJECTS { hwStorageAlarmReporting }
            STATUS current
            DESCRIPTION "Excessively High Capacity Usage Of Some Controller Enclosures"
            --#SEVERITY WARNING
            ::= { engineHighCapacityAndUneven 1 }

        -- 1.3.6.1.4.1.2011.2.251.20.1.2.2.15.40.329.2
        engineHighCapacityAndUneven-Resume NOTIFICATION-TYPE
            OBJECTS { hwStorageAlarmReporting }
            STATUS current
            DESCRIPTION "Recover: Excessively High Capacity Usage Of Some Controller Enclosures"
            --#SEVERITY INFORMATIONAL
            ::= { engineHighCapacityAndUneven 2 }

        -- 1.3.6.1.4.1.2011.2.251.20.1.2.2.15.49
        event OBJECT IDENTIFIER ::= { oidBasedTrap 49 }

        -- 1.3.6.1.4.1.2011.2.251.20.1.2.2.15.49.4
        eventAmountReachUpLimit OBJECT IDENTIFIER ::= { event 4 }

        -- 1.3.6.1.4.1.2011.2.251.20.1.2.2.15.49.4.1
        eventAmountReachUpLimit-Fault NOTIFICATION-TYPE
            OBJECTS { hwStorageAlarmReporting }
            STATUS current
            DESCRIPTION "The Space That Stores Event Logs Is To Be Used Up"
            --#SEVERITY WARNING
            ::= { eventAmountReachUpLimit 1 }

        -- 1.3.6.1.4.1.2011.2.251.20.1.2.2.15.49.4.2
        eventAmountReachUpLimit-Resume NOTIFICATION-TYPE
            OBJECTS { hwStorageAlarmReporting }
            STATUS current
            DESCRIPTION "Recover: The Space That Stores Event Logs Is To Be Used Up"
            --#SEVERITY INFORMATIONAL
            ::= { eventAmountReachUpLimit 2 }

        -- 1.3.6.1.4.1.2011.2.251.20.1.2.2.15.49.18
        cPUQuotaExceeded OBJECT IDENTIFIER ::= { event 18 }

        -- 1.3.6.1.4.1.2011.2.251.20.1.2.2.15.49.18.1
        cPUQuotaExceeded-Fault NOTIFICATION-TYPE
            OBJECTS { hwStorageAlarmReporting }
            STATUS current
            DESCRIPTION "CPU Quota Exceeded"
            --#SEVERITY WARNING
            ::= { cPUQuotaExceeded 1 }

        -- 1.3.6.1.4.1.2011.2.251.20.1.2.2.15.49.18.2
        cPUQuotaExceeded-Resume NOTIFICATION-TYPE
            OBJECTS { hwStorageAlarmReporting }
            STATUS current
            DESCRIPTION "Recover: CPU Quota Exceeded"
            --#SEVERITY INFORMATIONAL
            ::= { cPUQuotaExceeded 2 }

        -- 1.3.6.1.4.1.2011.2.251.20.1.2.2.15.49.65534
        trapTestAlarm OBJECT IDENTIFIER ::= { event 65534 }

        -- 1.3.6.1.4.1.2011.2.251.20.1.2.2.15.49.65534.1
        trapTestAlarm-Fault NOTIFICATION-TYPE
            OBJECTS { hwStorageAlarmReporting }
            STATUS current
            DESCRIPTION "Trap Test Alarm"
            --#SEVERITY INFORMATIONAL
            ::= { trapTestAlarm 1 }

        -- 1.3.6.1.4.1.2011.2.251.20.1.2.2.15.49.65534.2
        trapTestAlarm-Resume NOTIFICATION-TYPE
            OBJECTS { hwStorageAlarmReporting }
            STATUS current
            DESCRIPTION "Recover: Trap Test Alarm"
            --#SEVERITY INFORMATIONAL
            ::= { trapTestAlarm 2 }

        -- 1.3.6.1.4.1.2011.2.251.20.1.2.2.15.113
        om OBJECT IDENTIFIER ::= { oidBasedTrap 113 }

        -- 1.3.6.1.4.1.2011.2.251.20.1.2.2.15.113.3
        theCACertificateIssuedByTheStorageDeviceIsAboutToExpire OBJECT IDENTIFIER ::= { om 3 }

        -- 1.3.6.1.4.1.2011.2.251.20.1.2.2.15.113.3.1
        theCACertificateIssuedByTheStorageDeviceIsAboutToExpire-Fault NOTIFICATION-TYPE
            OBJECTS { hwStorageAlarmReporting }
            STATUS current
            DESCRIPTION "The CA Certificate Issued By The Storage Device Is About To Expire"
            --#SEVERITY WARNING
            ::= { theCACertificateIssuedByTheStorageDeviceIsAboutToExpire 1 }

        -- 1.3.6.1.4.1.2011.2.251.20.1.2.2.15.113.3.2
        theCACertificateIssuedByTheStorageDeviceIsAboutToExpire-Resume NOTIFICATION-TYPE
            OBJECTS { hwStorageAlarmReporting }
            STATUS current
            DESCRIPTION "Recover: The CA Certificate Issued By The Storage Device Is About To Expire"
            --#SEVERITY INFORMATIONAL
            ::= { theCACertificateIssuedByTheStorageDeviceIsAboutToExpire 2 }

        -- 1.3.6.1.4.1.2011.2.251.20.1.2.2.15.113.6
        theCACertificateIssuedByTheStorageDeviceExpires OBJECT IDENTIFIER ::= { om 6 }

        -- 1.3.6.1.4.1.2011.2.251.20.1.2.2.15.113.6.1
        theCACertificateIssuedByTheStorageDeviceExpires-Fault NOTIFICATION-TYPE
            OBJECTS { hwStorageAlarmReporting }
            STATUS current
            DESCRIPTION "The CA Certificate Issued By The Storage Device Expires"
            --#SEVERITY WARNING
            ::= { theCACertificateIssuedByTheStorageDeviceExpires 1 }

        -- 1.3.6.1.4.1.2011.2.251.20.1.2.2.15.113.6.2
        theCACertificateIssuedByTheStorageDeviceExpires-Resume NOTIFICATION-TYPE
            OBJECTS { hwStorageAlarmReporting }
            STATUS current
            DESCRIPTION "Recover: The CA Certificate Issued By The Storage Device Expires"
            --#SEVERITY INFORMATIONAL
            ::= { theCACertificateIssuedByTheStorageDeviceExpires 2 }

        -- 1.3.6.1.4.1.2011.2.251.20.1.2.2.15.113.7
        theTwoFactorAuthenticationEmailServerIsUnavailable OBJECT IDENTIFIER ::= { om 7 }

        -- 1.3.6.1.4.1.2011.2.251.20.1.2.2.15.113.7.1
        theTwoFactorAuthenticationEmailServerIsUnavailable-Fault NOTIFICATION-TYPE
            OBJECTS { hwStorageAlarmReporting }
            STATUS current
            DESCRIPTION "The TwoFactor Authentication Email Server Is Unavailable"
            --#SEVERITY WARNING
            ::= { theTwoFactorAuthenticationEmailServerIsUnavailable 1 }

        -- 1.3.6.1.4.1.2011.2.251.20.1.2.2.15.113.7.2
        theTwoFactorAuthenticationEmailServerIsUnavailable-Resume NOTIFICATION-TYPE
            OBJECTS { hwStorageAlarmReporting }
            STATUS current
            DESCRIPTION "Recover: The TwoFactor Authentication Email Server Is Unavailable"
            --#SEVERITY INFORMATIONAL
            ::= { theTwoFactorAuthenticationEmailServerIsUnavailable 2 }

        -- 1.3.6.1.4.1.2011.2.251.20.1.2.2.15.113.10
        bGPPeerConnectionStatusIsAbnormal OBJECT IDENTIFIER ::= { om 10 }

        -- 1.3.6.1.4.1.2011.2.251.20.1.2.2.15.113.10.1
        bGPPeerConnectionStatusIsAbnormal-Fault NOTIFICATION-TYPE
            OBJECTS { hwStorageAlarmReporting }
            STATUS current
            DESCRIPTION "BGP Peer Connection Status Is Abnormal"
            --#SEVERITY MAJOR
            ::= { bGPPeerConnectionStatusIsAbnormal 1 }

        -- 1.3.6.1.4.1.2011.2.251.20.1.2.2.15.113.10.2
        bGPPeerConnectionStatusIsAbnormal-Resume NOTIFICATION-TYPE
            OBJECTS { hwStorageAlarmReporting }
            STATUS current
            DESCRIPTION "Recover: BGP Peer Connection Status Is Abnormal"
            --#SEVERITY INFORMATIONAL
            ::= { bGPPeerConnectionStatusIsAbnormal 2 }

        -- 1.3.6.1.4.1.2011.2.251.20.1.2.2.15.113.11
        bFDSessionStatusOfTheBGPPeerIsAbnormal OBJECT IDENTIFIER ::= { om 11 }

        -- 1.3.6.1.4.1.2011.2.251.20.1.2.2.15.113.11.1
        bFDSessionStatusOfTheBGPPeerIsAbnormal-Fault NOTIFICATION-TYPE
            OBJECTS { hwStorageAlarmReporting }
            STATUS current
            DESCRIPTION "BFD Session Status Of The BGP Peer Is Abnormal"
            --#SEVERITY MAJOR
            ::= { bFDSessionStatusOfTheBGPPeerIsAbnormal 1 }

        -- 1.3.6.1.4.1.2011.2.251.20.1.2.2.15.113.11.2
        bFDSessionStatusOfTheBGPPeerIsAbnormal-Resume NOTIFICATION-TYPE
            OBJECTS { hwStorageAlarmReporting }
            STATUS current
            DESCRIPTION "Recover: BFD Session Status Of The BGP Peer Is Abnormal"
            --#SEVERITY INFORMATIONAL
            ::= { bFDSessionStatusOfTheBGPPeerIsAbnormal 2 }

        -- 1.3.6.1.4.1.2011.2.251.20.1.2.2.15.113.56
        failedToBackUpInternalKeyManagementServiceData OBJECT IDENTIFIER ::= { om 56 }

        -- 1.3.6.1.4.1.2011.2.251.20.1.2.2.15.113.56.1
        failedToBackUpInternalKeyManagementServiceData-Fault NOTIFICATION-TYPE
            OBJECTS { hwStorageAlarmReporting }
            STATUS current
            DESCRIPTION "Failed To Back Up Internal Key Management Service Data"
            --#SEVERITY WARNING
            ::= { failedToBackUpInternalKeyManagementServiceData 1 }

        -- 1.3.6.1.4.1.2011.2.251.20.1.2.2.15.113.56.2
        failedToBackUpInternalKeyManagementServiceData-Resume NOTIFICATION-TYPE
            OBJECTS { hwStorageAlarmReporting }
            STATUS current
            DESCRIPTION "Recover: Failed To Back Up Internal Key Management Service Data"
            --#SEVERITY INFORMATIONAL
            ::= { failedToBackUpInternalKeyManagementServiceData 2 }

        -- 1.3.6.1.4.1.2011.2.251.20.1.2.2.15.156
        vstorepair OBJECT IDENTIFIER ::= { oidBasedTrap 156 }

        -- 1.3.6.1.4.1.2011.2.251.20.1.2.2.15.156.1
        invalidVStorePair OBJECT IDENTIFIER ::= { vstorepair 1 }

        -- 1.3.6.1.4.1.2011.2.251.20.1.2.2.15.156.1.1
        invalidVStorePair-Fault NOTIFICATION-TYPE
            OBJECTS { hwStorageAlarmReporting }
            STATUS current
            DESCRIPTION "Invalid VStore Pair"
            --#SEVERITY CRITICAL
            ::= { invalidVStorePair 1 }

        -- 1.3.6.1.4.1.2011.2.251.20.1.2.2.15.156.1.2
        invalidVStorePair-Resume NOTIFICATION-TYPE
            OBJECTS { hwStorageAlarmReporting }
            STATUS current
            DESCRIPTION "Recover: Invalid VStore Pair"
            --#SEVERITY INFORMATIONAL
            ::= { invalidVStorePair 2 }

        -- 1.3.6.1.4.1.2011.2.251.20.1.2.2.15.156.4
        vStorePairConfigurationsAreDisconnected OBJECT IDENTIFIER ::= { vstorepair 4 }

        -- 1.3.6.1.4.1.2011.2.251.20.1.2.2.15.156.4.1
        vStorePairConfigurationsAreDisconnected-Fault NOTIFICATION-TYPE
            OBJECTS { hwStorageAlarmReporting }
            STATUS current
            DESCRIPTION "VStore Pair Configurations Are Disconnected"
            --#SEVERITY MAJOR
            ::= { vStorePairConfigurationsAreDisconnected 1 }

        -- 1.3.6.1.4.1.2011.2.251.20.1.2.2.15.156.4.2
        vStorePairConfigurationsAreDisconnected-Resume NOTIFICATION-TYPE
            OBJECTS { hwStorageAlarmReporting }
            STATUS current
            DESCRIPTION "Recover: VStore Pair Configurations Are Disconnected"
            --#SEVERITY INFORMATIONAL
            ::= { vStorePairConfigurationsAreDisconnected 2 }

        -- 1.3.6.1.4.1.2011.2.251.20.1.2.2.15.201
        system OBJECT IDENTIFIER ::= { oidBasedTrap 201 }

        -- 1.3.6.1.4.1.2011.2.251.20.1.2.2.15.201.1
        internalDatabaseServiceOfAStorageNodeIsAbnormal OBJECT IDENTIFIER ::= { system 1 }

        -- 1.3.6.1.4.1.2011.2.251.20.1.2.2.15.201.1.1
        internalDatabaseServiceOfAStorageNodeIsAbnormal-Fault NOTIFICATION-TYPE
            OBJECTS { hwStorageAlarmReporting }
            STATUS current
            DESCRIPTION "Internal Database Service Of A Storage Node Is Abnormal"
            --#SEVERITY MAJOR
            ::= { internalDatabaseServiceOfAStorageNodeIsAbnormal 1 }

        -- 1.3.6.1.4.1.2011.2.251.20.1.2.2.15.201.1.2
        internalDatabaseServiceOfAStorageNodeIsAbnormal-Resume NOTIFICATION-TYPE
            OBJECTS { hwStorageAlarmReporting }
            STATUS current
            DESCRIPTION "Recover: Internal Database Service Of A Storage Node Is Abnormal"
            --#SEVERITY INFORMATIONAL
            ::= { internalDatabaseServiceOfAStorageNodeIsAbnormal 2 }

        -- 1.3.6.1.4.1.2011.2.251.20.1.2.2.15.201.2
        theNumberOfWrittenLogsReachesTheLogQuota OBJECT IDENTIFIER ::= { system 2 }

        -- 1.3.6.1.4.1.2011.2.251.20.1.2.2.15.201.2.1
        theNumberOfWrittenLogsReachesTheLogQuota-Fault NOTIFICATION-TYPE
            OBJECTS { hwStorageAlarmReporting }
            STATUS current
            DESCRIPTION "The Number Of Written Logs Reaches The Log Quota"
            --#SEVERITY WARNING
            ::= { theNumberOfWrittenLogsReachesTheLogQuota 1 }

        -- 1.3.6.1.4.1.2011.2.251.20.1.2.2.15.201.2.2
        theNumberOfWrittenLogsReachesTheLogQuota-Resume NOTIFICATION-TYPE
            OBJECTS { hwStorageAlarmReporting }
            STATUS current
            DESCRIPTION "Recover: The Number Of Written Logs Reaches The Log Quota"
            --#SEVERITY INFORMATIONAL
            ::= { theNumberOfWrittenLogsReachesTheLogQuota 2 }

        -- 1.3.6.1.4.1.2011.2.251.20.1.2.2.15.201.6
        systemEnterSafeMode OBJECT IDENTIFIER ::= { system 6 }

        -- 1.3.6.1.4.1.2011.2.251.20.1.2.2.15.201.6.1
        systemEnterSafeMode-Fault NOTIFICATION-TYPE
            OBJECTS { hwStorageAlarmReporting }
            STATUS current
            DESCRIPTION "The System Has Entered Safe Mode"
            --#SEVERITY CRITICAL
            ::= { systemEnterSafeMode 1 }

        -- 1.3.6.1.4.1.2011.2.251.20.1.2.2.15.201.6.2
        systemEnterSafeMode-Resume NOTIFICATION-TYPE
            OBJECTS { hwStorageAlarmReporting }
            STATUS current
            DESCRIPTION "Recover: The System Has Entered Safe Mode"
            --#SEVERITY INFORMATIONAL
            ::= { systemEnterSafeMode 2 }

        -- 1.3.6.1.4.1.2011.2.251.20.1.2.2.15.201.21
        controllerWriteCacheIsDisabled OBJECT IDENTIFIER ::= { system 21 }

        -- 1.3.6.1.4.1.2011.2.251.20.1.2.2.15.201.21.1
        controllerWriteCacheIsDisabled-Fault NOTIFICATION-TYPE
            OBJECTS { hwStorageAlarmReporting }
            STATUS current
            DESCRIPTION "Controller Write Cache Is Disabled"
            --#SEVERITY MAJOR
            ::= { controllerWriteCacheIsDisabled 1 }

        -- 1.3.6.1.4.1.2011.2.251.20.1.2.2.15.201.21.2
        controllerWriteCacheIsDisabled-Resume NOTIFICATION-TYPE
            OBJECTS { hwStorageAlarmReporting }
            STATUS current
            DESCRIPTION "Recover: Controller Write Cache Is Disabled"
            --#SEVERITY INFORMATIONAL
            ::= { controllerWriteCacheIsDisabled 2 }

        -- 1.3.6.1.4.1.2011.2.251.20.1.2.2.15.201.22
        systemWriteCacheDisabled OBJECT IDENTIFIER ::= { system 22 }

        -- 1.3.6.1.4.1.2011.2.251.20.1.2.2.15.201.22.1
        systemWriteCacheDisabled-Fault NOTIFICATION-TYPE
            OBJECTS { hwStorageAlarmReporting }
            STATUS current
            DESCRIPTION "Write Cache Of A System Was Disabled"
            --#SEVERITY MAJOR
            ::= { systemWriteCacheDisabled 1 }

        -- 1.3.6.1.4.1.2011.2.251.20.1.2.2.15.201.22.2
        systemWriteCacheDisabled-Resume NOTIFICATION-TYPE
            OBJECTS { hwStorageAlarmReporting }
            STATUS current
            DESCRIPTION "Recover: Write Cache Of A System Was Disabled"
            --#SEVERITY INFORMATIONAL
            ::= { systemWriteCacheDisabled 2 }

        -- 1.3.6.1.4.1.2011.2.251.20.1.2.2.15.201.157
        internalComponentsOfTheSystemHaveRisks OBJECT IDENTIFIER ::= { system 157 }

        -- 1.3.6.1.4.1.2011.2.251.20.1.2.2.15.201.157.1
        internalComponentsOfTheSystemHaveRisks-Fault NOTIFICATION-TYPE
            OBJECTS { hwStorageAlarmReporting }
            STATUS current
            DESCRIPTION "Internal Components Of The System Have Risks"
            --#SEVERITY WARNING
            ::= { internalComponentsOfTheSystemHaveRisks 1 }

        -- 1.3.6.1.4.1.2011.2.251.20.1.2.2.15.201.157.2
        internalComponentsOfTheSystemHaveRisks-Resume NOTIFICATION-TYPE
            OBJECTS { hwStorageAlarmReporting }
            STATUS current
            DESCRIPTION "Recover: Internal Components Of The System Have Risks"
            --#SEVERITY INFORMATIONAL
            ::= { internalComponentsOfTheSystemHaveRisks 2 }

        -- 1.3.6.1.4.1.2011.2.251.20.1.2.2.15.201.317
        ipaddrConflict OBJECT IDENTIFIER ::= { system 317 }

        -- 1.3.6.1.4.1.2011.2.251.20.1.2.2.15.201.317.1
        ipaddrConflict-Fault NOTIFICATION-TYPE
            OBJECTS { hwStorageAlarmReporting }
            STATUS current
            DESCRIPTION "IP Address Conflict"
            --#SEVERITY MAJOR
            ::= { ipaddrConflict 1 }

        -- 1.3.6.1.4.1.2011.2.251.20.1.2.2.15.201.317.2
        ipaddrConflict-Resume NOTIFICATION-TYPE
            OBJECTS { hwStorageAlarmReporting }
            STATUS current
            DESCRIPTION "Recover: IP Address Conflict"
            --#SEVERITY INFORMATIONAL
            ::= { ipaddrConflict 2 }

        -- 1.3.6.1.4.1.2011.2.251.20.1.2.2.15.201.336
        componentsInTheSystemAreAbnormal OBJECT IDENTIFIER ::= { system 336 }

        -- 1.3.6.1.4.1.2011.2.251.20.1.2.2.15.201.336.1
        componentsInTheSystemAreAbnormal-Fault NOTIFICATION-TYPE
            OBJECTS { hwStorageAlarmReporting }
            STATUS current
            DESCRIPTION "Components In The System Are Abnormal"
            --#SEVERITY MAJOR
            ::= { componentsInTheSystemAreAbnormal 1 }

        -- 1.3.6.1.4.1.2011.2.251.20.1.2.2.15.201.336.2
        componentsInTheSystemAreAbnormal-Resume NOTIFICATION-TYPE
            OBJECTS { hwStorageAlarmReporting }
            STATUS current
            DESCRIPTION "Recover: Components In The System Are Abnormal"
            --#SEVERITY INFORMATIONAL
            ::= { componentsInTheSystemAreAbnormal 2 }

        -- 1.3.6.1.4.1.2011.2.251.20.1.2.2.15.201.337
        componentsInTheSystemAreAbnormalAndHaveBeenRepairedAutomatically OBJECT IDENTIFIER ::= { system 337 }

        -- 1.3.6.1.4.1.2011.2.251.20.1.2.2.15.201.337.1
        componentsInTheSystemAreAbnormalAndHaveBeenRepairedAutomatically-Fault NOTIFICATION-TYPE
            OBJECTS { hwStorageAlarmReporting }
            STATUS current
            DESCRIPTION "Components In The System Are Abnormal And Have Been Repaired Automatically"
            --#SEVERITY MAJOR
            ::= { componentsInTheSystemAreAbnormalAndHaveBeenRepairedAutomatically 1 }

        -- 1.3.6.1.4.1.2011.2.251.20.1.2.2.15.201.337.2
        componentsInTheSystemAreAbnormalAndHaveBeenRepairedAutomatically-Resume NOTIFICATION-TYPE
            OBJECTS { hwStorageAlarmReporting }
            STATUS current
            DESCRIPTION "Recover: Components In The System Are Abnormal And Have Been Repaired Automatically"
            --#SEVERITY INFORMATIONAL
            ::= { componentsInTheSystemAreAbnormalAndHaveBeenRepairedAutomatically 2 }

        -- 1.3.6.1.4.1.2011.2.251.20.1.2.2.15.201.340
        dnsIsUnavailable OBJECT IDENTIFIER ::= { system 340 }

        -- 1.3.6.1.4.1.2011.2.251.20.1.2.2.15.201.340.1
        dnsIsUnavailable-Fault NOTIFICATION-TYPE
            OBJECTS { hwStorageAlarmReporting }
            STATUS current
            DESCRIPTION "Management DNS Server Is Unavailable"
            --#SEVERITY WARNING
            ::= { dnsIsUnavailable 1 }

        -- 1.3.6.1.4.1.2011.2.251.20.1.2.2.15.201.340.2
        dnsIsUnavailable-Resume NOTIFICATION-TYPE
            OBJECTS { hwStorageAlarmReporting }
            STATUS current
            DESCRIPTION "Recover: Management DNS Server Is Unavailable"
            --#SEVERITY INFORMATIONAL
            ::= { dnsIsUnavailable 2 }

        -- 1.3.6.1.4.1.2011.2.251.20.1.2.2.15.201.341
        theProcessOfDaemonIsFaulty OBJECT IDENTIFIER ::= { system 341 }

        -- 1.3.6.1.4.1.2011.2.251.20.1.2.2.15.201.341.1
        theProcessOfDaemonIsFaulty-Fault NOTIFICATION-TYPE
            OBJECTS { hwStorageAlarmReporting }
            STATUS current
            DESCRIPTION "The Process Of Daemon Is Faulty"
            --#SEVERITY WARNING
            ::= { theProcessOfDaemonIsFaulty 1 }

        -- 1.3.6.1.4.1.2011.2.251.20.1.2.2.15.201.341.2
        theProcessOfDaemonIsFaulty-Resume NOTIFICATION-TYPE
            OBJECTS { hwStorageAlarmReporting }
            STATUS current
            DESCRIPTION "Recover: The Process Of Daemon Is Faulty"
            --#SEVERITY INFORMATIONAL
            ::= { theProcessOfDaemonIsFaulty 2 }

        -- 1.3.6.1.4.1.2011.2.251.20.1.2.2.15.201.343
        componentsInTheSystemOfTheControllerAreAbnormal OBJECT IDENTIFIER ::= { system 343 }

        -- 1.3.6.1.4.1.2011.2.251.20.1.2.2.15.201.343.1
        componentsInTheSystemOfTheControllerAreAbnormal-Fault NOTIFICATION-TYPE
            OBJECTS { hwStorageAlarmReporting }
            STATUS current
            DESCRIPTION "Components In The System Of The Controller Are Abnormal"
            --#SEVERITY WARNING
            ::= { componentsInTheSystemOfTheControllerAreAbnormal 1 }

        -- 1.3.6.1.4.1.2011.2.251.20.1.2.2.15.201.343.2
        componentsInTheSystemOfTheControllerAreAbnormal-Resume NOTIFICATION-TYPE
            OBJECTS { hwStorageAlarmReporting }
            STATUS current
            DESCRIPTION "Recover: Components In The System Of The Controller Are Abnormal"
            --#SEVERITY INFORMATIONAL
            ::= { componentsInTheSystemOfTheControllerAreAbnormal 2 }

        -- 1.3.6.1.4.1.2011.2.251.20.1.2.2.15.201.345
        theControllerWillEnterTheWriteProtectionMode OBJECT IDENTIFIER ::= { system 345 }

        -- 1.3.6.1.4.1.2011.2.251.20.1.2.2.15.201.345.1
        theControllerWillEnterTheWriteProtectionMode-Fault NOTIFICATION-TYPE
            OBJECTS { hwStorageAlarmReporting }
            STATUS current
            DESCRIPTION "The Controller Will Enter The Write Protection Mode"
            --#SEVERITY CRITICAL
            ::= { theControllerWillEnterTheWriteProtectionMode 1 }

        -- 1.3.6.1.4.1.2011.2.251.20.1.2.2.15.201.345.2
        theControllerWillEnterTheWriteProtectionMode-Resume NOTIFICATION-TYPE
            OBJECTS { hwStorageAlarmReporting }
            STATUS current
            DESCRIPTION "Recover: The Controller Will Enter The Write Protection Mode"
            --#SEVERITY INFORMATIONAL
            ::= { theControllerWillEnterTheWriteProtectionMode 2 }

        -- 1.3.6.1.4.1.2011.2.251.20.1.2.2.15.201.346
        theEffectiveCapacityInTheLicenseExceedsTheSystemSpecification OBJECT IDENTIFIER ::= { system 346 }

        -- 1.3.6.1.4.1.2011.2.251.20.1.2.2.15.201.346.1
        theEffectiveCapacityInTheLicenseExceedsTheSystemSpecification-Fault NOTIFICATION-TYPE
            OBJECTS { hwStorageAlarmReporting }
            STATUS current
            DESCRIPTION "The Effective Capacity In The License Exceeds The System Specification"
            --#SEVERITY CRITICAL
            ::= { theEffectiveCapacityInTheLicenseExceedsTheSystemSpecification 1 }

        -- 1.3.6.1.4.1.2011.2.251.20.1.2.2.15.201.346.2
        theEffectiveCapacityInTheLicenseExceedsTheSystemSpecification-Resume NOTIFICATION-TYPE
            OBJECTS { hwStorageAlarmReporting }
            STATUS current
            DESCRIPTION "Recover: The Effective Capacity In The License Exceeds The System Specification"
            --#SEVERITY INFORMATIONAL
            ::= { theEffectiveCapacityInTheLicenseExceedsTheSystemSpecification 2 }

        -- 1.3.6.1.4.1.2011.2.251.20.1.2.2.15.201.347
        theControllerWillEnterTheWriteProtectionMode1 OBJECT IDENTIFIER ::= { system 347 }

        -- 1.3.6.1.4.1.2011.2.251.20.1.2.2.15.201.347.1
        theControllerWillEnterTheWriteProtectionMode1-Fault NOTIFICATION-TYPE
            OBJECTS { hwStorageAlarmReporting }
            STATUS current
            DESCRIPTION "The Controller Will Enter The Write Protection Mode"
            --#SEVERITY CRITICAL
            ::= { theControllerWillEnterTheWriteProtectionMode1 1 }

        -- 1.3.6.1.4.1.2011.2.251.20.1.2.2.15.201.347.2
        theControllerWillEnterTheWriteProtectionMode1-Resume NOTIFICATION-TYPE
            OBJECTS { hwStorageAlarmReporting }
            STATUS current
            DESCRIPTION "Recover: The Controller Will Enter The Write Protection Mode"
            --#SEVERITY INFORMATIONAL
            ::= { theControllerWillEnterTheWriteProtectionMode1 2 }

        -- 1.3.6.1.4.1.2011.2.251.20.1.2.2.15.201.348
        aComponentInTheSystemIsAbnormal OBJECT IDENTIFIER ::= { system 348 }

        -- 1.3.6.1.4.1.2011.2.251.20.1.2.2.15.201.348.1
        aComponentInTheSystemIsAbnormal-Fault NOTIFICATION-TYPE
            OBJECTS { hwStorageAlarmReporting }
            STATUS current
            DESCRIPTION "A Component In The System Is Abnormal"
            --#SEVERITY MAJOR
            ::= { aComponentInTheSystemIsAbnormal 1 }

        -- 1.3.6.1.4.1.2011.2.251.20.1.2.2.15.201.348.2
        aComponentInTheSystemIsAbnormal-Resume NOTIFICATION-TYPE
            OBJECTS { hwStorageAlarmReporting }
            STATUS current
            DESCRIPTION "Recover: A Component In The System Is Abnormal"
            --#SEVERITY INFORMATIONAL
            ::= { aComponentInTheSystemIsAbnormal 2 }

        -- 1.3.6.1.4.1.2011.2.251.20.1.2.2.15.201.349
        failedToSynchronizeDNSZoneConfigurationsToTheSecondaryVStoreOfTheVStorePair OBJECT IDENTIFIER ::= { system 349 }

        -- 1.3.6.1.4.1.2011.2.251.20.1.2.2.15.201.349.1
        failedToSynchronizeDNSZoneConfigurationsToTheSecondaryVStoreOfTheVStorePair-Fault NOTIFICATION-TYPE
            OBJECTS { hwStorageAlarmReporting }
            STATUS current
            DESCRIPTION "Failed To Synchronize DNS Zone Configurations To The Secondary VStore Of The VStore Pair"
            --#SEVERITY MAJOR
            ::= { failedToSynchronizeDNSZoneConfigurationsToTheSecondaryVStoreOfTheVStorePair 1 }

        -- 1.3.6.1.4.1.2011.2.251.20.1.2.2.15.201.349.2
        failedToSynchronizeDNSZoneConfigurationsToTheSecondaryVStoreOfTheVStorePair-Resume NOTIFICATION-TYPE
            OBJECTS { hwStorageAlarmReporting }
            STATUS current
            DESCRIPTION "Recover: Failed To Synchronize DNS Zone Configurations To The Secondary VStore Of The VStore Pair"
            --#SEVERITY INFORMATIONAL
            ::= { failedToSynchronizeDNSZoneConfigurationsToTheSecondaryVStoreOfTheVStorePair 2 }

        -- 1.3.6.1.4.1.2011.2.251.20.1.2.2.15.201.351
        risksIdentifiedThroughSystemSelfcheck OBJECT IDENTIFIER ::= { system 351 }

        -- 1.3.6.1.4.1.2011.2.251.20.1.2.2.15.201.351.1
        risksIdentifiedThroughSystemSelfcheck-Fault NOTIFICATION-TYPE
            OBJECTS { hwStorageAlarmReporting }
            STATUS current
            DESCRIPTION "Risks Identified Through System Selfcheck"
            --#SEVERITY WARNING
            ::= { risksIdentifiedThroughSystemSelfcheck 1 }

        -- 1.3.6.1.4.1.2011.2.251.20.1.2.2.15.201.351.2
        risksIdentifiedThroughSystemSelfcheck-Resume NOTIFICATION-TYPE
            OBJECTS { hwStorageAlarmReporting }
            STATUS current
            DESCRIPTION "Recover: Risks Identified Through System Selfcheck"
            --#SEVERITY INFORMATIONAL
            ::= { risksIdentifiedThroughSystemSelfcheck 2 }

        -- 1.3.6.1.4.1.2011.2.251.20.1.2.2.15.201.353
        componentsOfTheControllerAreAbnormal OBJECT IDENTIFIER ::= { system 353 }

        -- 1.3.6.1.4.1.2011.2.251.20.1.2.2.15.201.353.1
        componentsOfTheControllerAreAbnormal-Fault NOTIFICATION-TYPE
            OBJECTS { hwStorageAlarmReporting }
            STATUS current
            DESCRIPTION "Components Of The Controller Are Abnormal"
            --#SEVERITY MAJOR
            ::= { componentsOfTheControllerAreAbnormal 1 }

        -- 1.3.6.1.4.1.2011.2.251.20.1.2.2.15.201.353.2
        componentsOfTheControllerAreAbnormal-Resume NOTIFICATION-TYPE
            OBJECTS { hwStorageAlarmReporting }
            STATUS current
            DESCRIPTION "Recover: Components Of The Controller Are Abnormal"
            --#SEVERITY INFORMATIONAL
            ::= { componentsOfTheControllerAreAbnormal 2 }

        -- 1.3.6.1.4.1.2011.2.251.20.1.2.2.15.201.356
        aComponentInTheExpansionModuleIsAbnormal OBJECT IDENTIFIER ::= { system 356 }

        -- 1.3.6.1.4.1.2011.2.251.20.1.2.2.15.201.356.1
        aComponentInTheExpansionModuleIsAbnormal-Fault NOTIFICATION-TYPE
            OBJECTS { hwStorageAlarmReporting }
            STATUS current
            DESCRIPTION "A Component In The Expansion Module Is Abnormal"
            --#SEVERITY MAJOR
            ::= { aComponentInTheExpansionModuleIsAbnormal 1 }

        -- 1.3.6.1.4.1.2011.2.251.20.1.2.2.15.201.356.2
        aComponentInTheExpansionModuleIsAbnormal-Resume NOTIFICATION-TYPE
            OBJECTS { hwStorageAlarmReporting }
            STATUS current
            DESCRIPTION "Recover: A Component In The Expansion Module Is Abnormal"
            --#SEVERITY INFORMATIONAL
            ::= { aComponentInTheExpansionModuleIsAbnormal 2 }

        -- 1.3.6.1.4.1.2011.2.251.20.1.2.2.15.201.358
        theSystemIsAboutToEnterTheWriteProtectionMode OBJECT IDENTIFIER ::= { system 358 }

        -- 1.3.6.1.4.1.2011.2.251.20.1.2.2.15.201.358.1
        theSystemIsAboutToEnterTheWriteProtectionMode-Fault NOTIFICATION-TYPE
            OBJECTS { hwStorageAlarmReporting }
            STATUS current
            DESCRIPTION "The System Is About To Enter The Write Protection Mode"
            --#SEVERITY MAJOR
            ::= { theSystemIsAboutToEnterTheWriteProtectionMode 1 }

        -- 1.3.6.1.4.1.2011.2.251.20.1.2.2.15.201.358.2
        theSystemIsAboutToEnterTheWriteProtectionMode-Resume NOTIFICATION-TYPE
            OBJECTS { hwStorageAlarmReporting }
            STATUS current
            DESCRIPTION "Recover: The System Is About To Enter The Write Protection Mode"
            --#SEVERITY INFORMATIONAL
            ::= { theSystemIsAboutToEnterTheWriteProtectionMode 2 }

        -- 1.3.6.1.4.1.2011.2.251.20.1.2.2.15.201.360
        containerIPAddressesConflict OBJECT IDENTIFIER ::= { system 360 }

        -- 1.3.6.1.4.1.2011.2.251.20.1.2.2.15.201.360.1
        containerIPAddressesConflict-Fault NOTIFICATION-TYPE
            OBJECTS { hwStorageAlarmReporting }
            STATUS current
            DESCRIPTION "Container IP Addresses Conflict"
            --#SEVERITY MAJOR
            ::= { containerIPAddressesConflict 1 }

        -- 1.3.6.1.4.1.2011.2.251.20.1.2.2.15.201.360.2
        containerIPAddressesConflict-Resume NOTIFICATION-TYPE
            OBJECTS { hwStorageAlarmReporting }
            STATUS current
            DESCRIPTION "Recover: Container IP Addresses Conflict"
            --#SEVERITY INFORMATIONAL
            ::= { containerIPAddressesConflict 2 }

        -- 1.3.6.1.4.1.2011.2.251.20.1.2.2.15.201.361
        theControllerIsAboutToEnterTheWriteThroughMode OBJECT IDENTIFIER ::= { system 361 }

        -- 1.3.6.1.4.1.2011.2.251.20.1.2.2.15.201.361.1
        theControllerIsAboutToEnterTheWriteThroughMode-Fault NOTIFICATION-TYPE
            OBJECTS { hwStorageAlarmReporting }
            STATUS current
            DESCRIPTION "The Controller Is About To Enter The WriteThrough Mode"
            --#SEVERITY CRITICAL
            ::= { theControllerIsAboutToEnterTheWriteThroughMode 1 }

        -- 1.3.6.1.4.1.2011.2.251.20.1.2.2.15.201.361.2
        theControllerIsAboutToEnterTheWriteThroughMode-Resume NOTIFICATION-TYPE
            OBJECTS { hwStorageAlarmReporting }
            STATUS current
            DESCRIPTION "Recover: The Controller Is About To Enter The WriteThrough Mode"
            --#SEVERITY INFORMATIONAL
            ::= { theControllerIsAboutToEnterTheWriteThroughMode 2 }

        -- 1.3.6.1.4.1.2011.2.251.20.1.2.2.15.201.365
        controllerIsFaultyWithErrorCode OBJECT IDENTIFIER ::= { system 365 }

        -- 1.3.6.1.4.1.2011.2.251.20.1.2.2.15.201.365.1
        controllerIsFaultyWithErrorCode-Fault NOTIFICATION-TYPE
            OBJECTS { hwStorageAlarmReporting }
            STATUS current
            DESCRIPTION "A Component In The System Is Abnormal"
            --#SEVERITY MAJOR
            ::= { controllerIsFaultyWithErrorCode 1 }

        -- 1.3.6.1.4.1.2011.2.251.20.1.2.2.15.201.365.2
        controllerIsFaultyWithErrorCode-Resume NOTIFICATION-TYPE
            OBJECTS { hwStorageAlarmReporting }
            STATUS current
            DESCRIPTION "Recover: A Component In The System Is Abnormal"
            --#SEVERITY INFORMATIONAL
            ::= { controllerIsFaultyWithErrorCode 2 }

        -- 1.3.6.1.4.1.2011.2.251.20.1.2.2.15.202
        user OBJECT IDENTIFIER ::= { oidBasedTrap 202 }

        -- 1.3.6.1.4.1.2011.2.251.20.1.2.2.15.202.1
        thePasswordHasNotBeenInitialized OBJECT IDENTIFIER ::= { user 1 }

        -- 1.3.6.1.4.1.2011.2.251.20.1.2.2.15.202.1.1
        thePasswordHasNotBeenInitialized-Fault NOTIFICATION-TYPE
            OBJECTS { hwStorageAlarmReporting }
            STATUS current
            DESCRIPTION "The Password Has Not Been Initialized"
            --#SEVERITY WARNING
            ::= { thePasswordHasNotBeenInitialized 1 }

        -- 1.3.6.1.4.1.2011.2.251.20.1.2.2.15.202.1.2
        thePasswordHasNotBeenInitialized-Resume NOTIFICATION-TYPE
            OBJECTS { hwStorageAlarmReporting }
            STATUS current
            DESCRIPTION "Recover: The Password Has Not Been Initialized"
            --#SEVERITY INFORMATIONAL
            ::= { thePasswordHasNotBeenInitialized 2 }

        -- 1.3.6.1.4.1.2011.2.251.20.1.2.2.15.202.14
        passwdOfUserIsAboutToExpire1 OBJECT IDENTIFIER ::= { user 14 }

        -- 1.3.6.1.4.1.2011.2.251.20.1.2.2.15.202.14.1
        passwdOfUserIsAboutToExpire1-Fault NOTIFICATION-TYPE
            OBJECTS { hwStorageAlarmReporting }
            STATUS current
            DESCRIPTION "The Password Of The User Is About To Expire"
            --#SEVERITY MAJOR
            ::= { passwdOfUserIsAboutToExpire1 1 }

        -- 1.3.6.1.4.1.2011.2.251.20.1.2.2.15.202.14.2
        passwdOfUserIsAboutToExpire1-Resume NOTIFICATION-TYPE
            OBJECTS { hwStorageAlarmReporting }
            STATUS current
            DESCRIPTION "Recover: The Password Of The User Is About To Expire"
            --#SEVERITY INFORMATIONAL
            ::= { passwdOfUserIsAboutToExpire1 2 }

        -- 1.3.6.1.4.1.2011.2.251.20.1.2.2.15.202.15
        passwdOfUserHasExpired1 OBJECT IDENTIFIER ::= { user 15 }

        -- 1.3.6.1.4.1.2011.2.251.20.1.2.2.15.202.15.1
        passwdOfUserHasExpired1-Fault NOTIFICATION-TYPE
            OBJECTS { hwStorageAlarmReporting }
            STATUS current
            DESCRIPTION "The Password Of The User Has Expired"
            --#SEVERITY CRITICAL
            ::= { passwdOfUserHasExpired1 1 }

        -- 1.3.6.1.4.1.2011.2.251.20.1.2.2.15.202.15.2
        passwdOfUserHasExpired1-Resume NOTIFICATION-TYPE
            OBJECTS { hwStorageAlarmReporting }
            STATUS current
            DESCRIPTION "Recover: The Password Of The User Has Expired"
            --#SEVERITY INFORMATIONAL
            ::= { passwdOfUserHasExpired1 2 }

        -- 1.3.6.1.4.1.2011.2.251.20.1.2.2.15.202.16
        passwdOfUserIsAboutToExpire OBJECT IDENTIFIER ::= { user 16 }

        -- 1.3.6.1.4.1.2011.2.251.20.1.2.2.15.202.16.1
        passwdOfUserIsAboutToExpire-Fault NOTIFICATION-TYPE
            OBJECTS { hwStorageAlarmReporting }
            STATUS current
            DESCRIPTION "The Password Is About To Expire"
            --#SEVERITY WARNING
            ::= { passwdOfUserIsAboutToExpire 1 }

        -- 1.3.6.1.4.1.2011.2.251.20.1.2.2.15.202.16.2
        passwdOfUserIsAboutToExpire-Resume NOTIFICATION-TYPE
            OBJECTS { hwStorageAlarmReporting }
            STATUS current
            DESCRIPTION "Recover: The Password Is About To Expire"
            --#SEVERITY INFORMATIONAL
            ::= { passwdOfUserIsAboutToExpire 2 }

        -- 1.3.6.1.4.1.2011.2.251.20.1.2.2.15.202.17
        passwdOfUserHasExpired OBJECT IDENTIFIER ::= { user 17 }

        -- 1.3.6.1.4.1.2011.2.251.20.1.2.2.15.202.17.1
        passwdOfUserHasExpired-Fault NOTIFICATION-TYPE
            OBJECTS { hwStorageAlarmReporting }
            STATUS current
            DESCRIPTION "The Password Has Expired"
            --#SEVERITY CRITICAL
            ::= { passwdOfUserHasExpired 1 }

        -- 1.3.6.1.4.1.2011.2.251.20.1.2.2.15.202.17.2
        passwdOfUserHasExpired-Resume NOTIFICATION-TYPE
            OBJECTS { hwStorageAlarmReporting }
            STATUS current
            DESCRIPTION "Recover: The Password Has Expired"
            --#SEVERITY INFORMATIONAL
            ::= { passwdOfUserHasExpired 2 }

        -- 1.3.6.1.4.1.2011.2.251.20.1.2.2.15.202.27
        theSuperAdministratorNeedsToReviewUserAccountInformation OBJECT IDENTIFIER ::= { user 27 }

        -- 1.3.6.1.4.1.2011.2.251.20.1.2.2.15.202.27.1
        theSuperAdministratorNeedsToReviewUserAccountInformation-Fault NOTIFICATION-TYPE
            OBJECTS { hwStorageAlarmReporting }
            STATUS current
            DESCRIPTION "The Super Administrator Needs To Review User Account Information"
            --#SEVERITY WARNING
            ::= { theSuperAdministratorNeedsToReviewUserAccountInformation 1 }

        -- 1.3.6.1.4.1.2011.2.251.20.1.2.2.15.202.27.2
        theSuperAdministratorNeedsToReviewUserAccountInformation-Resume NOTIFICATION-TYPE
            OBJECTS { hwStorageAlarmReporting }
            STATUS current
            DESCRIPTION "Recover: The Super Administrator Needs To Review User Account Information"
            --#SEVERITY INFORMATIONAL
            ::= { theSuperAdministratorNeedsToReviewUserAccountInformation 2 }

        -- 1.3.6.1.4.1.2011.2.251.20.1.2.2.15.202.65532
        testingTheAlarmFunction OBJECT IDENTIFIER ::= { user 65532 }

        -- 1.3.6.1.4.1.2011.2.251.20.1.2.2.15.202.65532.1
        testingTheAlarmFunction-Fault NOTIFICATION-TYPE
            OBJECTS { hwStorageAlarmReporting }
            STATUS current
            DESCRIPTION "Testing The Alarm Function"
            --#SEVERITY CRITICAL
            ::= { testingTheAlarmFunction 1 }

        -- 1.3.6.1.4.1.2011.2.251.20.1.2.2.15.202.65532.2
        testingTheAlarmFunction-Resume NOTIFICATION-TYPE
            OBJECTS { hwStorageAlarmReporting }
            STATUS current
            DESCRIPTION "Recover: Testing The Alarm Function"
            --#SEVERITY INFORMATIONAL
            ::= { testingTheAlarmFunction 2 }

        -- 1.3.6.1.4.1.2011.2.251.20.1.2.2.15.206
        enclosure OBJECT IDENTIFIER ::= { oidBasedTrap 206 }

        -- 1.3.6.1.4.1.2011.2.251.20.1.2.2.15.206.1
        failedToMonitorADiskEnclosure OBJECT IDENTIFIER ::= { enclosure 1 }

        -- 1.3.6.1.4.1.2011.2.251.20.1.2.2.15.206.1.1
        failedToMonitorADiskEnclosure-Fault NOTIFICATION-TYPE
            OBJECTS { hwStorageAlarmReporting }
            STATUS current
            DESCRIPTION "Failed To Monitor A Disk Enclosure"
            --#SEVERITY CRITICAL
            ::= { failedToMonitorADiskEnclosure 1 }

        -- 1.3.6.1.4.1.2011.2.251.20.1.2.2.15.206.1.2
        failedToMonitorADiskEnclosure-Resume NOTIFICATION-TYPE
            OBJECTS { hwStorageAlarmReporting }
            STATUS current
            DESCRIPTION "Recover: Failed To Monitor A Disk Enclosure"
            --#SEVERITY INFORMATIONAL
            ::= { failedToMonitorADiskEnclosure 2 }

        -- 1.3.6.1.4.1.2011.2.251.20.1.2.2.15.206.2
        diskEnclosureQuantityExceeds OBJECT IDENTIFIER ::= { enclosure 2 }

        -- 1.3.6.1.4.1.2011.2.251.20.1.2.2.15.206.2.1
        diskEnclosureQuantityExceeds-Fault NOTIFICATION-TYPE
            OBJECTS { hwStorageAlarmReporting }
            STATUS current
            DESCRIPTION "Disk Enclosure Quantity Exceeds The System Limit"
            --#SEVERITY WARNING
            ::= { diskEnclosureQuantityExceeds 1 }

        -- 1.3.6.1.4.1.2011.2.251.20.1.2.2.15.206.2.2
        diskEnclosureQuantityExceeds-Resume NOTIFICATION-TYPE
            OBJECTS { hwStorageAlarmReporting }
            STATUS current
            DESCRIPTION "Recover: Disk Enclosure Quantity Exceeds The System Limit"
            --#SEVERITY INFORMATIONAL
            ::= { diskEnclosureQuantityExceeds 2 }

        -- 1.3.6.1.4.1.2011.2.251.20.1.2.2.15.206.5
        diskEnclTempExceedsUpperLimit OBJECT IDENTIFIER ::= { enclosure 5 }

        -- 1.3.6.1.4.1.2011.2.251.20.1.2.2.15.206.5.1
        diskEnclTempExceedsUpperLimit-Fault NOTIFICATION-TYPE
            OBJECTS { hwStorageAlarmReporting }
            STATUS current
            DESCRIPTION "Disk Enclosure Temperature Exceeds The Upper Limit"
            --#SEVERITY MAJOR
            ::= { diskEnclTempExceedsUpperLimit 1 }

        -- 1.3.6.1.4.1.2011.2.251.20.1.2.2.15.206.5.2
        diskEnclTempExceedsUpperLimit-Resume NOTIFICATION-TYPE
            OBJECTS { hwStorageAlarmReporting }
            STATUS current
            DESCRIPTION "Recover: Disk Enclosure Temperature Exceeds The Upper Limit"
            --#SEVERITY INFORMATIONAL
            ::= { diskEnclTempExceedsUpperLimit 2 }

        -- 1.3.6.1.4.1.2011.2.251.20.1.2.2.15.206.6
        powerSupplyNotCompatible OBJECT IDENTIFIER ::= { enclosure 6 }

        -- 1.3.6.1.4.1.2011.2.251.20.1.2.2.15.206.6.1
        powerSupplyNotCompatible-Fault NOTIFICATION-TYPE
            OBJECTS { hwStorageAlarmReporting }
            STATUS current
            DESCRIPTION "Power Supplies In The Enclosure Are Inconsistent"
            --#SEVERITY MAJOR
            ::= { powerSupplyNotCompatible 1 }

        -- 1.3.6.1.4.1.2011.2.251.20.1.2.2.15.206.6.2
        powerSupplyNotCompatible-Resume NOTIFICATION-TYPE
            OBJECTS { hwStorageAlarmReporting }
            STATUS current
            DESCRIPTION "Recover: Power Supplies In The Enclosure Are Inconsistent"
            --#SEVERITY INFORMATIONAL
            ::= { powerSupplyNotCompatible 2 }

        -- 1.3.6.1.4.1.2011.2.251.20.1.2.2.15.206.7
        diskEnclTempIsBelowLimit OBJECT IDENTIFIER ::= { enclosure 7 }

        -- 1.3.6.1.4.1.2011.2.251.20.1.2.2.15.206.7.1
        diskEnclTempIsBelowLimit-Fault NOTIFICATION-TYPE
            OBJECTS { hwStorageAlarmReporting }
            STATUS current
            DESCRIPTION "Engine Or Disk Enclosure Temperature Is Below The Lower Limit"
            --#SEVERITY MAJOR
            ::= { diskEnclTempIsBelowLimit 1 }

        -- 1.3.6.1.4.1.2011.2.251.20.1.2.2.15.206.7.2
        diskEnclTempIsBelowLimit-Resume NOTIFICATION-TYPE
            OBJECTS { hwStorageAlarmReporting }
            STATUS current
            DESCRIPTION "Recover: Engine Or Disk Enclosure Temperature Is Below The Lower Limit"
            --#SEVERITY INFORMATIONAL
            ::= { diskEnclTempIsBelowLimit 2 }

        -- 1.3.6.1.4.1.2011.2.251.20.1.2.2.15.206.8
        ctrlEnclTempExceedsUpperLimit OBJECT IDENTIFIER ::= { enclosure 8 }

        -- 1.3.6.1.4.1.2011.2.251.20.1.2.2.15.206.8.1
        ctrlEnclTempExceedsUpperLimit-Fault NOTIFICATION-TYPE
            OBJECTS { hwStorageAlarmReporting }
            STATUS current
            DESCRIPTION "Controller Enclosure Temperature Exceeds The Upper Limit"
            --#SEVERITY MAJOR
            ::= { ctrlEnclTempExceedsUpperLimit 1 }

        -- 1.3.6.1.4.1.2011.2.251.20.1.2.2.15.206.8.2
        ctrlEnclTempExceedsUpperLimit-Resume NOTIFICATION-TYPE
            OBJECTS { hwStorageAlarmReporting }
            STATUS current
            DESCRIPTION "Recover: Controller Enclosure Temperature Exceeds The Upper Limit"
            --#SEVERITY INFORMATIONAL
            ::= { ctrlEnclTempExceedsUpperLimit 2 }

        -- 1.3.6.1.4.1.2011.2.251.20.1.2.2.15.206.9
        ctrlEnclTempIsFarBeyondUpLimit OBJECT IDENTIFIER ::= { enclosure 9 }

        -- 1.3.6.1.4.1.2011.2.251.20.1.2.2.15.206.9.1
        ctrlEnclTempIsFarBeyondUpLimit-Fault NOTIFICATION-TYPE
            OBJECTS { hwStorageAlarmReporting }
            STATUS current
            DESCRIPTION "Controller Enclosure Temperature Is Far Beyond The Upper Limit"
            --#SEVERITY CRITICAL
            ::= { ctrlEnclTempIsFarBeyondUpLimit 1 }

        -- 1.3.6.1.4.1.2011.2.251.20.1.2.2.15.206.9.2
        ctrlEnclTempIsFarBeyondUpLimit-Resume NOTIFICATION-TYPE
            OBJECTS { hwStorageAlarmReporting }
            STATUS current
            DESCRIPTION "Recover: Controller Enclosure Temperature Is Far Beyond The Upper Limit"
            --#SEVERITY INFORMATIONAL
            ::= { ctrlEnclTempIsFarBeyondUpLimit 2 }

        -- 1.3.6.1.4.1.2011.2.251.20.1.2.2.15.206.10
        diskEnclTempIsFarBeyondUpLimit OBJECT IDENTIFIER ::= { enclosure 10 }

        -- 1.3.6.1.4.1.2011.2.251.20.1.2.2.15.206.10.1
        diskEnclTempIsFarBeyondUpLimit-Fault NOTIFICATION-TYPE
            OBJECTS { hwStorageAlarmReporting }
            STATUS current
            DESCRIPTION "Disk Enclosure Temperature Is Far Beyond The Upper Limit"
            --#SEVERITY MAJOR
            ::= { diskEnclTempIsFarBeyondUpLimit 1 }

        -- 1.3.6.1.4.1.2011.2.251.20.1.2.2.15.206.10.2
        diskEnclTempIsFarBeyondUpLimit-Resume NOTIFICATION-TYPE
            OBJECTS { hwStorageAlarmReporting }
            STATUS current
            DESCRIPTION "Recover: Disk Enclosure Temperature Is Far Beyond The Upper Limit"
            --#SEVERITY INFORMATIONAL
            ::= { diskEnclTempIsFarBeyondUpLimit 2 }

        -- 1.3.6.1.4.1.2011.2.251.20.1.2.2.15.206.15
        anUnsupportedExpEnclConnected OBJECT IDENTIFIER ::= { enclosure 15 }

        -- 1.3.6.1.4.1.2011.2.251.20.1.2.2.15.206.15.1
        anUnsupportedExpEnclConnected-Fault NOTIFICATION-TYPE
            OBJECTS { hwStorageAlarmReporting }
            STATUS current
            DESCRIPTION "Controller Is Connected To An Unsupported Disk Enclosure"
            --#SEVERITY MAJOR
            ::= { anUnsupportedExpEnclConnected 1 }

        -- 1.3.6.1.4.1.2011.2.251.20.1.2.2.15.206.15.2
        anUnsupportedExpEnclConnected-Resume NOTIFICATION-TYPE
            OBJECTS { hwStorageAlarmReporting }
            STATUS current
            DESCRIPTION "Recover: Controller Is Connected To An Unsupported Disk Enclosure"
            --#SEVERITY INFORMATIONAL
            ::= { anUnsupportedExpEnclConnected 2 }

        -- 1.3.6.1.4.1.2011.2.251.20.1.2.2.15.206.23
        numOfEnclOnExpPortExceedsLimit OBJECT IDENTIFIER ::= { enclosure 23 }

        -- 1.3.6.1.4.1.2011.2.251.20.1.2.2.15.206.23.1
        numOfEnclOnExpPortExceedsLimit-Fault NOTIFICATION-TYPE
            OBJECTS { hwStorageAlarmReporting }
            STATUS current
            DESCRIPTION "The Number Of Disk Enclosures Connected To An Expansion Port Exceeds The System Specification"
            --#SEVERITY WARNING
            ::= { numOfEnclOnExpPortExceedsLimit 1 }

        -- 1.3.6.1.4.1.2011.2.251.20.1.2.2.15.206.23.2
        numOfEnclOnExpPortExceedsLimit-Resume NOTIFICATION-TYPE
            OBJECTS { hwStorageAlarmReporting }
            STATUS current
            DESCRIPTION "Recover: The Number Of Disk Enclosures Connected To An Expansion Port Exceeds The System Specification"
            --#SEVERITY INFORMATIONAL
            ::= { numOfEnclOnExpPortExceedsLimit 2 }

        -- 1.3.6.1.4.1.2011.2.251.20.1.2.2.15.206.42
        diskEnclosureIsSingleLink OBJECT IDENTIFIER ::= { enclosure 42 }

        -- 1.3.6.1.4.1.2011.2.251.20.1.2.2.15.206.42.1
        diskEnclosureIsSingleLink-Fault NOTIFICATION-TYPE
            OBJECTS { hwStorageAlarmReporting }
            STATUS current
            DESCRIPTION "Disk Enclosure Is Working In Single Link State"
            --#SEVERITY MAJOR
            ::= { diskEnclosureIsSingleLink 1 }

        -- 1.3.6.1.4.1.2011.2.251.20.1.2.2.15.206.42.2
        diskEnclosureIsSingleLink-Resume NOTIFICATION-TYPE
            OBJECTS { hwStorageAlarmReporting }
            STATUS current
            DESCRIPTION "Recover: Disk Enclosure Is Working In Single Link State"
            --#SEVERITY INFORMATIONAL
            ::= { diskEnclosureIsSingleLink 2 }

        -- 1.3.6.1.4.1.2011.2.251.20.1.2.2.15.206.43
        highDensityAreMixConnected OBJECT IDENTIFIER ::= { enclosure 43 }

        -- 1.3.6.1.4.1.2011.2.251.20.1.2.2.15.206.43.1
        highDensityAreMixConnected-Fault NOTIFICATION-TYPE
            OBJECTS { hwStorageAlarmReporting }
            STATUS current
            DESCRIPTION "From An Expansion Port, Disk Enclosures And HighDensity Disk Enclosures Are MixConnected"
            --#SEVERITY WARNING
            ::= { highDensityAreMixConnected 1 }

        -- 1.3.6.1.4.1.2011.2.251.20.1.2.2.15.206.43.2
        highDensityAreMixConnected-Resume NOTIFICATION-TYPE
            OBJECTS { hwStorageAlarmReporting }
            STATUS current
            DESCRIPTION "Recover: From An Expansion Port, Disk Enclosures And HighDensity Disk Enclosures Are MixConnected"
            --#SEVERITY INFORMATIONAL
            ::= { highDensityAreMixConnected 2 }

        -- 1.3.6.1.4.1.2011.2.251.20.1.2.2.15.206.46
        failedToMonitorTheRearPanel OBJECT IDENTIFIER ::= { enclosure 46 }

        -- 1.3.6.1.4.1.2011.2.251.20.1.2.2.15.206.46.1
        failedToMonitorTheRearPanel-Fault NOTIFICATION-TYPE
            OBJECTS { hwStorageAlarmReporting }
            STATUS current
            DESCRIPTION "The System Failed To Monitor The Rear Panel Of The Enclosure"
            --#SEVERITY CRITICAL
            ::= { failedToMonitorTheRearPanel 1 }

        -- 1.3.6.1.4.1.2011.2.251.20.1.2.2.15.206.46.2
        failedToMonitorTheRearPanel-Resume NOTIFICATION-TYPE
            OBJECTS { hwStorageAlarmReporting }
            STATUS current
            DESCRIPTION "Recover: The System Failed To Monitor The Rear Panel Of The Enclosure"
            --#SEVERITY INFORMATIONAL
            ::= { failedToMonitorTheRearPanel 2 }

        -- 1.3.6.1.4.1.2011.2.251.20.1.2.2.15.206.49
        enclosureIsFaulty OBJECT IDENTIFIER ::= { enclosure 49 }

        -- 1.3.6.1.4.1.2011.2.251.20.1.2.2.15.206.49.1
        enclosureIsFaulty-Fault NOTIFICATION-TYPE
            OBJECTS { hwStorageAlarmReporting }
            STATUS current
            DESCRIPTION "Faults Occurred On An Enclosure"
            --#SEVERITY MAJOR
            ::= { enclosureIsFaulty 1 }

        -- 1.3.6.1.4.1.2011.2.251.20.1.2.2.15.206.49.2
        enclosureIsFaulty-Resume NOTIFICATION-TYPE
            OBJECTS { hwStorageAlarmReporting }
            STATUS current
            DESCRIPTION "Recover: Faults Occurred On An Enclosure"
            --#SEVERITY INFORMATIONAL
            ::= { enclosureIsFaulty 2 }

        -- 1.3.6.1.4.1.2011.2.251.20.1.2.2.15.206.50
        enclosureIsUnrecognizable OBJECT IDENTIFIER ::= { enclosure 50 }

        -- 1.3.6.1.4.1.2011.2.251.20.1.2.2.15.206.50.1
        enclosureIsUnrecognizable-Fault NOTIFICATION-TYPE
            OBJECTS { hwStorageAlarmReporting }
            STATUS current
            DESCRIPTION "Failed To Identify A Controller Enclosure Or Disk Enclosure"
            --#SEVERITY MAJOR
            ::= { enclosureIsUnrecognizable 1 }

        -- 1.3.6.1.4.1.2011.2.251.20.1.2.2.15.206.50.2
        enclosureIsUnrecognizable-Resume NOTIFICATION-TYPE
            OBJECTS { hwStorageAlarmReporting }
            STATUS current
            DESCRIPTION "Recover: Failed To Identify A Controller Enclosure Or Disk Enclosure"
            --#SEVERITY INFORMATIONAL
            ::= { enclosureIsUnrecognizable 2 }

        -- 1.3.6.1.4.1.2011.2.251.20.1.2.2.15.206.52
        enclSpeedSmallerThanLoopSpeed OBJECT IDENTIFIER ::= { enclosure 52 }

        -- 1.3.6.1.4.1.2011.2.251.20.1.2.2.15.206.52.1
        enclSpeedSmallerThanLoopSpeed-Fault NOTIFICATION-TYPE
            OBJECTS { hwStorageAlarmReporting }
            STATUS current
            DESCRIPTION "The Disk Enclosure Speed Does Not Reach The Maximum Loop Speed"
            --#SEVERITY WARNING
            ::= { enclSpeedSmallerThanLoopSpeed 1 }

        -- 1.3.6.1.4.1.2011.2.251.20.1.2.2.15.206.52.2
        enclSpeedSmallerThanLoopSpeed-Resume NOTIFICATION-TYPE
            OBJECTS { hwStorageAlarmReporting }
            STATUS current
            DESCRIPTION "Recover: The Disk Enclosure Speed Does Not Reach The Maximum Loop Speed"
            --#SEVERITY INFORMATIONAL
            ::= { enclSpeedSmallerThanLoopSpeed 2 }

        -- 1.3.6.1.4.1.2011.2.251.20.1.2.2.15.206.59
        failedToMatchTheEnclosureType OBJECT IDENTIFIER ::= { enclosure 59 }

        -- 1.3.6.1.4.1.2011.2.251.20.1.2.2.15.206.59.1
        failedToMatchTheEnclosureType-Fault NOTIFICATION-TYPE
            OBJECTS { hwStorageAlarmReporting }
            STATUS current
            DESCRIPTION "The Enclosure Type Is Mismatched"
            --#SEVERITY WARNING
            ::= { failedToMatchTheEnclosureType 1 }

        -- 1.3.6.1.4.1.2011.2.251.20.1.2.2.15.206.59.2
        failedToMatchTheEnclosureType-Resume NOTIFICATION-TYPE
            OBJECTS { hwStorageAlarmReporting }
            STATUS current
            DESCRIPTION "Recover: The Enclosure Type Is Mismatched"
            --#SEVERITY INFORMATIONAL
            ::= { failedToMatchTheEnclosureType 2 }

        -- 1.3.6.1.4.1.2011.2.251.20.1.2.2.15.206.70
        theNumberOfDiskEnclosuresConnectedToAnExpansionPortExceedsTheSystemSpecification OBJECT IDENTIFIER ::= { enclosure 70 }

        -- 1.3.6.1.4.1.2011.2.251.20.1.2.2.15.206.70.1
        theNumberOfDiskEnclosuresConnectedToAnExpansionPortExceedsTheSystemSpecification-Fault NOTIFICATION-TYPE
            OBJECTS { hwStorageAlarmReporting }
            STATUS current
            DESCRIPTION "The Number Of Disk Enclosures Connected To An Expansion Port Exceeds The System Specification"
            --#SEVERITY WARNING
            ::= { theNumberOfDiskEnclosuresConnectedToAnExpansionPortExceedsTheSystemSpecification 1 }

        -- 1.3.6.1.4.1.2011.2.251.20.1.2.2.15.206.70.2
        theNumberOfDiskEnclosuresConnectedToAnExpansionPortExceedsTheSystemSpecification-Resume NOTIFICATION-TYPE
            OBJECTS { hwStorageAlarmReporting }
            STATUS current
            DESCRIPTION "Recover: The Number Of Disk Enclosures Connected To An Expansion Port Exceeds The System Specification"
            --#SEVERITY INFORMATIONAL
            ::= { theNumberOfDiskEnclosuresConnectedToAnExpansionPortExceedsTheSystemSpecification 2 }

        -- 1.3.6.1.4.1.2011.2.251.20.1.2.2.15.206.71
        anUnsupportedDiskEnclosureIsConnectedToTheSystem OBJECT IDENTIFIER ::= { enclosure 71 }

        -- 1.3.6.1.4.1.2011.2.251.20.1.2.2.15.206.71.1
        anUnsupportedDiskEnclosureIsConnectedToTheSystem-Fault NOTIFICATION-TYPE
            OBJECTS { hwStorageAlarmReporting }
            STATUS current
            DESCRIPTION "An Unsupported Disk Enclosure Is Connected To The System"
            --#SEVERITY MAJOR
            ::= { anUnsupportedDiskEnclosureIsConnectedToTheSystem 1 }

        -- 1.3.6.1.4.1.2011.2.251.20.1.2.2.15.206.71.2
        anUnsupportedDiskEnclosureIsConnectedToTheSystem-Resume NOTIFICATION-TYPE
            OBJECTS { hwStorageAlarmReporting }
            STATUS current
            DESCRIPTION "Recover: An Unsupported Disk Enclosure Is Connected To The System"
            --#SEVERITY INFORMATIONAL
            ::= { anUnsupportedDiskEnclosureIsConnectedToTheSystem 2 }

        -- 1.3.6.1.4.1.2011.2.251.20.1.2.2.15.206.72
        modelOfAnExpansionModuleInTheDiskEnclosureIsNotSupportedByTheSystem OBJECT IDENTIFIER ::= { enclosure 72 }

        -- 1.3.6.1.4.1.2011.2.251.20.1.2.2.15.206.72.1
        modelOfAnExpansionModuleInTheDiskEnclosureIsNotSupportedByTheSystem-Fault NOTIFICATION-TYPE
            OBJECTS { hwStorageAlarmReporting }
            STATUS current
            DESCRIPTION "Model Of An Expansion Module In The Disk Enclosure Is Not Supported By The System"
            --#SEVERITY WARNING
            ::= { modelOfAnExpansionModuleInTheDiskEnclosureIsNotSupportedByTheSystem 1 }

        -- 1.3.6.1.4.1.2011.2.251.20.1.2.2.15.206.72.2
        modelOfAnExpansionModuleInTheDiskEnclosureIsNotSupportedByTheSystem-Resume NOTIFICATION-TYPE
            OBJECTS { hwStorageAlarmReporting }
            STATUS current
            DESCRIPTION "Recover: Model Of An Expansion Module In The Disk Enclosure Is Not Supported By The System"
            --#SEVERITY INFORMATIONAL
            ::= { modelOfAnExpansionModuleInTheDiskEnclosureIsNotSupportedByTheSystem 2 }

        -- 1.3.6.1.4.1.2011.2.251.20.1.2.2.15.207
        controller OBJECT IDENTIFIER ::= { oidBasedTrap 207 }

        -- 1.3.6.1.4.1.2011.2.251.20.1.2.2.15.207.1
        sshServiceIsAbnormal OBJECT IDENTIFIER ::= { controller 1 }

        -- 1.3.6.1.4.1.2011.2.251.20.1.2.2.15.207.1.1
        sshServiceIsAbnormal-Fault NOTIFICATION-TYPE
            OBJECTS { hwStorageAlarmReporting }
            STATUS current
            DESCRIPTION "The SSH Service Is Abnormal"
            --#SEVERITY WARNING
            ::= { sshServiceIsAbnormal 1 }

        -- 1.3.6.1.4.1.2011.2.251.20.1.2.2.15.207.1.2
        sshServiceIsAbnormal-Resume NOTIFICATION-TYPE
            OBJECTS { hwStorageAlarmReporting }
            STATUS current
            DESCRIPTION "Recover: The SSH Service Is Abnormal"
            --#SEVERITY INFORMATIONAL
            ::= { sshServiceIsAbnormal 2 }

        -- 1.3.6.1.4.1.2011.2.251.20.1.2.2.15.207.2
        ftpServiceIsAbnormal OBJECT IDENTIFIER ::= { controller 2 }

        -- 1.3.6.1.4.1.2011.2.251.20.1.2.2.15.207.2.1
        ftpServiceIsAbnormal-Fault NOTIFICATION-TYPE
            OBJECTS { hwStorageAlarmReporting }
            STATUS current
            DESCRIPTION "The FTP Service Is Abnormal"
            --#SEVERITY WARNING
            ::= { ftpServiceIsAbnormal 1 }

        -- 1.3.6.1.4.1.2011.2.251.20.1.2.2.15.207.2.2
        ftpServiceIsAbnormal-Resume NOTIFICATION-TYPE
            OBJECTS { hwStorageAlarmReporting }
            STATUS current
            DESCRIPTION "Recover: The FTP Service Is Abnormal"
            --#SEVERITY INFORMATIONAL
            ::= { ftpServiceIsAbnormal 2 }

        -- 1.3.6.1.4.1.2011.2.251.20.1.2.2.15.207.5
        abnormalCommunicateBetweenCtrls OBJECT IDENTIFIER ::= { controller 5 }

        -- 1.3.6.1.4.1.2011.2.251.20.1.2.2.15.207.5.1
        abnormalCommunicateBetweenCtrls-Fault NOTIFICATION-TYPE
            OBJECTS { hwStorageAlarmReporting }
            STATUS current
            DESCRIPTION "Abnormal Communication Between Controllers"
            --#SEVERITY MAJOR
            ::= { abnormalCommunicateBetweenCtrls 1 }

        -- 1.3.6.1.4.1.2011.2.251.20.1.2.2.15.207.5.2
        abnormalCommunicateBetweenCtrls-Resume NOTIFICATION-TYPE
            OBJECTS { hwStorageAlarmReporting }
            STATUS current
            DESCRIPTION "Recover: Abnormal Communication Between Controllers"
            --#SEVERITY INFORMATIONAL
            ::= { abnormalCommunicateBetweenCtrls 2 }

        -- 1.3.6.1.4.1.2011.2.251.20.1.2.2.15.207.6
        controllerIsRemoved OBJECT IDENTIFIER ::= { controller 6 }

        -- 1.3.6.1.4.1.2011.2.251.20.1.2.2.15.207.6.1
        controllerIsRemoved-Fault NOTIFICATION-TYPE
            OBJECTS { hwStorageAlarmReporting }
            STATUS current
            DESCRIPTION "Controller Is Removed"
            --#SEVERITY MAJOR
            ::= { controllerIsRemoved 1 }

        -- 1.3.6.1.4.1.2011.2.251.20.1.2.2.15.207.6.2
        controllerIsRemoved-Resume NOTIFICATION-TYPE
            OBJECTS { hwStorageAlarmReporting }
            STATUS current
            DESCRIPTION "Recover: Controller Is Removed"
            --#SEVERITY INFORMATIONAL
            ::= { controllerIsRemoved 2 }

        -- 1.3.6.1.4.1.2011.2.251.20.1.2.2.15.207.7
        directoryIsOversized1 OBJECT IDENTIFIER ::= { controller 7 }

        -- 1.3.6.1.4.1.2011.2.251.20.1.2.2.15.207.7.1
        directoryIsOversized1-Fault NOTIFICATION-TYPE
            OBJECTS { hwStorageAlarmReporting }
            STATUS current
            DESCRIPTION "A Directory Is Oversized"
            --#SEVERITY WARNING
            ::= { directoryIsOversized1 1 }

        -- 1.3.6.1.4.1.2011.2.251.20.1.2.2.15.207.7.2
        directoryIsOversized1-Resume NOTIFICATION-TYPE
            OBJECTS { hwStorageAlarmReporting }
            STATUS current
            DESCRIPTION "Recover: A Directory Is Oversized"
            --#SEVERITY INFORMATIONAL
            ::= { directoryIsOversized1 2 }

        -- 1.3.6.1.4.1.2011.2.251.20.1.2.2.15.207.8
        excessiveFilesExistInADirectory OBJECT IDENTIFIER ::= { controller 8 }

        -- 1.3.6.1.4.1.2011.2.251.20.1.2.2.15.207.8.1
        excessiveFilesExistInADirectory-Fault NOTIFICATION-TYPE
            OBJECTS { hwStorageAlarmReporting }
            STATUS current
            DESCRIPTION "Excessive Files Exist In A Directory"
            --#SEVERITY WARNING
            ::= { excessiveFilesExistInADirectory 1 }

        -- 1.3.6.1.4.1.2011.2.251.20.1.2.2.15.207.8.2
        excessiveFilesExistInADirectory-Resume NOTIFICATION-TYPE
            OBJECTS { hwStorageAlarmReporting }
            STATUS current
            DESCRIPTION "Recover: Excessive Files Exist In A Directory"
            --#SEVERITY INFORMATIONAL
            ::= { excessiveFilesExistInADirectory 2 }

        -- 1.3.6.1.4.1.2011.2.251.20.1.2.2.15.207.9
        ntpSynchronizationIsAbnormal OBJECT IDENTIFIER ::= { controller 9 }

        -- 1.3.6.1.4.1.2011.2.251.20.1.2.2.15.207.9.1
        ntpSynchronizationIsAbnormal-Fault NOTIFICATION-TYPE
            OBJECTS { hwStorageAlarmReporting }
            STATUS current
            DESCRIPTION "NTP Time Synchronization Is Abnormal"
            --#SEVERITY WARNING
            ::= { ntpSynchronizationIsAbnormal 1 }

        -- 1.3.6.1.4.1.2011.2.251.20.1.2.2.15.207.9.2
        ntpSynchronizationIsAbnormal-Resume NOTIFICATION-TYPE
            OBJECTS { hwStorageAlarmReporting }
            STATUS current
            DESCRIPTION "Recover: NTP Time Synchronization Is Abnormal"
            --#SEVERITY INFORMATIONAL
            ::= { ntpSynchronizationIsAbnormal 2 }

        -- 1.3.6.1.4.1.2011.2.251.20.1.2.2.15.207.10
        controllerNetStackIsAbnormal OBJECT IDENTIFIER ::= { controller 10 }

        -- 1.3.6.1.4.1.2011.2.251.20.1.2.2.15.207.10.1
        controllerNetStackIsAbnormal-Fault NOTIFICATION-TYPE
            OBJECTS { hwStorageAlarmReporting }
            STATUS current
            DESCRIPTION "The Network Protocol Stack Of A Controller Is Abnormal"
            --#SEVERITY CRITICAL
            ::= { controllerNetStackIsAbnormal 1 }

        -- 1.3.6.1.4.1.2011.2.251.20.1.2.2.15.207.10.2
        controllerNetStackIsAbnormal-Resume NOTIFICATION-TYPE
            OBJECTS { hwStorageAlarmReporting }
            STATUS current
            DESCRIPTION "Recover: The Network Protocol Stack Of A Controller Is Abnormal"
            --#SEVERITY INFORMATIONAL
            ::= { controllerNetStackIsAbnormal 2 }

        -- 1.3.6.1.4.1.2011.2.251.20.1.2.2.15.207.11
        processCpuUsageIsTooHigh OBJECT IDENTIFIER ::= { controller 11 }

        -- 1.3.6.1.4.1.2011.2.251.20.1.2.2.15.207.11.1
        processCpuUsageIsTooHigh-Fault NOTIFICATION-TYPE
            OBJECTS { hwStorageAlarmReporting }
            STATUS current
            DESCRIPTION "The Process CPU Utilization Is Too High"
            --#SEVERITY WARNING
            ::= { processCpuUsageIsTooHigh 1 }

        -- 1.3.6.1.4.1.2011.2.251.20.1.2.2.15.207.11.2
        processCpuUsageIsTooHigh-Resume NOTIFICATION-TYPE
            OBJECTS { hwStorageAlarmReporting }
            STATUS current
            DESCRIPTION "Recover: The Process CPU Utilization Is Too High"
            --#SEVERITY INFORMATIONAL
            ::= { processCpuUsageIsTooHigh 2 }

        -- 1.3.6.1.4.1.2011.2.251.20.1.2.2.15.207.12
        processMemoryUsageIsTooHigh OBJECT IDENTIFIER ::= { controller 12 }

        -- 1.3.6.1.4.1.2011.2.251.20.1.2.2.15.207.12.1
        processMemoryUsageIsTooHigh-Fault NOTIFICATION-TYPE
            OBJECTS { hwStorageAlarmReporting }
            STATUS current
            DESCRIPTION "The Process Memory Usage Is Too High"
            --#SEVERITY WARNING
            ::= { processMemoryUsageIsTooHigh 1 }

        -- 1.3.6.1.4.1.2011.2.251.20.1.2.2.15.207.12.2
        processMemoryUsageIsTooHigh-Resume NOTIFICATION-TYPE
            OBJECTS { hwStorageAlarmReporting }
            STATUS current
            DESCRIPTION "Recover: The Process Memory Usage Is Too High"
            --#SEVERITY INFORMATIONAL
            ::= { processMemoryUsageIsTooHigh 2 }

        -- 1.3.6.1.4.1.2011.2.251.20.1.2.2.15.207.13
        cpuUsageTooHigh OBJECT IDENTIFIER ::= { controller 13 }

        -- 1.3.6.1.4.1.2011.2.251.20.1.2.2.15.207.13.1
        cpuUsageTooHigh-Fault NOTIFICATION-TYPE
            OBJECTS { hwStorageAlarmReporting }
            STATUS current
            DESCRIPTION "CPU Utilization Is Too High"
            --#SEVERITY WARNING
            ::= { cpuUsageTooHigh 1 }

        -- 1.3.6.1.4.1.2011.2.251.20.1.2.2.15.207.13.2
        cpuUsageTooHigh-Resume NOTIFICATION-TYPE
            OBJECTS { hwStorageAlarmReporting }
            STATUS current
            DESCRIPTION "Recover: CPU Utilization Is Too High"
            --#SEVERITY INFORMATIONAL
            ::= { cpuUsageTooHigh 2 }

        -- 1.3.6.1.4.1.2011.2.251.20.1.2.2.15.207.14
        memoryUsageTooHigh OBJECT IDENTIFIER ::= { controller 14 }

        -- 1.3.6.1.4.1.2011.2.251.20.1.2.2.15.207.14.1
        memoryUsageTooHigh-Fault NOTIFICATION-TYPE
            OBJECTS { hwStorageAlarmReporting }
            STATUS current
            DESCRIPTION "Memory Utilization Is Too High"
            --#SEVERITY WARNING
            ::= { memoryUsageTooHigh 1 }

        -- 1.3.6.1.4.1.2011.2.251.20.1.2.2.15.207.14.2
        memoryUsageTooHigh-Resume NOTIFICATION-TYPE
            OBJECTS { hwStorageAlarmReporting }
            STATUS current
            DESCRIPTION "Recover: Memory Utilization Is Too High"
            --#SEVERITY INFORMATIONAL
            ::= { memoryUsageTooHigh 2 }

        -- 1.3.6.1.4.1.2011.2.251.20.1.2.2.15.207.16
        theCcdbServiceIsAbnormal OBJECT IDENTIFIER ::= { controller 16 }

        -- 1.3.6.1.4.1.2011.2.251.20.1.2.2.15.207.16.1
        theCcdbServiceIsAbnormal-Fault NOTIFICATION-TYPE
            OBJECTS { hwStorageAlarmReporting }
            STATUS current
            DESCRIPTION "The CCDB Service Is Abnormal"
            --#SEVERITY MAJOR
            ::= { theCcdbServiceIsAbnormal 1 }

        -- 1.3.6.1.4.1.2011.2.251.20.1.2.2.15.207.16.2
        theCcdbServiceIsAbnormal-Resume NOTIFICATION-TYPE
            OBJECTS { hwStorageAlarmReporting }
            STATUS current
            DESCRIPTION "Recover: The CCDB Service Is Abnormal"
            --#SEVERITY INFORMATIONAL
            ::= { theCcdbServiceIsAbnormal 2 }

        -- 1.3.6.1.4.1.2011.2.251.20.1.2.2.15.207.17
        theCcdbServiceDegradation OBJECT IDENTIFIER ::= { controller 17 }

        -- 1.3.6.1.4.1.2011.2.251.20.1.2.2.15.207.17.1
        theCcdbServiceDegradation-Fault NOTIFICATION-TYPE
            OBJECTS { hwStorageAlarmReporting }
            STATUS current
            DESCRIPTION "The CCDB Service Is Degraded"
            --#SEVERITY MAJOR
            ::= { theCcdbServiceDegradation 1 }

        -- 1.3.6.1.4.1.2011.2.251.20.1.2.2.15.207.17.2
        theCcdbServiceDegradation-Resume NOTIFICATION-TYPE
            OBJECTS { hwStorageAlarmReporting }
            STATUS current
            DESCRIPTION "Recover: The CCDB Service Is Degraded"
            --#SEVERITY INFORMATIONAL
            ::= { theCcdbServiceDegradation 2 }

        -- 1.3.6.1.4.1.2011.2.251.20.1.2.2.15.207.21
        monitorControllersFailed OBJECT IDENTIFIER ::= { controller 21 }

        -- 1.3.6.1.4.1.2011.2.251.20.1.2.2.15.207.21.1
        monitorControllersFailed-Fault NOTIFICATION-TYPE
            OBJECTS { hwStorageAlarmReporting }
            STATUS current
            DESCRIPTION "Failed To Monitor Controllers Enclosure"
            --#SEVERITY CRITICAL
            ::= { monitorControllersFailed 1 }

        -- 1.3.6.1.4.1.2011.2.251.20.1.2.2.15.207.21.2
        monitorControllersFailed-Resume NOTIFICATION-TYPE
            OBJECTS { hwStorageAlarmReporting }
            STATUS current
            DESCRIPTION "Recover: Failed To Monitor Controllers Enclosure"
            --#SEVERITY INFORMATIONAL
            ::= { monitorControllersFailed 2 }

        -- 1.3.6.1.4.1.2011.2.251.20.1.2.2.15.207.47
        contorllersMemorySizeDiffer OBJECT IDENTIFIER ::= { controller 47 }

        -- 1.3.6.1.4.1.2011.2.251.20.1.2.2.15.207.47.1
        contorllersMemorySizeDiffer-Fault NOTIFICATION-TYPE
            OBJECTS { hwStorageAlarmReporting }
            STATUS current
            DESCRIPTION "Inconsistent Memory Capacities Between Controllers"
            --#SEVERITY MAJOR
            ::= { contorllersMemorySizeDiffer 1 }

        -- 1.3.6.1.4.1.2011.2.251.20.1.2.2.15.207.47.2
        contorllersMemorySizeDiffer-Resume NOTIFICATION-TYPE
            OBJECTS { hwStorageAlarmReporting }
            STATUS current
            DESCRIPTION "Recover: Inconsistent Memory Capacities Between Controllers"
            --#SEVERITY INFORMATIONAL
            ::= { contorllersMemorySizeDiffer 2 }

        -- 1.3.6.1.4.1.2011.2.251.20.1.2.2.15.207.54
        controllerServicesAbnormal OBJECT IDENTIFIER ::= { controller 54 }

        -- 1.3.6.1.4.1.2011.2.251.20.1.2.2.15.207.54.1
        controllerServicesAbnormal-Fault NOTIFICATION-TYPE
            OBJECTS { hwStorageAlarmReporting }
            STATUS current
            DESCRIPTION "Controller Services Are Abnormal"
            --#SEVERITY CRITICAL
            ::= { controllerServicesAbnormal 1 }

        -- 1.3.6.1.4.1.2011.2.251.20.1.2.2.15.207.54.2
        controllerServicesAbnormal-Resume NOTIFICATION-TYPE
            OBJECTS { hwStorageAlarmReporting }
            STATUS current
            DESCRIPTION "Recover: Controller Services Are Abnormal"
            --#SEVERITY INFORMATIONAL
            ::= { controllerServicesAbnormal 2 }

        -- 1.3.6.1.4.1.2011.2.251.20.1.2.2.15.207.93
        cpuUsageIsTooHigh OBJECT IDENTIFIER ::= { controller 93 }

        -- 1.3.6.1.4.1.2011.2.251.20.1.2.2.15.207.93.1
        cpuUsageIsTooHigh-Fault NOTIFICATION-TYPE
            OBJECTS { hwStorageAlarmReporting }
            STATUS current
            DESCRIPTION "CPU Utilization Is Too High"
            --#SEVERITY WARNING
            ::= { cpuUsageIsTooHigh 1 }

        -- 1.3.6.1.4.1.2011.2.251.20.1.2.2.15.207.93.2
        cpuUsageIsTooHigh-Resume NOTIFICATION-TYPE
            OBJECTS { hwStorageAlarmReporting }
            STATUS current
            DESCRIPTION "Recover: CPU Utilization Is Too High"
            --#SEVERITY INFORMATIONAL
            ::= { cpuUsageIsTooHigh 2 }

        -- 1.3.6.1.4.1.2011.2.251.20.1.2.2.15.207.94
        remainAvailableMemoryTooLow OBJECT IDENTIFIER ::= { controller 94 }

        -- 1.3.6.1.4.1.2011.2.251.20.1.2.2.15.207.94.1
        remainAvailableMemoryTooLow-Fault NOTIFICATION-TYPE
            OBJECTS { hwStorageAlarmReporting }
            STATUS current
            DESCRIPTION "Remaining Available Memory Is Too Low"
            --#SEVERITY WARNING
            ::= { remainAvailableMemoryTooLow 1 }

        -- 1.3.6.1.4.1.2011.2.251.20.1.2.2.15.207.94.2
        remainAvailableMemoryTooLow-Resume NOTIFICATION-TYPE
            OBJECTS { hwStorageAlarmReporting }
            STATUS current
            DESCRIPTION "Recover: Remaining Available Memory Is Too Low"
            --#SEVERITY INFORMATIONAL
            ::= { remainAvailableMemoryTooLow 2 }

        -- 1.3.6.1.4.1.2011.2.251.20.1.2.2.15.207.95
        controllerIsFaulty OBJECT IDENTIFIER ::= { controller 95 }

        -- 1.3.6.1.4.1.2011.2.251.20.1.2.2.15.207.95.1
        controllerIsFaulty-Fault NOTIFICATION-TYPE
            OBJECTS { hwStorageAlarmReporting }
            STATUS current
            DESCRIPTION "The Controller Is Faulty"
            --#SEVERITY MAJOR
            ::= { controllerIsFaulty 1 }

        -- 1.3.6.1.4.1.2011.2.251.20.1.2.2.15.207.95.2
        controllerIsFaulty-Resume NOTIFICATION-TYPE
            OBJECTS { hwStorageAlarmReporting }
            STATUS current
            DESCRIPTION "Recover: The Controller Is Faulty"
            --#SEVERITY INFORMATIONAL
            ::= { controllerIsFaulty 2 }

        -- 1.3.6.1.4.1.2011.2.251.20.1.2.2.15.207.96
        memoryCapacityIsNotSupported OBJECT IDENTIFIER ::= { controller 96 }

        -- 1.3.6.1.4.1.2011.2.251.20.1.2.2.15.207.96.1
        memoryCapacityIsNotSupported-Fault NOTIFICATION-TYPE
            OBJECTS { hwStorageAlarmReporting }
            STATUS current
            DESCRIPTION "Incorrect Controller Memory Capacity"
            --#SEVERITY MAJOR
            ::= { memoryCapacityIsNotSupported 1 }

        -- 1.3.6.1.4.1.2011.2.251.20.1.2.2.15.207.96.2
        memoryCapacityIsNotSupported-Resume NOTIFICATION-TYPE
            OBJECTS { hwStorageAlarmReporting }
            STATUS current
            DESCRIPTION "Recover: Incorrect Controller Memory Capacity"
            --#SEVERITY INFORMATIONAL
            ::= { memoryCapacityIsNotSupported 2 }

        -- 1.3.6.1.4.1.2011.2.251.20.1.2.2.15.207.97
        ctrlAndMgtCommunicateLinkFault2 OBJECT IDENTIFIER ::= { controller 97 }

        -- 1.3.6.1.4.1.2011.2.251.20.1.2.2.15.207.97.1
        ctrlAndMgtCommunicateLinkFault2-Fault NOTIFICATION-TYPE
            OBJECTS { hwStorageAlarmReporting }
            STATUS current
            DESCRIPTION "Communication Link Fault Among The Controller And Management Modules"
            --#SEVERITY MAJOR
            ::= { ctrlAndMgtCommunicateLinkFault2 1 }

        -- 1.3.6.1.4.1.2011.2.251.20.1.2.2.15.207.97.2
        ctrlAndMgtCommunicateLinkFault2-Resume NOTIFICATION-TYPE
            OBJECTS { hwStorageAlarmReporting }
            STATUS current
            DESCRIPTION "Recover: Communication Link Fault Among The Controller And Management Modules"
            --#SEVERITY INFORMATIONAL
            ::= { ctrlAndMgtCommunicateLinkFault2 2 }

        -- 1.3.6.1.4.1.2011.2.251.20.1.2.2.15.207.112
        theControllerIsBeingRepaired1 OBJECT IDENTIFIER ::= { controller 112 }

        -- 1.3.6.1.4.1.2011.2.251.20.1.2.2.15.207.112.1
        theControllerIsBeingRepaired1-Fault NOTIFICATION-TYPE
            OBJECTS { hwStorageAlarmReporting }
            STATUS current
            DESCRIPTION "The Controller Is Being Repaired"
            --#SEVERITY WARNING
            ::= { theControllerIsBeingRepaired1 1 }

        -- 1.3.6.1.4.1.2011.2.251.20.1.2.2.15.207.112.2
        theControllerIsBeingRepaired1-Resume NOTIFICATION-TYPE
            OBJECTS { hwStorageAlarmReporting }
            STATUS current
            DESCRIPTION "Recover: The Controller Is Being Repaired"
            --#SEVERITY INFORMATIONAL
            ::= { theControllerIsBeingRepaired1 2 }

        -- 1.3.6.1.4.1.2011.2.251.20.1.2.2.15.207.114
        controllerTypesAreDifferent OBJECT IDENTIFIER ::= { controller 114 }

        -- 1.3.6.1.4.1.2011.2.251.20.1.2.2.15.207.114.1
        controllerTypesAreDifferent-Fault NOTIFICATION-TYPE
            OBJECTS { hwStorageAlarmReporting }
            STATUS current
            DESCRIPTION "Types Of Controllers In The Enclosure Are Different"
            --#SEVERITY MAJOR
            ::= { controllerTypesAreDifferent 1 }

        -- 1.3.6.1.4.1.2011.2.251.20.1.2.2.15.207.114.2
        controllerTypesAreDifferent-Resume NOTIFICATION-TYPE
            OBJECTS { hwStorageAlarmReporting }
            STATUS current
            DESCRIPTION "Recover: Types Of Controllers In The Enclosure Are Different"
            --#SEVERITY INFORMATIONAL
            ::= { controllerTypesAreDifferent 2 }

        -- 1.3.6.1.4.1.2011.2.251.20.1.2.2.15.207.115
        theControllerFailsToBePoweredOn OBJECT IDENTIFIER ::= { controller 115 }

        -- 1.3.6.1.4.1.2011.2.251.20.1.2.2.15.207.115.1
        theControllerFailsToBePoweredOn-Fault NOTIFICATION-TYPE
            OBJECTS { hwStorageAlarmReporting }
            STATUS current
            DESCRIPTION "The Controller Fails To Be Powered On"
            --#SEVERITY CRITICAL
            ::= { theControllerFailsToBePoweredOn 1 }

        -- 1.3.6.1.4.1.2011.2.251.20.1.2.2.15.207.115.2
        theControllerFailsToBePoweredOn-Resume NOTIFICATION-TYPE
            OBJECTS { hwStorageAlarmReporting }
            STATUS current
            DESCRIPTION "Recover: The Controller Fails To Be Powered On"
            --#SEVERITY INFORMATIONAL
            ::= { theControllerFailsToBePoweredOn 2 }

        -- 1.3.6.1.4.1.2011.2.251.20.1.2.2.15.207.116
        controllerRunningStatusIsAbnormal OBJECT IDENTIFIER ::= { controller 116 }

        -- 1.3.6.1.4.1.2011.2.251.20.1.2.2.15.207.116.1
        controllerRunningStatusIsAbnormal-Fault NOTIFICATION-TYPE
            OBJECTS { hwStorageAlarmReporting }
            STATUS current
            DESCRIPTION "Controller Running Status Is Abnormal"
            --#SEVERITY CRITICAL
            ::= { controllerRunningStatusIsAbnormal 1 }

        -- 1.3.6.1.4.1.2011.2.251.20.1.2.2.15.207.116.2
        controllerRunningStatusIsAbnormal-Resume NOTIFICATION-TYPE
            OBJECTS { hwStorageAlarmReporting }
            STATUS current
            DESCRIPTION "Recover: Controller Running Status Is Abnormal"
            --#SEVERITY INFORMATIONAL
            ::= { controllerRunningStatusIsAbnormal 2 }

        -- 1.3.6.1.4.1.2011.2.251.20.1.2.2.15.207.118
        theControllerIsBeingRepaired3 OBJECT IDENTIFIER ::= { controller 118 }

        -- 1.3.6.1.4.1.2011.2.251.20.1.2.2.15.207.118.1
        theControllerIsBeingRepaired3-Fault NOTIFICATION-TYPE
            OBJECTS { hwStorageAlarmReporting }
            STATUS current
            DESCRIPTION "The Controller Is Being Repaired"
            --#SEVERITY WARNING
            ::= { theControllerIsBeingRepaired3 1 }

        -- 1.3.6.1.4.1.2011.2.251.20.1.2.2.15.207.118.2
        theControllerIsBeingRepaired3-Resume NOTIFICATION-TYPE
            OBJECTS { hwStorageAlarmReporting }
            STATUS current
            DESCRIPTION "Recover: The Controller Is Being Repaired"
            --#SEVERITY INFORMATIONAL
            ::= { theControllerIsBeingRepaired3 2 }

        -- 1.3.6.1.4.1.2011.2.251.20.1.2.2.15.207.119
        failedToMonitorTheController OBJECT IDENTIFIER ::= { controller 119 }

        -- 1.3.6.1.4.1.2011.2.251.20.1.2.2.15.207.119.1
        failedToMonitorTheController-Fault NOTIFICATION-TYPE
            OBJECTS { hwStorageAlarmReporting }
            STATUS current
            DESCRIPTION "Failed To Monitor The Controller"
            --#SEVERITY CRITICAL
            ::= { failedToMonitorTheController 1 }

        -- 1.3.6.1.4.1.2011.2.251.20.1.2.2.15.207.119.2
        failedToMonitorTheController-Resume NOTIFICATION-TYPE
            OBJECTS { hwStorageAlarmReporting }
            STATUS current
            DESCRIPTION "Recover: Failed To Monitor The Controller"
            --#SEVERITY INFORMATIONAL
            ::= { failedToMonitorTheController 2 }

        -- 1.3.6.1.4.1.2011.2.251.20.1.2.2.15.207.120
        ctlI2cCommuError OBJECT IDENTIFIER ::= { controller 120 }

        -- 1.3.6.1.4.1.2011.2.251.20.1.2.2.15.207.120.1
        ctlI2cCommuError-Fault NOTIFICATION-TYPE
            OBJECTS { hwStorageAlarmReporting }
            STATUS current
            DESCRIPTION "The Monitoring Link Between The Controller And Enclosure Is Faulty"
            --#SEVERITY MAJOR
            ::= { ctlI2cCommuError 1 }

        -- 1.3.6.1.4.1.2011.2.251.20.1.2.2.15.207.120.2
        ctlI2cCommuError-Resume NOTIFICATION-TYPE
            OBJECTS { hwStorageAlarmReporting }
            STATUS current
            DESCRIPTION "Recover: The Monitoring Link Between The Controller And Enclosure Is Faulty"
            --#SEVERITY INFORMATIONAL
            ::= { ctlI2cCommuError 2 }

        -- 1.3.6.1.4.1.2011.2.251.20.1.2.2.15.207.121
        controllerProtectWrite2 OBJECT IDENTIFIER ::= { controller 121 }

        -- 1.3.6.1.4.1.2011.2.251.20.1.2.2.15.207.121.1
        controllerProtectWrite2-Fault NOTIFICATION-TYPE
            OBJECTS { hwStorageAlarmReporting }
            STATUS current
            DESCRIPTION "Write Protection Is Enabled On A Controller"
            --#SEVERITY MAJOR
            ::= { controllerProtectWrite2 1 }

        -- 1.3.6.1.4.1.2011.2.251.20.1.2.2.15.207.121.2
        controllerProtectWrite2-Resume NOTIFICATION-TYPE
            OBJECTS { hwStorageAlarmReporting }
            STATUS current
            DESCRIPTION "Recover: Write Protection Is Enabled On A Controller"
            --#SEVERITY INFORMATIONAL
            ::= { controllerProtectWrite2 2 }

        -- 1.3.6.1.4.1.2011.2.251.20.1.2.2.15.207.122
        controllerProtectWrite1 OBJECT IDENTIFIER ::= { controller 122 }

        -- 1.3.6.1.4.1.2011.2.251.20.1.2.2.15.207.122.1
        controllerProtectWrite1-Fault NOTIFICATION-TYPE
            OBJECTS { hwStorageAlarmReporting }
            STATUS current
            DESCRIPTION "Write Protection Is Enabled On A Controller"
            --#SEVERITY MAJOR
            ::= { controllerProtectWrite1 1 }

        -- 1.3.6.1.4.1.2011.2.251.20.1.2.2.15.207.122.2
        controllerProtectWrite1-Resume NOTIFICATION-TYPE
            OBJECTS { hwStorageAlarmReporting }
            STATUS current
            DESCRIPTION "Recover: Write Protection Is Enabled On A Controller"
            --#SEVERITY INFORMATIONAL
            ::= { controllerProtectWrite1 2 }

        -- 1.3.6.1.4.1.2011.2.251.20.1.2.2.15.207.124
        controllerSoltIDIsIncorrect OBJECT IDENTIFIER ::= { controller 124 }

        -- 1.3.6.1.4.1.2011.2.251.20.1.2.2.15.207.124.1
        controllerSoltIDIsIncorrect-Fault NOTIFICATION-TYPE
            OBJECTS { hwStorageAlarmReporting }
            STATUS current
            DESCRIPTION "The Slot ID Of The Controller Module Is Incorrect"
            --#SEVERITY MAJOR
            ::= { controllerSoltIDIsIncorrect 1 }

        -- 1.3.6.1.4.1.2011.2.251.20.1.2.2.15.207.124.2
        controllerSoltIDIsIncorrect-Resume NOTIFICATION-TYPE
            OBJECTS { hwStorageAlarmReporting }
            STATUS current
            DESCRIPTION "Recover: The Slot ID Of The Controller Module Is Incorrect"
            --#SEVERITY INFORMATIONAL
            ::= { controllerSoltIDIsIncorrect 2 }

        -- 1.3.6.1.4.1.2011.2.251.20.1.2.2.15.207.125
        theControllerIsBeingRepaired2 OBJECT IDENTIFIER ::= { controller 125 }

        -- 1.3.6.1.4.1.2011.2.251.20.1.2.2.15.207.125.1
        theControllerIsBeingRepaired2-Fault NOTIFICATION-TYPE
            OBJECTS { hwStorageAlarmReporting }
            STATUS current
            DESCRIPTION "The Controller Is Being Repaired"
            --#SEVERITY WARNING
            ::= { theControllerIsBeingRepaired2 1 }

        -- 1.3.6.1.4.1.2011.2.251.20.1.2.2.15.207.125.2
        theControllerIsBeingRepaired2-Resume NOTIFICATION-TYPE
            OBJECTS { hwStorageAlarmReporting }
            STATUS current
            DESCRIPTION "Recover: The Controller Is Being Repaired"
            --#SEVERITY INFORMATIONAL
            ::= { theControllerIsBeingRepaired2 2 }

        -- 1.3.6.1.4.1.2011.2.251.20.1.2.2.15.207.126
        theControllerIsBeingRepaired OBJECT IDENTIFIER ::= { controller 126 }

        -- 1.3.6.1.4.1.2011.2.251.20.1.2.2.15.207.126.1
        theControllerIsBeingRepaired-Fault NOTIFICATION-TYPE
            OBJECTS { hwStorageAlarmReporting }
            STATUS current
            DESCRIPTION "The Controller Is Being Repaired"
            --#SEVERITY WARNING
            ::= { theControllerIsBeingRepaired 1 }

        -- 1.3.6.1.4.1.2011.2.251.20.1.2.2.15.207.126.2
        theControllerIsBeingRepaired-Resume NOTIFICATION-TYPE
            OBJECTS { hwStorageAlarmReporting }
            STATUS current
            DESCRIPTION "Recover: The Controller Is Being Repaired"
            --#SEVERITY INFORMATIONAL
            ::= { theControllerIsBeingRepaired 2 }

        -- 1.3.6.1.4.1.2011.2.251.20.1.2.2.15.207.128
        theControllerPoweronTimesOut OBJECT IDENTIFIER ::= { controller 128 }

        -- 1.3.6.1.4.1.2011.2.251.20.1.2.2.15.207.128.1
        theControllerPoweronTimesOut-Fault NOTIFICATION-TYPE
            OBJECTS { hwStorageAlarmReporting }
            STATUS current
            DESCRIPTION "The Controller Poweron Times Out"
            --#SEVERITY CRITICAL
            ::= { theControllerPoweronTimesOut 1 }

        -- 1.3.6.1.4.1.2011.2.251.20.1.2.2.15.207.128.2
        theControllerPoweronTimesOut-Resume NOTIFICATION-TYPE
            OBJECTS { hwStorageAlarmReporting }
            STATUS current
            DESCRIPTION "Recover: The Controller Poweron Times Out"
            --#SEVERITY INFORMATIONAL
            ::= { theControllerPoweronTimesOut 2 }

        -- 1.3.6.1.4.1.2011.2.251.20.1.2.2.15.207.131
        theControllerFailedToBePoweredOn OBJECT IDENTIFIER ::= { controller 131 }

        -- 1.3.6.1.4.1.2011.2.251.20.1.2.2.15.207.131.1
        theControllerFailedToBePoweredOn-Fault NOTIFICATION-TYPE
            OBJECTS { hwStorageAlarmReporting }
            STATUS current
            DESCRIPTION "The Controller Failed To Be Powered On"
            --#SEVERITY CRITICAL
            ::= { theControllerFailedToBePoweredOn 1 }

        -- 1.3.6.1.4.1.2011.2.251.20.1.2.2.15.207.131.2
        theControllerFailedToBePoweredOn-Resume NOTIFICATION-TYPE
            OBJECTS { hwStorageAlarmReporting }
            STATUS current
            DESCRIPTION "Recover: The Controller Failed To Be Powered On"
            --#SEVERITY INFORMATIONAL
            ::= { theControllerFailedToBePoweredOn 2 }

        -- 1.3.6.1.4.1.2011.2.251.20.1.2.2.15.207.134
        ctrlHeatRemovalSysFault OBJECT IDENTIFIER ::= { controller 134 }

        -- 1.3.6.1.4.1.2011.2.251.20.1.2.2.15.207.134.1
        ctrlHeatRemovalSysFault-Fault NOTIFICATION-TYPE
            OBJECTS { hwStorageAlarmReporting }
            STATUS current
            DESCRIPTION "Heat Dissipation System Of The Controller Is Faulty"
            --#SEVERITY MAJOR
            ::= { ctrlHeatRemovalSysFault 1 }

        -- 1.3.6.1.4.1.2011.2.251.20.1.2.2.15.207.134.2
        ctrlHeatRemovalSysFault-Resume NOTIFICATION-TYPE
            OBJECTS { hwStorageAlarmReporting }
            STATUS current
            DESCRIPTION "Recover: Heat Dissipation System Of The Controller Is Faulty"
            --#SEVERITY INFORMATIONAL
            ::= { ctrlHeatRemovalSysFault 2 }

        -- 1.3.6.1.4.1.2011.2.251.20.1.2.2.15.207.135
        connOfControllerExceedUpperLimit OBJECT IDENTIFIER ::= { controller 135 }

        -- 1.3.6.1.4.1.2011.2.251.20.1.2.2.15.207.135.1
        connOfControllerExceedUpperLimit-Fault NOTIFICATION-TYPE
            OBJECTS { hwStorageAlarmReporting }
            STATUS current
            DESCRIPTION "The Number Of ISCSI Initiator Connections On A Controller Exceeds The Upper Limit"
            --#SEVERITY MAJOR
            ::= { connOfControllerExceedUpperLimit 1 }

        -- 1.3.6.1.4.1.2011.2.251.20.1.2.2.15.207.135.2
        connOfControllerExceedUpperLimit-Resume NOTIFICATION-TYPE
            OBJECTS { hwStorageAlarmReporting }
            STATUS current
            DESCRIPTION "Recover: The Number Of ISCSI Initiator Connections On A Controller Exceeds The Upper Limit"
            --#SEVERITY INFORMATIONAL
            ::= { connOfControllerExceedUpperLimit 2 }

        -- 1.3.6.1.4.1.2011.2.251.20.1.2.2.15.207.136
        cmdOfControllerExceedUpperLimit OBJECT IDENTIFIER ::= { controller 136 }

        -- 1.3.6.1.4.1.2011.2.251.20.1.2.2.15.207.136.1
        cmdOfControllerExceedUpperLimit-Fault NOTIFICATION-TYPE
            OBJECTS { hwStorageAlarmReporting }
            STATUS current
            DESCRIPTION "The Number Of ISCSI Commands On A Controller Exceeds The Upper Limit"
            --#SEVERITY MAJOR
            ::= { cmdOfControllerExceedUpperLimit 1 }

        -- 1.3.6.1.4.1.2011.2.251.20.1.2.2.15.207.136.2
        cmdOfControllerExceedUpperLimit-Resume NOTIFICATION-TYPE
            OBJECTS { hwStorageAlarmReporting }
            STATUS current
            DESCRIPTION "Recover: The Number Of ISCSI Commands On A Controller Exceeds The Upper Limit"
            --#SEVERITY INFORMATIONAL
            ::= { cmdOfControllerExceedUpperLimit 2 }

        -- 1.3.6.1.4.1.2011.2.251.20.1.2.2.15.207.137
        failedToEnableTheAICacheAlgorithm OBJECT IDENTIFIER ::= { controller 137 }

        -- 1.3.6.1.4.1.2011.2.251.20.1.2.2.15.207.137.1
        failedToEnableTheAICacheAlgorithm-Fault NOTIFICATION-TYPE
            OBJECTS { hwStorageAlarmReporting }
            STATUS current
            DESCRIPTION "Failed To Enable The AI Cache Algorithm"
            --#SEVERITY WARNING
            ::= { failedToEnableTheAICacheAlgorithm 1 }

        -- 1.3.6.1.4.1.2011.2.251.20.1.2.2.15.207.137.2
        failedToEnableTheAICacheAlgorithm-Resume NOTIFICATION-TYPE
            OBJECTS { hwStorageAlarmReporting }
            STATUS current
            DESCRIPTION "Recover: Failed To Enable The AI Cache Algorithm"
            --#SEVERITY INFORMATIONAL
            ::= { failedToEnableTheAICacheAlgorithm 2 }

        -- 1.3.6.1.4.1.2011.2.251.20.1.2.2.15.207.138
        controllerProtectWrite OBJECT IDENTIFIER ::= { controller 138 }

        -- 1.3.6.1.4.1.2011.2.251.20.1.2.2.15.207.138.1
        controllerProtectWrite-Fault NOTIFICATION-TYPE
            OBJECTS { hwStorageAlarmReporting }
            STATUS current
            DESCRIPTION "Write Protection Is Enabled On A Controller"
            --#SEVERITY MAJOR
            ::= { controllerProtectWrite 1 }

        -- 1.3.6.1.4.1.2011.2.251.20.1.2.2.15.207.138.2
        controllerProtectWrite-Resume NOTIFICATION-TYPE
            OBJECTS { hwStorageAlarmReporting }
            STATUS current
            DESCRIPTION "Recover: Write Protection Is Enabled On A Controller"
            --#SEVERITY INFORMATIONAL
            ::= { controllerProtectWrite 2 }

        -- 1.3.6.1.4.1.2011.2.251.20.1.2.2.15.207.141
        aMemoryErrorOccurred OBJECT IDENTIFIER ::= { controller 141 }

        -- 1.3.6.1.4.1.2011.2.251.20.1.2.2.15.207.141.1
        aMemoryErrorOccurred-Fault NOTIFICATION-TYPE
            OBJECTS { hwStorageAlarmReporting }
            STATUS current
            DESCRIPTION "A Memory Error Occurred"
            --#SEVERITY MAJOR
            ::= { aMemoryErrorOccurred 1 }

        -- 1.3.6.1.4.1.2011.2.251.20.1.2.2.15.207.141.2
        aMemoryErrorOccurred-Resume NOTIFICATION-TYPE
            OBJECTS { hwStorageAlarmReporting }
            STATUS current
            DESCRIPTION "Recover: A Memory Error Occurred"
            --#SEVERITY INFORMATIONAL
            ::= { aMemoryErrorOccurred 2 }

        -- 1.3.6.1.4.1.2011.2.251.20.1.2.2.15.207.142
        theControllerIsFaulty OBJECT IDENTIFIER ::= { controller 142 }

        -- 1.3.6.1.4.1.2011.2.251.20.1.2.2.15.207.142.1
        theControllerIsFaulty-Fault NOTIFICATION-TYPE
            OBJECTS { hwStorageAlarmReporting }
            STATUS current
            DESCRIPTION "The Controller Is Faulty"
            --#SEVERITY MAJOR
            ::= { theControllerIsFaulty 1 }

        -- 1.3.6.1.4.1.2011.2.251.20.1.2.2.15.207.142.2
        theControllerIsFaulty-Resume NOTIFICATION-TYPE
            OBJECTS { hwStorageAlarmReporting }
            STATUS current
            DESCRIPTION "Recover: The Controller Is Faulty"
            --#SEVERITY INFORMATIONAL
            ::= { theControllerIsFaulty 2 }

        -- 1.3.6.1.4.1.2011.2.251.20.1.2.2.15.207.147
        anUncorrectableErrorOccursOnTheMemoryModule OBJECT IDENTIFIER ::= { controller 147 }

        -- 1.3.6.1.4.1.2011.2.251.20.1.2.2.15.207.147.1
        anUncorrectableErrorOccursOnTheMemoryModule-Fault NOTIFICATION-TYPE
            OBJECTS { hwStorageAlarmReporting }
            STATUS current
            DESCRIPTION "An Uncorrectable Error Occurs On The Memory Module"
            --#SEVERITY MAJOR
            ::= { anUncorrectableErrorOccursOnTheMemoryModule 1 }

        -- 1.3.6.1.4.1.2011.2.251.20.1.2.2.15.207.147.2
        anUncorrectableErrorOccursOnTheMemoryModule-Resume NOTIFICATION-TYPE
            OBJECTS { hwStorageAlarmReporting }
            STATUS current
            DESCRIPTION "Recover: An Uncorrectable Error Occurs On The Memory Module"
            --#SEVERITY INFORMATIONAL
            ::= { anUncorrectableErrorOccursOnTheMemoryModule 2 }

        -- 1.3.6.1.4.1.2011.2.251.20.1.2.2.15.207.148
        theNumberOfMemoryModulesOnTheControllerDoesNotMatch OBJECT IDENTIFIER ::= { controller 148 }

        -- 1.3.6.1.4.1.2011.2.251.20.1.2.2.15.207.148.1
        theNumberOfMemoryModulesOnTheControllerDoesNotMatch-Fault NOTIFICATION-TYPE
            OBJECTS { hwStorageAlarmReporting }
            STATUS current
            DESCRIPTION "The Number Of Memory Modules On The Controller Does Not Match"
            --#SEVERITY WARNING
            ::= { theNumberOfMemoryModulesOnTheControllerDoesNotMatch 1 }

        -- 1.3.6.1.4.1.2011.2.251.20.1.2.2.15.207.148.2
        theNumberOfMemoryModulesOnTheControllerDoesNotMatch-Resume NOTIFICATION-TYPE
            OBJECTS { hwStorageAlarmReporting }
            STATUS current
            DESCRIPTION "Recover: The Number Of Memory Modules On The Controller Does Not Match"
            --#SEVERITY INFORMATIONAL
            ::= { theNumberOfMemoryModulesOnTheControllerDoesNotMatch 2 }

        -- 1.3.6.1.4.1.2011.2.251.20.1.2.2.15.207.149
        aMemoryErrorOccurs OBJECT IDENTIFIER ::= { controller 149 }

        -- 1.3.6.1.4.1.2011.2.251.20.1.2.2.15.207.149.1
        aMemoryErrorOccurs-Fault NOTIFICATION-TYPE
            OBJECTS { hwStorageAlarmReporting }
            STATUS current
            DESCRIPTION "A Memory Error Occurs"
            --#SEVERITY MAJOR
            ::= { aMemoryErrorOccurs 1 }

        -- 1.3.6.1.4.1.2011.2.251.20.1.2.2.15.207.149.2
        aMemoryErrorOccurs-Resume NOTIFICATION-TYPE
            OBJECTS { hwStorageAlarmReporting }
            STATUS current
            DESCRIPTION "Recover: A Memory Error Occurs"
            --#SEVERITY INFORMATIONAL
            ::= { aMemoryErrorOccurs 2 }

        -- 1.3.6.1.4.1.2011.2.251.20.1.2.2.15.207.150
        theClusterServiceIsSubhealthy OBJECT IDENTIFIER ::= { controller 150 }

        -- 1.3.6.1.4.1.2011.2.251.20.1.2.2.15.207.150.1
        theClusterServiceIsSubhealthy-Fault NOTIFICATION-TYPE
            OBJECTS { hwStorageAlarmReporting }
            STATUS current
            DESCRIPTION "The Cluster Service Is Subhealthy"
            --#SEVERITY WARNING
            ::= { theClusterServiceIsSubhealthy 1 }

        -- 1.3.6.1.4.1.2011.2.251.20.1.2.2.15.207.150.2
        theClusterServiceIsSubhealthy-Resume NOTIFICATION-TYPE
            OBJECTS { hwStorageAlarmReporting }
            STATUS current
            DESCRIPTION "Recover: The Cluster Service Is Subhealthy"
            --#SEVERITY INFORMATIONAL
            ::= { theClusterServiceIsSubhealthy 2 }

        -- 1.3.6.1.4.1.2011.2.251.20.1.2.2.15.207.152
        memoryErrorOccurs OBJECT IDENTIFIER ::= { controller 152 }

        -- 1.3.6.1.4.1.2011.2.251.20.1.2.2.15.207.152.1
        memoryErrorOccurs-Fault NOTIFICATION-TYPE
            OBJECTS { hwStorageAlarmReporting }
            STATUS current
            DESCRIPTION "A Memory Error Occurs"
            --#SEVERITY MAJOR
            ::= { memoryErrorOccurs 1 }

        -- 1.3.6.1.4.1.2011.2.251.20.1.2.2.15.207.152.2
        memoryErrorOccurs-Resume NOTIFICATION-TYPE
            OBJECTS { hwStorageAlarmReporting }
            STATUS current
            DESCRIPTION "Recover: A Memory Error Occurs"
            --#SEVERITY INFORMATIONAL
            ::= { memoryErrorOccurs 2 }

        -- 1.3.6.1.4.1.2011.2.251.20.1.2.2.15.207.153
        memoryOccursUncorrectableError OBJECT IDENTIFIER ::= { controller 153 }

        -- 1.3.6.1.4.1.2011.2.251.20.1.2.2.15.207.153.1
        memoryOccursUncorrectableError-Fault NOTIFICATION-TYPE
            OBJECTS { hwStorageAlarmReporting }
            STATUS current
            DESCRIPTION "An Uncorrectable Error Occurs On The Memory"
            --#SEVERITY MAJOR
            ::= { memoryOccursUncorrectableError 1 }

        -- 1.3.6.1.4.1.2011.2.251.20.1.2.2.15.207.153.2
        memoryOccursUncorrectableError-Resume NOTIFICATION-TYPE
            OBJECTS { hwStorageAlarmReporting }
            STATUS current
            DESCRIPTION "Recover: An Uncorrectable Error Occurs On The Memory"
            --#SEVERITY INFORMATIONAL
            ::= { memoryOccursUncorrectableError 2 }

        -- 1.3.6.1.4.1.2011.2.251.20.1.2.2.15.207.154
        ctrlAndMgtCommunicateLinkFault1 OBJECT IDENTIFIER ::= { controller 154 }

        -- 1.3.6.1.4.1.2011.2.251.20.1.2.2.15.207.154.1
        ctrlAndMgtCommunicateLinkFault1-Fault NOTIFICATION-TYPE
            OBJECTS { hwStorageAlarmReporting }
            STATUS current
            DESCRIPTION "Communication Link Fault Among The Controller And Management Modules"
            --#SEVERITY MAJOR
            ::= { ctrlAndMgtCommunicateLinkFault1 1 }

        -- 1.3.6.1.4.1.2011.2.251.20.1.2.2.15.207.154.2
        ctrlAndMgtCommunicateLinkFault1-Resume NOTIFICATION-TYPE
            OBJECTS { hwStorageAlarmReporting }
            STATUS current
            DESCRIPTION "Recover: Communication Link Fault Among The Controller And Management Modules"
            --#SEVERITY INFORMATIONAL
            ::= { ctrlAndMgtCommunicateLinkFault1 2 }

        -- 1.3.6.1.4.1.2011.2.251.20.1.2.2.15.207.157
        theControllerMemoryManagementPolicyDoesNotTakeEffect OBJECT IDENTIFIER ::= { controller 157 }

        -- 1.3.6.1.4.1.2011.2.251.20.1.2.2.15.207.157.1
        theControllerMemoryManagementPolicyDoesNotTakeEffect-Fault NOTIFICATION-TYPE
            OBJECTS { hwStorageAlarmReporting }
            STATUS current
            DESCRIPTION "The Controller Memory Management Policy Does Not Take Effect"
            --#SEVERITY CRITICAL
            ::= { theControllerMemoryManagementPolicyDoesNotTakeEffect 1 }

        -- 1.3.6.1.4.1.2011.2.251.20.1.2.2.15.207.157.2
        theControllerMemoryManagementPolicyDoesNotTakeEffect-Resume NOTIFICATION-TYPE
            OBJECTS { hwStorageAlarmReporting }
            STATUS current
            DESCRIPTION "Recover: The Controller Memory Management Policy Does Not Take Effect"
            --#SEVERITY INFORMATIONAL
            ::= { theControllerMemoryManagementPolicyDoesNotTakeEffect 2 }

        -- 1.3.6.1.4.1.2011.2.251.20.1.2.2.15.207.158
        theCommunicationBetweenTheControllerAndComputeNodeIsAbnormal OBJECT IDENTIFIER ::= { controller 158 }

        -- 1.3.6.1.4.1.2011.2.251.20.1.2.2.15.207.158.1
        theCommunicationBetweenTheControllerAndComputeNodeIsAbnormal-Fault NOTIFICATION-TYPE
            OBJECTS { hwStorageAlarmReporting }
            STATUS current
            DESCRIPTION "The Communication Between The Controller And Compute Node Is Abnormal"
            --#SEVERITY MAJOR
            ::= { theCommunicationBetweenTheControllerAndComputeNodeIsAbnormal 1 }

        -- 1.3.6.1.4.1.2011.2.251.20.1.2.2.15.207.158.2
        theCommunicationBetweenTheControllerAndComputeNodeIsAbnormal-Resume NOTIFICATION-TYPE
            OBJECTS { hwStorageAlarmReporting }
            STATUS current
            DESCRIPTION "Recover: The Communication Between The Controller And Compute Node Is Abnormal"
            --#SEVERITY INFORMATIONAL
            ::= { theCommunicationBetweenTheControllerAndComputeNodeIsAbnormal 2 }

        -- 1.3.6.1.4.1.2011.2.251.20.1.2.2.15.207.159
        theControllerEntersTheWriteThroughMode OBJECT IDENTIFIER ::= { controller 159 }

        -- 1.3.6.1.4.1.2011.2.251.20.1.2.2.15.207.159.1
        theControllerEntersTheWriteThroughMode-Fault NOTIFICATION-TYPE
            OBJECTS { hwStorageAlarmReporting }
            STATUS current
            DESCRIPTION "The Controller Enters The WriteThrough Mode"
            --#SEVERITY MAJOR
            ::= { theControllerEntersTheWriteThroughMode 1 }

        -- 1.3.6.1.4.1.2011.2.251.20.1.2.2.15.207.159.2
        theControllerEntersTheWriteThroughMode-Resume NOTIFICATION-TYPE
            OBJECTS { hwStorageAlarmReporting }
            STATUS current
            DESCRIPTION "Recover: The Controller Enters The WriteThrough Mode"
            --#SEVERITY INFORMATIONAL
            ::= { theControllerEntersTheWriteThroughMode 2 }

        -- 1.3.6.1.4.1.2011.2.251.20.1.2.2.15.207.162
        ctrlAndMgtCommunicateLinkFault OBJECT IDENTIFIER ::= { controller 162 }

        -- 1.3.6.1.4.1.2011.2.251.20.1.2.2.15.207.162.1
        ctrlAndMgtCommunicateLinkFault-Fault NOTIFICATION-TYPE
            OBJECTS { hwStorageAlarmReporting }
            STATUS current
            DESCRIPTION "The Communication Link Between The Controller And Management Module Is Faulty"
            --#SEVERITY MAJOR
            ::= { ctrlAndMgtCommunicateLinkFault 1 }

        -- 1.3.6.1.4.1.2011.2.251.20.1.2.2.15.207.162.2
        ctrlAndMgtCommunicateLinkFault-Resume NOTIFICATION-TYPE
            OBJECTS { hwStorageAlarmReporting }
            STATUS current
            DESCRIPTION "Recover: The Communication Link Between The Controller And Management Module Is Faulty"
            --#SEVERITY INFORMATIONAL
            ::= { ctrlAndMgtCommunicateLinkFault 2 }

        -- 1.3.6.1.4.1.2011.2.251.20.1.2.2.15.207.163
        directoryIsOversized OBJECT IDENTIFIER ::= { controller 163 }

        -- 1.3.6.1.4.1.2011.2.251.20.1.2.2.15.207.163.1
        directoryIsOversized-Fault NOTIFICATION-TYPE
            OBJECTS { hwStorageAlarmReporting }
            STATUS current
            DESCRIPTION "A Directory Is Oversized"
            --#SEVERITY MAJOR
            ::= { directoryIsOversized 1 }

        -- 1.3.6.1.4.1.2011.2.251.20.1.2.2.15.207.163.2
        directoryIsOversized-Resume NOTIFICATION-TYPE
            OBJECTS { hwStorageAlarmReporting }
            STATUS current
            DESCRIPTION "Recover: A Directory Is Oversized"
            --#SEVERITY INFORMATIONAL
            ::= { directoryIsOversized 2 }

        -- 1.3.6.1.4.1.2011.2.251.20.1.2.2.15.207.164
        cpuIsFaulty OBJECT IDENTIFIER ::= { controller 164 }

        -- 1.3.6.1.4.1.2011.2.251.20.1.2.2.15.207.164.1
        cpuIsFaulty-Fault NOTIFICATION-TYPE
            OBJECTS { hwStorageAlarmReporting }
            STATUS current
            DESCRIPTION "CPU Module Fault"
            --#SEVERITY MAJOR
            ::= { cpuIsFaulty 1 }

        -- 1.3.6.1.4.1.2011.2.251.20.1.2.2.15.207.164.2
        cpuIsFaulty-Resume NOTIFICATION-TYPE
            OBJECTS { hwStorageAlarmReporting }
            STATUS current
            DESCRIPTION "Recover: CPU Module Fault"
            --#SEVERITY INFORMATIONAL
            ::= { cpuIsFaulty 2 }

        -- 1.3.6.1.4.1.2011.2.251.20.1.2.2.15.207.165
        cpuPeripheralIsFaulty OBJECT IDENTIFIER ::= { controller 165 }

        -- 1.3.6.1.4.1.2011.2.251.20.1.2.2.15.207.165.1
        cpuPeripheralIsFaulty-Fault NOTIFICATION-TYPE
            OBJECTS { hwStorageAlarmReporting }
            STATUS current
            DESCRIPTION "CPU Peripheral Module Fault"
            --#SEVERITY MAJOR
            ::= { cpuPeripheralIsFaulty 1 }

        -- 1.3.6.1.4.1.2011.2.251.20.1.2.2.15.207.165.2
        cpuPeripheralIsFaulty-Resume NOTIFICATION-TYPE
            OBJECTS { hwStorageAlarmReporting }
            STATUS current
            DESCRIPTION "Recover: CPU Peripheral Module Fault"
            --#SEVERITY INFORMATIONAL
            ::= { cpuPeripheralIsFaulty 2 }

        -- 1.3.6.1.4.1.2011.2.251.20.1.2.2.15.207.166
        clusterPowerOnTimeOut OBJECT IDENTIFIER ::= { controller 166 }

        -- 1.3.6.1.4.1.2011.2.251.20.1.2.2.15.207.166.1
        clusterPowerOnTimeOut-Fault NOTIFICATION-TYPE
            OBJECTS { hwStorageAlarmReporting }
            STATUS current
            DESCRIPTION "HyperScale Cluster Poweron Timed Out"
            --#SEVERITY CRITICAL
            ::= { clusterPowerOnTimeOut 1 }

        -- 1.3.6.1.4.1.2011.2.251.20.1.2.2.15.207.166.2
        clusterPowerOnTimeOut-Resume NOTIFICATION-TYPE
            OBJECTS { hwStorageAlarmReporting }
            STATUS current
            DESCRIPTION "Recover: HyperScale Cluster Poweron Timed Out"
            --#SEVERITY INFORMATIONAL
            ::= { clusterPowerOnTimeOut 2 }

        -- 1.3.6.1.4.1.2011.2.251.20.1.2.2.15.207.167
        clusterNodeStatusAbnormal OBJECT IDENTIFIER ::= { controller 167 }

        -- 1.3.6.1.4.1.2011.2.251.20.1.2.2.15.207.167.1
        clusterNodeStatusAbnormal-Fault NOTIFICATION-TYPE
            OBJECTS { hwStorageAlarmReporting }
            STATUS current
            DESCRIPTION "HyperScale Cluster Node Status Is Abnormal"
            --#SEVERITY CRITICAL
            ::= { clusterNodeStatusAbnormal 1 }

        -- 1.3.6.1.4.1.2011.2.251.20.1.2.2.15.207.167.2
        clusterNodeStatusAbnormal-Resume NOTIFICATION-TYPE
            OBJECTS { hwStorageAlarmReporting }
            STATUS current
            DESCRIPTION "Recover: HyperScale Cluster Node Status Is Abnormal"
            --#SEVERITY INFORMATIONAL
            ::= { clusterNodeStatusAbnormal 2 }

        -- 1.3.6.1.4.1.2011.2.251.20.1.2.2.15.208
        expansionmodule OBJECT IDENTIFIER ::= { oidBasedTrap 208 }

        -- 1.3.6.1.4.1.2011.2.251.20.1.2.2.15.208.1
        expansionModuleIsRemoved OBJECT IDENTIFIER ::= { expansionmodule 1 }

        -- 1.3.6.1.4.1.2011.2.251.20.1.2.2.15.208.1.1
        expansionModuleIsRemoved-Fault NOTIFICATION-TYPE
            OBJECTS { hwStorageAlarmReporting }
            STATUS current
            DESCRIPTION "Expansion Module Is Removed"
            --#SEVERITY MAJOR
            ::= { expansionModuleIsRemoved 1 }

        -- 1.3.6.1.4.1.2011.2.251.20.1.2.2.15.208.1.2
        expansionModuleIsRemoved-Resume NOTIFICATION-TYPE
            OBJECTS { hwStorageAlarmReporting }
            STATUS current
            DESCRIPTION "Recover: Expansion Module Is Removed"
            --#SEVERITY INFORMATIONAL
            ::= { expansionModuleIsRemoved 2 }

        -- 1.3.6.1.4.1.2011.2.251.20.1.2.2.15.208.20
        abnormalCommBetweenExpModules OBJECT IDENTIFIER ::= { expansionmodule 20 }

        -- 1.3.6.1.4.1.2011.2.251.20.1.2.2.15.208.20.1
        abnormalCommBetweenExpModules-Fault NOTIFICATION-TYPE
            OBJECTS { hwStorageAlarmReporting }
            STATUS current
            DESCRIPTION "Abnormal Communication Between Expansion Modules"
            --#SEVERITY MAJOR
            ::= { abnormalCommBetweenExpModules 1 }

        -- 1.3.6.1.4.1.2011.2.251.20.1.2.2.15.208.20.2
        abnormalCommBetweenExpModules-Resume NOTIFICATION-TYPE
            OBJECTS { hwStorageAlarmReporting }
            STATUS current
            DESCRIPTION "Recover: Abnormal Communication Between Expansion Modules"
            --#SEVERITY INFORMATIONAL
            ::= { abnormalCommBetweenExpModules 2 }

        -- 1.3.6.1.4.1.2011.2.251.20.1.2.2.15.208.23
        syncExpansionFirmwareFailed OBJECT IDENTIFIER ::= { expansionmodule 23 }

        -- 1.3.6.1.4.1.2011.2.251.20.1.2.2.15.208.23.1
        syncExpansionFirmwareFailed-Fault NOTIFICATION-TYPE
            OBJECTS { hwStorageAlarmReporting }
            STATUS current
            DESCRIPTION "Failed To Synchronize The Firmware Version Of An Expansion Module"
            --#SEVERITY MAJOR
            ::= { syncExpansionFirmwareFailed 1 }

        -- 1.3.6.1.4.1.2011.2.251.20.1.2.2.15.208.23.2
        syncExpansionFirmwareFailed-Resume NOTIFICATION-TYPE
            OBJECTS { hwStorageAlarmReporting }
            STATUS current
            DESCRIPTION "Recover: Failed To Synchronize The Firmware Version Of An Expansion Module"
            --#SEVERITY INFORMATIONAL
            ::= { syncExpansionFirmwareFailed 2 }

        -- 1.3.6.1.4.1.2011.2.251.20.1.2.2.15.208.24
        expansionModuleIsFaulty OBJECT IDENTIFIER ::= { expansionmodule 24 }

        -- 1.3.6.1.4.1.2011.2.251.20.1.2.2.15.208.24.1
        expansionModuleIsFaulty-Fault NOTIFICATION-TYPE
            OBJECTS { hwStorageAlarmReporting }
            STATUS current
            DESCRIPTION "Expansion Module Is Faulty"
            --#SEVERITY MAJOR
            ::= { expansionModuleIsFaulty 1 }

        -- 1.3.6.1.4.1.2011.2.251.20.1.2.2.15.208.24.2
        expansionModuleIsFaulty-Resume NOTIFICATION-TYPE
            OBJECTS { hwStorageAlarmReporting }
            STATUS current
            DESCRIPTION "Recover: Expansion Module Is Faulty"
            --#SEVERITY INFORMATIONAL
            ::= { expansionModuleIsFaulty 2 }

        -- 1.3.6.1.4.1.2011.2.251.20.1.2.2.15.208.29
        expansionModuleSpeedNotSupport OBJECT IDENTIFIER ::= { expansionmodule 29 }

        -- 1.3.6.1.4.1.2011.2.251.20.1.2.2.15.208.29.1
        expansionModuleSpeedNotSupport-Fault NOTIFICATION-TYPE
            OBJECTS { hwStorageAlarmReporting }
            STATUS current
            DESCRIPTION "The Expansion Module Speed Does Not Meet Specifications"
            --#SEVERITY MAJOR
            ::= { expansionModuleSpeedNotSupport 1 }

        -- 1.3.6.1.4.1.2011.2.251.20.1.2.2.15.208.29.2
        expansionModuleSpeedNotSupport-Resume NOTIFICATION-TYPE
            OBJECTS { hwStorageAlarmReporting }
            STATUS current
            DESCRIPTION "Recover: The Expansion Module Speed Does Not Meet Specifications"
            --#SEVERITY INFORMATIONAL
            ::= { expansionModuleSpeedNotSupport 2 }

        -- 1.3.6.1.4.1.2011.2.251.20.1.2.2.15.208.32
        expandFrameTypeInvalid OBJECT IDENTIFIER ::= { expansionmodule 32 }

        -- 1.3.6.1.4.1.2011.2.251.20.1.2.2.15.208.32.1
        expandFrameTypeInvalid-Fault NOTIFICATION-TYPE
            OBJECTS { hwStorageAlarmReporting }
            STATUS current
            DESCRIPTION "The Expansion Module Cannot Identify The Enclosure Type"
            --#SEVERITY MAJOR
            ::= { expandFrameTypeInvalid 1 }

        -- 1.3.6.1.4.1.2011.2.251.20.1.2.2.15.208.32.2
        expandFrameTypeInvalid-Resume NOTIFICATION-TYPE
            OBJECTS { hwStorageAlarmReporting }
            STATUS current
            DESCRIPTION "Recover: The Expansion Module Cannot Identify The Enclosure Type"
            --#SEVERITY INFORMATIONAL
            ::= { expandFrameTypeInvalid 2 }

        -- 1.3.6.1.4.1.2011.2.251.20.1.2.2.15.208.33
        expansionModuleIsBeingRepaired OBJECT IDENTIFIER ::= { expansionmodule 33 }

        -- 1.3.6.1.4.1.2011.2.251.20.1.2.2.15.208.33.1
        expansionModuleIsBeingRepaired-Fault NOTIFICATION-TYPE
            OBJECTS { hwStorageAlarmReporting }
            STATUS current
            DESCRIPTION "Expansion Module Is Being Repaired"
            --#SEVERITY WARNING
            ::= { expansionModuleIsBeingRepaired 1 }

        -- 1.3.6.1.4.1.2011.2.251.20.1.2.2.15.208.33.2
        expansionModuleIsBeingRepaired-Resume NOTIFICATION-TYPE
            OBJECTS { hwStorageAlarmReporting }
            STATUS current
            DESCRIPTION "Recover: Expansion Module Is Being Repaired"
            --#SEVERITY INFORMATIONAL
            ::= { expansionModuleIsBeingRepaired 2 }

        -- 1.3.6.1.4.1.2011.2.251.20.1.2.2.15.208.34
        expansionModuleRepairTimesOut OBJECT IDENTIFIER ::= { expansionmodule 34 }

        -- 1.3.6.1.4.1.2011.2.251.20.1.2.2.15.208.34.1
        expansionModuleRepairTimesOut-Fault NOTIFICATION-TYPE
            OBJECTS { hwStorageAlarmReporting }
            STATUS current
            DESCRIPTION "Expansion Module Repair Times Out"
            --#SEVERITY CRITICAL
            ::= { expansionModuleRepairTimesOut 1 }

        -- 1.3.6.1.4.1.2011.2.251.20.1.2.2.15.208.34.2
        expansionModuleRepairTimesOut-Resume NOTIFICATION-TYPE
            OBJECTS { hwStorageAlarmReporting }
            STATUS current
            DESCRIPTION "Recover: Expansion Module Repair Times Out"
            --#SEVERITY INFORMATIONAL
            ::= { expansionModuleRepairTimesOut 2 }

        -- 1.3.6.1.4.1.2011.2.251.20.1.2.2.15.208.35
        failedToRepairAnExpansionModule OBJECT IDENTIFIER ::= { expansionmodule 35 }

        -- 1.3.6.1.4.1.2011.2.251.20.1.2.2.15.208.35.1
        failedToRepairAnExpansionModule-Fault NOTIFICATION-TYPE
            OBJECTS { hwStorageAlarmReporting }
            STATUS current
            DESCRIPTION "Failed To Repair An Expansion Module"
            --#SEVERITY CRITICAL
            ::= { failedToRepairAnExpansionModule 1 }

        -- 1.3.6.1.4.1.2011.2.251.20.1.2.2.15.208.35.2
        failedToRepairAnExpansionModule-Resume NOTIFICATION-TYPE
            OBJECTS { hwStorageAlarmReporting }
            STATUS current
            DESCRIPTION "Recover: Failed To Repair An Expansion Module"
            --#SEVERITY INFORMATIONAL
            ::= { failedToRepairAnExpansionModule 2 }

        -- 1.3.6.1.4.1.2011.2.251.20.1.2.2.15.208.40
        expHeatRemovalSysFault OBJECT IDENTIFIER ::= { expansionmodule 40 }

        -- 1.3.6.1.4.1.2011.2.251.20.1.2.2.15.208.40.1
        expHeatRemovalSysFault-Fault NOTIFICATION-TYPE
            OBJECTS { hwStorageAlarmReporting }
            STATUS current
            DESCRIPTION "Heat Dissipation System Of The Expansion Module Is Faulty"
            --#SEVERITY MAJOR
            ::= { expHeatRemovalSysFault 1 }

        -- 1.3.6.1.4.1.2011.2.251.20.1.2.2.15.208.40.2
        expHeatRemovalSysFault-Resume NOTIFICATION-TYPE
            OBJECTS { hwStorageAlarmReporting }
            STATUS current
            DESCRIPTION "Recover: Heat Dissipation System Of The Expansion Module Is Faulty"
            --#SEVERITY INFORMATIONAL
            ::= { expHeatRemovalSysFault 2 }

        -- 1.3.6.1.4.1.2011.2.251.20.1.2.2.15.208.41
        expansionModuleIncompatible OBJECT IDENTIFIER ::= { expansionmodule 41 }

        -- 1.3.6.1.4.1.2011.2.251.20.1.2.2.15.208.41.1
        expansionModuleIncompatible-Fault NOTIFICATION-TYPE
            OBJECTS { hwStorageAlarmReporting }
            STATUS current
            DESCRIPTION "Expansion Module Firmware Is Incompatible With Storage Array Software"
            --#SEVERITY MAJOR
            ::= { expansionModuleIncompatible 1 }

        -- 1.3.6.1.4.1.2011.2.251.20.1.2.2.15.208.41.2
        expansionModuleIncompatible-Resume NOTIFICATION-TYPE
            OBJECTS { hwStorageAlarmReporting }
            STATUS current
            DESCRIPTION "Recover: Expansion Module Firmware Is Incompatible With Storage Array Software"
            --#SEVERITY INFORMATIONAL
            ::= { expansionModuleIncompatible 2 }

        -- 1.3.6.1.4.1.2011.2.251.20.1.2.2.15.208.42
        typesOfExpansionModulesInTheDiskEnclosureAreDifferent OBJECT IDENTIFIER ::= { expansionmodule 42 }

        -- 1.3.6.1.4.1.2011.2.251.20.1.2.2.15.208.42.1
        typesOfExpansionModulesInTheDiskEnclosureAreDifferent-Fault NOTIFICATION-TYPE
            OBJECTS { hwStorageAlarmReporting }
            STATUS current
            DESCRIPTION "Types Of Expansion Modules In The Disk Enclosure Are Different"
            --#SEVERITY MAJOR
            ::= { typesOfExpansionModulesInTheDiskEnclosureAreDifferent 1 }

        -- 1.3.6.1.4.1.2011.2.251.20.1.2.2.15.208.42.2
        typesOfExpansionModulesInTheDiskEnclosureAreDifferent-Resume NOTIFICATION-TYPE
            OBJECTS { hwStorageAlarmReporting }
            STATUS current
            DESCRIPTION "Recover: Types Of Expansion Modules In The Disk Enclosure Are Different"
            --#SEVERITY INFORMATIONAL
            ::= { typesOfExpansionModulesInTheDiskEnclosureAreDifferent 2 }

        -- 1.3.6.1.4.1.2011.2.251.20.1.2.2.15.208.43
        memCapOfExpIsIncorrect OBJECT IDENTIFIER ::= { expansionmodule 43 }

        -- 1.3.6.1.4.1.2011.2.251.20.1.2.2.15.208.43.1
        memCapOfExpIsIncorrect-Fault NOTIFICATION-TYPE
            OBJECTS { hwStorageAlarmReporting }
            STATUS current
            DESCRIPTION "Memory Capacity Of Expansion Module Is Incorrect"
            --#SEVERITY MAJOR
            ::= { memCapOfExpIsIncorrect 1 }

        -- 1.3.6.1.4.1.2011.2.251.20.1.2.2.15.208.43.2
        memCapOfExpIsIncorrect-Resume NOTIFICATION-TYPE
            OBJECTS { hwStorageAlarmReporting }
            STATUS current
            DESCRIPTION "Recover: Memory Capacity Of Expansion Module Is Incorrect"
            --#SEVERITY INFORMATIONAL
            ::= { memCapOfExpIsIncorrect 2 }

        -- 1.3.6.1.4.1.2011.2.251.20.1.2.2.15.208.45
        theSystemCannotMonitorAExpansionModule OBJECT IDENTIFIER ::= { expansionmodule 45 }

        -- 1.3.6.1.4.1.2011.2.251.20.1.2.2.15.208.45.1
        theSystemCannotMonitorAExpansionModule-Fault NOTIFICATION-TYPE
            OBJECTS { hwStorageAlarmReporting }
            STATUS current
            DESCRIPTION "The System Cannot Monitor A Expansion Module"
            --#SEVERITY CRITICAL
            ::= { theSystemCannotMonitorAExpansionModule 1 }

        -- 1.3.6.1.4.1.2011.2.251.20.1.2.2.15.208.45.2
        theSystemCannotMonitorAExpansionModule-Resume NOTIFICATION-TYPE
            OBJECTS { hwStorageAlarmReporting }
            STATUS current
            DESCRIPTION "Recover: The System Cannot Monitor A Expansion Module"
            --#SEVERITY INFORMATIONAL
            ::= { theSystemCannotMonitorAExpansionModule 2 }

        -- 1.3.6.1.4.1.2011.2.251.20.1.2.2.15.208.57
        sasExpansionModuleIncompatible OBJECT IDENTIFIER ::= { expansionmodule 57 }

        -- 1.3.6.1.4.1.2011.2.251.20.1.2.2.15.208.57.1
        sasExpansionModuleIncompatible-Fault NOTIFICATION-TYPE
            OBJECTS { hwStorageAlarmReporting }
            STATUS current
            DESCRIPTION "The Shared SAS Expansion Module Firmware Is Incompatible With Storage Array Software"
            --#SEVERITY MAJOR
            ::= { sasExpansionModuleIncompatible 1 }

        -- 1.3.6.1.4.1.2011.2.251.20.1.2.2.15.208.57.2
        sasExpansionModuleIncompatible-Resume NOTIFICATION-TYPE
            OBJECTS { hwStorageAlarmReporting }
            STATUS current
            DESCRIPTION "Recover: The Shared SAS Expansion Module Firmware Is Incompatible With Storage Array Software"
            --#SEVERITY INFORMATIONAL
            ::= { sasExpansionModuleIncompatible 2 }

        -- 1.3.6.1.4.1.2011.2.251.20.1.2.2.15.208.119
        expI2cCommuError OBJECT IDENTIFIER ::= { expansionmodule 119 }

        -- 1.3.6.1.4.1.2011.2.251.20.1.2.2.15.208.119.1
        expI2cCommuError-Fault NOTIFICATION-TYPE
            OBJECTS { hwStorageAlarmReporting }
            STATUS current
            DESCRIPTION "The Monitor Link Between The Expansion Module And The Enclosure Is Faulty"
            --#SEVERITY MAJOR
            ::= { expI2cCommuError 1 }

        -- 1.3.6.1.4.1.2011.2.251.20.1.2.2.15.208.119.2
        expI2cCommuError-Resume NOTIFICATION-TYPE
            OBJECTS { hwStorageAlarmReporting }
            STATUS current
            DESCRIPTION "Recover: The Monitor Link Between The Expansion Module And The Enclosure Is Faulty"
            --#SEVERITY INFORMATIONAL
            ::= { expI2cCommuError 2 }

        -- 1.3.6.1.4.1.2011.2.251.20.1.2.2.15.209
        interfacemodule OBJECT IDENTIFIER ::= { oidBasedTrap 209 }

        -- 1.3.6.1.4.1.2011.2.251.20.1.2.2.15.209.1
        managementModuleIsRemoved1 OBJECT IDENTIFIER ::= { interfacemodule 1 }

        -- 1.3.6.1.4.1.2011.2.251.20.1.2.2.15.209.1.1
        managementModuleIsRemoved1-Fault NOTIFICATION-TYPE
            OBJECTS { hwStorageAlarmReporting }
            STATUS current
            DESCRIPTION "Management Module Is Removed"
            --#SEVERITY MAJOR
            ::= { managementModuleIsRemoved1 1 }

        -- 1.3.6.1.4.1.2011.2.251.20.1.2.2.15.209.1.2
        managementModuleIsRemoved1-Resume NOTIFICATION-TYPE
            OBJECTS { hwStorageAlarmReporting }
            STATUS current
            DESCRIPTION "Recover: Management Module Is Removed"
            --#SEVERITY INFORMATIONAL
            ::= { managementModuleIsRemoved1 2 }

        -- 1.3.6.1.4.1.2011.2.251.20.1.2.2.15.209.3
        cmdOfCardExceedUpperLimit OBJECT IDENTIFIER ::= { interfacemodule 3 }

        -- 1.3.6.1.4.1.2011.2.251.20.1.2.2.15.209.3.1
        cmdOfCardExceedUpperLimit-Fault NOTIFICATION-TYPE
            OBJECTS { hwStorageAlarmReporting }
            STATUS current
            DESCRIPTION "Number Of Commands On A Module Exceeds The System Limit"
            --#SEVERITY MAJOR
            ::= { cmdOfCardExceedUpperLimit 1 }

        -- 1.3.6.1.4.1.2011.2.251.20.1.2.2.15.209.3.2
        cmdOfCardExceedUpperLimit-Resume NOTIFICATION-TYPE
            OBJECTS { hwStorageAlarmReporting }
            STATUS current
            DESCRIPTION "Recover: Number Of Commands On A Module Exceeds The System Limit"
            --#SEVERITY INFORMATIONAL
            ::= { cmdOfCardExceedUpperLimit 2 }

        -- 1.3.6.1.4.1.2011.2.251.20.1.2.2.15.209.4
        theMCUFirmwareVersionIsIncompatibleWithStorageArraySoftware OBJECT IDENTIFIER ::= { interfacemodule 4 }

        -- 1.3.6.1.4.1.2011.2.251.20.1.2.2.15.209.4.1
        theMCUFirmwareVersionIsIncompatibleWithStorageArraySoftware-Fault NOTIFICATION-TYPE
            OBJECTS { hwStorageAlarmReporting }
            STATUS current
            DESCRIPTION "The MCU Firmware Version Is Incompatible With Storage Array Software"
            --#SEVERITY MAJOR
            ::= { theMCUFirmwareVersionIsIncompatibleWithStorageArraySoftware 1 }

        -- 1.3.6.1.4.1.2011.2.251.20.1.2.2.15.209.4.2
        theMCUFirmwareVersionIsIncompatibleWithStorageArraySoftware-Resume NOTIFICATION-TYPE
            OBJECTS { hwStorageAlarmReporting }
            STATUS current
            DESCRIPTION "Recover: The MCU Firmware Version Is Incompatible With Storage Array Software"
            --#SEVERITY INFORMATIONAL
            ::= { theMCUFirmwareVersionIsIncompatibleWithStorageArraySoftware 2 }

        -- 1.3.6.1.4.1.2011.2.251.20.1.2.2.15.209.5
        interfaceModuleIsRemoved OBJECT IDENTIFIER ::= { interfacemodule 5 }

        -- 1.3.6.1.4.1.2011.2.251.20.1.2.2.15.209.5.1
        interfaceModuleIsRemoved-Fault NOTIFICATION-TYPE
            OBJECTS { hwStorageAlarmReporting }
            STATUS current
            DESCRIPTION "Interface Module Is Removed"
            --#SEVERITY MAJOR
            ::= { interfaceModuleIsRemoved 1 }

        -- 1.3.6.1.4.1.2011.2.251.20.1.2.2.15.209.5.2
        interfaceModuleIsRemoved-Resume NOTIFICATION-TYPE
            OBJECTS { hwStorageAlarmReporting }
            STATUS current
            DESCRIPTION "Recover: Interface Module Is Removed"
            --#SEVERITY INFORMATIONAL
            ::= { interfaceModuleIsRemoved 2 }

        -- 1.3.6.1.4.1.2011.2.251.20.1.2.2.15.209.8
        interfaceModuleIsUnrecognizable OBJECT IDENTIFIER ::= { interfacemodule 8 }

        -- 1.3.6.1.4.1.2011.2.251.20.1.2.2.15.209.8.1
        interfaceModuleIsUnrecognizable-Fault NOTIFICATION-TYPE
            OBJECTS { hwStorageAlarmReporting }
            STATUS current
            DESCRIPTION "Interface Module Is Unrecognizable"
            --#SEVERITY MAJOR
            ::= { interfaceModuleIsUnrecognizable 1 }

        -- 1.3.6.1.4.1.2011.2.251.20.1.2.2.15.209.8.2
        interfaceModuleIsUnrecognizable-Resume NOTIFICATION-TYPE
            OBJECTS { hwStorageAlarmReporting }
            STATUS current
            DESCRIPTION "Recover: Interface Module Is Unrecognizable"
            --#SEVERITY INFORMATIONAL
            ::= { interfaceModuleIsUnrecognizable 2 }

        -- 1.3.6.1.4.1.2011.2.251.20.1.2.2.15.209.9
        interfaceModuleTempExceedsLimit OBJECT IDENTIFIER ::= { interfacemodule 9 }

        -- 1.3.6.1.4.1.2011.2.251.20.1.2.2.15.209.9.1
        interfaceModuleTempExceedsLimit-Fault NOTIFICATION-TYPE
            OBJECTS { hwStorageAlarmReporting }
            STATUS current
            DESCRIPTION "Interface Module Temperature Exceeds The Upper Limit"
            --#SEVERITY WARNING
            ::= { interfaceModuleTempExceedsLimit 1 }

        -- 1.3.6.1.4.1.2011.2.251.20.1.2.2.15.209.9.2
        interfaceModuleTempExceedsLimit-Resume NOTIFICATION-TYPE
            OBJECTS { hwStorageAlarmReporting }
            STATUS current
            DESCRIPTION "Recover: Interface Module Temperature Exceeds The Upper Limit"
            --#SEVERITY INFORMATIONAL
            ::= { interfaceModuleTempExceedsLimit 2 }

        -- 1.3.6.1.4.1.2011.2.251.20.1.2.2.15.209.13
        interfaceNotRedundancy OBJECT IDENTIFIER ::= { interfacemodule 13 }

        -- 1.3.6.1.4.1.2011.2.251.20.1.2.2.15.209.13.1
        interfaceNotRedundancy-Fault NOTIFICATION-TYPE
            OBJECTS { hwStorageAlarmReporting }
            STATUS current
            DESCRIPTION "Port Redundancy Requirements Not Met"
            --#SEVERITY WARNING
            ::= { interfaceNotRedundancy 1 }

        -- 1.3.6.1.4.1.2011.2.251.20.1.2.2.15.209.13.2
        interfaceNotRedundancy-Resume NOTIFICATION-TYPE
            OBJECTS { hwStorageAlarmReporting }
            STATUS current
            DESCRIPTION "Recover: Port Redundancy Requirements Not Met"
            --#SEVERITY INFORMATIONAL
            ::= { interfaceNotRedundancy 2 }

        -- 1.3.6.1.4.1.2011.2.251.20.1.2.2.15.209.30
        monitorInterfaceModuleFailed OBJECT IDENTIFIER ::= { interfacemodule 30 }

        -- 1.3.6.1.4.1.2011.2.251.20.1.2.2.15.209.30.1
        monitorInterfaceModuleFailed-Fault NOTIFICATION-TYPE
            OBJECTS { hwStorageAlarmReporting }
            STATUS current
            DESCRIPTION "Interface Module Cannot Be Monitored"
            --#SEVERITY MAJOR
            ::= { monitorInterfaceModuleFailed 1 }

        -- 1.3.6.1.4.1.2011.2.251.20.1.2.2.15.209.30.2
        monitorInterfaceModuleFailed-Resume NOTIFICATION-TYPE
            OBJECTS { hwStorageAlarmReporting }
            STATUS current
            DESCRIPTION "Recover: Interface Module Cannot Be Monitored"
            --#SEVERITY INFORMATIONAL
            ::= { monitorInterfaceModuleFailed 2 }

        -- 1.3.6.1.4.1.2011.2.251.20.1.2.2.15.209.40
        interfaceModuleIncompatible OBJECT IDENTIFIER ::= { interfacemodule 40 }

        -- 1.3.6.1.4.1.2011.2.251.20.1.2.2.15.209.40.1
        interfaceModuleIncompatible-Fault NOTIFICATION-TYPE
            OBJECTS { hwStorageAlarmReporting }
            STATUS current
            DESCRIPTION "Interface Module Firmware Version Is Incompatible With Storage Array Software"
            --#SEVERITY MAJOR
            ::= { interfaceModuleIncompatible 1 }

        -- 1.3.6.1.4.1.2011.2.251.20.1.2.2.15.209.40.2
        interfaceModuleIncompatible-Resume NOTIFICATION-TYPE
            OBJECTS { hwStorageAlarmReporting }
            STATUS current
            DESCRIPTION "Recover: Interface Module Firmware Version Is Incompatible With Storage Array Software"
            --#SEVERITY INFORMATIONAL
            ::= { interfaceModuleIncompatible 2 }

        -- 1.3.6.1.4.1.2011.2.251.20.1.2.2.15.209.46
        abnormalCommunicateBetweenManageModules OBJECT IDENTIFIER ::= { interfacemodule 46 }

        -- 1.3.6.1.4.1.2011.2.251.20.1.2.2.15.209.46.1
        abnormalCommunicateBetweenManageModules-Fault NOTIFICATION-TYPE
            OBJECTS { hwStorageAlarmReporting }
            STATUS current
            DESCRIPTION "The Communication Between Management Modules Is Abnormal"
            --#SEVERITY MAJOR
            ::= { abnormalCommunicateBetweenManageModules 1 }

        -- 1.3.6.1.4.1.2011.2.251.20.1.2.2.15.209.46.2
        abnormalCommunicateBetweenManageModules-Resume NOTIFICATION-TYPE
            OBJECTS { hwStorageAlarmReporting }
            STATUS current
            DESCRIPTION "Recover: The Communication Between Management Modules Is Abnormal"
            --#SEVERITY INFORMATIONAL
            ::= { abnormalCommunicateBetweenManageModules 2 }

        -- 1.3.6.1.4.1.2011.2.251.20.1.2.2.15.209.50
        managementModuleIncompatible OBJECT IDENTIFIER ::= { interfacemodule 50 }

        -- 1.3.6.1.4.1.2011.2.251.20.1.2.2.15.209.50.1
        managementModuleIncompatible-Fault NOTIFICATION-TYPE
            OBJECTS { hwStorageAlarmReporting }
            STATUS current
            DESCRIPTION "The Management Module Firmware Is Incompatible With Storage Array Software"
            --#SEVERITY MAJOR
            ::= { managementModuleIncompatible 1 }

        -- 1.3.6.1.4.1.2011.2.251.20.1.2.2.15.209.50.2
        managementModuleIncompatible-Resume NOTIFICATION-TYPE
            OBJECTS { hwStorageAlarmReporting }
            STATUS current
            DESCRIPTION "Recover: The Management Module Firmware Is Incompatible With Storage Array Software"
            --#SEVERITY INFORMATIONAL
            ::= { managementModuleIncompatible 2 }

        -- 1.3.6.1.4.1.2011.2.251.20.1.2.2.15.209.56
        pcieChannelIsFaulty1 OBJECT IDENTIFIER ::= { interfacemodule 56 }

        -- 1.3.6.1.4.1.2011.2.251.20.1.2.2.15.209.56.1
        pcieChannelIsFaulty1-Fault NOTIFICATION-TYPE
            OBJECTS { hwStorageAlarmReporting }
            STATUS current
            DESCRIPTION "PCIe Channel Between An Interface Module And A Controller Is Abnormal"
            --#SEVERITY MAJOR
            ::= { pcieChannelIsFaulty1 1 }

        -- 1.3.6.1.4.1.2011.2.251.20.1.2.2.15.209.56.2
        pcieChannelIsFaulty1-Resume NOTIFICATION-TYPE
            OBJECTS { hwStorageAlarmReporting }
            STATUS current
            DESCRIPTION "Recover: PCIe Channel Between An Interface Module And A Controller Is Abnormal"
            --#SEVERITY INFORMATIONAL
            ::= { pcieChannelIsFaulty1 2 }

        -- 1.3.6.1.4.1.2011.2.251.20.1.2.2.15.209.57
        linkIntfCtrlAbnormal OBJECT IDENTIFIER ::= { interfacemodule 57 }

        -- 1.3.6.1.4.1.2011.2.251.20.1.2.2.15.209.57.1
        linkIntfCtrlAbnormal-Fault NOTIFICATION-TYPE
            OBJECTS { hwStorageAlarmReporting }
            STATUS current
            DESCRIPTION "The Link Between An Interface Module And A Controller Is Abnormal"
            --#SEVERITY MAJOR
            ::= { linkIntfCtrlAbnormal 1 }

        -- 1.3.6.1.4.1.2011.2.251.20.1.2.2.15.209.57.2
        linkIntfCtrlAbnormal-Resume NOTIFICATION-TYPE
            OBJECTS { hwStorageAlarmReporting }
            STATUS current
            DESCRIPTION "Recover: The Link Between An Interface Module And A Controller Is Abnormal"
            --#SEVERITY INFORMATIONAL
            ::= { linkIntfCtrlAbnormal 2 }

        -- 1.3.6.1.4.1.2011.2.251.20.1.2.2.15.209.59
        managementModuleIsRemoved OBJECT IDENTIFIER ::= { interfacemodule 59 }

        -- 1.3.6.1.4.1.2011.2.251.20.1.2.2.15.209.59.1
        managementModuleIsRemoved-Fault NOTIFICATION-TYPE
            OBJECTS { hwStorageAlarmReporting }
            STATUS current
            DESCRIPTION "Management Module Is Removed"
            --#SEVERITY MAJOR
            ::= { managementModuleIsRemoved 1 }

        -- 1.3.6.1.4.1.2011.2.251.20.1.2.2.15.209.59.2
        managementModuleIsRemoved-Resume NOTIFICATION-TYPE
            OBJECTS { hwStorageAlarmReporting }
            STATUS current
            DESCRIPTION "Recover: Management Module Is Removed"
            --#SEVERITY INFORMATIONAL
            ::= { managementModuleIsRemoved 2 }

        -- 1.3.6.1.4.1.2011.2.251.20.1.2.2.15.209.60
        managementModuleIsFaulty OBJECT IDENTIFIER ::= { interfacemodule 60 }

        -- 1.3.6.1.4.1.2011.2.251.20.1.2.2.15.209.60.1
        managementModuleIsFaulty-Fault NOTIFICATION-TYPE
            OBJECTS { hwStorageAlarmReporting }
            STATUS current
            DESCRIPTION "The Management Module Is Faulty"
            --#SEVERITY MAJOR
            ::= { managementModuleIsFaulty 1 }

        -- 1.3.6.1.4.1.2011.2.251.20.1.2.2.15.209.60.2
        managementModuleIsFaulty-Resume NOTIFICATION-TYPE
            OBJECTS { hwStorageAlarmReporting }
            STATUS current
            DESCRIPTION "Recover: The Management Module Is Faulty"
            --#SEVERITY INFORMATIONAL
            ::= { managementModuleIsFaulty 2 }

        -- 1.3.6.1.4.1.2011.2.251.20.1.2.2.15.209.61
        interfaceModuleIsFaulty OBJECT IDENTIFIER ::= { interfacemodule 61 }

        -- 1.3.6.1.4.1.2011.2.251.20.1.2.2.15.209.61.1
        interfaceModuleIsFaulty-Fault NOTIFICATION-TYPE
            OBJECTS { hwStorageAlarmReporting }
            STATUS current
            DESCRIPTION "Interface Module Is Faulty"
            --#SEVERITY MAJOR
            ::= { interfaceModuleIsFaulty 1 }

        -- 1.3.6.1.4.1.2011.2.251.20.1.2.2.15.209.61.2
        interfaceModuleIsFaulty-Resume NOTIFICATION-TYPE
            OBJECTS { hwStorageAlarmReporting }
            STATUS current
            DESCRIPTION "Recover: Interface Module Is Faulty"
            --#SEVERITY INFORMATIONAL
            ::= { interfaceModuleIsFaulty 2 }

        -- 1.3.6.1.4.1.2011.2.251.20.1.2.2.15.209.63
        interfaceSfpSpeedUnmatch OBJECT IDENTIFIER ::= { interfacemodule 63 }

        -- 1.3.6.1.4.1.2011.2.251.20.1.2.2.15.209.63.1
        interfaceSfpSpeedUnmatch-Fault NOTIFICATION-TYPE
            OBJECTS { hwStorageAlarmReporting }
            STATUS current
            DESCRIPTION "Speeds Of The Port And Optical Module In The Port Are Not The Same On An Interface Module"
            --#SEVERITY WARNING
            ::= { interfaceSfpSpeedUnmatch 1 }

        -- 1.3.6.1.4.1.2011.2.251.20.1.2.2.15.209.63.2
        interfaceSfpSpeedUnmatch-Resume NOTIFICATION-TYPE
            OBJECTS { hwStorageAlarmReporting }
            STATUS current
            DESCRIPTION "Recover: Speeds Of The Port And Optical Module In The Port Are Not The Same On An Interface Module"
            --#SEVERITY INFORMATIONAL
            ::= { interfaceSfpSpeedUnmatch 2 }

        -- 1.3.6.1.4.1.2011.2.251.20.1.2.2.15.209.68
        fruNotSupport OBJECT IDENTIFIER ::= { interfacemodule 68 }

        -- 1.3.6.1.4.1.2011.2.251.20.1.2.2.15.209.68.1
        fruNotSupport-Fault NOTIFICATION-TYPE
            OBJECTS { hwStorageAlarmReporting }
            STATUS current
            DESCRIPTION "Interface Module Not Supported"
            --#SEVERITY MAJOR
            ::= { fruNotSupport 1 }

        -- 1.3.6.1.4.1.2011.2.251.20.1.2.2.15.209.68.2
        fruNotSupport-Resume NOTIFICATION-TYPE
            OBJECTS { hwStorageAlarmReporting }
            STATUS current
            DESCRIPTION "Recover: Interface Module Not Supported"
            --#SEVERITY INFORMATIONAL
            ::= { fruNotSupport 2 }

        -- 1.3.6.1.4.1.2011.2.251.20.1.2.2.15.209.69
        intfNotMatchCorrectSlot OBJECT IDENTIFIER ::= { interfacemodule 69 }

        -- 1.3.6.1.4.1.2011.2.251.20.1.2.2.15.209.69.1
        intfNotMatchCorrectSlot-Fault NOTIFICATION-TYPE
            OBJECTS { hwStorageAlarmReporting }
            STATUS current
            DESCRIPTION "Interface Module Inserted Into An Incorrect Slot"
            --#SEVERITY MAJOR
            ::= { intfNotMatchCorrectSlot 1 }

        -- 1.3.6.1.4.1.2011.2.251.20.1.2.2.15.209.69.2
        intfNotMatchCorrectSlot-Resume NOTIFICATION-TYPE
            OBJECTS { hwStorageAlarmReporting }
            STATUS current
            DESCRIPTION "Recover: Interface Module Inserted Into An Incorrect Slot"
            --#SEVERITY INFORMATIONAL
            ::= { intfNotMatchCorrectSlot 2 }

        -- 1.3.6.1.4.1.2011.2.251.20.1.2.2.15.209.72
        mgtAndCtrlCommunicateLinkFault OBJECT IDENTIFIER ::= { interfacemodule 72 }

        -- 1.3.6.1.4.1.2011.2.251.20.1.2.2.15.209.72.1
        mgtAndCtrlCommunicateLinkFault-Fault NOTIFICATION-TYPE
            OBJECTS { hwStorageAlarmReporting }
            STATUS current
            DESCRIPTION "Communication Link Fault Between The Management Module And Controller"
            --#SEVERITY WARNING
            ::= { mgtAndCtrlCommunicateLinkFault 1 }

        -- 1.3.6.1.4.1.2011.2.251.20.1.2.2.15.209.72.2
        mgtAndCtrlCommunicateLinkFault-Resume NOTIFICATION-TYPE
            OBJECTS { hwStorageAlarmReporting }
            STATUS current
            DESCRIPTION "Recover: Communication Link Fault Between The Management Module And Controller"
            --#SEVERITY INFORMATIONAL
            ::= { mgtAndCtrlCommunicateLinkFault 2 }

        -- 1.3.6.1.4.1.2011.2.251.20.1.2.2.15.209.75
        intfNotMatchSuggestSlot OBJECT IDENTIFIER ::= { interfacemodule 75 }

        -- 1.3.6.1.4.1.2011.2.251.20.1.2.2.15.209.75.1
        intfNotMatchSuggestSlot-Fault NOTIFICATION-TYPE
            OBJECTS { hwStorageAlarmReporting }
            STATUS current
            DESCRIPTION "An Interface Module Is Not Inserted Into The Recommended Slot"
            --#SEVERITY WARNING
            ::= { intfNotMatchSuggestSlot 1 }

        -- 1.3.6.1.4.1.2011.2.251.20.1.2.2.15.209.75.2
        intfNotMatchSuggestSlot-Resume NOTIFICATION-TYPE
            OBJECTS { hwStorageAlarmReporting }
            STATUS current
            DESCRIPTION "Recover: An Interface Module Is Not Inserted Into The Recommended Slot"
            --#SEVERITY INFORMATIONAL
            ::= { intfNotMatchSuggestSlot 2 }

        -- 1.3.6.1.4.1.2011.2.251.20.1.2.2.15.209.76
        aSpareInterfaceModuleIsInsertedIntoAnIncorrectSlot OBJECT IDENTIFIER ::= { interfacemodule 76 }

        -- 1.3.6.1.4.1.2011.2.251.20.1.2.2.15.209.76.1
        aSpareInterfaceModuleIsInsertedIntoAnIncorrectSlot-Fault NOTIFICATION-TYPE
            OBJECTS { hwStorageAlarmReporting }
            STATUS current
            DESCRIPTION "A Spare Interface Module Is Inserted Into An Incorrect Slot"
            --#SEVERITY MAJOR
            ::= { aSpareInterfaceModuleIsInsertedIntoAnIncorrectSlot 1 }

        -- 1.3.6.1.4.1.2011.2.251.20.1.2.2.15.209.76.2
        aSpareInterfaceModuleIsInsertedIntoAnIncorrectSlot-Resume NOTIFICATION-TYPE
            OBJECTS { hwStorageAlarmReporting }
            STATUS current
            DESCRIPTION "Recover: A Spare Interface Module Is Inserted Into An Incorrect Slot"
            --#SEVERITY INFORMATIONAL
            ::= { aSpareInterfaceModuleIsInsertedIntoAnIncorrectSlot 2 }

        -- 1.3.6.1.4.1.2011.2.251.20.1.2.2.15.209.77
        connOfCardExceedUpperLimit OBJECT IDENTIFIER ::= { interfacemodule 77 }

        -- 1.3.6.1.4.1.2011.2.251.20.1.2.2.15.209.77.1
        connOfCardExceedUpperLimit-Fault NOTIFICATION-TYPE
            OBJECTS { hwStorageAlarmReporting }
            STATUS current
            DESCRIPTION "The Number Of ISCSI Initiator Connections On An Interface Module Exceeds The Upper Limit"
            --#SEVERITY MAJOR
            ::= { connOfCardExceedUpperLimit 1 }

        -- 1.3.6.1.4.1.2011.2.251.20.1.2.2.15.209.77.2
        connOfCardExceedUpperLimit-Resume NOTIFICATION-TYPE
            OBJECTS { hwStorageAlarmReporting }
            STATUS current
            DESCRIPTION "Recover: The Number Of ISCSI Initiator Connections On An Interface Module Exceeds The Upper Limit"
            --#SEVERITY INFORMATIONAL
            ::= { connOfCardExceedUpperLimit 2 }

        -- 1.3.6.1.4.1.2011.2.251.20.1.2.2.15.209.78
        incorrectWorkingModeOfAnInterfaceModule OBJECT IDENTIFIER ::= { interfacemodule 78 }

        -- 1.3.6.1.4.1.2011.2.251.20.1.2.2.15.209.78.1
        incorrectWorkingModeOfAnInterfaceModule-Fault NOTIFICATION-TYPE
            OBJECTS { hwStorageAlarmReporting }
            STATUS current
            DESCRIPTION "Incorrect Working Mode Of An Interface Module"
            --#SEVERITY MAJOR
            ::= { incorrectWorkingModeOfAnInterfaceModule 1 }

        -- 1.3.6.1.4.1.2011.2.251.20.1.2.2.15.209.78.2
        incorrectWorkingModeOfAnInterfaceModule-Resume NOTIFICATION-TYPE
            OBJECTS { hwStorageAlarmReporting }
            STATUS current
            DESCRIPTION "Recover: Incorrect Working Mode Of An Interface Module"
            --#SEVERITY INFORMATIONAL
            ::= { incorrectWorkingModeOfAnInterfaceModule 2 }

        -- 1.3.6.1.4.1.2011.2.251.20.1.2.2.15.209.81
        managementModuleNotSupport OBJECT IDENTIFIER ::= { interfacemodule 81 }

        -- 1.3.6.1.4.1.2011.2.251.20.1.2.2.15.209.81.1
        managementModuleNotSupport-Fault NOTIFICATION-TYPE
            OBJECTS { hwStorageAlarmReporting }
            STATUS current
            DESCRIPTION "Management Module Not Supported"
            --#SEVERITY MAJOR
            ::= { managementModuleNotSupport 1 }

        -- 1.3.6.1.4.1.2011.2.251.20.1.2.2.15.209.81.2
        managementModuleNotSupport-Resume NOTIFICATION-TYPE
            OBJECTS { hwStorageAlarmReporting }
            STATUS current
            DESCRIPTION "Recover: Management Module Not Supported"
            --#SEVERITY INFORMATIONAL
            ::= { managementModuleNotSupport 2 }

        -- 1.3.6.1.4.1.2011.2.251.20.1.2.2.15.209.82
        theCommunicationLinkBetweenTheManagementModuleAndControllerIsFaulty OBJECT IDENTIFIER ::= { interfacemodule 82 }

        -- 1.3.6.1.4.1.2011.2.251.20.1.2.2.15.209.82.1
        theCommunicationLinkBetweenTheManagementModuleAndControllerIsFaulty-Fault NOTIFICATION-TYPE
            OBJECTS { hwStorageAlarmReporting }
            STATUS current
            DESCRIPTION "The Communication Link Between The Management Module And Controller Is Faulty"
            --#SEVERITY WARNING
            ::= { theCommunicationLinkBetweenTheManagementModuleAndControllerIsFaulty 1 }

        -- 1.3.6.1.4.1.2011.2.251.20.1.2.2.15.209.82.2
        theCommunicationLinkBetweenTheManagementModuleAndControllerIsFaulty-Resume NOTIFICATION-TYPE
            OBJECTS { hwStorageAlarmReporting }
            STATUS current
            DESCRIPTION "Recover: The Communication Link Between The Management Module And Controller Is Faulty"
            --#SEVERITY INFORMATIONAL
            ::= { theCommunicationLinkBetweenTheManagementModuleAndControllerIsFaulty 2 }

        -- 1.3.6.1.4.1.2011.2.251.20.1.2.2.15.209.83
        pcieChannelIsFaulty OBJECT IDENTIFIER ::= { interfacemodule 83 }

        -- 1.3.6.1.4.1.2011.2.251.20.1.2.2.15.209.83.1
        pcieChannelIsFaulty-Fault NOTIFICATION-TYPE
            OBJECTS { hwStorageAlarmReporting }
            STATUS current
            DESCRIPTION "The PCIe Channel Between An Interface Module And A Controller Is Abnormal"
            --#SEVERITY MAJOR
            ::= { pcieChannelIsFaulty 1 }

        -- 1.3.6.1.4.1.2011.2.251.20.1.2.2.15.209.83.2
        pcieChannelIsFaulty-Resume NOTIFICATION-TYPE
            OBJECTS { hwStorageAlarmReporting }
            STATUS current
            DESCRIPTION "Recover: The PCIe Channel Between An Interface Module And A Controller Is Abnormal"
            --#SEVERITY INFORMATIONAL
            ::= { pcieChannelIsFaulty 2 }

        -- 1.3.6.1.4.1.2011.2.251.20.1.2.2.15.209.87
        anUnsupportedSpareInterfaceModuleIsInsertedIntoTheSlot OBJECT IDENTIFIER ::= { interfacemodule 87 }

        -- 1.3.6.1.4.1.2011.2.251.20.1.2.2.15.209.87.1
        anUnsupportedSpareInterfaceModuleIsInsertedIntoTheSlot-Fault NOTIFICATION-TYPE
            OBJECTS { hwStorageAlarmReporting }
            STATUS current
            DESCRIPTION "An Unsupported Spare Interface Module Is Inserted Into The Slot"
            --#SEVERITY MAJOR
            ::= { anUnsupportedSpareInterfaceModuleIsInsertedIntoTheSlot 1 }

        -- 1.3.6.1.4.1.2011.2.251.20.1.2.2.15.209.87.2
        anUnsupportedSpareInterfaceModuleIsInsertedIntoTheSlot-Resume NOTIFICATION-TYPE
            OBJECTS { hwStorageAlarmReporting }
            STATUS current
            DESCRIPTION "Recover: An Unsupported Spare Interface Module Is Inserted Into The Slot"
            --#SEVERITY INFORMATIONAL
            ::= { anUnsupportedSpareInterfaceModuleIsInsertedIntoTheSlot 2 }

        -- 1.3.6.1.4.1.2011.2.251.20.1.2.2.15.209.89
        theInterfaceModuleIsIncompatibleWithTheOceanStorOSKernelVersion OBJECT IDENTIFIER ::= { interfacemodule 89 }

        -- 1.3.6.1.4.1.2011.2.251.20.1.2.2.15.209.89.1
        theInterfaceModuleIsIncompatibleWithTheOceanStorOSKernelVersion-Fault NOTIFICATION-TYPE
            OBJECTS { hwStorageAlarmReporting }
            STATUS current
            DESCRIPTION "The Interface Module Is Incompatible With The OceanStor OS Kernel Version"
            --#SEVERITY MAJOR
            ::= { theInterfaceModuleIsIncompatibleWithTheOceanStorOSKernelVersion 1 }

        -- 1.3.6.1.4.1.2011.2.251.20.1.2.2.15.209.89.2
        theInterfaceModuleIsIncompatibleWithTheOceanStorOSKernelVersion-Resume NOTIFICATION-TYPE
            OBJECTS { hwStorageAlarmReporting }
            STATUS current
            DESCRIPTION "Recover: The Interface Module Is Incompatible With The OceanStor OS Kernel Version"
            --#SEVERITY INFORMATIONAL
            ::= { theInterfaceModuleIsIncompatibleWithTheOceanStorOSKernelVersion 2 }

        -- 1.3.6.1.4.1.2011.2.251.20.1.2.2.15.209.91
        theInterfaceModuleIsInAbnormalStatus OBJECT IDENTIFIER ::= { interfacemodule 91 }

        -- 1.3.6.1.4.1.2011.2.251.20.1.2.2.15.209.91.1
        theInterfaceModuleIsInAbnormalStatus-Fault NOTIFICATION-TYPE
            OBJECTS { hwStorageAlarmReporting }
            STATUS current
            DESCRIPTION "The Interface Module Is In Abnormal Status"
            --#SEVERITY WARNING
            ::= { theInterfaceModuleIsInAbnormalStatus 1 }

        -- 1.3.6.1.4.1.2011.2.251.20.1.2.2.15.209.91.2
        theInterfaceModuleIsInAbnormalStatus-Resume NOTIFICATION-TYPE
            OBJECTS { hwStorageAlarmReporting }
            STATUS current
            DESCRIPTION "Recover: The Interface Module Is In Abnormal Status"
            --#SEVERITY INFORMATIONAL
            ::= { theInterfaceModuleIsInAbnormalStatus 2 }

        -- 1.3.6.1.4.1.2011.2.251.20.1.2.2.15.209.94
        riserCardChipFaults OBJECT IDENTIFIER ::= { interfacemodule 94 }

        -- 1.3.6.1.4.1.2011.2.251.20.1.2.2.15.209.94.1
        riserCardChipFaults-Fault NOTIFICATION-TYPE
            OBJECTS { hwStorageAlarmReporting }
            STATUS current
            DESCRIPTION "Riser Card Chip Faults"
            --#SEVERITY MAJOR
            ::= { riserCardChipFaults 1 }

        -- 1.3.6.1.4.1.2011.2.251.20.1.2.2.15.209.94.2
        riserCardChipFaults-Resume NOTIFICATION-TYPE
            OBJECTS { hwStorageAlarmReporting }
            STATUS current
            DESCRIPTION "Recover: Riser Card Chip Faults"
            --#SEVERITY INFORMATIONAL
            ::= { riserCardChipFaults 2 }

        -- 1.3.6.1.4.1.2011.2.251.20.1.2.2.15.209.106
        interfaceModuleIsFaultyWithOpn OBJECT IDENTIFIER ::= { interfacemodule 106 }

        -- 1.3.6.1.4.1.2011.2.251.20.1.2.2.15.209.106.1
        interfaceModuleIsFaultyWithOpn-Fault NOTIFICATION-TYPE
            OBJECTS { hwStorageAlarmReporting }
            STATUS current
            DESCRIPTION "Interface Module Is Faulty"
            --#SEVERITY MAJOR
            ::= { interfaceModuleIsFaultyWithOpn 1 }

        -- 1.3.6.1.4.1.2011.2.251.20.1.2.2.15.209.106.2
        interfaceModuleIsFaultyWithOpn-Resume NOTIFICATION-TYPE
            OBJECTS { hwStorageAlarmReporting }
            STATUS current
            DESCRIPTION "Recover: Interface Module Is Faulty"
            --#SEVERITY INFORMATIONAL
            ::= { interfaceModuleIsFaultyWithOpn 2 }

        -- 1.3.6.1.4.1.2011.2.251.20.1.2.2.15.210
        bbu OBJECT IDENTIFIER ::= { oidBasedTrap 210 }

        -- 1.3.6.1.4.1.2011.2.251.20.1.2.2.15.210.4
        bbuModuleIsRemoved OBJECT IDENTIFIER ::= { bbu 4 }

        -- 1.3.6.1.4.1.2011.2.251.20.1.2.2.15.210.4.1
        bbuModuleIsRemoved-Fault NOTIFICATION-TYPE
            OBJECTS { hwStorageAlarmReporting }
            STATUS current
            DESCRIPTION "BBU Module Is Removed"
            --#SEVERITY MAJOR
            ::= { bbuModuleIsRemoved 1 }

        -- 1.3.6.1.4.1.2011.2.251.20.1.2.2.15.210.4.2
        bbuModuleIsRemoved-Resume NOTIFICATION-TYPE
            OBJECTS { hwStorageAlarmReporting }
            STATUS current
            DESCRIPTION "Recover: BBU Module Is Removed"
            --#SEVERITY INFORMATIONAL
            ::= { bbuModuleIsRemoved 2 }

        -- 1.3.6.1.4.1.2011.2.251.20.1.2.2.15.210.5
        bbuModuleTempExceedsLimit OBJECT IDENTIFIER ::= { bbu 5 }

        -- 1.3.6.1.4.1.2011.2.251.20.1.2.2.15.210.5.1
        bbuModuleTempExceedsLimit-Fault NOTIFICATION-TYPE
            OBJECTS { hwStorageAlarmReporting }
            STATUS current
            DESCRIPTION "BBU Module Temperature Exceeds The Upper Limit"
            --#SEVERITY MAJOR
            ::= { bbuModuleTempExceedsLimit 1 }

        -- 1.3.6.1.4.1.2011.2.251.20.1.2.2.15.210.5.2
        bbuModuleTempExceedsLimit-Resume NOTIFICATION-TYPE
            OBJECTS { hwStorageAlarmReporting }
            STATUS current
            DESCRIPTION "Recover: BBU Module Temperature Exceeds The Upper Limit"
            --#SEVERITY INFORMATIONAL
            ::= { bbuModuleTempExceedsLimit 2 }

        -- 1.3.6.1.4.1.2011.2.251.20.1.2.2.15.210.20
        failedToMonitorABBUModule OBJECT IDENTIFIER ::= { bbu 20 }

        -- 1.3.6.1.4.1.2011.2.251.20.1.2.2.15.210.20.1
        failedToMonitorABBUModule-Fault NOTIFICATION-TYPE
            OBJECTS { hwStorageAlarmReporting }
            STATUS current
            DESCRIPTION "BBU Module Cannot Be Monitored"
            --#SEVERITY MAJOR
            ::= { failedToMonitorABBUModule 1 }

        -- 1.3.6.1.4.1.2011.2.251.20.1.2.2.15.210.20.2
        failedToMonitorABBUModule-Resume NOTIFICATION-TYPE
            OBJECTS { hwStorageAlarmReporting }
            STATUS current
            DESCRIPTION "Recover: BBU Module Cannot Be Monitored"
            --#SEVERITY INFORMATIONAL
            ::= { failedToMonitorABBUModule 2 }

        -- 1.3.6.1.4.1.2011.2.251.20.1.2.2.15.210.25
        bbuModuleTypeDoesNotComply OBJECT IDENTIFIER ::= { bbu 25 }

        -- 1.3.6.1.4.1.2011.2.251.20.1.2.2.15.210.25.1
        bbuModuleTypeDoesNotComply-Fault NOTIFICATION-TYPE
            OBJECTS { hwStorageAlarmReporting }
            STATUS current
            DESCRIPTION "The BBU Type Does Not Comply With The System Specification"
            --#SEVERITY MAJOR
            ::= { bbuModuleTypeDoesNotComply 1 }

        -- 1.3.6.1.4.1.2011.2.251.20.1.2.2.15.210.25.2
        bbuModuleTypeDoesNotComply-Resume NOTIFICATION-TYPE
            OBJECTS { hwStorageAlarmReporting }
            STATUS current
            DESCRIPTION "Recover: The BBU Type Does Not Comply With The System Specification"
            --#SEVERITY INFORMATIONAL
            ::= { bbuModuleTypeDoesNotComply 2 }

        -- 1.3.6.1.4.1.2011.2.251.20.1.2.2.15.210.27
        bbuModuleTempIsBelowLimit OBJECT IDENTIFIER ::= { bbu 27 }

        -- 1.3.6.1.4.1.2011.2.251.20.1.2.2.15.210.27.1
        bbuModuleTempIsBelowLimit-Fault NOTIFICATION-TYPE
            OBJECTS { hwStorageAlarmReporting }
            STATUS current
            DESCRIPTION "BBU Module Temperature Is Below The Lower Limit"
            --#SEVERITY MAJOR
            ::= { bbuModuleTempIsBelowLimit 1 }

        -- 1.3.6.1.4.1.2011.2.251.20.1.2.2.15.210.27.2
        bbuModuleTempIsBelowLimit-Resume NOTIFICATION-TYPE
            OBJECTS { hwStorageAlarmReporting }
            STATUS current
            DESCRIPTION "Recover: BBU Module Temperature Is Below The Lower Limit"
            --#SEVERITY INFORMATIONAL
            ::= { bbuModuleTempIsBelowLimit 2 }

        -- 1.3.6.1.4.1.2011.2.251.20.1.2.2.15.210.28
        bbuModuleIsFaulty OBJECT IDENTIFIER ::= { bbu 28 }

        -- 1.3.6.1.4.1.2011.2.251.20.1.2.2.15.210.28.1
        bbuModuleIsFaulty-Fault NOTIFICATION-TYPE
            OBJECTS { hwStorageAlarmReporting }
            STATUS current
            DESCRIPTION "BBU Module Is Faulty"
            --#SEVERITY MAJOR
            ::= { bbuModuleIsFaulty 1 }

        -- 1.3.6.1.4.1.2011.2.251.20.1.2.2.15.210.28.2
        bbuModuleIsFaulty-Resume NOTIFICATION-TYPE
            OBJECTS { hwStorageAlarmReporting }
            STATUS current
            DESCRIPTION "Recover: BBU Module Is Faulty"
            --#SEVERITY INFORMATIONAL
            ::= { bbuModuleIsFaulty 2 }

        -- 1.3.6.1.4.1.2011.2.251.20.1.2.2.15.210.29
        bbuModuleLifeIsOvertime OBJECT IDENTIFIER ::= { bbu 29 }

        -- 1.3.6.1.4.1.2011.2.251.20.1.2.2.15.210.29.1
        bbuModuleLifeIsOvertime-Fault NOTIFICATION-TYPE
            OBJECTS { hwStorageAlarmReporting }
            STATUS current
            DESCRIPTION "BBU Module Reaches Its Expiration Date Or Is Aging"
            --#SEVERITY CRITICAL
            ::= { bbuModuleLifeIsOvertime 1 }

        -- 1.3.6.1.4.1.2011.2.251.20.1.2.2.15.210.29.2
        bbuModuleLifeIsOvertime-Resume NOTIFICATION-TYPE
            OBJECTS { hwStorageAlarmReporting }
            STATUS current
            DESCRIPTION "Recover: BBU Module Reaches Its Expiration Date Or Is Aging"
            --#SEVERITY INFORMATIONAL
            ::= { bbuModuleLifeIsOvertime 2 }

        -- 1.3.6.1.4.1.2011.2.251.20.1.2.2.15.210.30
        bbuModuleIsAboutToExpire OBJECT IDENTIFIER ::= { bbu 30 }

        -- 1.3.6.1.4.1.2011.2.251.20.1.2.2.15.210.30.1
        bbuModuleIsAboutToExpire-Fault NOTIFICATION-TYPE
            OBJECTS { hwStorageAlarmReporting }
            STATUS current
            DESCRIPTION "BBU Module Is About To Expire"
            --#SEVERITY MAJOR
            ::= { bbuModuleIsAboutToExpire 1 }

        -- 1.3.6.1.4.1.2011.2.251.20.1.2.2.15.210.30.2
        bbuModuleIsAboutToExpire-Resume NOTIFICATION-TYPE
            OBJECTS { hwStorageAlarmReporting }
            STATUS current
            DESCRIPTION "Recover: BBU Module Is About To Expire"
            --#SEVERITY INFORMATIONAL
            ::= { bbuModuleIsAboutToExpire 2 }

        -- 1.3.6.1.4.1.2011.2.251.20.1.2.2.15.210.37
        potentialPowerBackupRisks OBJECT IDENTIFIER ::= { bbu 37 }

        -- 1.3.6.1.4.1.2011.2.251.20.1.2.2.15.210.37.1
        potentialPowerBackupRisks-Fault NOTIFICATION-TYPE
            OBJECTS { hwStorageAlarmReporting }
            STATUS current
            DESCRIPTION "Potential Risks Of System Backup Power"
            --#SEVERITY MAJOR
            ::= { potentialPowerBackupRisks 1 }

        -- 1.3.6.1.4.1.2011.2.251.20.1.2.2.15.210.37.2
        potentialPowerBackupRisks-Resume NOTIFICATION-TYPE
            OBJECTS { hwStorageAlarmReporting }
            STATUS current
            DESCRIPTION "Recover: Potential Risks Of System Backup Power"
            --#SEVERITY INFORMATIONAL
            ::= { potentialPowerBackupRisks 2 }

        -- 1.3.6.1.4.1.2011.2.251.20.1.2.2.15.210.39
        bbuFirmwareIncompatible OBJECT IDENTIFIER ::= { bbu 39 }

        -- 1.3.6.1.4.1.2011.2.251.20.1.2.2.15.210.39.1
        bbuFirmwareIncompatible-Fault NOTIFICATION-TYPE
            OBJECTS { hwStorageAlarmReporting }
            STATUS current
            DESCRIPTION "BBU Firmware Is Incompatible With Storage Array Software"
            --#SEVERITY WARNING
            ::= { bbuFirmwareIncompatible 1 }

        -- 1.3.6.1.4.1.2011.2.251.20.1.2.2.15.210.39.2
        bbuFirmwareIncompatible-Resume NOTIFICATION-TYPE
            OBJECTS { hwStorageAlarmReporting }
            STATUS current
            DESCRIPTION "Recover: BBU Firmware Is Incompatible With Storage Array Software"
            --#SEVERITY INFORMATIONAL
            ::= { bbuFirmwareIncompatible 2 }

        -- 1.3.6.1.4.1.2011.2.251.20.1.2.2.15.211
        fanmodule OBJECT IDENTIFIER ::= { oidBasedTrap 211 }

        -- 1.3.6.1.4.1.2011.2.251.20.1.2.2.15.211.3
        fanModuleIsRemoved OBJECT IDENTIFIER ::= { fanmodule 3 }

        -- 1.3.6.1.4.1.2011.2.251.20.1.2.2.15.211.3.1
        fanModuleIsRemoved-Fault NOTIFICATION-TYPE
            OBJECTS { hwStorageAlarmReporting }
            STATUS current
            DESCRIPTION "Fan Module Removed"
            --#SEVERITY MAJOR
            ::= { fanModuleIsRemoved 1 }

        -- 1.3.6.1.4.1.2011.2.251.20.1.2.2.15.211.3.2
        fanModuleIsRemoved-Resume NOTIFICATION-TYPE
            OBJECTS { hwStorageAlarmReporting }
            STATUS current
            DESCRIPTION "Recover: Fan Module Removed"
            --#SEVERITY INFORMATIONAL
            ::= { fanModuleIsRemoved 2 }

        -- 1.3.6.1.4.1.2011.2.251.20.1.2.2.15.211.20
        failedToMonitorAFanModule OBJECT IDENTIFIER ::= { fanmodule 20 }

        -- 1.3.6.1.4.1.2011.2.251.20.1.2.2.15.211.20.1
        failedToMonitorAFanModule-Fault NOTIFICATION-TYPE
            OBJECTS { hwStorageAlarmReporting }
            STATUS current
            DESCRIPTION "Fan Module Cannot Be Monitored"
            --#SEVERITY MAJOR
            ::= { failedToMonitorAFanModule 1 }

        -- 1.3.6.1.4.1.2011.2.251.20.1.2.2.15.211.20.2
        failedToMonitorAFanModule-Resume NOTIFICATION-TYPE
            OBJECTS { hwStorageAlarmReporting }
            STATUS current
            DESCRIPTION "Recover: Fan Module Cannot Be Monitored"
            --#SEVERITY INFORMATIONAL
            ::= { failedToMonitorAFanModule 2 }

        -- 1.3.6.1.4.1.2011.2.251.20.1.2.2.15.211.21
        fanModuleIsFaulty OBJECT IDENTIFIER ::= { fanmodule 21 }

        -- 1.3.6.1.4.1.2011.2.251.20.1.2.2.15.211.21.1
        fanModuleIsFaulty-Fault NOTIFICATION-TYPE
            OBJECTS { hwStorageAlarmReporting }
            STATUS current
            DESCRIPTION "Fan Module Is Faulty"
            --#SEVERITY MAJOR
            ::= { fanModuleIsFaulty 1 }

        -- 1.3.6.1.4.1.2011.2.251.20.1.2.2.15.211.21.2
        fanModuleIsFaulty-Resume NOTIFICATION-TYPE
            OBJECTS { hwStorageAlarmReporting }
            STATUS current
            DESCRIPTION "Recover: Fan Module Is Faulty"
            --#SEVERITY INFORMATIONAL
            ::= { fanModuleIsFaulty 2 }

        -- 1.3.6.1.4.1.2011.2.251.20.1.2.2.15.211.23
        ctrlFanFaulty OBJECT IDENTIFIER ::= { fanmodule 23 }

        -- 1.3.6.1.4.1.2011.2.251.20.1.2.2.15.211.23.1
        ctrlFanFaulty-Fault NOTIFICATION-TYPE
            OBJECTS { hwStorageAlarmReporting }
            STATUS current
            DESCRIPTION "Faulty Fan Module"
            --#SEVERITY MAJOR
            ::= { ctrlFanFaulty 1 }

        -- 1.3.6.1.4.1.2011.2.251.20.1.2.2.15.211.23.2
        ctrlFanFaulty-Resume NOTIFICATION-TYPE
            OBJECTS { hwStorageAlarmReporting }
            STATUS current
            DESCRIPTION "Recover: Faulty Fan Module"
            --#SEVERITY INFORMATIONAL
            ::= { ctrlFanFaulty 2 }

        -- 1.3.6.1.4.1.2011.2.251.20.1.2.2.15.211.24
        expFanFaulty OBJECT IDENTIFIER ::= { fanmodule 24 }

        -- 1.3.6.1.4.1.2011.2.251.20.1.2.2.15.211.24.1
        expFanFaulty-Fault NOTIFICATION-TYPE
            OBJECTS { hwStorageAlarmReporting }
            STATUS current
            DESCRIPTION "Faulty Fan Module"
            --#SEVERITY MAJOR
            ::= { expFanFaulty 1 }

        -- 1.3.6.1.4.1.2011.2.251.20.1.2.2.15.211.24.2
        expFanFaulty-Resume NOTIFICATION-TYPE
            OBJECTS { hwStorageAlarmReporting }
            STATUS current
            DESCRIPTION "Recover: Faulty Fan Module"
            --#SEVERITY INFORMATIONAL
            ::= { expFanFaulty 2 }

        -- 1.3.6.1.4.1.2011.2.251.20.1.2.2.15.211.25
        fanCtlBoardFanFaulty OBJECT IDENTIFIER ::= { fanmodule 25 }

        -- 1.3.6.1.4.1.2011.2.251.20.1.2.2.15.211.25.1
        fanCtlBoardFanFaulty-Fault NOTIFICATION-TYPE
            OBJECTS { hwStorageAlarmReporting }
            STATUS current
            DESCRIPTION "The Fan Module Is Faulty"
            --#SEVERITY MAJOR
            ::= { fanCtlBoardFanFaulty 1 }

        -- 1.3.6.1.4.1.2011.2.251.20.1.2.2.15.211.25.2
        fanCtlBoardFanFaulty-Resume NOTIFICATION-TYPE
            OBJECTS { hwStorageAlarmReporting }
            STATUS current
            DESCRIPTION "Recover: The Fan Module Is Faulty"
            --#SEVERITY INFORMATIONAL
            ::= { fanCtlBoardFanFaulty 2 }

        -- 1.3.6.1.4.1.2011.2.251.20.1.2.2.15.216
        storagepool OBJECT IDENTIFIER ::= { oidBasedTrap 216 }

        -- 1.3.6.1.4.1.2011.2.251.20.1.2.2.15.216.1
        storagePoolIsDegraded OBJECT IDENTIFIER ::= { storagepool 1 }

        -- 1.3.6.1.4.1.2011.2.251.20.1.2.2.15.216.1.1
        storagePoolIsDegraded-Fault NOTIFICATION-TYPE
            OBJECTS { hwStorageAlarmReporting }
            STATUS current
            DESCRIPTION "Storage Pool Is Degraded"
            --#SEVERITY CRITICAL
            ::= { storagePoolIsDegraded 1 }

        -- 1.3.6.1.4.1.2011.2.251.20.1.2.2.15.216.1.2
        storagePoolIsDegraded-Resume NOTIFICATION-TYPE
            OBJECTS { hwStorageAlarmReporting }
            STATUS current
            DESCRIPTION "Recover: Storage Pool Is Degraded"
            --#SEVERITY INFORMATIONAL
            ::= { storagePoolIsDegraded 2 }

        -- 1.3.6.1.4.1.2011.2.251.20.1.2.2.15.216.2
        storagePoolIsFaulty OBJECT IDENTIFIER ::= { storagepool 2 }

        -- 1.3.6.1.4.1.2011.2.251.20.1.2.2.15.216.2.1
        storagePoolIsFaulty-Fault NOTIFICATION-TYPE
            OBJECTS { hwStorageAlarmReporting }
            STATUS current
            DESCRIPTION "Storage Pool Is Faulty"
            --#SEVERITY CRITICAL
            ::= { storagePoolIsFaulty 1 }

        -- 1.3.6.1.4.1.2011.2.251.20.1.2.2.15.216.2.2
        storagePoolIsFaulty-Resume NOTIFICATION-TYPE
            OBJECTS { hwStorageAlarmReporting }
            STATUS current
            DESCRIPTION "Recover: Storage Pool Is Faulty"
            --#SEVERITY INFORMATIONAL
            ::= { storagePoolIsFaulty 2 }

        -- 1.3.6.1.4.1.2011.2.251.20.1.2.2.15.216.10
        currentUsageOfTheBackupStoragePoolExceedsTheThreshold OBJECT IDENTIFIER ::= { storagepool 10 }

        -- 1.3.6.1.4.1.2011.2.251.20.1.2.2.15.216.10.1
        currentUsageOfTheBackupStoragePoolExceedsTheThreshold-Fault NOTIFICATION-TYPE
            OBJECTS { hwStorageAlarmReporting }
            STATUS current
            DESCRIPTION "Current Usage Of The Backup Storage Pool Exceeds The Threshold"
            --#SEVERITY WARNING
            ::= { currentUsageOfTheBackupStoragePoolExceedsTheThreshold 1 }

        -- 1.3.6.1.4.1.2011.2.251.20.1.2.2.15.216.10.2
        currentUsageOfTheBackupStoragePoolExceedsTheThreshold-Resume NOTIFICATION-TYPE
            OBJECTS { hwStorageAlarmReporting }
            STATUS current
            DESCRIPTION "Recover: Current Usage Of The Backup Storage Pool Exceeds The Threshold"
            --#SEVERITY INFORMATIONAL
            ::= { currentUsageOfTheBackupStoragePoolExceedsTheThreshold 2 }

        -- 1.3.6.1.4.1.2011.2.251.20.1.2.2.15.216.21
        aStoragePoolIsOffline OBJECT IDENTIFIER ::= { storagepool 21 }

        -- 1.3.6.1.4.1.2011.2.251.20.1.2.2.15.216.21.1
        aStoragePoolIsOffline-Fault NOTIFICATION-TYPE
            OBJECTS { hwStorageAlarmReporting }
            STATUS current
            DESCRIPTION "A Storage Pool Is Offline"
            --#SEVERITY CRITICAL
            ::= { aStoragePoolIsOffline 1 }

        -- 1.3.6.1.4.1.2011.2.251.20.1.2.2.15.216.21.2
        aStoragePoolIsOffline-Resume NOTIFICATION-TYPE
            OBJECTS { hwStorageAlarmReporting }
            STATUS current
            DESCRIPTION "Recover: A Storage Pool Is Offline"
            --#SEVERITY INFORMATIONAL
            ::= { aStoragePoolIsOffline 2 }

        -- 1.3.6.1.4.1.2011.2.251.20.1.2.2.15.216.281
        storagePoolCapacityNotEnough1 OBJECT IDENTIFIER ::= { storagepool 281 }

        -- 1.3.6.1.4.1.2011.2.251.20.1.2.2.15.216.281.1
        storagePoolCapacityNotEnough1-Fault NOTIFICATION-TYPE
            OBJECTS { hwStorageAlarmReporting }
            STATUS current
            DESCRIPTION "Storage Pool Remaining Capacity Is Insufficient"
            --#SEVERITY MAJOR
            ::= { storagePoolCapacityNotEnough1 1 }

        -- 1.3.6.1.4.1.2011.2.251.20.1.2.2.15.216.281.2
        storagePoolCapacityNotEnough1-Resume NOTIFICATION-TYPE
            OBJECTS { hwStorageAlarmReporting }
            STATUS current
            DESCRIPTION "Recover: Storage Pool Remaining Capacity Is Insufficient"
            --#SEVERITY INFORMATIONAL
            ::= { storagePoolCapacityNotEnough1 2 }

        -- 1.3.6.1.4.1.2011.2.251.20.1.2.2.15.216.285
        storagePoolCapacityIsUsedUp1 OBJECT IDENTIFIER ::= { storagepool 285 }

        -- 1.3.6.1.4.1.2011.2.251.20.1.2.2.15.216.285.1
        storagePoolCapacityIsUsedUp1-Fault NOTIFICATION-TYPE
            OBJECTS { hwStorageAlarmReporting }
            STATUS current
            DESCRIPTION "Storage Pool Capacity Is Used Up"
            --#SEVERITY CRITICAL
            ::= { storagePoolCapacityIsUsedUp1 1 }

        -- 1.3.6.1.4.1.2011.2.251.20.1.2.2.15.216.285.2
        storagePoolCapacityIsUsedUp1-Resume NOTIFICATION-TYPE
            OBJECTS { hwStorageAlarmReporting }
            STATUS current
            DESCRIPTION "Recover: Storage Pool Capacity Is Used Up"
            --#SEVERITY INFORMATIONAL
            ::= { storagePoolCapacityIsUsedUp1 2 }

        -- 1.3.6.1.4.1.2011.2.251.20.1.2.2.15.216.288
        storagePoolCapacityShouldUseUp OBJECT IDENTIFIER ::= { storagepool 288 }

        -- 1.3.6.1.4.1.2011.2.251.20.1.2.2.15.216.288.1
        storagePoolCapacityShouldUseUp-Fault NOTIFICATION-TYPE
            OBJECTS { hwStorageAlarmReporting }
            STATUS current
            DESCRIPTION "Storage Pool Capacity Is About To Be Used Up"
            --#SEVERITY CRITICAL
            ::= { storagePoolCapacityShouldUseUp 1 }

        -- 1.3.6.1.4.1.2011.2.251.20.1.2.2.15.216.288.2
        storagePoolCapacityShouldUseUp-Resume NOTIFICATION-TYPE
            OBJECTS { hwStorageAlarmReporting }
            STATUS current
            DESCRIPTION "Recover: Storage Pool Capacity Is About To Be Used Up"
            --#SEVERITY INFORMATIONAL
            ::= { storagePoolCapacityShouldUseUp 2 }

        -- 1.3.6.1.4.1.2011.2.251.20.1.2.2.15.216.322
        theEffectiveCapacityOfTheSystemIsInsufficient OBJECT IDENTIFIER ::= { storagepool 322 }

        -- 1.3.6.1.4.1.2011.2.251.20.1.2.2.15.216.322.1
        theEffectiveCapacityOfTheSystemIsInsufficient-Fault NOTIFICATION-TYPE
            OBJECTS { hwStorageAlarmReporting }
            STATUS current
            DESCRIPTION "The Effective Capacity Of The System Is Insufficient"
            --#SEVERITY MAJOR
            ::= { theEffectiveCapacityOfTheSystemIsInsufficient 1 }

        -- 1.3.6.1.4.1.2011.2.251.20.1.2.2.15.216.322.2
        theEffectiveCapacityOfTheSystemIsInsufficient-Resume NOTIFICATION-TYPE
            OBJECTS { hwStorageAlarmReporting }
            STATUS current
            DESCRIPTION "Recover: The Effective Capacity Of The System Is Insufficient"
            --#SEVERITY INFORMATIONAL
            ::= { theEffectiveCapacityOfTheSystemIsInsufficient 2 }

        -- 1.3.6.1.4.1.2011.2.251.20.1.2.2.15.216.323
        theEffectiveCapacityOfTheSystemIsAboutToBeUsedUp OBJECT IDENTIFIER ::= { storagepool 323 }

        -- 1.3.6.1.4.1.2011.2.251.20.1.2.2.15.216.323.1
        theEffectiveCapacityOfTheSystemIsAboutToBeUsedUp-Fault NOTIFICATION-TYPE
            OBJECTS { hwStorageAlarmReporting }
            STATUS current
            DESCRIPTION "The Effective Capacity Of The System Is About To Be Used Up"
            --#SEVERITY CRITICAL
            ::= { theEffectiveCapacityOfTheSystemIsAboutToBeUsedUp 1 }

        -- 1.3.6.1.4.1.2011.2.251.20.1.2.2.15.216.323.2
        theEffectiveCapacityOfTheSystemIsAboutToBeUsedUp-Resume NOTIFICATION-TYPE
            OBJECTS { hwStorageAlarmReporting }
            STATUS current
            DESCRIPTION "Recover: The Effective Capacity Of The System Is About To Be Used Up"
            --#SEVERITY INFORMATIONAL
            ::= { theEffectiveCapacityOfTheSystemIsAboutToBeUsedUp 2 }

        -- 1.3.6.1.4.1.2011.2.251.20.1.2.2.15.216.324
        theEffectiveCapacityOfTheSystemIsUsedUp OBJECT IDENTIFIER ::= { storagepool 324 }

        -- 1.3.6.1.4.1.2011.2.251.20.1.2.2.15.216.324.1
        theEffectiveCapacityOfTheSystemIsUsedUp-Fault NOTIFICATION-TYPE
            OBJECTS { hwStorageAlarmReporting }
            STATUS current
            DESCRIPTION "The Effective Capacity Of The System Is Used Up"
            --#SEVERITY CRITICAL
            ::= { theEffectiveCapacityOfTheSystemIsUsedUp 1 }

        -- 1.3.6.1.4.1.2011.2.251.20.1.2.2.15.216.324.2
        theEffectiveCapacityOfTheSystemIsUsedUp-Resume NOTIFICATION-TYPE
            OBJECTS { hwStorageAlarmReporting }
            STATUS current
            DESCRIPTION "Recover: The Effective Capacity Of The System Is Used Up"
            --#SEVERITY INFORMATIONAL
            ::= { theEffectiveCapacityOfTheSystemIsUsedUp 2 }

        -- 1.3.6.1.4.1.2011.2.251.20.1.2.2.15.216.328
        theUsedEffectiveCapacityIsNotAsExpected OBJECT IDENTIFIER ::= { storagepool 328 }

        -- 1.3.6.1.4.1.2011.2.251.20.1.2.2.15.216.328.1
        theUsedEffectiveCapacityIsNotAsExpected-Fault NOTIFICATION-TYPE
            OBJECTS { hwStorageAlarmReporting }
            STATUS current
            DESCRIPTION "The Used Effective Capacity Is Not As Expected"
            --#SEVERITY MAJOR
            ::= { theUsedEffectiveCapacityIsNotAsExpected 1 }

        -- 1.3.6.1.4.1.2011.2.251.20.1.2.2.15.216.328.2
        theUsedEffectiveCapacityIsNotAsExpected-Resume NOTIFICATION-TYPE
            OBJECTS { hwStorageAlarmReporting }
            STATUS current
            DESCRIPTION "Recover: The Used Effective Capacity Is Not As Expected"
            --#SEVERITY INFORMATIONAL
            ::= { theUsedEffectiveCapacityIsNotAsExpected 2 }

        -- 1.3.6.1.4.1.2011.2.251.20.1.2.2.15.216.337
        storagePoolCapacityIsUsedUp OBJECT IDENTIFIER ::= { storagepool 337 }

        -- 1.3.6.1.4.1.2011.2.251.20.1.2.2.15.216.337.1
        storagePoolCapacityIsUsedUp-Fault NOTIFICATION-TYPE
            OBJECTS { hwStorageAlarmReporting }
            STATUS current
            DESCRIPTION "Storage Pool Capacity Is Used Up"
            --#SEVERITY CRITICAL
            ::= { storagePoolCapacityIsUsedUp 1 }

        -- 1.3.6.1.4.1.2011.2.251.20.1.2.2.15.216.337.2
        storagePoolCapacityIsUsedUp-Resume NOTIFICATION-TYPE
            OBJECTS { hwStorageAlarmReporting }
            STATUS current
            DESCRIPTION "Recover: Storage Pool Capacity Is Used Up"
            --#SEVERITY INFORMATIONAL
            ::= { storagePoolCapacityIsUsedUp 2 }

        -- 1.3.6.1.4.1.2011.2.251.20.1.2.2.15.216.345
        storagePoolCapacityNotEnough OBJECT IDENTIFIER ::= { storagepool 345 }

        -- 1.3.6.1.4.1.2011.2.251.20.1.2.2.15.216.345.1
        storagePoolCapacityNotEnough-Fault NOTIFICATION-TYPE
            OBJECTS { hwStorageAlarmReporting }
            STATUS current
            DESCRIPTION "Storage Pool Remaining Capacity Is Insufficient"
            --#SEVERITY MAJOR
            ::= { storagePoolCapacityNotEnough 1 }

        -- 1.3.6.1.4.1.2011.2.251.20.1.2.2.15.216.345.2
        storagePoolCapacityNotEnough-Resume NOTIFICATION-TYPE
            OBJECTS { hwStorageAlarmReporting }
            STATUS current
            DESCRIPTION "Recover: Storage Pool Remaining Capacity Is Insufficient"
            --#SEVERITY INFORMATIONAL
            ::= { storagePoolCapacityNotEnough 2 }

        -- 1.3.6.1.4.1.2011.2.251.20.1.2.2.15.216.346
        storagePoolCapacityShouldUseUp2 OBJECT IDENTIFIER ::= { storagepool 346 }

        -- 1.3.6.1.4.1.2011.2.251.20.1.2.2.15.216.346.1
        storagePoolCapacityShouldUseUp2-Fault NOTIFICATION-TYPE
            OBJECTS { hwStorageAlarmReporting }
            STATUS current
            DESCRIPTION "The Storage Pool Capacity Is About To Be Used Up"
            --#SEVERITY CRITICAL
            ::= { storagePoolCapacityShouldUseUp2 1 }

        -- 1.3.6.1.4.1.2011.2.251.20.1.2.2.15.216.346.2
        storagePoolCapacityShouldUseUp2-Resume NOTIFICATION-TYPE
            OBJECTS { hwStorageAlarmReporting }
            STATUS current
            DESCRIPTION "Recover: The Storage Pool Capacity Is About To Be Used Up"
            --#SEVERITY INFORMATIONAL
            ::= { storagePoolCapacityShouldUseUp2 2 }

        -- 1.3.6.1.4.1.2011.2.251.20.1.2.2.15.216.358
        storagePoolCapacityShouldUseUp1 OBJECT IDENTIFIER ::= { storagepool 358 }

        -- 1.3.6.1.4.1.2011.2.251.20.1.2.2.15.216.358.1
        storagePoolCapacityShouldUseUp1-Fault NOTIFICATION-TYPE
            OBJECTS { hwStorageAlarmReporting }
            STATUS current
            DESCRIPTION "The Storage Pool Capacity Is About To Be Used Up"
            --#SEVERITY CRITICAL
            ::= { storagePoolCapacityShouldUseUp1 1 }

        -- 1.3.6.1.4.1.2011.2.251.20.1.2.2.15.216.358.2
        storagePoolCapacityShouldUseUp1-Resume NOTIFICATION-TYPE
            OBJECTS { hwStorageAlarmReporting }
            STATUS current
            DESCRIPTION "Recover: The Storage Pool Capacity Is About To Be Used Up"
            --#SEVERITY INFORMATIONAL
            ::= { storagePoolCapacityShouldUseUp1 2 }

        -- 1.3.6.1.4.1.2011.2.251.20.1.2.2.15.218
        smartcachepool OBJECT IDENTIFIER ::= { oidBasedTrap 218 }

        -- 1.3.6.1.4.1.2011.2.251.20.1.2.2.15.218.3
        differentDiskType OBJECT IDENTIFIER ::= { smartcachepool 3 }

        -- 1.3.6.1.4.1.2011.2.251.20.1.2.2.15.218.3.1
        differentDiskType-Fault NOTIFICATION-TYPE
            OBJECTS { hwStorageAlarmReporting }
            STATUS current
            DESCRIPTION "Inconsistent Smart Cache Disk Types"
            --#SEVERITY MAJOR
            ::= { differentDiskType 1 }

        -- 1.3.6.1.4.1.2011.2.251.20.1.2.2.15.218.3.2
        differentDiskType-Resume NOTIFICATION-TYPE
            OBJECTS { hwStorageAlarmReporting }
            STATUS current
            DESCRIPTION "Recover: Inconsistent Smart Cache Disk Types"
            --#SEVERITY INFORMATIONAL
            ::= { differentDiskType 2 }

        -- 1.3.6.1.4.1.2011.2.251.20.1.2.2.15.218.4
        inconsistentEncryptionTypesBeforeAndAfterDiskReplacement OBJECT IDENTIFIER ::= { smartcachepool 4 }

        -- 1.3.6.1.4.1.2011.2.251.20.1.2.2.15.218.4.1
        inconsistentEncryptionTypesBeforeAndAfterDiskReplacement-Fault NOTIFICATION-TYPE
            OBJECTS { hwStorageAlarmReporting }
            STATUS current
            DESCRIPTION "Inconsistent Encryption Types Before And After Disk Replacement"
            --#SEVERITY MAJOR
            ::= { inconsistentEncryptionTypesBeforeAndAfterDiskReplacement 1 }

        -- 1.3.6.1.4.1.2011.2.251.20.1.2.2.15.218.4.2
        inconsistentEncryptionTypesBeforeAndAfterDiskReplacement-Resume NOTIFICATION-TYPE
            OBJECTS { hwStorageAlarmReporting }
            STATUS current
            DESCRIPTION "Recover: Inconsistent Encryption Types Before And After Disk Replacement"
            --#SEVERITY INFORMATIONAL
            ::= { inconsistentEncryptionTypesBeforeAndAfterDiskReplacement 2 }

        -- 1.3.6.1.4.1.2011.2.251.20.1.2.2.15.218.5
        diskIsRemovedFromSmartCachePool OBJECT IDENTIFIER ::= { smartcachepool 5 }

        -- 1.3.6.1.4.1.2011.2.251.20.1.2.2.15.218.5.1
        diskIsRemovedFromSmartCachePool-Fault NOTIFICATION-TYPE
            OBJECTS { hwStorageAlarmReporting }
            STATUS current
            DESCRIPTION "A Disk Is Removed From A Smart Cache Pool"
            --#SEVERITY MAJOR
            ::= { diskIsRemovedFromSmartCachePool 1 }

        -- 1.3.6.1.4.1.2011.2.251.20.1.2.2.15.218.5.2
        diskIsRemovedFromSmartCachePool-Resume NOTIFICATION-TYPE
            OBJECTS { hwStorageAlarmReporting }
            STATUS current
            DESCRIPTION "Recover: A Disk Is Removed From A Smart Cache Pool"
            --#SEVERITY INFORMATIONAL
            ::= { diskIsRemovedFromSmartCachePool 2 }

        -- 1.3.6.1.4.1.2011.2.251.20.1.2.2.15.218.6
        newDiskCapacityInsufficieny OBJECT IDENTIFIER ::= { smartcachepool 6 }

        -- 1.3.6.1.4.1.2011.2.251.20.1.2.2.15.218.6.1
        newDiskCapacityInsufficieny-Fault NOTIFICATION-TYPE
            OBJECTS { hwStorageAlarmReporting }
            STATUS current
            DESCRIPTION "A New Disk Fails To Be Added To The Smart Cache Pool"
            --#SEVERITY MAJOR
            ::= { newDiskCapacityInsufficieny 1 }

        -- 1.3.6.1.4.1.2011.2.251.20.1.2.2.15.218.6.2
        newDiskCapacityInsufficieny-Resume NOTIFICATION-TYPE
            OBJECTS { hwStorageAlarmReporting }
            STATUS current
            DESCRIPTION "Recover: A New Disk Fails To Be Added To The Smart Cache Pool"
            --#SEVERITY INFORMATIONAL
            ::= { newDiskCapacityInsufficieny 2 }

        -- 1.3.6.1.4.1.2011.2.251.20.1.2.2.15.218.7
        theModelOfTheNewDiskIsDifferentFromTheReplacedOneAndCannotBeAddedToTheSmartCachePool OBJECT IDENTIFIER ::= { smartcachepool 7 }

        -- 1.3.6.1.4.1.2011.2.251.20.1.2.2.15.218.7.1
        theModelOfTheNewDiskIsDifferentFromTheReplacedOneAndCannotBeAddedToTheSmartCachePool-Fault NOTIFICATION-TYPE
            OBJECTS { hwStorageAlarmReporting }
            STATUS current
            DESCRIPTION "The Model Of The New Disk Is Different From The Replaced One And Cannot Be Added To The Smart Cache Pool"
            --#SEVERITY MAJOR
            ::= { theModelOfTheNewDiskIsDifferentFromTheReplacedOneAndCannotBeAddedToTheSmartCachePool 1 }

        -- 1.3.6.1.4.1.2011.2.251.20.1.2.2.15.218.7.2
        theModelOfTheNewDiskIsDifferentFromTheReplacedOneAndCannotBeAddedToTheSmartCachePool-Resume NOTIFICATION-TYPE
            OBJECTS { hwStorageAlarmReporting }
            STATUS current
            DESCRIPTION "Recover: The Model Of The New Disk Is Different From The Replaced One And Cannot Be Added To The Smart Cache Pool"
            --#SEVERITY INFORMATIONAL
            ::= { theModelOfTheNewDiskIsDifferentFromTheReplacedOneAndCannotBeAddedToTheSmartCachePool 2 }

        -- 1.3.6.1.4.1.2011.2.251.20.1.2.2.15.218.8
        theNewDiskFailedToBeAddedToTheSmartCachePool OBJECT IDENTIFIER ::= { smartcachepool 8 }

        -- 1.3.6.1.4.1.2011.2.251.20.1.2.2.15.218.8.1
        theNewDiskFailedToBeAddedToTheSmartCachePool-Fault NOTIFICATION-TYPE
            OBJECTS { hwStorageAlarmReporting }
            STATUS current
            DESCRIPTION "The New Disk Failed To Be Added To The Smart Cache Pool"
            --#SEVERITY MAJOR
            ::= { theNewDiskFailedToBeAddedToTheSmartCachePool 1 }

        -- 1.3.6.1.4.1.2011.2.251.20.1.2.2.15.218.8.2
        theNewDiskFailedToBeAddedToTheSmartCachePool-Resume NOTIFICATION-TYPE
            OBJECTS { hwStorageAlarmReporting }
            STATUS current
            DESCRIPTION "Recover: The New Disk Failed To Be Added To The Smart Cache Pool"
            --#SEVERITY INFORMATIONAL
            ::= { theNewDiskFailedToBeAddedToTheSmartCachePool 2 }

        -- 1.3.6.1.4.1.2011.2.251.20.1.2.2.15.218.9
        theSmartCachePoolReconstructionFailed OBJECT IDENTIFIER ::= { smartcachepool 9 }

        -- 1.3.6.1.4.1.2011.2.251.20.1.2.2.15.218.9.1
        theSmartCachePoolReconstructionFailed-Fault NOTIFICATION-TYPE
            OBJECTS { hwStorageAlarmReporting }
            STATUS current
            DESCRIPTION "The Smart Cache Pool Reconstruction Failed"
            --#SEVERITY MAJOR
            ::= { theSmartCachePoolReconstructionFailed 1 }

        -- 1.3.6.1.4.1.2011.2.251.20.1.2.2.15.218.9.2
        theSmartCachePoolReconstructionFailed-Resume NOTIFICATION-TYPE
            OBJECTS { hwStorageAlarmReporting }
            STATUS current
            DESCRIPTION "Recover: The Smart Cache Pool Reconstruction Failed"
            --#SEVERITY INFORMATIONAL
            ::= { theSmartCachePoolReconstructionFailed 2 }

        -- 1.3.6.1.4.1.2011.2.251.20.1.2.2.15.218.10
        theSmartCachePoolPrecopyFailed OBJECT IDENTIFIER ::= { smartcachepool 10 }

        -- 1.3.6.1.4.1.2011.2.251.20.1.2.2.15.218.10.1
        theSmartCachePoolPrecopyFailed-Fault NOTIFICATION-TYPE
            OBJECTS { hwStorageAlarmReporting }
            STATUS current
            DESCRIPTION "The Smart Cache Pool Precopy Failed"
            --#SEVERITY MAJOR
            ::= { theSmartCachePoolPrecopyFailed 1 }

        -- 1.3.6.1.4.1.2011.2.251.20.1.2.2.15.218.10.2
        theSmartCachePoolPrecopyFailed-Resume NOTIFICATION-TYPE
            OBJECTS { hwStorageAlarmReporting }
            STATUS current
            DESCRIPTION "Recover: The Smart Cache Pool Precopy Failed"
            --#SEVERITY INFORMATIONAL
            ::= { theSmartCachePoolPrecopyFailed 2 }

        -- 1.3.6.1.4.1.2011.2.251.20.1.2.2.15.221
        consistencygroup OBJECT IDENTIFIER ::= { oidBasedTrap 221 }

        -- 1.3.6.1.4.1.2011.2.251.20.1.2.2.15.221.1
        remoteReplicationCGIsInterrupted1 OBJECT IDENTIFIER ::= { consistencygroup 1 }

        -- 1.3.6.1.4.1.2011.2.251.20.1.2.2.15.221.1.1
        remoteReplicationCGIsInterrupted1-Fault NOTIFICATION-TYPE
            OBJECTS { hwStorageAlarmReporting }
            STATUS current
            DESCRIPTION "Remote Replication Consistency Group Is Disconnected"
            --#SEVERITY MAJOR
            ::= { remoteReplicationCGIsInterrupted1 1 }

        -- 1.3.6.1.4.1.2011.2.251.20.1.2.2.15.221.1.2
        remoteReplicationCGIsInterrupted1-Resume NOTIFICATION-TYPE
            OBJECTS { hwStorageAlarmReporting }
            STATUS current
            DESCRIPTION "Recover: Remote Replication Consistency Group Is Disconnected"
            --#SEVERITY INFORMATIONAL
            ::= { remoteReplicationCGIsInterrupted1 2 }

        -- 1.3.6.1.4.1.2011.2.251.20.1.2.2.15.221.2
        remoteReplicationCGIsUnavailable OBJECT IDENTIFIER ::= { consistencygroup 2 }

        -- 1.3.6.1.4.1.2011.2.251.20.1.2.2.15.221.2.1
        remoteReplicationCGIsUnavailable-Fault NOTIFICATION-TYPE
            OBJECTS { hwStorageAlarmReporting }
            STATUS current
            DESCRIPTION "Remote Replication Consistency Group Is Unavailable"
            --#SEVERITY CRITICAL
            ::= { remoteReplicationCGIsUnavailable 1 }

        -- 1.3.6.1.4.1.2011.2.251.20.1.2.2.15.221.2.2
        remoteReplicationCGIsUnavailable-Resume NOTIFICATION-TYPE
            OBJECTS { hwStorageAlarmReporting }
            STATUS current
            DESCRIPTION "Recover: Remote Replication Consistency Group Is Unavailable"
            --#SEVERITY INFORMATIONAL
            ::= { remoteReplicationCGIsUnavailable 2 }

        -- 1.3.6.1.4.1.2011.2.251.20.1.2.2.15.221.4
        remoteReplicationCGAutoSplit OBJECT IDENTIFIER ::= { consistencygroup 4 }

        -- 1.3.6.1.4.1.2011.2.251.20.1.2.2.15.221.4.1
        remoteReplicationCGAutoSplit-Fault NOTIFICATION-TYPE
            OBJECTS { hwStorageAlarmReporting }
            STATUS current
            DESCRIPTION "Remote Replication Consistency Group Is Automatically Split"
            --#SEVERITY WARNING
            ::= { remoteReplicationCGAutoSplit 1 }

        -- 1.3.6.1.4.1.2011.2.251.20.1.2.2.15.221.4.2
        remoteReplicationCGAutoSplit-Resume NOTIFICATION-TYPE
            OBJECTS { hwStorageAlarmReporting }
            STATUS current
            DESCRIPTION "Recover: Remote Replication Consistency Group Is Automatically Split"
            --#SEVERITY INFORMATIONAL
            ::= { remoteReplicationCGAutoSplit 2 }

        -- 1.3.6.1.4.1.2011.2.251.20.1.2.2.15.221.9
        remoteReplicationCGIsInterrupted OBJECT IDENTIFIER ::= { consistencygroup 9 }

        -- 1.3.6.1.4.1.2011.2.251.20.1.2.2.15.221.9.1
        remoteReplicationCGIsInterrupted-Fault NOTIFICATION-TYPE
            OBJECTS { hwStorageAlarmReporting }
            STATUS current
            DESCRIPTION "Remote Replication Consistency Group Is Disconnected"
            --#SEVERITY MAJOR
            ::= { remoteReplicationCGIsInterrupted 1 }

        -- 1.3.6.1.4.1.2011.2.251.20.1.2.2.15.221.9.2
        remoteReplicationCGIsInterrupted-Resume NOTIFICATION-TYPE
            OBJECTS { hwStorageAlarmReporting }
            STATUS current
            DESCRIPTION "Recover: Remote Replication Consistency Group Is Disconnected"
            --#SEVERITY INFORMATIONAL
            ::= { remoteReplicationCGIsInterrupted 2 }

        -- 1.3.6.1.4.1.2011.2.251.20.1.2.2.15.221.12
        hyperMetroCGAutoDisconnect1 OBJECT IDENTIFIER ::= { consistencygroup 12 }

        -- 1.3.6.1.4.1.2011.2.251.20.1.2.2.15.221.12.1
        hyperMetroCGAutoDisconnect1-Fault NOTIFICATION-TYPE
            OBJECTS { hwStorageAlarmReporting }
            STATUS current
            DESCRIPTION "A HyperMetro Consistency Group Is Automatically Disconnected And The Local LUNs Cannot Provide Services"
            --#SEVERITY WARNING
            ::= { hyperMetroCGAutoDisconnect1 1 }

        -- 1.3.6.1.4.1.2011.2.251.20.1.2.2.15.221.12.2
        hyperMetroCGAutoDisconnect1-Resume NOTIFICATION-TYPE
            OBJECTS { hwStorageAlarmReporting }
            STATUS current
            DESCRIPTION "Recover: A HyperMetro Consistency Group Is Automatically Disconnected And The Local LUNs Cannot Provide Services"
            --#SEVERITY INFORMATIONAL
            ::= { hyperMetroCGAutoDisconnect1 2 }

        -- 1.3.6.1.4.1.2011.2.251.20.1.2.2.15.221.13
        hyperMetroCGAutoDisconnect OBJECT IDENTIFIER ::= { consistencygroup 13 }

        -- 1.3.6.1.4.1.2011.2.251.20.1.2.2.15.221.13.1
        hyperMetroCGAutoDisconnect-Fault NOTIFICATION-TYPE
            OBJECTS { hwStorageAlarmReporting }
            STATUS current
            DESCRIPTION "A HyperMetro Consistency Group Is Automatically Disconnected And The Local LUNs Continue To Provide Services"
            --#SEVERITY WARNING
            ::= { hyperMetroCGAutoDisconnect 1 }

        -- 1.3.6.1.4.1.2011.2.251.20.1.2.2.15.221.13.2
        hyperMetroCGAutoDisconnect-Resume NOTIFICATION-TYPE
            OBJECTS { hwStorageAlarmReporting }
            STATUS current
            DESCRIPTION "Recover: A HyperMetro Consistency Group Is Automatically Disconnected And The Local LUNs Continue To Provide Services"
            --#SEVERITY INFORMATIONAL
            ::= { hyperMetroCGAutoDisconnect 2 }

        -- 1.3.6.1.4.1.2011.2.251.20.1.2.2.15.221.14
        autoStartSynRemoteRepCGFails OBJECT IDENTIFIER ::= { consistencygroup 14 }

        -- 1.3.6.1.4.1.2011.2.251.20.1.2.2.15.221.14.1
        autoStartSynRemoteRepCGFails-Fault NOTIFICATION-TYPE
            OBJECTS { hwStorageAlarmReporting }
            STATUS current
            DESCRIPTION "Remote Replication Consistency Group Failed To Synchronize Data Automatically"
            --#SEVERITY MAJOR
            ::= { autoStartSynRemoteRepCGFails 1 }

        -- 1.3.6.1.4.1.2011.2.251.20.1.2.2.15.221.14.2
        autoStartSynRemoteRepCGFails-Resume NOTIFICATION-TYPE
            OBJECTS { hwStorageAlarmReporting }
            STATUS current
            DESCRIPTION "Recover: Remote Replication Consistency Group Failed To Synchronize Data Automatically"
            --#SEVERITY INFORMATIONAL
            ::= { autoStartSynRemoteRepCGFails 2 }

        -- 1.3.6.1.4.1.2011.2.251.20.1.2.2.15.221.15
        rmConsistencyRecoveredNew OBJECT IDENTIFIER ::= { consistencygroup 15 }

        -- 1.3.6.1.4.1.2011.2.251.20.1.2.2.15.221.15.1
        rmConsistencyRecoveredNew-Fault NOTIFICATION-TYPE
            OBJECTS { hwStorageAlarmReporting }
            STATUS current
            DESCRIPTION "The Remote Replication Consistency Group Enters The ToBeRecovered State And Data On The Primary End Cannot Be Synchronized To The Remote End"
            --#SEVERITY MAJOR
            ::= { rmConsistencyRecoveredNew 1 }

        -- 1.3.6.1.4.1.2011.2.251.20.1.2.2.15.221.15.2
        rmConsistencyRecoveredNew-Resume NOTIFICATION-TYPE
            OBJECTS { hwStorageAlarmReporting }
            STATUS current
            DESCRIPTION "Recover: The Remote Replication Consistency Group Enters The ToBeRecovered State And Data On The Primary End Cannot Be Synchronized To The Remote End"
            --#SEVERITY INFORMATIONAL
            ::= { rmConsistencyRecoveredNew 2 }

        -- 1.3.6.1.4.1.2011.2.251.20.1.2.2.15.224
        remotedevice OBJECT IDENTIFIER ::= { oidBasedTrap 224 }

        -- 1.3.6.1.4.1.2011.2.251.20.1.2.2.15.224.14
        remoteDeviceIsSetToBeUnableToRecoverAutomatically OBJECT IDENTIFIER ::= { remotedevice 14 }

        -- 1.3.6.1.4.1.2011.2.251.20.1.2.2.15.224.14.1
        remoteDeviceIsSetToBeUnableToRecoverAutomatically-Fault NOTIFICATION-TYPE
            OBJECTS { hwStorageAlarmReporting }
            STATUS current
            DESCRIPTION "Remote Device Is Set To Be Unable To Recover Automatically"
            --#SEVERITY MAJOR
            ::= { remoteDeviceIsSetToBeUnableToRecoverAutomatically 1 }

        -- 1.3.6.1.4.1.2011.2.251.20.1.2.2.15.224.14.2
        remoteDeviceIsSetToBeUnableToRecoverAutomatically-Resume NOTIFICATION-TYPE
            OBJECTS { hwStorageAlarmReporting }
            STATUS current
            DESCRIPTION "Recover: Remote Device Is Set To Be Unable To Recover Automatically"
            --#SEVERITY INFORMATIONAL
            ::= { remoteDeviceIsSetToBeUnableToRecoverAutomatically 2 }

        -- 1.3.6.1.4.1.2011.2.251.20.1.2.2.15.224.67
        noRedundantLinkExistsBetweenTheLocalArrayAndRemoteDevice OBJECT IDENTIFIER ::= { remotedevice 67 }

        -- 1.3.6.1.4.1.2011.2.251.20.1.2.2.15.224.67.1
        noRedundantLinkExistsBetweenTheLocalArrayAndRemoteDevice-Fault NOTIFICATION-TYPE
            OBJECTS { hwStorageAlarmReporting }
            STATUS current
            DESCRIPTION "No Redundant Link Exists Between The Local Array And Remote Device"
            --#SEVERITY WARNING
            ::= { noRedundantLinkExistsBetweenTheLocalArrayAndRemoteDevice 1 }

        -- 1.3.6.1.4.1.2011.2.251.20.1.2.2.15.224.67.2
        noRedundantLinkExistsBetweenTheLocalArrayAndRemoteDevice-Resume NOTIFICATION-TYPE
            OBJECTS { hwStorageAlarmReporting }
            STATUS current
            DESCRIPTION "Recover: No Redundant Link Exists Between The Local Array And Remote Device"
            --#SEVERITY INFORMATIONAL
            ::= { noRedundantLinkExistsBetweenTheLocalArrayAndRemoteDevice 2 }

        -- 1.3.6.1.4.1.2011.2.251.20.1.2.2.15.224.68
        receptionOfMessagesFromTheWDMDeviceIsAbnormal OBJECT IDENTIFIER ::= { remotedevice 68 }

        -- 1.3.6.1.4.1.2011.2.251.20.1.2.2.15.224.68.1
        receptionOfMessagesFromTheWDMDeviceIsAbnormal-Fault NOTIFICATION-TYPE
            OBJECTS { hwStorageAlarmReporting }
            STATUS current
            DESCRIPTION "Reception Of Messages From The WDM Device Is Abnormal"
            --#SEVERITY WARNING
            ::= { receptionOfMessagesFromTheWDMDeviceIsAbnormal 1 }

        -- 1.3.6.1.4.1.2011.2.251.20.1.2.2.15.224.68.2
        receptionOfMessagesFromTheWDMDeviceIsAbnormal-Resume NOTIFICATION-TYPE
            OBJECTS { hwStorageAlarmReporting }
            STATUS current
            DESCRIPTION "Recover: Reception Of Messages From The WDM Device Is Abnormal"
            --#SEVERITY INFORMATIONAL
            ::= { receptionOfMessagesFromTheWDMDeviceIsAbnormal 2 }

        -- 1.3.6.1.4.1.2011.2.251.20.1.2.2.15.224.69
        remoteDeviceIsFaulty OBJECT IDENTIFIER ::= { remotedevice 69 }

        -- 1.3.6.1.4.1.2011.2.251.20.1.2.2.15.224.69.1
        remoteDeviceIsFaulty-Fault NOTIFICATION-TYPE
            OBJECTS { hwStorageAlarmReporting }
            STATUS current
            DESCRIPTION "Remote Device Is Faulty"
            --#SEVERITY MAJOR
            ::= { remoteDeviceIsFaulty 1 }

        -- 1.3.6.1.4.1.2011.2.251.20.1.2.2.15.224.69.2
        remoteDeviceIsFaulty-Resume NOTIFICATION-TYPE
            OBJECTS { hwStorageAlarmReporting }
            STATUS current
            DESCRIPTION "Recover: Remote Device Is Faulty"
            --#SEVERITY INFORMATIONAL
            ::= { remoteDeviceIsFaulty 2 }

        -- 1.3.6.1.4.1.2011.2.251.20.1.2.2.15.224.71
        theLinkAuthenticationBetweenStorageDevicesFailed OBJECT IDENTIFIER ::= { remotedevice 71 }

        -- 1.3.6.1.4.1.2011.2.251.20.1.2.2.15.224.71.1
        theLinkAuthenticationBetweenStorageDevicesFailed-Fault NOTIFICATION-TYPE
            OBJECTS { hwStorageAlarmReporting }
            STATUS current
            DESCRIPTION "The Link Authentication Between Storage Devices Failed"
            --#SEVERITY WARNING
            ::= { theLinkAuthenticationBetweenStorageDevicesFailed 1 }

        -- 1.3.6.1.4.1.2011.2.251.20.1.2.2.15.224.71.2
        theLinkAuthenticationBetweenStorageDevicesFailed-Resume NOTIFICATION-TYPE
            OBJECTS { hwStorageAlarmReporting }
            STATUS current
            DESCRIPTION "Recover: The Link Authentication Between Storage Devices Failed"
            --#SEVERITY INFORMATIONAL
            ::= { theLinkAuthenticationBetweenStorageDevicesFailed 2 }

        -- 1.3.6.1.4.1.2011.2.251.20.1.2.2.15.224.73
        theReplicationLinkBetweenTheStorageArrayAndTheInterfaceModuleOfTheRemoteDeviceDoesNotMeetTheRedundancyRequirements OBJECT IDENTIFIER ::= { remotedevice 73 }

        -- 1.3.6.1.4.1.2011.2.251.20.1.2.2.15.224.73.1
        theReplicationLinkBetweenTheStorageArrayAndTheInterfaceModuleOfTheRemoteDeviceDoesNotMeetTheRedundancyRequirements-Fault NOTIFICATION-TYPE
            OBJECTS { hwStorageAlarmReporting }
            STATUS current
            DESCRIPTION "The Replication Link Between The Storage Array And The Interface Module Of The Remote Device Does Not Meet The Redundancy Requirements"
            --#SEVERITY WARNING
            ::= { theReplicationLinkBetweenTheStorageArrayAndTheInterfaceModuleOfTheRemoteDeviceDoesNotMeetTheRedundancyRequirements 1 }

        -- 1.3.6.1.4.1.2011.2.251.20.1.2.2.15.224.73.2
        theReplicationLinkBetweenTheStorageArrayAndTheInterfaceModuleOfTheRemoteDeviceDoesNotMeetTheRedundancyRequirements-Resume NOTIFICATION-TYPE
            OBJECTS { hwStorageAlarmReporting }
            STATUS current
            DESCRIPTION "Recover: The Replication Link Between The Storage Array And The Interface Module Of The Remote Device Does Not Meet The Redundancy Requirements"
            --#SEVERITY INFORMATIONAL
            ::= { theReplicationLinkBetweenTheStorageArrayAndTheInterfaceModuleOfTheRemoteDeviceDoesNotMeetTheRedundancyRequirements 2 }

        -- 1.3.6.1.4.1.2011.2.251.20.1.2.2.15.224.74
        externalARRAYToOnlyOneController OBJECT IDENTIFIER ::= { remotedevice 74 }

        -- 1.3.6.1.4.1.2011.2.251.20.1.2.2.15.224.74.1
        externalARRAYToOnlyOneController-Fault NOTIFICATION-TYPE
            OBJECTS { hwStorageAlarmReporting }
            STATUS current
            DESCRIPTION "The External Storage Is Connected To Only One Controller"
            --#SEVERITY MAJOR
            ::= { externalARRAYToOnlyOneController 1 }

        -- 1.3.6.1.4.1.2011.2.251.20.1.2.2.15.224.74.2
        externalARRAYToOnlyOneController-Resume NOTIFICATION-TYPE
            OBJECTS { hwStorageAlarmReporting }
            STATUS current
            DESCRIPTION "Recover: The External Storage Is Connected To Only One Controller"
            --#SEVERITY INFORMATIONAL
            ::= { externalARRAYToOnlyOneController 2 }

        -- 1.3.6.1.4.1.2011.2.251.20.1.2.2.15.224.75
        externalARRAYOffline OBJECT IDENTIFIER ::= { remotedevice 75 }

        -- 1.3.6.1.4.1.2011.2.251.20.1.2.2.15.224.75.1
        externalARRAYOffline-Fault NOTIFICATION-TYPE
            OBJECTS { hwStorageAlarmReporting }
            STATUS current
            DESCRIPTION "The External Storage Is Offline"
            --#SEVERITY MAJOR
            ::= { externalARRAYOffline 1 }

        -- 1.3.6.1.4.1.2011.2.251.20.1.2.2.15.224.75.2
        externalARRAYOffline-Resume NOTIFICATION-TYPE
            OBJECTS { hwStorageAlarmReporting }
            STATUS current
            DESCRIPTION "Recover: The External Storage Is Offline"
            --#SEVERITY INFORMATIONAL
            ::= { externalARRAYOffline 2 }

        -- 1.3.6.1.4.1.2011.2.251.20.1.2.2.15.224.80
        theRemoteDeviceIsOffline OBJECT IDENTIFIER ::= { remotedevice 80 }

        -- 1.3.6.1.4.1.2011.2.251.20.1.2.2.15.224.80.1
        theRemoteDeviceIsOffline-Fault NOTIFICATION-TYPE
            OBJECTS { hwStorageAlarmReporting }
            STATUS current
            DESCRIPTION "The Remote Device Is Offline"
            --#SEVERITY MAJOR
            ::= { theRemoteDeviceIsOffline 1 }

        -- 1.3.6.1.4.1.2011.2.251.20.1.2.2.15.224.80.2
        theRemoteDeviceIsOffline-Resume NOTIFICATION-TYPE
            OBJECTS { hwStorageAlarmReporting }
            STATUS current
            DESCRIPTION "Recover: The Remote Device Is Offline"
            --#SEVERITY INFORMATIONAL
            ::= { theRemoteDeviceIsOffline 2 }

        -- 1.3.6.1.4.1.2011.2.251.20.1.2.2.15.224.81
        theProtocolLinkOfTheRemoteDeviceIsDisconnected OBJECT IDENTIFIER ::= { remotedevice 81 }

        -- 1.3.6.1.4.1.2011.2.251.20.1.2.2.15.224.81.1
        theProtocolLinkOfTheRemoteDeviceIsDisconnected-Fault NOTIFICATION-TYPE
            OBJECTS { hwStorageAlarmReporting }
            STATUS current
            DESCRIPTION "The Protocol Link Of The Remote Device Is Disconnected"
            --#SEVERITY MAJOR
            ::= { theProtocolLinkOfTheRemoteDeviceIsDisconnected 1 }

        -- 1.3.6.1.4.1.2011.2.251.20.1.2.2.15.224.81.2
        theProtocolLinkOfTheRemoteDeviceIsDisconnected-Resume NOTIFICATION-TYPE
            OBJECTS { hwStorageAlarmReporting }
            STATUS current
            DESCRIPTION "Recover: The Protocol Link Of The Remote Device Is Disconnected"
            --#SEVERITY INFORMATIONAL
            ::= { theProtocolLinkOfTheRemoteDeviceIsDisconnected 2 }

        -- 1.3.6.1.4.1.2011.2.251.20.1.2.2.15.224.82
        protocolConnectionOfTheRemoteDeviceIsNotRedundant OBJECT IDENTIFIER ::= { remotedevice 82 }

        -- 1.3.6.1.4.1.2011.2.251.20.1.2.2.15.224.82.1
        protocolConnectionOfTheRemoteDeviceIsNotRedundant-Fault NOTIFICATION-TYPE
            OBJECTS { hwStorageAlarmReporting }
            STATUS current
            DESCRIPTION "Protocol Connection Of The Remote Device Is Not Redundant"
            --#SEVERITY WARNING
            ::= { protocolConnectionOfTheRemoteDeviceIsNotRedundant 1 }

        -- 1.3.6.1.4.1.2011.2.251.20.1.2.2.15.224.82.2
        protocolConnectionOfTheRemoteDeviceIsNotRedundant-Resume NOTIFICATION-TYPE
            OBJECTS { hwStorageAlarmReporting }
            STATUS current
            DESCRIPTION "Recover: Protocol Connection Of The Remote Device Is Not Redundant"
            --#SEVERITY INFORMATIONAL
            ::= { protocolConnectionOfTheRemoteDeviceIsNotRedundant 2 }

        -- 1.3.6.1.4.1.2011.2.251.20.1.2.2.15.224.83
        createRmtdSuccess OBJECT IDENTIFIER ::= { remotedevice 83 }

        -- 1.3.6.1.4.1.2011.2.251.20.1.2.2.15.224.83.1
        createRmtdSuccess-Fault NOTIFICATION-TYPE
            OBJECTS { hwStorageAlarmReporting }
            STATUS current
            DESCRIPTION "Succeeded In Creating A Remote Device"
            --#SEVERITY INFORMATIONAL
            ::= { createRmtdSuccess 1 }

        -- 1.3.6.1.4.1.2011.2.251.20.1.2.2.15.224.83.2
        createRmtdSuccess-Resume NOTIFICATION-TYPE
            OBJECTS { hwStorageAlarmReporting }
            STATUS current
            DESCRIPTION "Recover: Succeeded In Creating A Remote Device"
            --#SEVERITY INFORMATIONAL
            ::= { createRmtdSuccess 2 }

        -- 1.3.6.1.4.1.2011.2.251.20.1.2.2.15.224.84
        createRmtdFail OBJECT IDENTIFIER ::= { remotedevice 84 }

        -- 1.3.6.1.4.1.2011.2.251.20.1.2.2.15.224.84.1
        createRmtdFail-Fault NOTIFICATION-TYPE
            OBJECTS { hwStorageAlarmReporting }
            STATUS current
            DESCRIPTION "Failed To Create A Remote Device"
            --#SEVERITY INFORMATIONAL
            ::= { createRmtdFail 1 }

        -- 1.3.6.1.4.1.2011.2.251.20.1.2.2.15.224.84.2
        createRmtdFail-Resume NOTIFICATION-TYPE
            OBJECTS { hwStorageAlarmReporting }
            STATUS current
            DESCRIPTION "Recover: Failed To Create A Remote Device"
            --#SEVERITY INFORMATIONAL
            ::= { createRmtdFail 2 }

        -- 1.3.6.1.4.1.2011.2.251.20.1.2.2.15.224.85
        succeededInDeletingARemoteDevice OBJECT IDENTIFIER ::= { remotedevice 85 }

        -- 1.3.6.1.4.1.2011.2.251.20.1.2.2.15.224.85.1
        succeededInDeletingARemoteDevice-Fault NOTIFICATION-TYPE
            OBJECTS { hwStorageAlarmReporting }
            STATUS current
            DESCRIPTION "Succeeded In Deleting A Remote Device"
            --#SEVERITY INFORMATIONAL
            ::= { succeededInDeletingARemoteDevice 1 }

        -- 1.3.6.1.4.1.2011.2.251.20.1.2.2.15.224.85.2
        succeededInDeletingARemoteDevice-Resume NOTIFICATION-TYPE
            OBJECTS { hwStorageAlarmReporting }
            STATUS current
            DESCRIPTION "Recover: Succeeded In Deleting A Remote Device"
            --#SEVERITY INFORMATIONAL
            ::= { succeededInDeletingARemoteDevice 2 }

        -- 1.3.6.1.4.1.2011.2.251.20.1.2.2.15.224.86
        failedToDeleteARemoteDevice OBJECT IDENTIFIER ::= { remotedevice 86 }

        -- 1.3.6.1.4.1.2011.2.251.20.1.2.2.15.224.86.1
        failedToDeleteARemoteDevice-Fault NOTIFICATION-TYPE
            OBJECTS { hwStorageAlarmReporting }
            STATUS current
            DESCRIPTION "Failed To Delete A Remote Device"
            --#SEVERITY INFORMATIONAL
            ::= { failedToDeleteARemoteDevice 1 }

        -- 1.3.6.1.4.1.2011.2.251.20.1.2.2.15.224.86.2
        failedToDeleteARemoteDevice-Resume NOTIFICATION-TYPE
            OBJECTS { hwStorageAlarmReporting }
            STATUS current
            DESCRIPTION "Recover: Failed To Delete A Remote Device"
            --#SEVERITY INFORMATIONAL
            ::= { failedToDeleteARemoteDevice 2 }

        -- 1.3.6.1.4.1.2011.2.251.20.1.2.2.15.224.87
        succeededInModifyingARemoteDevice OBJECT IDENTIFIER ::= { remotedevice 87 }

        -- 1.3.6.1.4.1.2011.2.251.20.1.2.2.15.224.87.1
        succeededInModifyingARemoteDevice-Fault NOTIFICATION-TYPE
            OBJECTS { hwStorageAlarmReporting }
            STATUS current
            DESCRIPTION "Succeeded In Modifying A Remote Device"
            --#SEVERITY INFORMATIONAL
            ::= { succeededInModifyingARemoteDevice 1 }

        -- 1.3.6.1.4.1.2011.2.251.20.1.2.2.15.224.87.2
        succeededInModifyingARemoteDevice-Resume NOTIFICATION-TYPE
            OBJECTS { hwStorageAlarmReporting }
            STATUS current
            DESCRIPTION "Recover: Succeeded In Modifying A Remote Device"
            --#SEVERITY INFORMATIONAL
            ::= { succeededInModifyingARemoteDevice 2 }

        -- 1.3.6.1.4.1.2011.2.251.20.1.2.2.15.224.88
        failedToModifyARemoteDevice OBJECT IDENTIFIER ::= { remotedevice 88 }

        -- 1.3.6.1.4.1.2011.2.251.20.1.2.2.15.224.88.1
        failedToModifyARemoteDevice-Fault NOTIFICATION-TYPE
            OBJECTS { hwStorageAlarmReporting }
            STATUS current
            DESCRIPTION "Failed To Modify A Remote Device"
            --#SEVERITY INFORMATIONAL
            ::= { failedToModifyARemoteDevice 1 }

        -- 1.3.6.1.4.1.2011.2.251.20.1.2.2.15.224.88.2
        failedToModifyARemoteDevice-Resume NOTIFICATION-TYPE
            OBJECTS { hwStorageAlarmReporting }
            STATUS current
            DESCRIPTION "Recover: Failed To Modify A Remote Device"
            --#SEVERITY INFORMATIONAL
            ::= { failedToModifyARemoteDevice 2 }

        -- 1.3.6.1.4.1.2011.2.251.20.1.2.2.15.224.89
        succeededInCreatingAnIPGroup OBJECT IDENTIFIER ::= { remotedevice 89 }

        -- 1.3.6.1.4.1.2011.2.251.20.1.2.2.15.224.89.1
        succeededInCreatingAnIPGroup-Fault NOTIFICATION-TYPE
            OBJECTS { hwStorageAlarmReporting }
            STATUS current
            DESCRIPTION "Succeeded In Creating An IP Group"
            --#SEVERITY INFORMATIONAL
            ::= { succeededInCreatingAnIPGroup 1 }

        -- 1.3.6.1.4.1.2011.2.251.20.1.2.2.15.224.89.2
        succeededInCreatingAnIPGroup-Resume NOTIFICATION-TYPE
            OBJECTS { hwStorageAlarmReporting }
            STATUS current
            DESCRIPTION "Recover: Succeeded In Creating An IP Group"
            --#SEVERITY INFORMATIONAL
            ::= { succeededInCreatingAnIPGroup 2 }

        -- 1.3.6.1.4.1.2011.2.251.20.1.2.2.15.224.90
        failedToCreateAnIPGroup OBJECT IDENTIFIER ::= { remotedevice 90 }

        -- 1.3.6.1.4.1.2011.2.251.20.1.2.2.15.224.90.1
        failedToCreateAnIPGroup-Fault NOTIFICATION-TYPE
            OBJECTS { hwStorageAlarmReporting }
            STATUS current
            DESCRIPTION "Failed To Create An IP Group"
            --#SEVERITY INFORMATIONAL
            ::= { failedToCreateAnIPGroup 1 }

        -- 1.3.6.1.4.1.2011.2.251.20.1.2.2.15.224.90.2
        failedToCreateAnIPGroup-Resume NOTIFICATION-TYPE
            OBJECTS { hwStorageAlarmReporting }
            STATUS current
            DESCRIPTION "Recover: Failed To Create An IP Group"
            --#SEVERITY INFORMATIONAL
            ::= { failedToCreateAnIPGroup 2 }

        -- 1.3.6.1.4.1.2011.2.251.20.1.2.2.15.224.91
        succeededInDeletingAnIPGroup OBJECT IDENTIFIER ::= { remotedevice 91 }

        -- 1.3.6.1.4.1.2011.2.251.20.1.2.2.15.224.91.1
        succeededInDeletingAnIPGroup-Fault NOTIFICATION-TYPE
            OBJECTS { hwStorageAlarmReporting }
            STATUS current
            DESCRIPTION "Succeeded In Deleting An IP Group"
            --#SEVERITY INFORMATIONAL
            ::= { succeededInDeletingAnIPGroup 1 }

        -- 1.3.6.1.4.1.2011.2.251.20.1.2.2.15.224.91.2
        succeededInDeletingAnIPGroup-Resume NOTIFICATION-TYPE
            OBJECTS { hwStorageAlarmReporting }
            STATUS current
            DESCRIPTION "Recover: Succeeded In Deleting An IP Group"
            --#SEVERITY INFORMATIONAL
            ::= { succeededInDeletingAnIPGroup 2 }

        -- 1.3.6.1.4.1.2011.2.251.20.1.2.2.15.224.92
        failedToDeleteAnIPGroup OBJECT IDENTIFIER ::= { remotedevice 92 }

        -- 1.3.6.1.4.1.2011.2.251.20.1.2.2.15.224.92.1
        failedToDeleteAnIPGroup-Fault NOTIFICATION-TYPE
            OBJECTS { hwStorageAlarmReporting }
            STATUS current
            DESCRIPTION "Failed To Delete An IP Group"
            --#SEVERITY INFORMATIONAL
            ::= { failedToDeleteAnIPGroup 1 }

        -- 1.3.6.1.4.1.2011.2.251.20.1.2.2.15.224.92.2
        failedToDeleteAnIPGroup-Resume NOTIFICATION-TYPE
            OBJECTS { hwStorageAlarmReporting }
            STATUS current
            DESCRIPTION "Recover: Failed To Delete An IP Group"
            --#SEVERITY INFORMATIONAL
            ::= { failedToDeleteAnIPGroup 2 }

        -- 1.3.6.1.4.1.2011.2.251.20.1.2.2.15.224.95
        succeededInDeletingAnIPAddressFromTheIPGroup OBJECT IDENTIFIER ::= { remotedevice 95 }

        -- 1.3.6.1.4.1.2011.2.251.20.1.2.2.15.224.95.1
        succeededInDeletingAnIPAddressFromTheIPGroup-Fault NOTIFICATION-TYPE
            OBJECTS { hwStorageAlarmReporting }
            STATUS current
            DESCRIPTION "Succeeded In Deleting An IP Address From The IP Group"
            --#SEVERITY INFORMATIONAL
            ::= { succeededInDeletingAnIPAddressFromTheIPGroup 1 }

        -- 1.3.6.1.4.1.2011.2.251.20.1.2.2.15.224.95.2
        succeededInDeletingAnIPAddressFromTheIPGroup-Resume NOTIFICATION-TYPE
            OBJECTS { hwStorageAlarmReporting }
            STATUS current
            DESCRIPTION "Recover: Succeeded In Deleting An IP Address From The IP Group"
            --#SEVERITY INFORMATIONAL
            ::= { succeededInDeletingAnIPAddressFromTheIPGroup 2 }

        -- 1.3.6.1.4.1.2011.2.251.20.1.2.2.15.224.112
        succeededInReconnectingTheRemoteDevice OBJECT IDENTIFIER ::= { remotedevice 112 }

        -- 1.3.6.1.4.1.2011.2.251.20.1.2.2.15.224.112.1
        succeededInReconnectingTheRemoteDevice-Fault NOTIFICATION-TYPE
            OBJECTS { hwStorageAlarmReporting }
            STATUS current
            DESCRIPTION "Succeeded In Reconnecting The Remote Device"
            --#SEVERITY INFORMATIONAL
            ::= { succeededInReconnectingTheRemoteDevice 1 }

        -- 1.3.6.1.4.1.2011.2.251.20.1.2.2.15.224.112.2
        succeededInReconnectingTheRemoteDevice-Resume NOTIFICATION-TYPE
            OBJECTS { hwStorageAlarmReporting }
            STATUS current
            DESCRIPTION "Recover: Succeeded In Reconnecting The Remote Device"
            --#SEVERITY INFORMATIONAL
            ::= { succeededInReconnectingTheRemoteDevice 2 }

        -- 1.3.6.1.4.1.2011.2.251.20.1.2.2.15.224.113
        failedToReconnectTheRemoteDevice OBJECT IDENTIFIER ::= { remotedevice 113 }

        -- 1.3.6.1.4.1.2011.2.251.20.1.2.2.15.224.113.1
        failedToReconnectTheRemoteDevice-Fault NOTIFICATION-TYPE
            OBJECTS { hwStorageAlarmReporting }
            STATUS current
            DESCRIPTION "Failed To Reconnect The Remote Device"
            --#SEVERITY INFORMATIONAL
            ::= { failedToReconnectTheRemoteDevice 1 }

        -- 1.3.6.1.4.1.2011.2.251.20.1.2.2.15.224.113.2
        failedToReconnectTheRemoteDevice-Resume NOTIFICATION-TYPE
            OBJECTS { hwStorageAlarmReporting }
            STATUS current
            DESCRIPTION "Recover: Failed To Reconnect The Remote Device"
            --#SEVERITY INFORMATIONAL
            ::= { failedToReconnectTheRemoteDevice 2 }

        -- 1.3.6.1.4.1.2011.2.251.20.1.2.2.15.224.119
        replicationLinkIsIsolatedBecauseItIsSubhealthy OBJECT IDENTIFIER ::= { remotedevice 119 }

        -- 1.3.6.1.4.1.2011.2.251.20.1.2.2.15.224.119.1
        replicationLinkIsIsolatedBecauseItIsSubhealthy-Fault NOTIFICATION-TYPE
            OBJECTS { hwStorageAlarmReporting }
            STATUS current
            DESCRIPTION "Replication Link Is Isolated Because It Is Subhealthy"
            --#SEVERITY WARNING
            ::= { replicationLinkIsIsolatedBecauseItIsSubhealthy 1 }

        -- 1.3.6.1.4.1.2011.2.251.20.1.2.2.15.224.119.2
        replicationLinkIsIsolatedBecauseItIsSubhealthy-Resume NOTIFICATION-TYPE
            OBJECTS { hwStorageAlarmReporting }
            STATUS current
            DESCRIPTION "Recover: Replication Link Is Isolated Because It Is Subhealthy"
            --#SEVERITY INFORMATIONAL
            ::= { replicationLinkIsIsolatedBecauseItIsSubhealthy 2 }

        -- 1.3.6.1.4.1.2011.2.251.20.1.2.2.15.224.120
        theWDMDeviceIsDisconnected OBJECT IDENTIFIER ::= { remotedevice 120 }

        -- 1.3.6.1.4.1.2011.2.251.20.1.2.2.15.224.120.1
        theWDMDeviceIsDisconnected-Fault NOTIFICATION-TYPE
            OBJECTS { hwStorageAlarmReporting }
            STATUS current
            DESCRIPTION "The WDM Device Is Disconnected"
            --#SEVERITY WARNING
            ::= { theWDMDeviceIsDisconnected 1 }

        -- 1.3.6.1.4.1.2011.2.251.20.1.2.2.15.224.120.2
        theWDMDeviceIsDisconnected-Resume NOTIFICATION-TYPE
            OBJECTS { hwStorageAlarmReporting }
            STATUS current
            DESCRIPTION "Recover: The WDM Device Is Disconnected"
            --#SEVERITY INFORMATIONAL
            ::= { theWDMDeviceIsDisconnected 2 }

        -- 1.3.6.1.4.1.2011.2.251.20.1.2.2.15.224.121
        remoteDevPortNumInsuff OBJECT IDENTIFIER ::= { remotedevice 121 }

        -- 1.3.6.1.4.1.2011.2.251.20.1.2.2.15.224.121.1
        remoteDevPortNumInsuff-Fault NOTIFICATION-TYPE
            OBJECTS { hwStorageAlarmReporting }
            STATUS current
            DESCRIPTION "Controller Links Of The Remote Device Are Insufficient"
            --#SEVERITY WARNING
            ::= { remoteDevPortNumInsuff 1 }

        -- 1.3.6.1.4.1.2011.2.251.20.1.2.2.15.224.121.2
        remoteDevPortNumInsuff-Resume NOTIFICATION-TYPE
            OBJECTS { hwStorageAlarmReporting }
            STATUS current
            DESCRIPTION "Recover: Controller Links Of The Remote Device Are Insufficient"
            --#SEVERITY INFORMATIONAL
            ::= { remoteDevPortNumInsuff 2 }

        -- 1.3.6.1.4.1.2011.2.251.20.1.2.2.15.224.302
        theLinkFromTheLocalStorageToTheExternalStorageDoesNotMeetTheRedundancyRequirements OBJECT IDENTIFIER ::= { remotedevice 302 }

        -- 1.3.6.1.4.1.2011.2.251.20.1.2.2.15.224.302.1
        theLinkFromTheLocalStorageToTheExternalStorageDoesNotMeetTheRedundancyRequirements-Fault NOTIFICATION-TYPE
            OBJECTS { hwStorageAlarmReporting }
            STATUS current
            DESCRIPTION "The Link From The Local Storage To The External Storage Does Not Meet The Redundancy Requirements"
            --#SEVERITY MAJOR
            ::= { theLinkFromTheLocalStorageToTheExternalStorageDoesNotMeetTheRedundancyRequirements 1 }

        -- 1.3.6.1.4.1.2011.2.251.20.1.2.2.15.224.302.2
        theLinkFromTheLocalStorageToTheExternalStorageDoesNotMeetTheRedundancyRequirements-Resume NOTIFICATION-TYPE
            OBJECTS { hwStorageAlarmReporting }
            STATUS current
            DESCRIPTION "Recover: The Link From The Local Storage To The External Storage Does Not Meet The Redundancy Requirements"
            --#SEVERITY INFORMATIONAL
            ::= { theLinkFromTheLocalStorageToTheExternalStorageDoesNotMeetTheRedundancyRequirements 2 }

        -- 1.3.6.1.4.1.2011.2.251.20.1.2.2.15.234
        sfpopticalelectricalmodule OBJECT IDENTIFIER ::= { oidBasedTrap 234 }

        -- 1.3.6.1.4.1.2011.2.251.20.1.2.2.15.234.3
        portOpticalModuleIsFaulty OBJECT IDENTIFIER ::= { sfpopticalelectricalmodule 3 }

        -- 1.3.6.1.4.1.2011.2.251.20.1.2.2.15.234.3.1
        portOpticalModuleIsFaulty-Fault NOTIFICATION-TYPE
            OBJECTS { hwStorageAlarmReporting }
            STATUS current
            DESCRIPTION "Port Optical Module Is Faulty"
            --#SEVERITY MAJOR
            ::= { portOpticalModuleIsFaulty 1 }

        -- 1.3.6.1.4.1.2011.2.251.20.1.2.2.15.234.3.2
        portOpticalModuleIsFaulty-Resume NOTIFICATION-TYPE
            OBJECTS { hwStorageAlarmReporting }
            STATUS current
            DESCRIPTION "Recover: Port Optical Module Is Faulty"
            --#SEVERITY INFORMATIONAL
            ::= { portOpticalModuleIsFaulty 2 }

        -- 1.3.6.1.4.1.2011.2.251.20.1.2.2.15.234.4
        opticalModuleTypeIsIncompatible OBJECT IDENTIFIER ::= { sfpopticalelectricalmodule 4 }

        -- 1.3.6.1.4.1.2011.2.251.20.1.2.2.15.234.4.1
        opticalModuleTypeIsIncompatible-Fault NOTIFICATION-TYPE
            OBJECTS { hwStorageAlarmReporting }
            STATUS current
            DESCRIPTION "Port Unavailable Due To Incompatible Optical Module Type"
            --#SEVERITY WARNING
            ::= { opticalModuleTypeIsIncompatible 1 }

        -- 1.3.6.1.4.1.2011.2.251.20.1.2.2.15.234.4.2
        opticalModuleTypeIsIncompatible-Resume NOTIFICATION-TYPE
            OBJECTS { hwStorageAlarmReporting }
            STATUS current
            DESCRIPTION "Recover: Port Unavailable Due To Incompatible Optical Module Type"
            --#SEVERITY INFORMATIONAL
            ::= { opticalModuleTypeIsIncompatible 2 }

        -- 1.3.6.1.4.1.2011.2.251.20.1.2.2.15.234.5
        opticalModuleRateIsInconsistent OBJECT IDENTIFIER ::= { sfpopticalelectricalmodule 5 }

        -- 1.3.6.1.4.1.2011.2.251.20.1.2.2.15.234.5.1
        opticalModuleRateIsInconsistent-Fault NOTIFICATION-TYPE
            OBJECTS { hwStorageAlarmReporting }
            STATUS current
            DESCRIPTION "Optical Module Rate Is Inconsistent With That Of Its Port"
            --#SEVERITY MAJOR
            ::= { opticalModuleRateIsInconsistent 1 }

        -- 1.3.6.1.4.1.2011.2.251.20.1.2.2.15.234.5.2
        opticalModuleRateIsInconsistent-Resume NOTIFICATION-TYPE
            OBJECTS { hwStorageAlarmReporting }
            STATUS current
            DESCRIPTION "Recover: Optical Module Rate Is Inconsistent With That Of Its Port"
            --#SEVERITY INFORMATIONAL
            ::= { opticalModuleRateIsInconsistent 2 }

        -- 1.3.6.1.4.1.2011.2.251.20.1.2.2.15.234.20
        portLinkIsAbnormal OBJECT IDENTIFIER ::= { sfpopticalelectricalmodule 20 }

        -- 1.3.6.1.4.1.2011.2.251.20.1.2.2.15.234.20.1
        portLinkIsAbnormal-Fault NOTIFICATION-TYPE
            OBJECTS { hwStorageAlarmReporting }
            STATUS current
            DESCRIPTION "Abnormal Port Link"
            --#SEVERITY MAJOR
            ::= { portLinkIsAbnormal 1 }

        -- 1.3.6.1.4.1.2011.2.251.20.1.2.2.15.234.20.2
        portLinkIsAbnormal-Resume NOTIFICATION-TYPE
            OBJECTS { hwStorageAlarmReporting }
            STATUS current
            DESCRIPTION "Recover: Abnormal Port Link"
            --#SEVERITY INFORMATIONAL
            ::= { portLinkIsAbnormal 2 }

        -- 1.3.6.1.4.1.2011.2.251.20.1.2.2.15.234.21
        failedToMonitorAnOpticalModule OBJECT IDENTIFIER ::= { sfpopticalelectricalmodule 21 }

        -- 1.3.6.1.4.1.2011.2.251.20.1.2.2.15.234.21.1
        failedToMonitorAnOpticalModule-Fault NOTIFICATION-TYPE
            OBJECTS { hwStorageAlarmReporting }
            STATUS current
            DESCRIPTION "Optical Module Cannot Be Monitored"
            --#SEVERITY MAJOR
            ::= { failedToMonitorAnOpticalModule 1 }

        -- 1.3.6.1.4.1.2011.2.251.20.1.2.2.15.234.21.2
        failedToMonitorAnOpticalModule-Resume NOTIFICATION-TYPE
            OBJECTS { hwStorageAlarmReporting }
            STATUS current
            DESCRIPTION "Recover: Optical Module Cannot Be Monitored"
            --#SEVERITY INFORMATIONAL
            ::= { failedToMonitorAnOpticalModule 2 }

        -- 1.3.6.1.4.1.2011.2.251.20.1.2.2.15.234.22
        opticalModuleTempIsBelowLimit OBJECT IDENTIFIER ::= { sfpopticalelectricalmodule 22 }

        -- 1.3.6.1.4.1.2011.2.251.20.1.2.2.15.234.22.1
        opticalModuleTempIsBelowLimit-Fault NOTIFICATION-TYPE
            OBJECTS { hwStorageAlarmReporting }
            STATUS current
            DESCRIPTION "Optical Module Temperature Is Below The Lower Limit"
            --#SEVERITY MAJOR
            ::= { opticalModuleTempIsBelowLimit 1 }

        -- 1.3.6.1.4.1.2011.2.251.20.1.2.2.15.234.22.2
        opticalModuleTempIsBelowLimit-Resume NOTIFICATION-TYPE
            OBJECTS { hwStorageAlarmReporting }
            STATUS current
            DESCRIPTION "Recover: Optical Module Temperature Is Below The Lower Limit"
            --#SEVERITY INFORMATIONAL
            ::= { opticalModuleTempIsBelowLimit 2 }

        -- 1.3.6.1.4.1.2011.2.251.20.1.2.2.15.234.23
        opticalModuleTempExceedsLimit OBJECT IDENTIFIER ::= { sfpopticalelectricalmodule 23 }

        -- 1.3.6.1.4.1.2011.2.251.20.1.2.2.15.234.23.1
        opticalModuleTempExceedsLimit-Fault NOTIFICATION-TYPE
            OBJECTS { hwStorageAlarmReporting }
            STATUS current
            DESCRIPTION "Optical Module Temperature Exceeds The Upper Limit"
            --#SEVERITY MAJOR
            ::= { opticalModuleTempExceedsLimit 1 }

        -- 1.3.6.1.4.1.2011.2.251.20.1.2.2.15.234.23.2
        opticalModuleTempExceedsLimit-Resume NOTIFICATION-TYPE
            OBJECTS { hwStorageAlarmReporting }
            STATUS current
            DESCRIPTION "Recover: Optical Module Temperature Exceeds The Upper Limit"
            --#SEVERITY INFORMATIONAL
            ::= { opticalModuleTempExceedsLimit 2 }

        -- 1.3.6.1.4.1.2011.2.251.20.1.2.2.15.234.24
        failedToMonitorOpOrEleModule OBJECT IDENTIFIER ::= { sfpopticalelectricalmodule 24 }

        -- 1.3.6.1.4.1.2011.2.251.20.1.2.2.15.234.24.1
        failedToMonitorOpOrEleModule-Fault NOTIFICATION-TYPE
            OBJECTS { hwStorageAlarmReporting }
            STATUS current
            DESCRIPTION "The System Failed To Monitor An Optical Or Electrical Module"
            --#SEVERITY MAJOR
            ::= { failedToMonitorOpOrEleModule 1 }

        -- 1.3.6.1.4.1.2011.2.251.20.1.2.2.15.234.24.2
        failedToMonitorOpOrEleModule-Resume NOTIFICATION-TYPE
            OBJECTS { hwStorageAlarmReporting }
            STATUS current
            DESCRIPTION "Recover: The System Failed To Monitor An Optical Or Electrical Module"
            --#SEVERITY INFORMATIONAL
            ::= { failedToMonitorOpOrEleModule 2 }

        -- 1.3.6.1.4.1.2011.2.251.20.1.2.2.15.234.27
        electricalModuleRateIsInconsistentWithThatOfItsPort OBJECT IDENTIFIER ::= { sfpopticalelectricalmodule 27 }

        -- 1.3.6.1.4.1.2011.2.251.20.1.2.2.15.234.27.1
        electricalModuleRateIsInconsistentWithThatOfItsPort-Fault NOTIFICATION-TYPE
            OBJECTS { hwStorageAlarmReporting }
            STATUS current
            DESCRIPTION "Electrical Module Rate Is Inconsistent With That Of Its Port"
            --#SEVERITY MAJOR
            ::= { electricalModuleRateIsInconsistentWithThatOfItsPort 1 }

        -- 1.3.6.1.4.1.2011.2.251.20.1.2.2.15.234.27.2
        electricalModuleRateIsInconsistentWithThatOfItsPort-Resume NOTIFICATION-TYPE
            OBJECTS { hwStorageAlarmReporting }
            STATUS current
            DESCRIPTION "Recover: Electrical Module Rate Is Inconsistent With That Of Its Port"
            --#SEVERITY INFORMATIONAL
            ::= { electricalModuleRateIsInconsistentWithThatOfItsPort 2 }

        -- 1.3.6.1.4.1.2011.2.251.20.1.2.2.15.234.29
        theOpticalElectricalModuleIsNotSupportedByThePort OBJECT IDENTIFIER ::= { sfpopticalelectricalmodule 29 }

        -- 1.3.6.1.4.1.2011.2.251.20.1.2.2.15.234.29.1
        theOpticalElectricalModuleIsNotSupportedByThePort-Fault NOTIFICATION-TYPE
            OBJECTS { hwStorageAlarmReporting }
            STATUS current
            DESCRIPTION "The OpticalElectrical Module Is Not Supported By The Port"
            --#SEVERITY MAJOR
            ::= { theOpticalElectricalModuleIsNotSupportedByThePort 1 }

        -- 1.3.6.1.4.1.2011.2.251.20.1.2.2.15.234.29.2
        theOpticalElectricalModuleIsNotSupportedByThePort-Resume NOTIFICATION-TYPE
            OBJECTS { hwStorageAlarmReporting }
            STATUS current
            DESCRIPTION "Recover: The OpticalElectrical Module Is Not Supported By The Port"
            --#SEVERITY INFORMATIONAL
            ::= { theOpticalElectricalModuleIsNotSupportedByThePort 2 }

        -- 1.3.6.1.4.1.2011.2.251.20.1.2.2.15.237
        memory OBJECT IDENTIFIER ::= { oidBasedTrap 237 }

        -- 1.3.6.1.4.1.2011.2.251.20.1.2.2.15.237.12
        theMemoryIsFaulty2 OBJECT IDENTIFIER ::= { memory 12 }

        -- 1.3.6.1.4.1.2011.2.251.20.1.2.2.15.237.12.1
        theMemoryIsFaulty2-Fault NOTIFICATION-TYPE
            OBJECTS { hwStorageAlarmReporting }
            STATUS current
            DESCRIPTION "The Memory Is Faulty"
            --#SEVERITY MAJOR
            ::= { theMemoryIsFaulty2 1 }

        -- 1.3.6.1.4.1.2011.2.251.20.1.2.2.15.237.12.2
        theMemoryIsFaulty2-Resume NOTIFICATION-TYPE
            OBJECTS { hwStorageAlarmReporting }
            STATUS current
            DESCRIPTION "Recover: The Memory Is Faulty"
            --#SEVERITY INFORMATIONAL
            ::= { theMemoryIsFaulty2 2 }

        -- 1.3.6.1.4.1.2011.2.251.20.1.2.2.15.237.13
        theMemoryIsFaulty3 OBJECT IDENTIFIER ::= { memory 13 }

        -- 1.3.6.1.4.1.2011.2.251.20.1.2.2.15.237.13.1
        theMemoryIsFaulty3-Fault NOTIFICATION-TYPE
            OBJECTS { hwStorageAlarmReporting }
            STATUS current
            DESCRIPTION "The Memory Is Faulty"
            --#SEVERITY MAJOR
            ::= { theMemoryIsFaulty3 1 }

        -- 1.3.6.1.4.1.2011.2.251.20.1.2.2.15.237.13.2
        theMemoryIsFaulty3-Resume NOTIFICATION-TYPE
            OBJECTS { hwStorageAlarmReporting }
            STATUS current
            DESCRIPTION "Recover: The Memory Is Faulty"
            --#SEVERITY INFORMATIONAL
            ::= { theMemoryIsFaulty3 2 }

        -- 1.3.6.1.4.1.2011.2.251.20.1.2.2.15.237.14
        memoryAuthenticationFailed OBJECT IDENTIFIER ::= { memory 14 }

        -- 1.3.6.1.4.1.2011.2.251.20.1.2.2.15.237.14.1
        memoryAuthenticationFailed-Fault NOTIFICATION-TYPE
            OBJECTS { hwStorageAlarmReporting }
            STATUS current
            DESCRIPTION "Memory Authentication Failed"
            --#SEVERITY WARNING
            ::= { memoryAuthenticationFailed 1 }

        -- 1.3.6.1.4.1.2011.2.251.20.1.2.2.15.237.14.2
        memoryAuthenticationFailed-Resume NOTIFICATION-TYPE
            OBJECTS { hwStorageAlarmReporting }
            STATUS current
            DESCRIPTION "Recover: Memory Authentication Failed"
            --#SEVERITY INFORMATIONAL
            ::= { memoryAuthenticationFailed 2 }

        -- 1.3.6.1.4.1.2011.2.251.20.1.2.2.15.237.15
        theMemorySlotIsIncorrect OBJECT IDENTIFIER ::= { memory 15 }

        -- 1.3.6.1.4.1.2011.2.251.20.1.2.2.15.237.15.1
        theMemorySlotIsIncorrect-Fault NOTIFICATION-TYPE
            OBJECTS { hwStorageAlarmReporting }
            STATUS current
            DESCRIPTION "The Memory Slot Is Incorrect"
            --#SEVERITY WARNING
            ::= { theMemorySlotIsIncorrect 1 }

        -- 1.3.6.1.4.1.2011.2.251.20.1.2.2.15.237.15.2
        theMemorySlotIsIncorrect-Resume NOTIFICATION-TYPE
            OBJECTS { hwStorageAlarmReporting }
            STATUS current
            DESCRIPTION "Recover: The Memory Slot Is Incorrect"
            --#SEVERITY INFORMATIONAL
            ::= { theMemorySlotIsIncorrect 2 }

        -- 1.3.6.1.4.1.2011.2.251.20.1.2.2.15.237.16
        aCorrectableErrorOccurredOnTheMemory1 OBJECT IDENTIFIER ::= { memory 16 }

        -- 1.3.6.1.4.1.2011.2.251.20.1.2.2.15.237.16.1
        aCorrectableErrorOccurredOnTheMemory1-Fault NOTIFICATION-TYPE
            OBJECTS { hwStorageAlarmReporting }
            STATUS current
            DESCRIPTION "A Correctable Error Occurred On The Memory"
            --#SEVERITY WARNING
            ::= { aCorrectableErrorOccurredOnTheMemory1 1 }

        -- 1.3.6.1.4.1.2011.2.251.20.1.2.2.15.237.16.2
        aCorrectableErrorOccurredOnTheMemory1-Resume NOTIFICATION-TYPE
            OBJECTS { hwStorageAlarmReporting }
            STATUS current
            DESCRIPTION "Recover: A Correctable Error Occurred On The Memory"
            --#SEVERITY INFORMATIONAL
            ::= { aCorrectableErrorOccurredOnTheMemory1 2 }

        -- 1.3.6.1.4.1.2011.2.251.20.1.2.2.15.237.17
        theMemoryIsFaulty1 OBJECT IDENTIFIER ::= { memory 17 }

        -- 1.3.6.1.4.1.2011.2.251.20.1.2.2.15.237.17.1
        theMemoryIsFaulty1-Fault NOTIFICATION-TYPE
            OBJECTS { hwStorageAlarmReporting }
            STATUS current
            DESCRIPTION "The Memory Is Faulty"
            --#SEVERITY MAJOR
            ::= { theMemoryIsFaulty1 1 }

        -- 1.3.6.1.4.1.2011.2.251.20.1.2.2.15.237.17.2
        theMemoryIsFaulty1-Resume NOTIFICATION-TYPE
            OBJECTS { hwStorageAlarmReporting }
            STATUS current
            DESCRIPTION "Recover: The Memory Is Faulty"
            --#SEVERITY INFORMATIONAL
            ::= { theMemoryIsFaulty1 2 }

        -- 1.3.6.1.4.1.2011.2.251.20.1.2.2.15.237.18
        theMemoryIsFaulty OBJECT IDENTIFIER ::= { memory 18 }

        -- 1.3.6.1.4.1.2011.2.251.20.1.2.2.15.237.18.1
        theMemoryIsFaulty-Fault NOTIFICATION-TYPE
            OBJECTS { hwStorageAlarmReporting }
            STATUS current
            DESCRIPTION "The Memory Is Faulty"
            --#SEVERITY MAJOR
            ::= { theMemoryIsFaulty 1 }

        -- 1.3.6.1.4.1.2011.2.251.20.1.2.2.15.237.18.2
        theMemoryIsFaulty-Resume NOTIFICATION-TYPE
            OBJECTS { hwStorageAlarmReporting }
            STATUS current
            DESCRIPTION "Recover: The Memory Is Faulty"
            --#SEVERITY INFORMATIONAL
            ::= { theMemoryIsFaulty 2 }

        -- 1.3.6.1.4.1.2011.2.251.20.1.2.2.15.237.19
        aCorrectableErrorOccurredOnTheMemory OBJECT IDENTIFIER ::= { memory 19 }

        -- 1.3.6.1.4.1.2011.2.251.20.1.2.2.15.237.19.1
        aCorrectableErrorOccurredOnTheMemory-Fault NOTIFICATION-TYPE
            OBJECTS { hwStorageAlarmReporting }
            STATUS current
            DESCRIPTION "A Correctable Error Occurred On The Memory"
            --#SEVERITY WARNING
            ::= { aCorrectableErrorOccurredOnTheMemory 1 }

        -- 1.3.6.1.4.1.2011.2.251.20.1.2.2.15.237.19.2
        aCorrectableErrorOccurredOnTheMemory-Resume NOTIFICATION-TYPE
            OBJECTS { hwStorageAlarmReporting }
            STATUS current
            DESCRIPTION "Recover: A Correctable Error Occurred On The Memory"
            --#SEVERITY INFORMATIONAL
            ::= { aCorrectableErrorOccurredOnTheMemory 2 }

        -- 1.3.6.1.4.1.2011.2.251.20.1.2.2.15.244
        license OBJECT IDENTIFIER ::= { oidBasedTrap 244 }

        -- 1.3.6.1.4.1.2011.2.251.20.1.2.2.15.244.1
        licenseIsAboutToExpire OBJECT IDENTIFIER ::= { license 1 }

        -- 1.3.6.1.4.1.2011.2.251.20.1.2.2.15.244.1.1
        licenseIsAboutToExpire-Fault NOTIFICATION-TYPE
            OBJECTS { hwStorageAlarmReporting }
            STATUS current
            DESCRIPTION "The License Is About To Expire"
            --#SEVERITY WARNING
            ::= { licenseIsAboutToExpire 1 }

        -- 1.3.6.1.4.1.2011.2.251.20.1.2.2.15.244.1.2
        licenseIsAboutToExpire-Resume NOTIFICATION-TYPE
            OBJECTS { hwStorageAlarmReporting }
            STATUS current
            DESCRIPTION "Recover: The License Is About To Expire"
            --#SEVERITY INFORMATIONAL
            ::= { licenseIsAboutToExpire 2 }

        -- 1.3.6.1.4.1.2011.2.251.20.1.2.2.15.244.2
        licenseHasExpired OBJECT IDENTIFIER ::= { license 2 }

        -- 1.3.6.1.4.1.2011.2.251.20.1.2.2.15.244.2.1
        licenseHasExpired-Fault NOTIFICATION-TYPE
            OBJECTS { hwStorageAlarmReporting }
            STATUS current
            DESCRIPTION "The License Has Expired"
            --#SEVERITY MAJOR
            ::= { licenseHasExpired 1 }

        -- 1.3.6.1.4.1.2011.2.251.20.1.2.2.15.244.2.2
        licenseHasExpired-Resume NOTIFICATION-TYPE
            OBJECTS { hwStorageAlarmReporting }
            STATUS current
            DESCRIPTION "Recover: The License Has Expired"
            --#SEVERITY INFORMATIONAL
            ::= { licenseHasExpired 2 }

        -- 1.3.6.1.4.1.2011.2.251.20.1.2.2.15.244.6
        licenseIsInvalidWithStartDate OBJECT IDENTIFIER ::= { license 6 }

        -- 1.3.6.1.4.1.2011.2.251.20.1.2.2.15.244.6.1
        licenseIsInvalidWithStartDate-Fault NOTIFICATION-TYPE
            OBJECTS { hwStorageAlarmReporting }
            STATUS current
            DESCRIPTION "The License Is Invalid"
            --#SEVERITY CRITICAL
            ::= { licenseIsInvalidWithStartDate 1 }

        -- 1.3.6.1.4.1.2011.2.251.20.1.2.2.15.244.6.2
        licenseIsInvalidWithStartDate-Resume NOTIFICATION-TYPE
            OBJECTS { hwStorageAlarmReporting }
            STATUS current
            DESCRIPTION "Recover: The License Is Invalid"
            --#SEVERITY INFORMATIONAL
            ::= { licenseIsInvalidWithStartDate 2 }

        -- 1.3.6.1.4.1.2011.2.251.20.1.2.2.15.250
        remotelun OBJECT IDENTIFIER ::= { oidBasedTrap 250 }

        -- 1.3.6.1.4.1.2011.2.251.20.1.2.2.15.250.1
        remoteLunExceedUpperLimit OBJECT IDENTIFIER ::= { remotelun 1 }

        -- 1.3.6.1.4.1.2011.2.251.20.1.2.2.15.250.1.1
        remoteLunExceedUpperLimit-Fault NOTIFICATION-TYPE
            OBJECTS { hwStorageAlarmReporting }
            STATUS current
            DESCRIPTION "The Number Of External LUNs Reaches The Upper Limit"
            --#SEVERITY WARNING
            ::= { remoteLunExceedUpperLimit 1 }

        -- 1.3.6.1.4.1.2011.2.251.20.1.2.2.15.250.1.2
        remoteLunExceedUpperLimit-Resume NOTIFICATION-TYPE
            OBJECTS { hwStorageAlarmReporting }
            STATUS current
            DESCRIPTION "Recover: The Number Of External LUNs Reaches The Upper Limit"
            --#SEVERITY INFORMATIONAL
            ::= { remoteLunExceedUpperLimit 2 }

        -- 1.3.6.1.4.1.2011.2.251.20.1.2.2.15.250.3
        heterogeneousLinkConnectionFailures OBJECT IDENTIFIER ::= { remotelun 3 }

        -- 1.3.6.1.4.1.2011.2.251.20.1.2.2.15.250.3.1
        heterogeneousLinkConnectionFailures-Fault NOTIFICATION-TYPE
            OBJECTS { hwStorageAlarmReporting }
            STATUS current
            DESCRIPTION "Heterogeneous Link Connection Failures"
            --#SEVERITY WARNING
            ::= { heterogeneousLinkConnectionFailures 1 }

        -- 1.3.6.1.4.1.2011.2.251.20.1.2.2.15.250.3.2
        heterogeneousLinkConnectionFailures-Resume NOTIFICATION-TYPE
            OBJECTS { hwStorageAlarmReporting }
            STATUS current
            DESCRIPTION "Recover: Heterogeneous Link Connection Failures"
            --#SEVERITY INFORMATIONAL
            ::= { heterogeneousLinkConnectionFailures 2 }

        -- 1.3.6.1.4.1.2011.2.251.20.1.2.2.15.250.76
        remoteLunPathExceedUpperLimit OBJECT IDENTIFIER ::= { remotelun 76 }

        -- 1.3.6.1.4.1.2011.2.251.20.1.2.2.15.250.76.1
        remoteLunPathExceedUpperLimit-Fault NOTIFICATION-TYPE
            OBJECTS { hwStorageAlarmReporting }
            STATUS current
            DESCRIPTION "The Number Of Paths Of External LUNs Reaches The Upper Limit"
            --#SEVERITY WARNING
            ::= { remoteLunPathExceedUpperLimit 1 }

        -- 1.3.6.1.4.1.2011.2.251.20.1.2.2.15.250.76.2
        remoteLunPathExceedUpperLimit-Resume NOTIFICATION-TYPE
            OBJECTS { hwStorageAlarmReporting }
            STATUS current
            DESCRIPTION "Recover: The Number Of Paths Of External LUNs Reaches The Upper Limit"
            --#SEVERITY INFORMATIONAL
            ::= { remoteLunPathExceedUpperLimit 2 }

        -- 1.3.6.1.4.1.2011.2.251.20.1.2.2.15.253
        lunmigrationtask OBJECT IDENTIFIER ::= { oidBasedTrap 253 }

        -- 1.3.6.1.4.1.2011.2.251.20.1.2.2.15.253.8
        almSmartMigrationErr OBJECT IDENTIFIER ::= { lunmigrationtask 8 }

        -- 1.3.6.1.4.1.2011.2.251.20.1.2.2.15.253.8.1
        almSmartMigrationErr-Fault NOTIFICATION-TYPE
            OBJECTS { hwStorageAlarmReporting }
            STATUS current
            DESCRIPTION "LUN Migration Is Faulty"
            --#SEVERITY MAJOR
            ::= { almSmartMigrationErr 1 }

        -- 1.3.6.1.4.1.2011.2.251.20.1.2.2.15.253.8.2
        almSmartMigrationErr-Resume NOTIFICATION-TYPE
            OBJECTS { hwStorageAlarmReporting }
            STATUS current
            DESCRIPTION "Recover: LUN Migration Is Faulty"
            --#SEVERITY INFORMATIONAL
            ::= { almSmartMigrationErr 2 }

        -- 1.3.6.1.4.1.2011.2.251.20.1.2.2.15.255
        hostlink OBJECT IDENTIFIER ::= { oidBasedTrap 255 }

        -- 1.3.6.1.4.1.2011.2.251.20.1.2.2.15.255.36
        theHostPathDoesNotMeetTheRedundancySpecifications OBJECT IDENTIFIER ::= { hostlink 36 }

        -- 1.3.6.1.4.1.2011.2.251.20.1.2.2.15.255.36.1
        theHostPathDoesNotMeetTheRedundancySpecifications-Fault NOTIFICATION-TYPE
            OBJECTS { hwStorageAlarmReporting }
            STATUS current
            DESCRIPTION "Paths Between The Host And Storage Array Do Not Meet Redundancy Requirements"
            --#SEVERITY MAJOR
            ::= { theHostPathDoesNotMeetTheRedundancySpecifications 1 }

        -- 1.3.6.1.4.1.2011.2.251.20.1.2.2.15.255.36.2
        theHostPathDoesNotMeetTheRedundancySpecifications-Resume NOTIFICATION-TYPE
            OBJECTS { hwStorageAlarmReporting }
            STATUS current
            DESCRIPTION "Recover: Paths Between The Host And Storage Array Do Not Meet Redundancy Requirements"
            --#SEVERITY INFORMATIONAL
            ::= { theHostPathDoesNotMeetTheRedundancySpecifications 2 }

        -- 1.3.6.1.4.1.2011.2.251.20.1.2.2.15.255.37
        theHostPathDoesNotMeetTheRedundancySpecification OBJECT IDENTIFIER ::= { hostlink 37 }

        -- 1.3.6.1.4.1.2011.2.251.20.1.2.2.15.255.37.1
        theHostPathDoesNotMeetTheRedundancySpecification-Fault NOTIFICATION-TYPE
            OBJECTS { hwStorageAlarmReporting }
            STATUS current
            DESCRIPTION "Paths Between The Host And Storage Array Do Not Meet Redundancy Requirements"
            --#SEVERITY MAJOR
            ::= { theHostPathDoesNotMeetTheRedundancySpecification 1 }

        -- 1.3.6.1.4.1.2011.2.251.20.1.2.2.15.255.37.2
        theHostPathDoesNotMeetTheRedundancySpecification-Resume NOTIFICATION-TYPE
            OBJECTS { hwStorageAlarmReporting }
            STATUS current
            DESCRIPTION "Recover: Paths Between The Host And Storage Array Do Not Meet Redundancy Requirements"
            --#SEVERITY INFORMATIONAL
            ::= { theHostPathDoesNotMeetTheRedundancySpecification 2 }

        -- 1.3.6.1.4.1.2011.2.251.20.1.2.2.15.255.38
        hostPathDoesNotMeetTheRedundancySpecifications OBJECT IDENTIFIER ::= { hostlink 38 }

        -- 1.3.6.1.4.1.2011.2.251.20.1.2.2.15.255.38.1
        hostPathDoesNotMeetTheRedundancySpecifications-Fault NOTIFICATION-TYPE
            OBJECTS { hwStorageAlarmReporting }
            STATUS current
            DESCRIPTION "Paths Between The Host And Storage Array Do Not Meet Redundancy Requirements"
            --#SEVERITY MAJOR
            ::= { hostPathDoesNotMeetTheRedundancySpecifications 1 }

        -- 1.3.6.1.4.1.2011.2.251.20.1.2.2.15.255.38.2
        hostPathDoesNotMeetTheRedundancySpecifications-Resume NOTIFICATION-TYPE
            OBJECTS { hwStorageAlarmReporting }
            STATUS current
            DESCRIPTION "Recover: Paths Between The Host And Storage Array Do Not Meet Redundancy Requirements"
            --#SEVERITY INFORMATIONAL
            ::= { hostPathDoesNotMeetTheRedundancySpecifications 2 }

        -- 1.3.6.1.4.1.2011.2.251.20.1.2.2.15.263
        replicationpair OBJECT IDENTIFIER ::= { oidBasedTrap 263 }

        -- 1.3.6.1.4.1.2011.2.251.20.1.2.2.15.263.21
        addRemoteReplicationToCGFails OBJECT IDENTIFIER ::= { replicationpair 21 }

        -- 1.3.6.1.4.1.2011.2.251.20.1.2.2.15.263.21.1
        addRemoteReplicationToCGFails-Fault NOTIFICATION-TYPE
            OBJECTS { hwStorageAlarmReporting }
            STATUS current
            DESCRIPTION "Failed To Add Remote Replication To A Consistent Group"
            --#SEVERITY WARNING
            ::= { addRemoteReplicationToCGFails 1 }

        -- 1.3.6.1.4.1.2011.2.251.20.1.2.2.15.263.21.2
        addRemoteReplicationToCGFails-Resume NOTIFICATION-TYPE
            OBJECTS { hwStorageAlarmReporting }
            STATUS current
            DESCRIPTION "Recover: Failed To Add Remote Replication To A Consistent Group"
            --#SEVERITY INFORMATIONAL
            ::= { addRemoteReplicationToCGFails 2 }

        -- 1.3.6.1.4.1.2011.2.251.20.1.2.2.15.263.22
        failedRecoverRmReplication OBJECT IDENTIFIER ::= { replicationpair 22 }

        -- 1.3.6.1.4.1.2011.2.251.20.1.2.2.15.263.22.1
        failedRecoverRmReplication-Fault NOTIFICATION-TYPE
            OBJECTS { hwStorageAlarmReporting }
            STATUS current
            DESCRIPTION "Failed To Recover The LUN Remote Replication Service At The Array End"
            --#SEVERITY CRITICAL
            ::= { failedRecoverRmReplication 1 }

        -- 1.3.6.1.4.1.2011.2.251.20.1.2.2.15.263.22.2
        failedRecoverRmReplication-Resume NOTIFICATION-TYPE
            OBJECTS { hwStorageAlarmReporting }
            STATUS current
            DESCRIPTION "Recover: Failed To Recover The LUN Remote Replication Service At The Array End"
            --#SEVERITY INFORMATIONAL
            ::= { failedRecoverRmReplication 2 }

        -- 1.3.6.1.4.1.2011.2.251.20.1.2.2.15.263.27
        fsRmPairRecovered OBJECT IDENTIFIER ::= { replicationpair 27 }

        -- 1.3.6.1.4.1.2011.2.251.20.1.2.2.15.263.27.1
        fsRmPairRecovered-Fault NOTIFICATION-TYPE
            OBJECTS { hwStorageAlarmReporting }
            STATUS current
            DESCRIPTION "File Remote Replication Enters The ToBeRecovered Status And Data At The Primary End Cannot Be Synchronized To The Remote End"
            --#SEVERITY MAJOR
            ::= { fsRmPairRecovered 1 }

        -- 1.3.6.1.4.1.2011.2.251.20.1.2.2.15.263.27.2
        fsRmPairRecovered-Resume NOTIFICATION-TYPE
            OBJECTS { hwStorageAlarmReporting }
            STATUS current
            DESCRIPTION "Recover: File Remote Replication Enters The ToBeRecovered Status And Data At The Primary End Cannot Be Synchronized To The Remote End"
            --#SEVERITY INFORMATIONAL
            ::= { fsRmPairRecovered 2 }

        -- 1.3.6.1.4.1.2011.2.251.20.1.2.2.15.263.36
        fsRemoteReplicationPairFault OBJECT IDENTIFIER ::= { replicationpair 36 }

        -- 1.3.6.1.4.1.2011.2.251.20.1.2.2.15.263.36.1
        fsRemoteReplicationPairFault-Fault NOTIFICATION-TYPE
            OBJECTS { hwStorageAlarmReporting }
            STATUS current
            DESCRIPTION "A Remote Replication Is Interrupted Unexpectedly"
            --#SEVERITY MAJOR
            ::= { fsRemoteReplicationPairFault 1 }

        -- 1.3.6.1.4.1.2011.2.251.20.1.2.2.15.263.36.2
        fsRemoteReplicationPairFault-Resume NOTIFICATION-TYPE
            OBJECTS { hwStorageAlarmReporting }
            STATUS current
            DESCRIPTION "Recover: A Remote Replication Is Interrupted Unexpectedly"
            --#SEVERITY INFORMATIONAL
            ::= { fsRemoteReplicationPairFault 2 }

        -- 1.3.6.1.4.1.2011.2.251.20.1.2.2.15.263.38
        rmPairRecoveredNew OBJECT IDENTIFIER ::= { replicationpair 38 }

        -- 1.3.6.1.4.1.2011.2.251.20.1.2.2.15.263.38.1
        rmPairRecoveredNew-Fault NOTIFICATION-TYPE
            OBJECTS { hwStorageAlarmReporting }
            STATUS current
            DESCRIPTION "The Remote Replication Pair Enters The ToBeRecovered State Data On The Primary End Cannot Be Synchronized To The Remote End"
            --#SEVERITY MAJOR
            ::= { rmPairRecoveredNew 1 }

        -- 1.3.6.1.4.1.2011.2.251.20.1.2.2.15.263.38.2
        rmPairRecoveredNew-Resume NOTIFICATION-TYPE
            OBJECTS { hwStorageAlarmReporting }
            STATUS current
            DESCRIPTION "Recover: The Remote Replication Pair Enters The ToBeRecovered State Data On The Primary End Cannot Be Synchronized To The Remote End"
            --#SEVERITY INFORMATIONAL
            ::= { rmPairRecoveredNew 2 }

        -- 1.3.6.1.4.1.2011.2.251.20.1.2.2.15.263.56
        remoteReplicationIsInterrupted OBJECT IDENTIFIER ::= { replicationpair 56 }

        -- 1.3.6.1.4.1.2011.2.251.20.1.2.2.15.263.56.1
        remoteReplicationIsInterrupted-Fault NOTIFICATION-TYPE
            OBJECTS { hwStorageAlarmReporting }
            STATUS current
            DESCRIPTION "Remote Replication Is Interrupted"
            --#SEVERITY MAJOR
            ::= { remoteReplicationIsInterrupted 1 }

        -- 1.3.6.1.4.1.2011.2.251.20.1.2.2.15.263.56.2
        remoteReplicationIsInterrupted-Resume NOTIFICATION-TYPE
            OBJECTS { hwStorageAlarmReporting }
            STATUS current
            DESCRIPTION "Recover: Remote Replication Is Interrupted"
            --#SEVERITY INFORMATIONAL
            ::= { remoteReplicationIsInterrupted 2 }

        -- 1.3.6.1.4.1.2011.2.251.20.1.2.2.15.263.57
        remoteReplicationIsInvalid OBJECT IDENTIFIER ::= { replicationpair 57 }

        -- 1.3.6.1.4.1.2011.2.251.20.1.2.2.15.263.57.1
        remoteReplicationIsInvalid-Fault NOTIFICATION-TYPE
            OBJECTS { hwStorageAlarmReporting }
            STATUS current
            DESCRIPTION "Remote Replication Is Unavailable"
            --#SEVERITY CRITICAL
            ::= { remoteReplicationIsInvalid 1 }

        -- 1.3.6.1.4.1.2011.2.251.20.1.2.2.15.263.57.2
        remoteReplicationIsInvalid-Resume NOTIFICATION-TYPE
            OBJECTS { hwStorageAlarmReporting }
            STATUS current
            DESCRIPTION "Recover: Remote Replication Is Unavailable"
            --#SEVERITY INFORMATIONAL
            ::= { remoteReplicationIsInvalid 2 }

        -- 1.3.6.1.4.1.2011.2.251.20.1.2.2.15.263.58
        autoStartSynRemoteRepFails OBJECT IDENTIFIER ::= { replicationpair 58 }

        -- 1.3.6.1.4.1.2011.2.251.20.1.2.2.15.263.58.1
        autoStartSynRemoteRepFails-Fault NOTIFICATION-TYPE
            OBJECTS { hwStorageAlarmReporting }
            STATUS current
            DESCRIPTION "Remote Replication Failed To Synchronize Data Automatically"
            --#SEVERITY MAJOR
            ::= { autoStartSynRemoteRepFails 1 }

        -- 1.3.6.1.4.1.2011.2.251.20.1.2.2.15.263.58.2
        autoStartSynRemoteRepFails-Resume NOTIFICATION-TYPE
            OBJECTS { hwStorageAlarmReporting }
            STATUS current
            DESCRIPTION "Recover: Remote Replication Failed To Synchronize Data Automatically"
            --#SEVERITY INFORMATIONAL
            ::= { autoStartSynRemoteRepFails 2 }

        -- 1.3.6.1.4.1.2011.2.251.20.1.2.2.15.263.274
        fsRemoteReplicationPairInvalid OBJECT IDENTIFIER ::= { replicationpair 274 }

        -- 1.3.6.1.4.1.2011.2.251.20.1.2.2.15.263.274.1
        fsRemoteReplicationPairInvalid-Fault NOTIFICATION-TYPE
            OBJECTS { hwStorageAlarmReporting }
            STATUS current
            DESCRIPTION "A Remote Replication Is Unavailable"
            --#SEVERITY CRITICAL
            ::= { fsRemoteReplicationPairInvalid 1 }

        -- 1.3.6.1.4.1.2011.2.251.20.1.2.2.15.263.274.2
        fsRemoteReplicationPairInvalid-Resume NOTIFICATION-TYPE
            OBJECTS { hwStorageAlarmReporting }
            STATUS current
            DESCRIPTION "Recover: A Remote Replication Is Unavailable"
            --#SEVERITY INFORMATIONAL
            ::= { fsRemoteReplicationPairInvalid 2 }

        -- 1.3.6.1.4.1.2011.2.251.20.1.2.2.15.263.275
        fsRemoteReplicationPairFault1 OBJECT IDENTIFIER ::= { replicationpair 275 }

        -- 1.3.6.1.4.1.2011.2.251.20.1.2.2.15.263.275.1
        fsRemoteReplicationPairFault1-Fault NOTIFICATION-TYPE
            OBJECTS { hwStorageAlarmReporting }
            STATUS current
            DESCRIPTION "A Remote Replication Pair Is Interrupted Unexpectedly"
            --#SEVERITY MAJOR
            ::= { fsRemoteReplicationPairFault1 1 }

        -- 1.3.6.1.4.1.2011.2.251.20.1.2.2.15.263.275.2
        fsRemoteReplicationPairFault1-Resume NOTIFICATION-TYPE
            OBJECTS { hwStorageAlarmReporting }
            STATUS current
            DESCRIPTION "Recover: A Remote Replication Pair Is Interrupted Unexpectedly"
            --#SEVERITY INFORMATIONAL
            ::= { fsRemoteReplicationPairFault1 2 }

        -- 1.3.6.1.4.1.2011.2.251.20.1.2.2.15.263.304
        fsRemoteReplicationAutoSyncFail OBJECT IDENTIFIER ::= { replicationpair 304 }

        -- 1.3.6.1.4.1.2011.2.251.20.1.2.2.15.263.304.1
        fsRemoteReplicationAutoSyncFail-Fault NOTIFICATION-TYPE
            OBJECTS { hwStorageAlarmReporting }
            STATUS current
            DESCRIPTION "A Remote Replication Pair Fails To Synchronize Data Automatically"
            --#SEVERITY MAJOR
            ::= { fsRemoteReplicationAutoSyncFail 1 }

        -- 1.3.6.1.4.1.2011.2.251.20.1.2.2.15.263.304.2
        fsRemoteReplicationAutoSyncFail-Resume NOTIFICATION-TYPE
            OBJECTS { hwStorageAlarmReporting }
            STATUS current
            DESCRIPTION "Recover: A Remote Replication Pair Fails To Synchronize Data Automatically"
            --#SEVERITY INFORMATIONAL
            ::= { fsRemoteReplicationAutoSyncFail 2 }

        -- 1.3.6.1.4.1.2011.2.251.20.1.2.2.15.263.311
        remoteReplicationAutomaticSplit OBJECT IDENTIFIER ::= { replicationpair 311 }

        -- 1.3.6.1.4.1.2011.2.251.20.1.2.2.15.263.311.1
        remoteReplicationAutomaticSplit-Fault NOTIFICATION-TYPE
            OBJECTS { hwStorageAlarmReporting }
            STATUS current
            DESCRIPTION "Remote Replication Is Automatically Split"
            --#SEVERITY WARNING
            ::= { remoteReplicationAutomaticSplit 1 }

        -- 1.3.6.1.4.1.2011.2.251.20.1.2.2.15.263.311.2
        remoteReplicationAutomaticSplit-Resume NOTIFICATION-TYPE
            OBJECTS { hwStorageAlarmReporting }
            STATUS current
            DESCRIPTION "Recover: Remote Replication Is Automatically Split"
            --#SEVERITY INFORMATIONAL
            ::= { remoteReplicationAutomaticSplit 2 }

        -- 1.3.6.1.4.1.2011.2.251.20.1.2.2.15.264
        eula OBJECT IDENTIFIER ::= { oidBasedTrap 264 }

        -- 1.3.6.1.4.1.2011.2.251.20.1.2.2.15.264.1
        eULANotSigned OBJECT IDENTIFIER ::= { eula 1 }

        -- 1.3.6.1.4.1.2011.2.251.20.1.2.2.15.264.1.1
        eULANotSigned-Fault NOTIFICATION-TYPE
            OBJECTS { hwStorageAlarmReporting }
            STATUS current
            DESCRIPTION "EULA Not Signed"
            --#SEVERITY WARNING
            ::= { eULANotSigned 1 }

        -- 1.3.6.1.4.1.2011.2.251.20.1.2.2.15.264.1.2
        eULANotSigned-Resume NOTIFICATION-TYPE
            OBJECTS { hwStorageAlarmReporting }
            STATUS current
            DESCRIPTION "Recover: EULA Not Signed"
            --#SEVERITY INFORMATIONAL
            ::= { eULANotSigned 2 }

        -- 1.3.6.1.4.1.2011.2.251.20.1.2.2.15.266
        diskdomain OBJECT IDENTIFIER ::= { oidBasedTrap 266 }

        -- 1.3.6.1.4.1.2011.2.251.20.1.2.2.15.266.1
        diskDomainDegradation OBJECT IDENTIFIER ::= { diskdomain 1 }

        -- 1.3.6.1.4.1.2011.2.251.20.1.2.2.15.266.1.1
        diskDomainDegradation-Fault NOTIFICATION-TYPE
            OBJECTS { hwStorageAlarmReporting }
            STATUS current
            DESCRIPTION "Disk Domain Is Degraded"
            --#SEVERITY MAJOR
            ::= { diskDomainDegradation 1 }

        -- 1.3.6.1.4.1.2011.2.251.20.1.2.2.15.266.1.2
        diskDomainDegradation-Resume NOTIFICATION-TYPE
            OBJECTS { hwStorageAlarmReporting }
            STATUS current
            DESCRIPTION "Recover: Disk Domain Is Degraded"
            --#SEVERITY INFORMATIONAL
            ::= { diskDomainDegradation 2 }

        -- 1.3.6.1.4.1.2011.2.251.20.1.2.2.15.266.2
        diskDomainFault OBJECT IDENTIFIER ::= { diskdomain 2 }

        -- 1.3.6.1.4.1.2011.2.251.20.1.2.2.15.266.2.1
        diskDomainFault-Fault NOTIFICATION-TYPE
            OBJECTS { hwStorageAlarmReporting }
            STATUS current
            DESCRIPTION "Disk Domain Is Faulty"
            --#SEVERITY CRITICAL
            ::= { diskDomainFault 1 }

        -- 1.3.6.1.4.1.2011.2.251.20.1.2.2.15.266.2.2
        diskDomainFault-Resume NOTIFICATION-TYPE
            OBJECTS { hwStorageAlarmReporting }
            STATUS current
            DESCRIPTION "Recover: Disk Domain Is Faulty"
            --#SEVERITY INFORMATIONAL
            ::= { diskDomainFault 2 }

        -- 1.3.6.1.4.1.2011.2.251.20.1.2.2.15.266.3
        diskDomainIsOffline OBJECT IDENTIFIER ::= { diskdomain 3 }

        -- 1.3.6.1.4.1.2011.2.251.20.1.2.2.15.266.3.1
        diskDomainIsOffline-Fault NOTIFICATION-TYPE
            OBJECTS { hwStorageAlarmReporting }
            STATUS current
            DESCRIPTION "Disk Domain Is Offline"
            --#SEVERITY CRITICAL
            ::= { diskDomainIsOffline 1 }

        -- 1.3.6.1.4.1.2011.2.251.20.1.2.2.15.266.3.2
        diskDomainIsOffline-Resume NOTIFICATION-TYPE
            OBJECTS { hwStorageAlarmReporting }
            STATUS current
            DESCRIPTION "Recover: Disk Domain Is Offline"
            --#SEVERITY INFORMATIONAL
            ::= { diskDomainIsOffline 2 }

        -- 1.3.6.1.4.1.2011.2.251.20.1.2.2.15.266.6
        differentDiskType1 OBJECT IDENTIFIER ::= { diskdomain 6 }

        -- 1.3.6.1.4.1.2011.2.251.20.1.2.2.15.266.6.1
        differentDiskType1-Fault NOTIFICATION-TYPE
            OBJECTS { hwStorageAlarmReporting }
            STATUS current
            DESCRIPTION "Inconsistent Disk Types"
            --#SEVERITY MAJOR
            ::= { differentDiskType1 1 }

        -- 1.3.6.1.4.1.2011.2.251.20.1.2.2.15.266.6.2
        differentDiskType1-Resume NOTIFICATION-TYPE
            OBJECTS { hwStorageAlarmReporting }
            STATUS current
            DESCRIPTION "Recover: Inconsistent Disk Types"
            --#SEVERITY INFORMATIONAL
            ::= { differentDiskType1 2 }

        -- 1.3.6.1.4.1.2011.2.251.20.1.2.2.15.266.8
        diskIsRemovedFromDiskDomain OBJECT IDENTIFIER ::= { diskdomain 8 }

        -- 1.3.6.1.4.1.2011.2.251.20.1.2.2.15.266.8.1
        diskIsRemovedFromDiskDomain-Fault NOTIFICATION-TYPE
            OBJECTS { hwStorageAlarmReporting }
            STATUS current
            DESCRIPTION "A Disk Is Removed From A Disk Domain"
            --#SEVERITY MAJOR
            ::= { diskIsRemovedFromDiskDomain 1 }

        -- 1.3.6.1.4.1.2011.2.251.20.1.2.2.15.266.8.2
        diskIsRemovedFromDiskDomain-Resume NOTIFICATION-TYPE
            OBJECTS { hwStorageAlarmReporting }
            STATUS current
            DESCRIPTION "Recover: A Disk Is Removed From A Disk Domain"
            --#SEVERITY INFORMATIONAL
            ::= { diskIsRemovedFromDiskDomain 2 }

        -- 1.3.6.1.4.1.2011.2.251.20.1.2.2.15.266.11
        diskDomainReconstructionFailed OBJECT IDENTIFIER ::= { diskdomain 11 }

        -- 1.3.6.1.4.1.2011.2.251.20.1.2.2.15.266.11.1
        diskDomainReconstructionFailed-Fault NOTIFICATION-TYPE
            OBJECTS { hwStorageAlarmReporting }
            STATUS current
            DESCRIPTION "Disk Domain Reconstruction Failed"
            --#SEVERITY MAJOR
            ::= { diskDomainReconstructionFailed 1 }

        -- 1.3.6.1.4.1.2011.2.251.20.1.2.2.15.266.11.2
        diskDomainReconstructionFailed-Resume NOTIFICATION-TYPE
            OBJECTS { hwStorageAlarmReporting }
            STATUS current
            DESCRIPTION "Recover: Disk Domain Reconstruction Failed"
            --#SEVERITY INFORMATIONAL
            ::= { diskDomainReconstructionFailed 2 }

        -- 1.3.6.1.4.1.2011.2.251.20.1.2.2.15.266.14
        diskDomainPreCopyFailed OBJECT IDENTIFIER ::= { diskdomain 14 }

        -- 1.3.6.1.4.1.2011.2.251.20.1.2.2.15.266.14.1
        diskDomainPreCopyFailed-Fault NOTIFICATION-TYPE
            OBJECTS { hwStorageAlarmReporting }
            STATUS current
            DESCRIPTION "Disk Domain PreCopy Failed"
            --#SEVERITY MAJOR
            ::= { diskDomainPreCopyFailed 1 }

        -- 1.3.6.1.4.1.2011.2.251.20.1.2.2.15.266.14.2
        diskDomainPreCopyFailed-Resume NOTIFICATION-TYPE
            OBJECTS { hwStorageAlarmReporting }
            STATUS current
            DESCRIPTION "Recover: Disk Domain PreCopy Failed"
            --#SEVERITY INFORMATIONAL
            ::= { diskDomainPreCopyFailed 2 }

        -- 1.3.6.1.4.1.2011.2.251.20.1.2.2.15.266.32
        newDiskCapacityInsufficieny1 OBJECT IDENTIFIER ::= { diskdomain 32 }

        -- 1.3.6.1.4.1.2011.2.251.20.1.2.2.15.266.32.1
        newDiskCapacityInsufficieny1-Fault NOTIFICATION-TYPE
            OBJECTS { hwStorageAlarmReporting }
            STATUS current
            DESCRIPTION "A New Disk Fails To Be Added To The Disk Domain"
            --#SEVERITY MAJOR
            ::= { newDiskCapacityInsufficieny1 1 }

        -- 1.3.6.1.4.1.2011.2.251.20.1.2.2.15.266.32.2
        newDiskCapacityInsufficieny1-Resume NOTIFICATION-TYPE
            OBJECTS { hwStorageAlarmReporting }
            STATUS current
            DESCRIPTION "Recover: A New Disk Fails To Be Added To The Disk Domain"
            --#SEVERITY INFORMATIONAL
            ::= { newDiskCapacityInsufficieny1 2 }

        -- 1.3.6.1.4.1.2011.2.251.20.1.2.2.15.266.85
        diskDomainHasAMediumError OBJECT IDENTIFIER ::= { diskdomain 85 }

        -- 1.3.6.1.4.1.2011.2.251.20.1.2.2.15.266.85.1
        diskDomainHasAMediumError-Fault NOTIFICATION-TYPE
            OBJECTS { hwStorageAlarmReporting }
            STATUS current
            DESCRIPTION "A Disk Domain Has A Medium Error"
            --#SEVERITY CRITICAL
            ::= { diskDomainHasAMediumError 1 }

        -- 1.3.6.1.4.1.2011.2.251.20.1.2.2.15.266.85.2
        diskDomainHasAMediumError-Resume NOTIFICATION-TYPE
            OBJECTS { hwStorageAlarmReporting }
            STATUS current
            DESCRIPTION "Recover: A Disk Domain Has A Medium Error"
            --#SEVERITY INFORMATIONAL
            ::= { diskDomainHasAMediumError 2 }

        -- 1.3.6.1.4.1.2011.2.251.20.1.2.2.15.266.87
        internalResourceOfTheDiskDomainIsNotEnough OBJECT IDENTIFIER ::= { diskdomain 87 }

        -- 1.3.6.1.4.1.2011.2.251.20.1.2.2.15.266.87.1
        internalResourceOfTheDiskDomainIsNotEnough-Fault NOTIFICATION-TYPE
            OBJECTS { hwStorageAlarmReporting }
            STATUS current
            DESCRIPTION "Internal Resource Of The Disk Domain Is Not Enough"
            --#SEVERITY CRITICAL
            ::= { internalResourceOfTheDiskDomainIsNotEnough 1 }

        -- 1.3.6.1.4.1.2011.2.251.20.1.2.2.15.266.87.2
        internalResourceOfTheDiskDomainIsNotEnough-Resume NOTIFICATION-TYPE
            OBJECTS { hwStorageAlarmReporting }
            STATUS current
            DESCRIPTION "Recover: Internal Resource Of The Disk Domain Is Not Enough"
            --#SEVERITY INFORMATIONAL
            ::= { internalResourceOfTheDiskDomainIsNotEnough 2 }

        -- 1.3.6.1.4.1.2011.2.251.20.1.2.2.15.266.95
        theSelfEncryptingDiskKeyInADiskDomainHasExpired OBJECT IDENTIFIER ::= { diskdomain 95 }

        -- 1.3.6.1.4.1.2011.2.251.20.1.2.2.15.266.95.1
        theSelfEncryptingDiskKeyInADiskDomainHasExpired-Fault NOTIFICATION-TYPE
            OBJECTS { hwStorageAlarmReporting }
            STATUS current
            DESCRIPTION "The SelfEncrypting Disk Key In A Disk Domain Has Expired"
            --#SEVERITY CRITICAL
            ::= { theSelfEncryptingDiskKeyInADiskDomainHasExpired 1 }

        -- 1.3.6.1.4.1.2011.2.251.20.1.2.2.15.266.95.2
        theSelfEncryptingDiskKeyInADiskDomainHasExpired-Resume NOTIFICATION-TYPE
            OBJECTS { hwStorageAlarmReporting }
            STATUS current
            DESCRIPTION "Recover: The SelfEncrypting Disk Key In A Disk Domain Has Expired"
            --#SEVERITY INFORMATIONAL
            ::= { theSelfEncryptingDiskKeyInADiskDomainHasExpired 2 }

        -- 1.3.6.1.4.1.2011.2.251.20.1.2.2.15.266.96
        theSelfEncryptingDiskKeyInADiskDomainIsAboutToExpire OBJECT IDENTIFIER ::= { diskdomain 96 }

        -- 1.3.6.1.4.1.2011.2.251.20.1.2.2.15.266.96.1
        theSelfEncryptingDiskKeyInADiskDomainIsAboutToExpire-Fault NOTIFICATION-TYPE
            OBJECTS { hwStorageAlarmReporting }
            STATUS current
            DESCRIPTION "The SelfEncrypting Disk Key In A Disk Domain Is About To Expire"
            --#SEVERITY WARNING
            ::= { theSelfEncryptingDiskKeyInADiskDomainIsAboutToExpire 1 }

        -- 1.3.6.1.4.1.2011.2.251.20.1.2.2.15.266.96.2
        theSelfEncryptingDiskKeyInADiskDomainIsAboutToExpire-Resume NOTIFICATION-TYPE
            OBJECTS { hwStorageAlarmReporting }
            STATUS current
            DESCRIPTION "Recover: The SelfEncrypting Disk Key In A Disk Domain Is About To Expire"
            --#SEVERITY INFORMATIONAL
            ::= { theSelfEncryptingDiskKeyInADiskDomainIsAboutToExpire 2 }

        -- 1.3.6.1.4.1.2011.2.251.20.1.2.2.15.266.104
        hotSpareCapacityInsufficient1 OBJECT IDENTIFIER ::= { diskdomain 104 }

        -- 1.3.6.1.4.1.2011.2.251.20.1.2.2.15.266.104.1
        hotSpareCapacityInsufficient1-Fault NOTIFICATION-TYPE
            OBJECTS { hwStorageAlarmReporting }
            STATUS current
            DESCRIPTION "The Hot Spare Space Of The Disk Domain Is Insufficient"
            --#SEVERITY CRITICAL
            ::= { hotSpareCapacityInsufficient1 1 }

        -- 1.3.6.1.4.1.2011.2.251.20.1.2.2.15.266.104.2
        hotSpareCapacityInsufficient1-Resume NOTIFICATION-TYPE
            OBJECTS { hwStorageAlarmReporting }
            STATUS current
            DESCRIPTION "Recover: The Hot Spare Space Of The Disk Domain Is Insufficient"
            --#SEVERITY INFORMATIONAL
            ::= { hotSpareCapacityInsufficient1 2 }

        -- 1.3.6.1.4.1.2011.2.251.20.1.2.2.15.266.108
        theNewDiskFailedToBeAddedToTheDiskDomain OBJECT IDENTIFIER ::= { diskdomain 108 }

        -- 1.3.6.1.4.1.2011.2.251.20.1.2.2.15.266.108.1
        theNewDiskFailedToBeAddedToTheDiskDomain-Fault NOTIFICATION-TYPE
            OBJECTS { hwStorageAlarmReporting }
            STATUS current
            DESCRIPTION "The New Disk Failed To Be Added To The Disk Domain"
            --#SEVERITY MAJOR
            ::= { theNewDiskFailedToBeAddedToTheDiskDomain 1 }

        -- 1.3.6.1.4.1.2011.2.251.20.1.2.2.15.266.108.2
        theNewDiskFailedToBeAddedToTheDiskDomain-Resume NOTIFICATION-TYPE
            OBJECTS { hwStorageAlarmReporting }
            STATUS current
            DESCRIPTION "Recover: The New Disk Failed To Be Added To The Disk Domain"
            --#SEVERITY INFORMATIONAL
            ::= { theNewDiskFailedToBeAddedToTheDiskDomain 2 }

        -- 1.3.6.1.4.1.2011.2.251.20.1.2.2.15.266.109
        inconsistentEncryptionTypesBeforeAndAfterDiskReplacement1 OBJECT IDENTIFIER ::= { diskdomain 109 }

        -- 1.3.6.1.4.1.2011.2.251.20.1.2.2.15.266.109.1
        inconsistentEncryptionTypesBeforeAndAfterDiskReplacement1-Fault NOTIFICATION-TYPE
            OBJECTS { hwStorageAlarmReporting }
            STATUS current
            DESCRIPTION "Inconsistent Encryption Types Before And After Disk Replacement"
            --#SEVERITY MAJOR
            ::= { inconsistentEncryptionTypesBeforeAndAfterDiskReplacement1 1 }

        -- 1.3.6.1.4.1.2011.2.251.20.1.2.2.15.266.109.2
        inconsistentEncryptionTypesBeforeAndAfterDiskReplacement1-Resume NOTIFICATION-TYPE
            OBJECTS { hwStorageAlarmReporting }
            STATUS current
            DESCRIPTION "Recover: Inconsistent Encryption Types Before And After Disk Replacement"
            --#SEVERITY INFORMATIONAL
            ::= { inconsistentEncryptionTypesBeforeAndAfterDiskReplacement1 2 }

        -- 1.3.6.1.4.1.2011.2.251.20.1.2.2.15.266.110
        diskDomainLosesEnclosurelevelRedundancyCapability OBJECT IDENTIFIER ::= { diskdomain 110 }

        -- 1.3.6.1.4.1.2011.2.251.20.1.2.2.15.266.110.1
        diskDomainLosesEnclosurelevelRedundancyCapability-Fault NOTIFICATION-TYPE
            OBJECTS { hwStorageAlarmReporting }
            STATUS current
            DESCRIPTION "Disk Domain Loses Enclosurelevel Redundancy Capability"
            --#SEVERITY WARNING
            ::= { diskDomainLosesEnclosurelevelRedundancyCapability 1 }

        -- 1.3.6.1.4.1.2011.2.251.20.1.2.2.15.266.110.2
        diskDomainLosesEnclosurelevelRedundancyCapability-Resume NOTIFICATION-TYPE
            OBJECTS { hwStorageAlarmReporting }
            STATUS current
            DESCRIPTION "Recover: Disk Domain Loses Enclosurelevel Redundancy Capability"
            --#SEVERITY INFORMATIONAL
            ::= { diskDomainLosesEnclosurelevelRedundancyCapability 2 }

        -- 1.3.6.1.4.1.2011.2.251.20.1.2.2.15.266.112
        theDiskDomainCannotProvideEnclosureLevelRedundancyDueToDiskLocationChange OBJECT IDENTIFIER ::= { diskdomain 112 }

        -- 1.3.6.1.4.1.2011.2.251.20.1.2.2.15.266.112.1
        theDiskDomainCannotProvideEnclosureLevelRedundancyDueToDiskLocationChange-Fault NOTIFICATION-TYPE
            OBJECTS { hwStorageAlarmReporting }
            STATUS current
            DESCRIPTION "The Disk Domain Cannot Provide EnclosureLevel Redundancy Due To Disk Location Change"
            --#SEVERITY MAJOR
            ::= { theDiskDomainCannotProvideEnclosureLevelRedundancyDueToDiskLocationChange 1 }

        -- 1.3.6.1.4.1.2011.2.251.20.1.2.2.15.266.112.2
        theDiskDomainCannotProvideEnclosureLevelRedundancyDueToDiskLocationChange-Resume NOTIFICATION-TYPE
            OBJECTS { hwStorageAlarmReporting }
            STATUS current
            DESCRIPTION "Recover: The Disk Domain Cannot Provide EnclosureLevel Redundancy Due To Disk Location Change"
            --#SEVERITY INFORMATIONAL
            ::= { theDiskDomainCannotProvideEnclosureLevelRedundancyDueToDiskLocationChange 2 }

        -- 1.3.6.1.4.1.2011.2.251.20.1.2.2.15.266.116
        theBackgroundInspectionTaskOfTheDiskDomainIsAbnormal OBJECT IDENTIFIER ::= { diskdomain 116 }

        -- 1.3.6.1.4.1.2011.2.251.20.1.2.2.15.266.116.1
        theBackgroundInspectionTaskOfTheDiskDomainIsAbnormal-Fault NOTIFICATION-TYPE
            OBJECTS { hwStorageAlarmReporting }
            STATUS current
            DESCRIPTION "The Background Inspection Task Of The Disk Domain Is Abnormal"
            --#SEVERITY WARNING
            ::= { theBackgroundInspectionTaskOfTheDiskDomainIsAbnormal 1 }

        -- 1.3.6.1.4.1.2011.2.251.20.1.2.2.15.266.116.2
        theBackgroundInspectionTaskOfTheDiskDomainIsAbnormal-Resume NOTIFICATION-TYPE
            OBJECTS { hwStorageAlarmReporting }
            STATUS current
            DESCRIPTION "Recover: The Background Inspection Task Of The Disk Domain Is Abnormal"
            --#SEVERITY INFORMATIONAL
            ::= { theBackgroundInspectionTaskOfTheDiskDomainIsAbnormal 2 }

        -- 1.3.6.1.4.1.2011.2.251.20.1.2.2.15.266.121
        hotSpareCapacityInsufficient OBJECT IDENTIFIER ::= { diskdomain 121 }

        -- 1.3.6.1.4.1.2011.2.251.20.1.2.2.15.266.121.1
        hotSpareCapacityInsufficient-Fault NOTIFICATION-TYPE
            OBJECTS { hwStorageAlarmReporting }
            STATUS current
            DESCRIPTION "The SSD Space In The Disk Domain Is Insufficient"
            --#SEVERITY MAJOR
            ::= { hotSpareCapacityInsufficient 1 }

        -- 1.3.6.1.4.1.2011.2.251.20.1.2.2.15.266.121.2
        hotSpareCapacityInsufficient-Resume NOTIFICATION-TYPE
            OBJECTS { hwStorageAlarmReporting }
            STATUS current
            DESCRIPTION "Recover: The SSD Space In The Disk Domain Is Insufficient"
            --#SEVERITY INFORMATIONAL
            ::= { hotSpareCapacityInsufficient 2 }

        -- 1.3.6.1.4.1.2011.2.251.20.1.2.2.15.266.122
        aComponentInTheDiskDomainIsAbnormal OBJECT IDENTIFIER ::= { diskdomain 122 }

        -- 1.3.6.1.4.1.2011.2.251.20.1.2.2.15.266.122.1
        aComponentInTheDiskDomainIsAbnormal-Fault NOTIFICATION-TYPE
            OBJECTS { hwStorageAlarmReporting }
            STATUS current
            DESCRIPTION "A Component In The Disk Domain Is Abnormal"
            --#SEVERITY MAJOR
            ::= { aComponentInTheDiskDomainIsAbnormal 1 }

        -- 1.3.6.1.4.1.2011.2.251.20.1.2.2.15.266.122.2
        aComponentInTheDiskDomainIsAbnormal-Resume NOTIFICATION-TYPE
            OBJECTS { hwStorageAlarmReporting }
            STATUS current
            DESCRIPTION "Recover: A Component In The Disk Domain Is Abnormal"
            --#SEVERITY INFORMATIONAL
            ::= { aComponentInTheDiskDomainIsAbnormal 2 }

        -- 1.3.6.1.4.1.2011.2.251.20.1.2.2.15.266.124
        thePerformanceLayerQuotaOfTheStoragePoolIsInsufficient OBJECT IDENTIFIER ::= { diskdomain 124 }

        -- 1.3.6.1.4.1.2011.2.251.20.1.2.2.15.266.124.1
        thePerformanceLayerQuotaOfTheStoragePoolIsInsufficient-Fault NOTIFICATION-TYPE
            OBJECTS { hwStorageAlarmReporting }
            STATUS current
            DESCRIPTION "The Performance Layer Quota Of The Storage Pool Is Insufficient"
            --#SEVERITY MAJOR
            ::= { thePerformanceLayerQuotaOfTheStoragePoolIsInsufficient 1 }

        -- 1.3.6.1.4.1.2011.2.251.20.1.2.2.15.266.124.2
        thePerformanceLayerQuotaOfTheStoragePoolIsInsufficient-Resume NOTIFICATION-TYPE
            OBJECTS { hwStorageAlarmReporting }
            STATUS current
            DESCRIPTION "Recover: The Performance Layer Quota Of The Storage Pool Is Insufficient"
            --#SEVERITY INFORMATIONAL
            ::= { thePerformanceLayerQuotaOfTheStoragePoolIsInsufficient 2 }

        -- 1.3.6.1.4.1.2011.2.251.20.1.2.2.15.266.125
        theHotSpareSpaceAtThePerformanceLayerIsInsufficient OBJECT IDENTIFIER ::= { diskdomain 125 }

        -- 1.3.6.1.4.1.2011.2.251.20.1.2.2.15.266.125.1
        theHotSpareSpaceAtThePerformanceLayerIsInsufficient-Fault NOTIFICATION-TYPE
            OBJECTS { hwStorageAlarmReporting }
            STATUS current
            DESCRIPTION "The Hot Spare Space At The Performance Layer Is Insufficient"
            --#SEVERITY MAJOR
            ::= { theHotSpareSpaceAtThePerformanceLayerIsInsufficient 1 }

        -- 1.3.6.1.4.1.2011.2.251.20.1.2.2.15.266.125.2
        theHotSpareSpaceAtThePerformanceLayerIsInsufficient-Resume NOTIFICATION-TYPE
            OBJECTS { hwStorageAlarmReporting }
            STATUS current
            DESCRIPTION "Recover: The Hot Spare Space At The Performance Layer Is Insufficient"
            --#SEVERITY INFORMATIONAL
            ::= { theHotSpareSpaceAtThePerformanceLayerIsInsufficient 2 }

        -- 1.3.6.1.4.1.2011.2.251.20.1.2.2.15.266.126
        aDiskIsRemovedFromThePerformanceLayer OBJECT IDENTIFIER ::= { diskdomain 126 }

        -- 1.3.6.1.4.1.2011.2.251.20.1.2.2.15.266.126.1
        aDiskIsRemovedFromThePerformanceLayer-Fault NOTIFICATION-TYPE
            OBJECTS { hwStorageAlarmReporting }
            STATUS current
            DESCRIPTION "A Disk Is Removed From The Performance Layer"
            --#SEVERITY MAJOR
            ::= { aDiskIsRemovedFromThePerformanceLayer 1 }

        -- 1.3.6.1.4.1.2011.2.251.20.1.2.2.15.266.126.2
        aDiskIsRemovedFromThePerformanceLayer-Resume NOTIFICATION-TYPE
            OBJECTS { hwStorageAlarmReporting }
            STATUS current
            DESCRIPTION "Recover: A Disk Is Removed From The Performance Layer"
            --#SEVERITY INFORMATIONAL
            ::= { aDiskIsRemovedFromThePerformanceLayer 2 }

        -- 1.3.6.1.4.1.2011.2.251.20.1.2.2.15.266.127
        theNewDiskIsNotAddedToThePerformanceLayer OBJECT IDENTIFIER ::= { diskdomain 127 }

        -- 1.3.6.1.4.1.2011.2.251.20.1.2.2.15.266.127.1
        theNewDiskIsNotAddedToThePerformanceLayer-Fault NOTIFICATION-TYPE
            OBJECTS { hwStorageAlarmReporting }
            STATUS current
            DESCRIPTION "The New Disk Is Not Added To The Performance Layer"
            --#SEVERITY MAJOR
            ::= { theNewDiskIsNotAddedToThePerformanceLayer 1 }

        -- 1.3.6.1.4.1.2011.2.251.20.1.2.2.15.266.127.2
        theNewDiskIsNotAddedToThePerformanceLayer-Resume NOTIFICATION-TYPE
            OBJECTS { hwStorageAlarmReporting }
            STATUS current
            DESCRIPTION "Recover: The New Disk Is Not Added To The Performance Layer"
            --#SEVERITY INFORMATIONAL
            ::= { theNewDiskIsNotAddedToThePerformanceLayer 2 }

        -- 1.3.6.1.4.1.2011.2.251.20.1.2.2.15.266.128
        theMemberDiskTypesAreInconsistent OBJECT IDENTIFIER ::= { diskdomain 128 }

        -- 1.3.6.1.4.1.2011.2.251.20.1.2.2.15.266.128.1
        theMemberDiskTypesAreInconsistent-Fault NOTIFICATION-TYPE
            OBJECTS { hwStorageAlarmReporting }
            STATUS current
            DESCRIPTION "The Member Disk Types Are Inconsistent"
            --#SEVERITY MAJOR
            ::= { theMemberDiskTypesAreInconsistent 1 }

        -- 1.3.6.1.4.1.2011.2.251.20.1.2.2.15.266.128.2
        theMemberDiskTypesAreInconsistent-Resume NOTIFICATION-TYPE
            OBJECTS { hwStorageAlarmReporting }
            STATUS current
            DESCRIPTION "Recover: The Member Disk Types Are Inconsistent"
            --#SEVERITY INFORMATIONAL
            ::= { theMemberDiskTypesAreInconsistent 2 }

        -- 1.3.6.1.4.1.2011.2.251.20.1.2.2.15.266.129
        theMemberDiskEncryptionTypesAreInconsistent OBJECT IDENTIFIER ::= { diskdomain 129 }

        -- 1.3.6.1.4.1.2011.2.251.20.1.2.2.15.266.129.1
        theMemberDiskEncryptionTypesAreInconsistent-Fault NOTIFICATION-TYPE
            OBJECTS { hwStorageAlarmReporting }
            STATUS current
            DESCRIPTION "The Member Disk Encryption Types Are Inconsistent"
            --#SEVERITY MAJOR
            ::= { theMemberDiskEncryptionTypesAreInconsistent 1 }

        -- 1.3.6.1.4.1.2011.2.251.20.1.2.2.15.266.129.2
        theMemberDiskEncryptionTypesAreInconsistent-Resume NOTIFICATION-TYPE
            OBJECTS { hwStorageAlarmReporting }
            STATUS current
            DESCRIPTION "Recover: The Member Disk Encryption Types Are Inconsistent"
            --#SEVERITY INFORMATIONAL
            ::= { theMemberDiskEncryptionTypesAreInconsistent 2 }

        -- 1.3.6.1.4.1.2011.2.251.20.1.2.2.15.266.130
        failedToAddTheNewDiskToThePerformanceLayer OBJECT IDENTIFIER ::= { diskdomain 130 }

        -- 1.3.6.1.4.1.2011.2.251.20.1.2.2.15.266.130.1
        failedToAddTheNewDiskToThePerformanceLayer-Fault NOTIFICATION-TYPE
            OBJECTS { hwStorageAlarmReporting }
            STATUS current
            DESCRIPTION "Failed To Add The New Disk To The Performance Layer"
            --#SEVERITY MAJOR
            ::= { failedToAddTheNewDiskToThePerformanceLayer 1 }

        -- 1.3.6.1.4.1.2011.2.251.20.1.2.2.15.266.130.2
        failedToAddTheNewDiskToThePerformanceLayer-Resume NOTIFICATION-TYPE
            OBJECTS { hwStorageAlarmReporting }
            STATUS current
            DESCRIPTION "Recover: Failed To Add The New Disk To The Performance Layer"
            --#SEVERITY INFORMATIONAL
            ::= { failedToAddTheNewDiskToThePerformanceLayer 2 }

        -- 1.3.6.1.4.1.2011.2.251.20.1.2.2.15.266.131
        theNewDiskIsNotAddedToThePerformanceLayerDueToAnInconsistentModel OBJECT IDENTIFIER ::= { diskdomain 131 }

        -- 1.3.6.1.4.1.2011.2.251.20.1.2.2.15.266.131.1
        theNewDiskIsNotAddedToThePerformanceLayerDueToAnInconsistentModel-Fault NOTIFICATION-TYPE
            OBJECTS { hwStorageAlarmReporting }
            STATUS current
            DESCRIPTION "The New Disk Is Not Added To The Performance Layer Due To An Inconsistent Model"
            --#SEVERITY MAJOR
            ::= { theNewDiskIsNotAddedToThePerformanceLayerDueToAnInconsistentModel 1 }

        -- 1.3.6.1.4.1.2011.2.251.20.1.2.2.15.266.131.2
        theNewDiskIsNotAddedToThePerformanceLayerDueToAnInconsistentModel-Resume NOTIFICATION-TYPE
            OBJECTS { hwStorageAlarmReporting }
            STATUS current
            DESCRIPTION "Recover: The New Disk Is Not Added To The Performance Layer Due To An Inconsistent Model"
            --#SEVERITY INFORMATIONAL
            ::= { theNewDiskIsNotAddedToThePerformanceLayerDueToAnInconsistentModel 2 }

        -- 1.3.6.1.4.1.2011.2.251.20.1.2.2.15.266.134
        diskDomainSelfCheck OBJECT IDENTIFIER ::= { diskdomain 134 }

        -- 1.3.6.1.4.1.2011.2.251.20.1.2.2.15.266.134.1
        diskDomainSelfCheck-Fault NOTIFICATION-TYPE
            OBJECTS { hwStorageAlarmReporting }
            STATUS current
            DESCRIPTION "Disk Domain SelfCheck"
            --#SEVERITY MAJOR
            ::= { diskDomainSelfCheck 1 }

        -- 1.3.6.1.4.1.2011.2.251.20.1.2.2.15.266.134.2
        diskDomainSelfCheck-Resume NOTIFICATION-TYPE
            OBJECTS { hwStorageAlarmReporting }
            STATUS current
            DESCRIPTION "Recover: Disk Domain SelfCheck"
            --#SEVERITY INFORMATIONAL
            ::= { diskDomainSelfCheck 2 }

        -- 1.3.6.1.4.1.2011.2.251.20.1.2.2.15.266.136
        newDiskInconsistentHardwareModel OBJECT IDENTIFIER ::= { diskdomain 136 }

        -- 1.3.6.1.4.1.2011.2.251.20.1.2.2.15.266.136.1
        newDiskInconsistentHardwareModel-Fault NOTIFICATION-TYPE
            OBJECTS { hwStorageAlarmReporting }
            STATUS current
            DESCRIPTION "The New Disk Is Not Added To The Disk Domain"
            --#SEVERITY MAJOR
            ::= { newDiskInconsistentHardwareModel 1 }

        -- 1.3.6.1.4.1.2011.2.251.20.1.2.2.15.266.136.2
        newDiskInconsistentHardwareModel-Resume NOTIFICATION-TYPE
            OBJECTS { hwStorageAlarmReporting }
            STATUS current
            DESCRIPTION "Recover: The New Disk Is Not Added To The Disk Domain"
            --#SEVERITY INFORMATIONAL
            ::= { newDiskInconsistentHardwareModel 2 }

        -- 1.3.6.1.4.1.2011.2.251.20.1.2.2.15.266.137
        theDiskDomainScaleInTaskIsAboutToBeRolledBack1 OBJECT IDENTIFIER ::= { diskdomain 137 }

        -- 1.3.6.1.4.1.2011.2.251.20.1.2.2.15.266.137.1
        theDiskDomainScaleInTaskIsAboutToBeRolledBack1-Fault NOTIFICATION-TYPE
            OBJECTS { hwStorageAlarmReporting }
            STATUS current
            DESCRIPTION "The Disk Domain ScaleIn Task Is About To Be Rolled Back"
            --#SEVERITY MAJOR
            ::= { theDiskDomainScaleInTaskIsAboutToBeRolledBack1 1 }

        -- 1.3.6.1.4.1.2011.2.251.20.1.2.2.15.266.137.2
        theDiskDomainScaleInTaskIsAboutToBeRolledBack1-Resume NOTIFICATION-TYPE
            OBJECTS { hwStorageAlarmReporting }
            STATUS current
            DESCRIPTION "Recover: The Disk Domain ScaleIn Task Is About To Be Rolled Back"
            --#SEVERITY INFORMATIONAL
            ::= { theDiskDomainScaleInTaskIsAboutToBeRolledBack1 2 }

        -- 1.3.6.1.4.1.2011.2.251.20.1.2.2.15.266.138
        theDiskDomainScaleInTaskIsAboutToBeRolledBack OBJECT IDENTIFIER ::= { diskdomain 138 }

        -- 1.3.6.1.4.1.2011.2.251.20.1.2.2.15.266.138.1
        theDiskDomainScaleInTaskIsAboutToBeRolledBack-Fault NOTIFICATION-TYPE
            OBJECTS { hwStorageAlarmReporting }
            STATUS current
            DESCRIPTION "The Disk Domain ScaleIn Task Is About To Be Rolled Back"
            --#SEVERITY MAJOR
            ::= { theDiskDomainScaleInTaskIsAboutToBeRolledBack 1 }

        -- 1.3.6.1.4.1.2011.2.251.20.1.2.2.15.266.138.2
        theDiskDomainScaleInTaskIsAboutToBeRolledBack-Resume NOTIFICATION-TYPE
            OBJECTS { hwStorageAlarmReporting }
            STATUS current
            DESCRIPTION "Recover: The Disk Domain ScaleIn Task Is About To Be Rolled Back"
            --#SEVERITY INFORMATIONAL
            ::= { theDiskDomainScaleInTaskIsAboutToBeRolledBack 2 }

        -- 1.3.6.1.4.1.2011.2.251.20.1.2.2.15.266.140
        diskDomainAssociatedWithThePerformanceLayerLosesEnclosurelevelRedundancyCapabilityDueToDiskLocationChange OBJECT IDENTIFIER ::= { diskdomain 140 }

        -- 1.3.6.1.4.1.2011.2.251.20.1.2.2.15.266.140.1
        diskDomainAssociatedWithThePerformanceLayerLosesEnclosurelevelRedundancyCapabilityDueToDiskLocationChange-Fault NOTIFICATION-TYPE
            OBJECTS { hwStorageAlarmReporting }
            STATUS current
            DESCRIPTION "Disk Domain Associated With The Performance Layer Loses Enclosurelevel Redundancy Capability Due To Disk Location Change"
            --#SEVERITY MAJOR
            ::= { diskDomainAssociatedWithThePerformanceLayerLosesEnclosurelevelRedundancyCapabilityDueToDiskLocationChange 1 }

        -- 1.3.6.1.4.1.2011.2.251.20.1.2.2.15.266.140.2
        diskDomainAssociatedWithThePerformanceLayerLosesEnclosurelevelRedundancyCapabilityDueToDiskLocationChange-Resume NOTIFICATION-TYPE
            OBJECTS { hwStorageAlarmReporting }
            STATUS current
            DESCRIPTION "Recover: Disk Domain Associated With The Performance Layer Loses Enclosurelevel Redundancy Capability Due To Disk Location Change"
            --#SEVERITY INFORMATIONAL
            ::= { diskDomainAssociatedWithThePerformanceLayerLosesEnclosurelevelRedundancyCapabilityDueToDiskLocationChange 2 }

        -- 1.3.6.1.4.1.2011.2.251.20.1.2.2.15.266.141
        diskDomainLosesEnclosurelevelRedundancyCapability1 OBJECT IDENTIFIER ::= { diskdomain 141 }

        -- 1.3.6.1.4.1.2011.2.251.20.1.2.2.15.266.141.1
        diskDomainLosesEnclosurelevelRedundancyCapability1-Fault NOTIFICATION-TYPE
            OBJECTS { hwStorageAlarmReporting }
            STATUS current
            DESCRIPTION "Disk Domain Loses Enclosurelevel Redundancy Capability"
            --#SEVERITY MAJOR
            ::= { diskDomainLosesEnclosurelevelRedundancyCapability1 1 }

        -- 1.3.6.1.4.1.2011.2.251.20.1.2.2.15.266.141.2
        diskDomainLosesEnclosurelevelRedundancyCapability1-Resume NOTIFICATION-TYPE
            OBJECTS { hwStorageAlarmReporting }
            STATUS current
            DESCRIPTION "Recover: Disk Domain Loses Enclosurelevel Redundancy Capability"
            --#SEVERITY INFORMATIONAL
            ::= { diskDomainLosesEnclosurelevelRedundancyCapability1 2 }

        -- 1.3.6.1.4.1.2011.2.251.20.1.2.2.15.266.142
        theNewDiskCannotBeAddedToThePerformanceLayer OBJECT IDENTIFIER ::= { diskdomain 142 }

        -- 1.3.6.1.4.1.2011.2.251.20.1.2.2.15.266.142.1
        theNewDiskCannotBeAddedToThePerformanceLayer-Fault NOTIFICATION-TYPE
            OBJECTS { hwStorageAlarmReporting }
            STATUS current
            DESCRIPTION "The New Disk Cannot Be Added To The Performance Layer"
            --#SEVERITY MAJOR
            ::= { theNewDiskCannotBeAddedToThePerformanceLayer 1 }

        -- 1.3.6.1.4.1.2011.2.251.20.1.2.2.15.266.142.2
        theNewDiskCannotBeAddedToThePerformanceLayer-Resume NOTIFICATION-TYPE
            OBJECTS { hwStorageAlarmReporting }
            STATUS current
            DESCRIPTION "Recover: The New Disk Cannot Be Added To The Performance Layer"
            --#SEVERITY INFORMATIONAL
            ::= { theNewDiskCannotBeAddedToThePerformanceLayer 2 }

        -- 1.3.6.1.4.1.2011.2.251.20.1.2.2.15.266.143
        diskDomainCapNotAvailable OBJECT IDENTIFIER ::= { diskdomain 143 }

        -- 1.3.6.1.4.1.2011.2.251.20.1.2.2.15.266.143.1
        diskDomainCapNotAvailable-Fault NOTIFICATION-TYPE
            OBJECTS { hwStorageAlarmReporting }
            STATUS current
            DESCRIPTION "Some Capacity Of The Disk Domain May Be Unavailable"
            --#SEVERITY MAJOR
            ::= { diskDomainCapNotAvailable 1 }

        -- 1.3.6.1.4.1.2011.2.251.20.1.2.2.15.266.143.2
        diskDomainCapNotAvailable-Resume NOTIFICATION-TYPE
            OBJECTS { hwStorageAlarmReporting }
            STATUS current
            DESCRIPTION "Recover: Some Capacity Of The Disk Domain May Be Unavailable"
            --#SEVERITY INFORMATIONAL
            ::= { diskDomainCapNotAvailable 2 }

        -- 1.3.6.1.4.1.2011.2.251.20.1.2.2.15.266.144
        lossEnclosureLevelAbilityAlarm OBJECT IDENTIFIER ::= { diskdomain 144 }

        -- 1.3.6.1.4.1.2011.2.251.20.1.2.2.15.266.144.1
        lossEnclosureLevelAbilityAlarm-Fault NOTIFICATION-TYPE
            OBJECTS { hwStorageAlarmReporting }
            STATUS current
            DESCRIPTION "Disk Domain Loses Distributed EC Redundancy Capability"
            --#SEVERITY CRITICAL
            ::= { lossEnclosureLevelAbilityAlarm 1 }

        -- 1.3.6.1.4.1.2011.2.251.20.1.2.2.15.266.144.2
        lossEnclosureLevelAbilityAlarm-Resume NOTIFICATION-TYPE
            OBJECTS { hwStorageAlarmReporting }
            STATUS current
            DESCRIPTION "Recover: Disk Domain Loses Distributed EC Redundancy Capability"
            --#SEVERITY INFORMATIONAL
            ::= { lossEnclosureLevelAbilityAlarm 2 }

        -- 1.3.6.1.4.1.2011.2.251.20.1.2.2.15.266.145
        diskRoamingAlarmBetweenController OBJECT IDENTIFIER ::= { diskdomain 145 }

        -- 1.3.6.1.4.1.2011.2.251.20.1.2.2.15.266.145.1
        diskRoamingAlarmBetweenController-Fault NOTIFICATION-TYPE
            OBJECTS { hwStorageAlarmReporting }
            STATUS current
            DESCRIPTION "Disk Domain Associated With The Performance Layer Loses Distributed EC Redundancy Capability Due To Disk Location Change"
            --#SEVERITY MAJOR
            ::= { diskRoamingAlarmBetweenController 1 }

        -- 1.3.6.1.4.1.2011.2.251.20.1.2.2.15.266.145.2
        diskRoamingAlarmBetweenController-Resume NOTIFICATION-TYPE
            OBJECTS { hwStorageAlarmReporting }
            STATUS current
            DESCRIPTION "Recover: Disk Domain Associated With The Performance Layer Loses Distributed EC Redundancy Capability Due To Disk Location Change"
            --#SEVERITY INFORMATIONAL
            ::= { diskRoamingAlarmBetweenController 2 }

        -- 1.3.6.1.4.1.2011.2.251.20.1.2.2.15.266.148
        capCheckPointAbnormal OBJECT IDENTIFIER ::= { diskdomain 148 }

        -- 1.3.6.1.4.1.2011.2.251.20.1.2.2.15.266.148.1
        capCheckPointAbnormal-Fault NOTIFICATION-TYPE
            OBJECTS { hwStorageAlarmReporting }
            STATUS current
            DESCRIPTION "The Disk Domain Capacity Is Found To Be Abnormal In A Check"
            --#SEVERITY MAJOR
            ::= { capCheckPointAbnormal 1 }

        -- 1.3.6.1.4.1.2011.2.251.20.1.2.2.15.266.148.2
        capCheckPointAbnormal-Resume NOTIFICATION-TYPE
            OBJECTS { hwStorageAlarmReporting }
            STATUS current
            DESCRIPTION "Recover: The Disk Domain Capacity Is Found To Be Abnormal In A Check"
            --#SEVERITY INFORMATIONAL
            ::= { capCheckPointAbnormal 2 }

        -- 1.3.6.1.4.1.2011.2.251.20.1.2.2.15.266.293
        theModelOfTheNewDiskIsDifferentFromTheReplacedOneAndCannotBeAddedToTheDiskDomain OBJECT IDENTIFIER ::= { diskdomain 293 }

        -- 1.3.6.1.4.1.2011.2.251.20.1.2.2.15.266.293.1
        theModelOfTheNewDiskIsDifferentFromTheReplacedOneAndCannotBeAddedToTheDiskDomain-Fault NOTIFICATION-TYPE
            OBJECTS { hwStorageAlarmReporting }
            STATUS current
            DESCRIPTION "The Model Of The New Disk Is Different From The Replaced One And Cannot Be Added To The Disk Domain"
            --#SEVERITY MAJOR
            ::= { theModelOfTheNewDiskIsDifferentFromTheReplacedOneAndCannotBeAddedToTheDiskDomain 1 }

        -- 1.3.6.1.4.1.2011.2.251.20.1.2.2.15.266.293.2
        theModelOfTheNewDiskIsDifferentFromTheReplacedOneAndCannotBeAddedToTheDiskDomain-Resume NOTIFICATION-TYPE
            OBJECTS { hwStorageAlarmReporting }
            STATUS current
            DESCRIPTION "Recover: The Model Of The New Disk Is Different From The Replaced One And Cannot Be Added To The Disk Domain"
            --#SEVERITY INFORMATIONAL
            ::= { theModelOfTheNewDiskIsDifferentFromTheReplacedOneAndCannotBeAddedToTheDiskDomain 2 }

        -- 1.3.6.1.4.1.2011.2.251.20.1.2.2.15.267
        storageengine OBJECT IDENTIFIER ::= { oidBasedTrap 267 }

        -- 1.3.6.1.4.1.2011.2.251.20.1.2.2.15.267.5
        theAmountOfWrittenDataReachesTheSpecificationOfEffectiveCapacity OBJECT IDENTIFIER ::= { storageengine 5 }

        -- 1.3.6.1.4.1.2011.2.251.20.1.2.2.15.267.5.1
        theAmountOfWrittenDataReachesTheSpecificationOfEffectiveCapacity-Fault NOTIFICATION-TYPE
            OBJECTS { hwStorageAlarmReporting }
            STATUS current
            DESCRIPTION "The Amount Of Written Data Reaches The Specification Of Effective Capacity"
            --#SEVERITY MAJOR
            ::= { theAmountOfWrittenDataReachesTheSpecificationOfEffectiveCapacity 1 }

        -- 1.3.6.1.4.1.2011.2.251.20.1.2.2.15.267.5.2
        theAmountOfWrittenDataReachesTheSpecificationOfEffectiveCapacity-Resume NOTIFICATION-TYPE
            OBJECTS { hwStorageAlarmReporting }
            STATUS current
            DESCRIPTION "Recover: The Amount Of Written Data Reaches The Specification Of Effective Capacity"
            --#SEVERITY INFORMATIONAL
            ::= { theAmountOfWrittenDataReachesTheSpecificationOfEffectiveCapacity 2 }

        -- 1.3.6.1.4.1.2011.2.251.20.1.2.2.15.267.6
        theAmountOfWrittenDataExceedsTheSpecificationOfEffectiveCapacity OBJECT IDENTIFIER ::= { storageengine 6 }

        -- 1.3.6.1.4.1.2011.2.251.20.1.2.2.15.267.6.1
        theAmountOfWrittenDataExceedsTheSpecificationOfEffectiveCapacity-Fault NOTIFICATION-TYPE
            OBJECTS { hwStorageAlarmReporting }
            STATUS current
            DESCRIPTION "The Amount Of Written Data Exceeds The Specification Of Effective Capacity"
            --#SEVERITY CRITICAL
            ::= { theAmountOfWrittenDataExceedsTheSpecificationOfEffectiveCapacity 1 }

        -- 1.3.6.1.4.1.2011.2.251.20.1.2.2.15.267.6.2
        theAmountOfWrittenDataExceedsTheSpecificationOfEffectiveCapacity-Resume NOTIFICATION-TYPE
            OBJECTS { hwStorageAlarmReporting }
            STATUS current
            DESCRIPTION "Recover: The Amount Of Written Data Exceeds The Specification Of Effective Capacity"
            --#SEVERITY INFORMATIONAL
            ::= { theAmountOfWrittenDataExceedsTheSpecificationOfEffectiveCapacity 2 }

        -- 1.3.6.1.4.1.2011.2.251.20.1.2.2.15.269
        qos OBJECT IDENTIFIER ::= { oidBasedTrap 269 }

        -- 1.3.6.1.4.1.2011.2.251.20.1.2.2.15.269.53
        smartQoSExceedThreshold OBJECT IDENTIFIER ::= { qos 53 }

        -- 1.3.6.1.4.1.2011.2.251.20.1.2.2.15.269.53.1
        smartQoSExceedThreshold-Fault NOTIFICATION-TYPE
            OBJECTS { hwStorageAlarmReporting }
            STATUS current
            DESCRIPTION "Service Performance Continuously Exceeds The Alarm Threshold Of The SmartQoS Upper Limit Policy"
            --#SEVERITY WARNING
            ::= { smartQoSExceedThreshold 1 }

        -- 1.3.6.1.4.1.2011.2.251.20.1.2.2.15.269.53.2
        smartQoSExceedThreshold-Resume NOTIFICATION-TYPE
            OBJECTS { hwStorageAlarmReporting }
            STATUS current
            DESCRIPTION "Recover: Service Performance Continuously Exceeds The Alarm Threshold Of The SmartQoS Upper Limit Policy"
            --#SEVERITY INFORMATIONAL
            ::= { smartQoSExceedThreshold 2 }

        -- 1.3.6.1.4.1.2011.2.251.20.1.2.2.15.269.57
        performanceOfTheSmartQoSPolicyFailedToReachTheSpecifiedControlObjective OBJECT IDENTIFIER ::= { qos 57 }

        -- 1.3.6.1.4.1.2011.2.251.20.1.2.2.15.269.57.1
        performanceOfTheSmartQoSPolicyFailedToReachTheSpecifiedControlObjective-Fault NOTIFICATION-TYPE
            OBJECTS { hwStorageAlarmReporting }
            STATUS current
            DESCRIPTION "Performance Of The SmartQoS Policy Failed To Reach The Specified Control Objective"
            --#SEVERITY WARNING
            ::= { performanceOfTheSmartQoSPolicyFailedToReachTheSpecifiedControlObjective 1 }

        -- 1.3.6.1.4.1.2011.2.251.20.1.2.2.15.269.57.2
        performanceOfTheSmartQoSPolicyFailedToReachTheSpecifiedControlObjective-Resume NOTIFICATION-TYPE
            OBJECTS { hwStorageAlarmReporting }
            STATUS current
            DESCRIPTION "Recover: Performance Of The SmartQoS Policy Failed To Reach The Specified Control Objective"
            --#SEVERITY INFORMATIONAL
            ::= { performanceOfTheSmartQoSPolicyFailedToReachTheSpecifiedControlObjective 2 }

        -- 1.3.6.1.4.1.2011.2.251.20.1.2.2.15.269.99
        controllerIsOverload OBJECT IDENTIFIER ::= { qos 99 }

        -- 1.3.6.1.4.1.2011.2.251.20.1.2.2.15.269.99.1
        controllerIsOverload-Fault NOTIFICATION-TYPE
            OBJECTS { hwStorageAlarmReporting }
            STATUS current
            DESCRIPTION "The Controller Is Overloaded"
            --#SEVERITY WARNING
            ::= { controllerIsOverload 1 }

        -- 1.3.6.1.4.1.2011.2.251.20.1.2.2.15.269.99.2
        controllerIsOverload-Resume NOTIFICATION-TYPE
            OBJECTS { hwStorageAlarmReporting }
            STATUS current
            DESCRIPTION "Recover: The Controller Is Overloaded"
            --#SEVERITY INFORMATIONAL
            ::= { controllerIsOverload 2 }

        -- 1.3.6.1.4.1.2011.2.251.20.1.2.2.15.279
        lif OBJECT IDENTIFIER ::= { oidBasedTrap 279 }

        -- 1.3.6.1.4.1.2011.2.251.20.1.2.2.15.279.1
        failedToSynchronizeLogicalPortConfigurationsToTheSecondaryVStoreOfTheVStorePair OBJECT IDENTIFIER ::= { lif 1 }

        -- 1.3.6.1.4.1.2011.2.251.20.1.2.2.15.279.1.1
        failedToSynchronizeLogicalPortConfigurationsToTheSecondaryVStoreOfTheVStorePair-Fault NOTIFICATION-TYPE
            OBJECTS { hwStorageAlarmReporting }
            STATUS current
            DESCRIPTION "Failed To Synchronize Logical Port Configurations To The Secondary VStore Of The VStore Pair"
            --#SEVERITY MAJOR
            ::= { failedToSynchronizeLogicalPortConfigurationsToTheSecondaryVStoreOfTheVStorePair 1 }

        -- 1.3.6.1.4.1.2011.2.251.20.1.2.2.15.279.1.2
        failedToSynchronizeLogicalPortConfigurationsToTheSecondaryVStoreOfTheVStorePair-Resume NOTIFICATION-TYPE
            OBJECTS { hwStorageAlarmReporting }
            STATUS current
            DESCRIPTION "Recover: Failed To Synchronize Logical Port Configurations To The Secondary VStore Of The VStore Pair"
            --#SEVERITY INFORMATIONAL
            ::= { failedToSynchronizeLogicalPortConfigurationsToTheSecondaryVStoreOfTheVStorePair 2 }

        -- 1.3.6.1.4.1.2011.2.251.20.1.2.2.15.279.2
        theFirewallConfigurationsOfTheVStorePairAtThePrimaryAndSecondarySitesAreInconsistent OBJECT IDENTIFIER ::= { lif 2 }

        -- 1.3.6.1.4.1.2011.2.251.20.1.2.2.15.279.2.1
        theFirewallConfigurationsOfTheVStorePairAtThePrimaryAndSecondarySitesAreInconsistent-Fault NOTIFICATION-TYPE
            OBJECTS { hwStorageAlarmReporting }
            STATUS current
            DESCRIPTION "The Firewall Configurations Of The VStore Pair At The Primary And Secondary Sites Are Inconsistent"
            --#SEVERITY MAJOR
            ::= { theFirewallConfigurationsOfTheVStorePairAtThePrimaryAndSecondarySitesAreInconsistent 1 }

        -- 1.3.6.1.4.1.2011.2.251.20.1.2.2.15.279.2.2
        theFirewallConfigurationsOfTheVStorePairAtThePrimaryAndSecondarySitesAreInconsistent-Resume NOTIFICATION-TYPE
            OBJECTS { hwStorageAlarmReporting }
            STATUS current
            DESCRIPTION "Recover: The Firewall Configurations Of The VStore Pair At The Primary And Secondary Sites Are Inconsistent"
            --#SEVERITY INFORMATIONAL
            ::= { theFirewallConfigurationsOfTheVStorePairAtThePrimaryAndSecondarySitesAreInconsistent 2 }

        -- 1.3.6.1.4.1.2011.2.251.20.1.2.2.15.279.3
        theDNSLoadBalancingSwitchesOnThePrimaryAndSecondarySitesOfTheVStorePairAreInDifferentStates OBJECT IDENTIFIER ::= { lif 3 }

        -- 1.3.6.1.4.1.2011.2.251.20.1.2.2.15.279.3.1
        theDNSLoadBalancingSwitchesOnThePrimaryAndSecondarySitesOfTheVStorePairAreInDifferentStates-Fault NOTIFICATION-TYPE
            OBJECTS { hwStorageAlarmReporting }
            STATUS current
            DESCRIPTION "The DNS Load Balancing Switches On The Primary And Secondary Sites Of The VStore Pair Are In Different States"
            --#SEVERITY MAJOR
            ::= { theDNSLoadBalancingSwitchesOnThePrimaryAndSecondarySitesOfTheVStorePairAreInDifferentStates 1 }

        -- 1.3.6.1.4.1.2011.2.251.20.1.2.2.15.279.3.2
        theDNSLoadBalancingSwitchesOnThePrimaryAndSecondarySitesOfTheVStorePairAreInDifferentStates-Resume NOTIFICATION-TYPE
            OBJECTS { hwStorageAlarmReporting }
            STATUS current
            DESCRIPTION "Recover: The DNS Load Balancing Switches On The Primary And Secondary Sites Of The VStore Pair Are In Different States"
            --#SEVERITY INFORMATIONAL
            ::= { theDNSLoadBalancingSwitchesOnThePrimaryAndSecondarySitesOfTheVStorePairAreInDifferentStates 2 }

        -- 1.3.6.1.4.1.2011.2.251.20.1.2.2.15.285
        antivirus OBJECT IDENTIFIER ::= { oidBasedTrap 285 }

        -- 1.3.6.1.4.1.2011.2.251.20.1.2.2.15.285.68
        antivirusServerIsFault OBJECT IDENTIFIER ::= { antivirus 68 }

        -- 1.3.6.1.4.1.2011.2.251.20.1.2.2.15.285.68.1
        antivirusServerIsFault-Fault NOTIFICATION-TYPE
            OBJECTS { hwStorageAlarmReporting }
            STATUS current
            DESCRIPTION "The Antivirus Server Is Faulty"
            --#SEVERITY WARNING
            ::= { antivirusServerIsFault 1 }

        -- 1.3.6.1.4.1.2011.2.251.20.1.2.2.15.285.68.2
        antivirusServerIsFault-Resume NOTIFICATION-TYPE
            OBJECTS { hwStorageAlarmReporting }
            STATUS current
            DESCRIPTION "Recover: The Antivirus Server Is Faulty"
            --#SEVERITY INFORMATIONAL
            ::= { antivirusServerIsFault 2 }

        -- 1.3.6.1.4.1.2011.2.251.20.1.2.2.15.285.72
        noAntivirusServerIsAvailable OBJECT IDENTIFIER ::= { antivirus 72 }

        -- 1.3.6.1.4.1.2011.2.251.20.1.2.2.15.285.72.1
        noAntivirusServerIsAvailable-Fault NOTIFICATION-TYPE
            OBJECTS { hwStorageAlarmReporting }
            STATUS current
            DESCRIPTION "No Antivirus Server Is Available"
            --#SEVERITY MAJOR
            ::= { noAntivirusServerIsAvailable 1 }

        -- 1.3.6.1.4.1.2011.2.251.20.1.2.2.15.285.72.2
        noAntivirusServerIsAvailable-Resume NOTIFICATION-TYPE
            OBJECTS { hwStorageAlarmReporting }
            STATUS current
            DESCRIPTION "Recover: No Antivirus Server Is Available"
            --#SEVERITY INFORMATIONAL
            ::= { noAntivirusServerIsAvailable 2 }

        -- 1.3.6.1.4.1.2011.2.251.20.1.2.2.15.285.74
        theAntivirusServerIsOverloaded OBJECT IDENTIFIER ::= { antivirus 74 }

        -- 1.3.6.1.4.1.2011.2.251.20.1.2.2.15.285.74.1
        theAntivirusServerIsOverloaded-Fault NOTIFICATION-TYPE
            OBJECTS { hwStorageAlarmReporting }
            STATUS current
            DESCRIPTION "The Antivirus Server Is Overloaded"
            --#SEVERITY WARNING
            ::= { theAntivirusServerIsOverloaded 1 }

        -- 1.3.6.1.4.1.2011.2.251.20.1.2.2.15.285.74.2
        theAntivirusServerIsOverloaded-Resume NOTIFICATION-TYPE
            OBJECTS { hwStorageAlarmReporting }
            STATUS current
            DESCRIPTION "Recover: The Antivirus Server Is Overloaded"
            --#SEVERITY INFORMATIONAL
            ::= { theAntivirusServerIsOverloaded 2 }

        -- 1.3.6.1.4.1.2011.2.251.20.1.2.2.15.289
        failovergroup OBJECT IDENTIFIER ::= { oidBasedTrap 289 }

        -- 1.3.6.1.4.1.2011.2.251.20.1.2.2.15.289.1
        memberPortsOfTheFailoverGroupDoNotMeetRedundancyRequirements1 OBJECT IDENTIFIER ::= { failovergroup 1 }

        -- 1.3.6.1.4.1.2011.2.251.20.1.2.2.15.289.1.1
        memberPortsOfTheFailoverGroupDoNotMeetRedundancyRequirements1-Fault NOTIFICATION-TYPE
            OBJECTS { hwStorageAlarmReporting }
            STATUS current
            DESCRIPTION "Member Ports Of The Failover Group Do Not Meet Redundancy Requirements"
            --#SEVERITY WARNING
            ::= { memberPortsOfTheFailoverGroupDoNotMeetRedundancyRequirements1 1 }

        -- 1.3.6.1.4.1.2011.2.251.20.1.2.2.15.289.1.2
        memberPortsOfTheFailoverGroupDoNotMeetRedundancyRequirements1-Resume NOTIFICATION-TYPE
            OBJECTS { hwStorageAlarmReporting }
            STATUS current
            DESCRIPTION "Recover: Member Ports Of The Failover Group Do Not Meet Redundancy Requirements"
            --#SEVERITY INFORMATIONAL
            ::= { memberPortsOfTheFailoverGroupDoNotMeetRedundancyRequirements1 2 }

        -- 1.3.6.1.4.1.2011.2.251.20.1.2.2.15.289.2
        memberPortsOfTheFailoverGroupDoNotMeetRedundancyRequirements OBJECT IDENTIFIER ::= { failovergroup 2 }

        -- 1.3.6.1.4.1.2011.2.251.20.1.2.2.15.289.2.1
        memberPortsOfTheFailoverGroupDoNotMeetRedundancyRequirements-Fault NOTIFICATION-TYPE
            OBJECTS { hwStorageAlarmReporting }
            STATUS current
            DESCRIPTION "Member Ports Of The Failover Group Do Not Meet Redundancy Requirements"
            --#SEVERITY WARNING
            ::= { memberPortsOfTheFailoverGroupDoNotMeetRedundancyRequirements 1 }

        -- 1.3.6.1.4.1.2011.2.251.20.1.2.2.15.289.2.2
        memberPortsOfTheFailoverGroupDoNotMeetRedundancyRequirements-Resume NOTIFICATION-TYPE
            OBJECTS { hwStorageAlarmReporting }
            STATUS current
            DESCRIPTION "Recover: Member Ports Of The Failover Group Do Not Meet Redundancy Requirements"
            --#SEVERITY INFORMATIONAL
            ::= { memberPortsOfTheFailoverGroupDoNotMeetRedundancyRequirements 2 }

        -- 1.3.6.1.4.1.2011.2.251.20.1.2.2.15.289.4
        failoverNoRedundancy OBJECT IDENTIFIER ::= { failovergroup 4 }

        -- 1.3.6.1.4.1.2011.2.251.20.1.2.2.15.289.4.1
        failoverNoRedundancy-Fault NOTIFICATION-TYPE
            OBJECTS { hwStorageAlarmReporting }
            STATUS current
            DESCRIPTION "Member Ports Of The Failover Group Do Not Meet Redundancy Requirements"
            --#SEVERITY WARNING
            ::= { failoverNoRedundancy 1 }

        -- 1.3.6.1.4.1.2011.2.251.20.1.2.2.15.289.4.2
        failoverNoRedundancy-Resume NOTIFICATION-TYPE
            OBJECTS { hwStorageAlarmReporting }
            STATUS current
            DESCRIPTION "Recover: Member Ports Of The Failover Group Do Not Meet Redundancy Requirements"
            --#SEVERITY INFORMATIONAL
            ::= { failoverNoRedundancy 2 }

        -- 1.3.6.1.4.1.2011.2.251.20.1.2.2.15.306
        assistantcoolingunit OBJECT IDENTIFIER ::= { oidBasedTrap 306 }

        -- 1.3.6.1.4.1.2011.2.251.20.1.2.2.15.306.2
        assistantCoolingUnitRemoved OBJECT IDENTIFIER ::= { assistantcoolingunit 2 }

        -- 1.3.6.1.4.1.2011.2.251.20.1.2.2.15.306.2.1
        assistantCoolingUnitRemoved-Fault NOTIFICATION-TYPE
            OBJECTS { hwStorageAlarmReporting }
            STATUS current
            DESCRIPTION "Assistant Cooling Module Removed"
            --#SEVERITY MAJOR
            ::= { assistantCoolingUnitRemoved 1 }

        -- 1.3.6.1.4.1.2011.2.251.20.1.2.2.15.306.2.2
        assistantCoolingUnitRemoved-Resume NOTIFICATION-TYPE
            OBJECTS { hwStorageAlarmReporting }
            STATUS current
            DESCRIPTION "Recover: Assistant Cooling Module Removed"
            --#SEVERITY INFORMATIONAL
            ::= { assistantCoolingUnitRemoved 2 }

        -- 1.3.6.1.4.1.2011.2.251.20.1.2.2.15.306.4
        assistCoolingUnitMonitorFailed OBJECT IDENTIFIER ::= { assistantcoolingunit 4 }

        -- 1.3.6.1.4.1.2011.2.251.20.1.2.2.15.306.4.1
        assistCoolingUnitMonitorFailed-Fault NOTIFICATION-TYPE
            OBJECTS { hwStorageAlarmReporting }
            STATUS current
            DESCRIPTION "The System Failed To Monitor Assistant Cooling Unit"
            --#SEVERITY MAJOR
            ::= { assistCoolingUnitMonitorFailed 1 }

        -- 1.3.6.1.4.1.2011.2.251.20.1.2.2.15.306.4.2
        assistCoolingUnitMonitorFailed-Resume NOTIFICATION-TYPE
            OBJECTS { hwStorageAlarmReporting }
            STATUS current
            DESCRIPTION "Recover: The System Failed To Monitor Assistant Cooling Unit"
            --#SEVERITY INFORMATIONAL
            ::= { assistCoolingUnitMonitorFailed 2 }

        -- 1.3.6.1.4.1.2011.2.251.20.1.2.2.15.306.5
        coolingUnitIsUnrecognizable OBJECT IDENTIFIER ::= { assistantcoolingunit 5 }

        -- 1.3.6.1.4.1.2011.2.251.20.1.2.2.15.306.5.1
        coolingUnitIsUnrecognizable-Fault NOTIFICATION-TYPE
            OBJECTS { hwStorageAlarmReporting }
            STATUS current
            DESCRIPTION "Assistant Cooling Unit Is Unrecognizable"
            --#SEVERITY MAJOR
            ::= { coolingUnitIsUnrecognizable 1 }

        -- 1.3.6.1.4.1.2011.2.251.20.1.2.2.15.306.5.2
        coolingUnitIsUnrecognizable-Resume NOTIFICATION-TYPE
            OBJECTS { hwStorageAlarmReporting }
            STATUS current
            DESCRIPTION "Recover: Assistant Cooling Unit Is Unrecognizable"
            --#SEVERITY INFORMATIONAL
            ::= { coolingUnitIsUnrecognizable 2 }

        -- 1.3.6.1.4.1.2011.2.251.20.1.2.2.15.306.6
        coolingUnitIsIncompatible OBJECT IDENTIFIER ::= { assistantcoolingunit 6 }

        -- 1.3.6.1.4.1.2011.2.251.20.1.2.2.15.306.6.1
        coolingUnitIsIncompatible-Fault NOTIFICATION-TYPE
            OBJECTS { hwStorageAlarmReporting }
            STATUS current
            DESCRIPTION "The Auxiliary Heat Dissipation Module Is Incompatible With The Controller Module"
            --#SEVERITY MAJOR
            ::= { coolingUnitIsIncompatible 1 }

        -- 1.3.6.1.4.1.2011.2.251.20.1.2.2.15.306.6.2
        coolingUnitIsIncompatible-Resume NOTIFICATION-TYPE
            OBJECTS { hwStorageAlarmReporting }
            STATUS current
            DESCRIPTION "Recover: The Auxiliary Heat Dissipation Module Is Incompatible With The Controller Module"
            --#SEVERITY INFORMATIONAL
            ::= { coolingUnitIsIncompatible 2 }

        -- 1.3.6.1.4.1.2011.2.251.20.1.2.2.15.306.68
        assistantCoolingUnitIsFaulty OBJECT IDENTIFIER ::= { assistantcoolingunit 68 }

        -- 1.3.6.1.4.1.2011.2.251.20.1.2.2.15.306.68.1
        assistantCoolingUnitIsFaulty-Fault NOTIFICATION-TYPE
            OBJECTS { hwStorageAlarmReporting }
            STATUS current
            DESCRIPTION "Assistant Cooling Unit Is Faulty"
            --#SEVERITY MAJOR
            ::= { assistantCoolingUnitIsFaulty 1 }

        -- 1.3.6.1.4.1.2011.2.251.20.1.2.2.15.306.68.2
        assistantCoolingUnitIsFaulty-Resume NOTIFICATION-TYPE
            OBJECTS { hwStorageAlarmReporting }
            STATUS current
            DESCRIPTION "Recover: Assistant Cooling Unit Is Faulty"
            --#SEVERITY INFORMATIONAL
            ::= { assistantCoolingUnitIsFaulty 2 }

        -- 1.3.6.1.4.1.2011.2.251.20.1.2.2.15.350
        dedupeandcompress OBJECT IDENTIFIER ::= { oidBasedTrap 350 }

        -- 1.3.6.1.4.1.2011.2.251.20.1.2.2.15.350.2
        metadataMediaErrorsExistInVariablelengthDeduplication OBJECT IDENTIFIER ::= { dedupeandcompress 2 }

        -- 1.3.6.1.4.1.2011.2.251.20.1.2.2.15.350.2.1
        metadataMediaErrorsExistInVariablelengthDeduplication-Fault NOTIFICATION-TYPE
            OBJECTS { hwStorageAlarmReporting }
            STATUS current
            DESCRIPTION "Metadata Media Errors Exist In Variablelength Deduplication"
            --#SEVERITY WARNING
            ::= { metadataMediaErrorsExistInVariablelengthDeduplication 1 }

        -- 1.3.6.1.4.1.2011.2.251.20.1.2.2.15.350.2.2
        metadataMediaErrorsExistInVariablelengthDeduplication-Resume NOTIFICATION-TYPE
            OBJECTS { hwStorageAlarmReporting }
            STATUS current
            DESCRIPTION "Recover: Metadata Media Errors Exist In Variablelength Deduplication"
            --#SEVERITY INFORMATIONAL
            ::= { metadataMediaErrorsExistInVariablelengthDeduplication 2 }

        -- 1.3.6.1.4.1.2011.2.251.20.1.2.2.15.350.6
        reductionSpeedIsLow OBJECT IDENTIFIER ::= { dedupeandcompress 6 }

        -- 1.3.6.1.4.1.2011.2.251.20.1.2.2.15.350.6.1
        reductionSpeedIsLow-Fault NOTIFICATION-TYPE
            OBJECTS { hwStorageAlarmReporting }
            STATUS current
            DESCRIPTION "Low Data Reduction Speed"
            --#SEVERITY WARNING
            ::= { reductionSpeedIsLow 1 }

        -- 1.3.6.1.4.1.2011.2.251.20.1.2.2.15.350.6.2
        reductionSpeedIsLow-Resume NOTIFICATION-TYPE
            OBJECTS { hwStorageAlarmReporting }
            STATUS current
            DESCRIPTION "Recover: Low Data Reduction Speed"
            --#SEVERITY INFORMATIONAL
            ::= { reductionSpeedIsLow 2 }

        -- 1.3.6.1.4.1.2011.2.251.20.1.2.2.15.447
        cache OBJECT IDENTIFIER ::= { oidBasedTrap 447 }

        -- 1.3.6.1.4.1.2011.2.251.20.1.2.2.15.447.2
        systemComponentAnomaly OBJECT IDENTIFIER ::= { cache 2 }

        -- 1.3.6.1.4.1.2011.2.251.20.1.2.2.15.447.2.1
        systemComponentAnomaly-Fault NOTIFICATION-TYPE
            OBJECTS { hwStorageAlarmReporting }
            STATUS current
            DESCRIPTION "A Component In The System Is Abnormal"
            --#SEVERITY MAJOR
            ::= { systemComponentAnomaly 1 }

        -- 1.3.6.1.4.1.2011.2.251.20.1.2.2.15.447.2.2
        systemComponentAnomaly-Resume NOTIFICATION-TYPE
            OBJECTS { hwStorageAlarmReporting }
            STATUS current
            DESCRIPTION "Recover: A Component In The System Is Abnormal"
            --#SEVERITY INFORMATIONAL
            ::= { systemComponentAnomaly 2 }

        -- 1.3.6.1.4.1.2011.2.251.20.1.2.2.15.447.301
        writeProtectionIsEnabledForSomeFileSystemsLUNsOrSpaceThatStoresHistoricalPerformanceData OBJECT IDENTIFIER ::= { cache 301 }

        -- 1.3.6.1.4.1.2011.2.251.20.1.2.2.15.447.301.1
        writeProtectionIsEnabledForSomeFileSystemsLUNsOrSpaceThatStoresHistoricalPerformanceData-Fault NOTIFICATION-TYPE
            OBJECTS { hwStorageAlarmReporting }
            STATUS current
            DESCRIPTION "Write Protection Is Enabled For Some File Systems, LUNs, Or Space That Stores Historical Performance Data"
            --#SEVERITY MAJOR
            ::= { writeProtectionIsEnabledForSomeFileSystemsLUNsOrSpaceThatStoresHistoricalPerformanceData 1 }

        -- 1.3.6.1.4.1.2011.2.251.20.1.2.2.15.447.301.2
        writeProtectionIsEnabledForSomeFileSystemsLUNsOrSpaceThatStoresHistoricalPerformanceData-Resume NOTIFICATION-TYPE
            OBJECTS { hwStorageAlarmReporting }
            STATUS current
            DESCRIPTION "Recover: Write Protection Is Enabled For Some File Systems, LUNs, Or Space That Stores Historical Performance Data"
            --#SEVERITY INFORMATIONAL
            ::= { writeProtectionIsEnabledForSomeFileSystemsLUNsOrSpaceThatStoresHistoricalPerformanceData 2 }

        -- 1.3.6.1.4.1.2011.2.251.20.1.2.2.15.558
        upgrade OBJECT IDENTIFIER ::= { oidBasedTrap 558 }

        -- 1.3.6.1.4.1.2011.2.251.20.1.2.2.15.558.7
        ctrlenclFirmwareIncompatible OBJECT IDENTIFIER ::= { upgrade 7 }

        -- 1.3.6.1.4.1.2011.2.251.20.1.2.2.15.558.7.1
        ctrlenclFirmwareIncompatible-Fault NOTIFICATION-TYPE
            OBJECTS { hwStorageAlarmReporting }
            STATUS current
            DESCRIPTION "The Hardware Version Of The Controller Enclosure Or Smart Disk Enclosure Is Incompatible With Storage System Software"
            --#SEVERITY MAJOR
            ::= { ctrlenclFirmwareIncompatible 1 }

        -- 1.3.6.1.4.1.2011.2.251.20.1.2.2.15.558.7.2
        ctrlenclFirmwareIncompatible-Resume NOTIFICATION-TYPE
            OBJECTS { hwStorageAlarmReporting }
            STATUS current
            DESCRIPTION "Recover: The Hardware Version Of The Controller Enclosure Or Smart Disk Enclosure Is Incompatible With Storage System Software"
            --#SEVERITY INFORMATIONAL
            ::= { ctrlenclFirmwareIncompatible 2 }

        -- 1.3.6.1.4.1.2011.2.251.20.1.2.2.15.558.17
        incompatibleHardwareOfTheSpareController OBJECT IDENTIFIER ::= { upgrade 17 }

        -- 1.3.6.1.4.1.2011.2.251.20.1.2.2.15.558.17.1
        incompatibleHardwareOfTheSpareController-Fault NOTIFICATION-TYPE
            OBJECTS { hwStorageAlarmReporting }
            STATUS current
            DESCRIPTION "Incompatible Hardware Of The Spare Controller"
            --#SEVERITY CRITICAL
            ::= { incompatibleHardwareOfTheSpareController 1 }

        -- 1.3.6.1.4.1.2011.2.251.20.1.2.2.15.558.17.2
        incompatibleHardwareOfTheSpareController-Resume NOTIFICATION-TYPE
            OBJECTS { hwStorageAlarmReporting }
            STATUS current
            DESCRIPTION "Recover: Incompatible Hardware Of The Spare Controller"
            --#SEVERITY INFORMATIONAL
            ::= { incompatibleHardwareOfTheSpareController 2 }

        -- 1.3.6.1.4.1.2011.2.251.20.1.2.2.15.580
        initiator OBJECT IDENTIFIER ::= { oidBasedTrap 580 }

        -- 1.3.6.1.4.1.2011.2.251.20.1.2.2.15.580.6
        theNumberOfIntermittentDisconnectionsOfTheLinkWhereTheInitiatorResidesExceedsTheThreshold OBJECT IDENTIFIER ::= { initiator 6 }

        -- 1.3.6.1.4.1.2011.2.251.20.1.2.2.15.580.6.1
        theNumberOfIntermittentDisconnectionsOfTheLinkWhereTheInitiatorResidesExceedsTheThreshold-Fault NOTIFICATION-TYPE
            OBJECTS { hwStorageAlarmReporting }
            STATUS current
            DESCRIPTION "The Number Of Intermittent Disconnections Of The Link Where The Initiator Resides Exceeds The Threshold"
            --#SEVERITY WARNING
            ::= { theNumberOfIntermittentDisconnectionsOfTheLinkWhereTheInitiatorResidesExceedsTheThreshold 1 }

        -- 1.3.6.1.4.1.2011.2.251.20.1.2.2.15.580.6.2
        theNumberOfIntermittentDisconnectionsOfTheLinkWhereTheInitiatorResidesExceedsTheThreshold-Resume NOTIFICATION-TYPE
            OBJECTS { hwStorageAlarmReporting }
            STATUS current
            DESCRIPTION "Recover: The Number Of Intermittent Disconnections Of The Link Where The Initiator Resides Exceeds The Threshold"
            --#SEVERITY INFORMATIONAL
            ::= { theNumberOfIntermittentDisconnectionsOfTheLinkWhereTheInitiatorResidesExceedsTheThreshold 2 }

        -- 1.3.6.1.4.1.2011.2.251.20.1.2.2.15.580.17
        theLinkEstablishmentBetweenTheHostAndArrayIsAbnormal OBJECT IDENTIFIER ::= { initiator 17 }

        -- 1.3.6.1.4.1.2011.2.251.20.1.2.2.15.580.17.1
        theLinkEstablishmentBetweenTheHostAndArrayIsAbnormal-Fault NOTIFICATION-TYPE
            OBJECTS { hwStorageAlarmReporting }
            STATUS current
            DESCRIPTION "The Link Establishment Between The Host And Array Is Abnormal"
            --#SEVERITY WARNING
            ::= { theLinkEstablishmentBetweenTheHostAndArrayIsAbnormal 1 }

        -- 1.3.6.1.4.1.2011.2.251.20.1.2.2.15.580.17.2
        theLinkEstablishmentBetweenTheHostAndArrayIsAbnormal-Resume NOTIFICATION-TYPE
            OBJECTS { hwStorageAlarmReporting }
            STATUS current
            DESCRIPTION "Recover: The Link Establishment Between The Host And Array Is Abnormal"
            --#SEVERITY INFORMATIONAL
            ::= { theLinkEstablishmentBetweenTheHostAndArrayIsAbnormal 2 }

        -- 1.3.6.1.4.1.2011.2.251.20.1.2.2.15.580.20
        initiatorExceedLimit OBJECT IDENTIFIER ::= { initiator 20 }

        -- 1.3.6.1.4.1.2011.2.251.20.1.2.2.15.580.20.1
        initiatorExceedLimit-Fault NOTIFICATION-TYPE
            OBJECTS { hwStorageAlarmReporting }
            STATUS current
            DESCRIPTION "Number Of Initiators Connected To A Port Exceeds The Upper Limit"
            --#SEVERITY MAJOR
            ::= { initiatorExceedLimit 1 }

        -- 1.3.6.1.4.1.2011.2.251.20.1.2.2.15.580.20.2
        initiatorExceedLimit-Resume NOTIFICATION-TYPE
            OBJECTS { hwStorageAlarmReporting }
            STATUS current
            DESCRIPTION "Recover: Number Of Initiators Connected To A Port Exceeds The Upper Limit"
            --#SEVERITY INFORMATIONAL
            ::= { initiatorExceedLimit 2 }

        -- 1.3.6.1.4.1.2011.2.251.20.1.2.2.15.580.48
        numberOfInitiatorConnectionsOnAPortExceedsTheSystemLimit OBJECT IDENTIFIER ::= { initiator 48 }

        -- 1.3.6.1.4.1.2011.2.251.20.1.2.2.15.580.48.1
        numberOfInitiatorConnectionsOnAPortExceedsTheSystemLimit-Fault NOTIFICATION-TYPE
            OBJECTS { hwStorageAlarmReporting }
            STATUS current
            DESCRIPTION "Number Of Initiator Connections On A Port Exceeds The System Limit"
            --#SEVERITY MAJOR
            ::= { numberOfInitiatorConnectionsOnAPortExceedsTheSystemLimit 1 }

        -- 1.3.6.1.4.1.2011.2.251.20.1.2.2.15.580.48.2
        numberOfInitiatorConnectionsOnAPortExceedsTheSystemLimit-Resume NOTIFICATION-TYPE
            OBJECTS { hwStorageAlarmReporting }
            STATUS current
            DESCRIPTION "Recover: Number Of Initiator Connections On A Port Exceeds The System Limit"
            --#SEVERITY INFORMATIONAL
            ::= { numberOfInitiatorConnectionsOnAPortExceedsTheSystemLimit 2 }

        -- 1.3.6.1.4.1.2011.2.251.20.1.2.2.15.580.4103
        linkIsDisconnected OBJECT IDENTIFIER ::= { initiator 4103 }

        -- 1.3.6.1.4.1.2011.2.251.20.1.2.2.15.580.4103.1
        linkIsDisconnected-Fault NOTIFICATION-TYPE
            OBJECTS { hwStorageAlarmReporting }
            STATUS current
            DESCRIPTION "The Link Between A Host And The Storage Array Is Disconnected"
            --#SEVERITY WARNING
            ::= { linkIsDisconnected 1 }

        -- 1.3.6.1.4.1.2011.2.251.20.1.2.2.15.580.4103.2
        linkIsDisconnected-Resume NOTIFICATION-TYPE
            OBJECTS { hwStorageAlarmReporting }
            STATUS current
            DESCRIPTION "Recover: The Link Between A Host And The Storage Array Is Disconnected"
            --#SEVERITY INFORMATIONAL
            ::= { linkIsDisconnected 2 }

        -- 1.3.6.1.4.1.2011.2.251.20.1.2.2.15.580.4104
        failedToEstablishALinkBetweenTheHostAndDiskArray OBJECT IDENTIFIER ::= { initiator 4104 }

        -- 1.3.6.1.4.1.2011.2.251.20.1.2.2.15.580.4104.1
        failedToEstablishALinkBetweenTheHostAndDiskArray-Fault NOTIFICATION-TYPE
            OBJECTS { hwStorageAlarmReporting }
            STATUS current
            DESCRIPTION "Failed To Establish A Link Between The Host And Disk Array"
            --#SEVERITY WARNING
            ::= { failedToEstablishALinkBetweenTheHostAndDiskArray 1 }

        -- 1.3.6.1.4.1.2011.2.251.20.1.2.2.15.580.4104.2
        failedToEstablishALinkBetweenTheHostAndDiskArray-Resume NOTIFICATION-TYPE
            OBJECTS { hwStorageAlarmReporting }
            STATUS current
            DESCRIPTION "Recover: Failed To Establish A Link Between The Host And Disk Array"
            --#SEVERITY INFORMATIONAL
            ::= { failedToEstablishALinkBetweenTheHostAndDiskArray 2 }

        -- 1.3.6.1.4.1.2011.2.251.20.1.2.2.15.580.4106
        initiatorsAssociatedWithMultipleHostsRepeat OBJECT IDENTIFIER ::= { initiator 4106 }

        -- 1.3.6.1.4.1.2011.2.251.20.1.2.2.15.580.4106.1
        initiatorsAssociatedWithMultipleHostsRepeat-Fault NOTIFICATION-TYPE
            OBJECTS { hwStorageAlarmReporting }
            STATUS current
            DESCRIPTION "Initiators With The Same NVMe Host ID Exist On Different Hosts"
            --#SEVERITY MAJOR
            ::= { initiatorsAssociatedWithMultipleHostsRepeat 1 }

        -- 1.3.6.1.4.1.2011.2.251.20.1.2.2.15.580.4106.2
        initiatorsAssociatedWithMultipleHostsRepeat-Resume NOTIFICATION-TYPE
            OBJECTS { hwStorageAlarmReporting }
            STATUS current
            DESCRIPTION "Recover: Initiators With The Same NVMe Host ID Exist On Different Hosts"
            --#SEVERITY INFORMATIONAL
            ::= { initiatorsAssociatedWithMultipleHostsRepeat 2 }

        -- 1.3.6.1.4.1.2011.2.251.20.1.2.2.15.580.4107
        hostHasInitiatorsWithDifferentNvmeHostIds OBJECT IDENTIFIER ::= { initiator 4107 }

        -- 1.3.6.1.4.1.2011.2.251.20.1.2.2.15.580.4107.1
        hostHasInitiatorsWithDifferentNvmeHostIds-Fault NOTIFICATION-TYPE
            OBJECTS { hwStorageAlarmReporting }
            STATUS current
            DESCRIPTION "Initiators With Different NVMe Host IDs Exist On The Same Host"
            --#SEVERITY MAJOR
            ::= { hostHasInitiatorsWithDifferentNvmeHostIds 1 }

        -- 1.3.6.1.4.1.2011.2.251.20.1.2.2.15.580.4107.2
        hostHasInitiatorsWithDifferentNvmeHostIds-Resume NOTIFICATION-TYPE
            OBJECTS { hwStorageAlarmReporting }
            STATUS current
            DESCRIPTION "Recover: Initiators With Different NVMe Host IDs Exist On The Same Host"
            --#SEVERITY INFORMATIONAL
            ::= { hostHasInitiatorsWithDifferentNvmeHostIds 2 }

        -- 1.3.6.1.4.1.2011.2.251.20.1.2.2.15.633
        smartmove OBJECT IDENTIFIER ::= { oidBasedTrap 633 }

        -- 1.3.6.1.4.1.2011.2.251.20.1.2.2.15.633.1
        smartMoveDomainIsFaulty OBJECT IDENTIFIER ::= { smartmove 1 }

        -- 1.3.6.1.4.1.2011.2.251.20.1.2.2.15.633.1.1
        smartMoveDomainIsFaulty-Fault NOTIFICATION-TYPE
            OBJECTS { hwStorageAlarmReporting }
            STATUS current
            DESCRIPTION "SmartMove Domain Is Faulty"
            --#SEVERITY MAJOR
            ::= { smartMoveDomainIsFaulty 1 }

        -- 1.3.6.1.4.1.2011.2.251.20.1.2.2.15.633.1.2
        smartMoveDomainIsFaulty-Resume NOTIFICATION-TYPE
            OBJECTS { hwStorageAlarmReporting }
            STATUS current
            DESCRIPTION "Recover: SmartMove Domain Is Faulty"
            --#SEVERITY INFORMATIONAL
            ::= { smartMoveDomainIsFaulty 2 }

        -- 1.3.6.1.4.1.2011.2.251.20.1.2.2.15.633.2
        smartMoveDomainIsUnavailable OBJECT IDENTIFIER ::= { smartmove 2 }

        -- 1.3.6.1.4.1.2011.2.251.20.1.2.2.15.633.2.1
        smartMoveDomainIsUnavailable-Fault NOTIFICATION-TYPE
            OBJECTS { hwStorageAlarmReporting }
            STATUS current
            DESCRIPTION "SmartMove Domain Is Unavailable"
            --#SEVERITY CRITICAL
            ::= { smartMoveDomainIsUnavailable 1 }

        -- 1.3.6.1.4.1.2011.2.251.20.1.2.2.15.633.2.2
        smartMoveDomainIsUnavailable-Resume NOTIFICATION-TYPE
            OBJECTS { hwStorageAlarmReporting }
            STATUS current
            DESCRIPTION "Recover: SmartMove Domain Is Unavailable"
            --#SEVERITY INFORMATIONAL
            ::= { smartMoveDomainIsUnavailable 2 }

        -- 1.3.6.1.4.1.2011.2.251.20.1.2.2.15.633.3
        smartMoveVStorePairConfigurationsAreDisconnectedUnexpectedly OBJECT IDENTIFIER ::= { smartmove 3 }

        -- 1.3.6.1.4.1.2011.2.251.20.1.2.2.15.633.3.1
        smartMoveVStorePairConfigurationsAreDisconnectedUnexpectedly-Fault NOTIFICATION-TYPE
            OBJECTS { hwStorageAlarmReporting }
            STATUS current
            DESCRIPTION "SmartMove VStore Pair Configurations Are Disconnected Unexpectedly"
            --#SEVERITY MAJOR
            ::= { smartMoveVStorePairConfigurationsAreDisconnectedUnexpectedly 1 }

        -- 1.3.6.1.4.1.2011.2.251.20.1.2.2.15.633.3.2
        smartMoveVStorePairConfigurationsAreDisconnectedUnexpectedly-Resume NOTIFICATION-TYPE
            OBJECTS { hwStorageAlarmReporting }
            STATUS current
            DESCRIPTION "Recover: SmartMove VStore Pair Configurations Are Disconnected Unexpectedly"
            --#SEVERITY INFORMATIONAL
            ::= { smartMoveVStorePairConfigurationsAreDisconnectedUnexpectedly 2 }

        -- 1.3.6.1.4.1.2011.2.251.20.1.2.2.15.633.4
        smartMoveVStorePairIsInvalid OBJECT IDENTIFIER ::= { smartmove 4 }

        -- 1.3.6.1.4.1.2011.2.251.20.1.2.2.15.633.4.1
        smartMoveVStorePairIsInvalid-Fault NOTIFICATION-TYPE
            OBJECTS { hwStorageAlarmReporting }
            STATUS current
            DESCRIPTION "SmartMove VStore Pair Is Invalid"
            --#SEVERITY CRITICAL
            ::= { smartMoveVStorePairIsInvalid 1 }

        -- 1.3.6.1.4.1.2011.2.251.20.1.2.2.15.633.4.2
        smartMoveVStorePairIsInvalid-Resume NOTIFICATION-TYPE
            OBJECTS { hwStorageAlarmReporting }
            STATUS current
            DESCRIPTION "Recover: SmartMove VStore Pair Is Invalid"
            --#SEVERITY INFORMATIONAL
            ::= { smartMoveVStorePairIsInvalid 2 }

        -- 1.3.6.1.4.1.2011.2.251.20.1.2.2.15.633.6
        smartMoveFileSystemPairIsUnavailable OBJECT IDENTIFIER ::= { smartmove 6 }

        -- 1.3.6.1.4.1.2011.2.251.20.1.2.2.15.633.6.1
        smartMoveFileSystemPairIsUnavailable-Fault NOTIFICATION-TYPE
            OBJECTS { hwStorageAlarmReporting }
            STATUS current
            DESCRIPTION "SmartMove File System Pair Is Unavailable"
            --#SEVERITY CRITICAL
            ::= { smartMoveFileSystemPairIsUnavailable 1 }

        -- 1.3.6.1.4.1.2011.2.251.20.1.2.2.15.633.6.2
        smartMoveFileSystemPairIsUnavailable-Resume NOTIFICATION-TYPE
            OBJECTS { hwStorageAlarmReporting }
            STATUS current
            DESCRIPTION "Recover: SmartMove File System Pair Is Unavailable"
            --#SEVERITY INFORMATIONAL
            ::= { smartMoveFileSystemPairIsUnavailable 2 }

        -- 1.3.6.1.4.1.2011.2.251.20.1.2.2.15.633.9
        smartMovePairFault OBJECT IDENTIFIER ::= { smartmove 9 }

        -- 1.3.6.1.4.1.2011.2.251.20.1.2.2.15.633.9.1
        smartMovePairFault-Fault NOTIFICATION-TYPE
            OBJECTS { hwStorageAlarmReporting }
            STATUS current
            DESCRIPTION "SmartMove Pair Fault"
            --#SEVERITY MAJOR
            ::= { smartMovePairFault 1 }

        -- 1.3.6.1.4.1.2011.2.251.20.1.2.2.15.633.9.2
        smartMovePairFault-Resume NOTIFICATION-TYPE
            OBJECTS { hwStorageAlarmReporting }
            STATUS current
            DESCRIPTION "Recover: SmartMove Pair Fault"
            --#SEVERITY INFORMATIONAL
            ::= { smartMovePairFault 2 }

        -- 1.3.6.1.4.1.2011.2.251.20.1.2.2.15.633.10
        smartMovePairInvalid OBJECT IDENTIFIER ::= { smartmove 10 }

        -- 1.3.6.1.4.1.2011.2.251.20.1.2.2.15.633.10.1
        smartMovePairInvalid-Fault NOTIFICATION-TYPE
            OBJECTS { hwStorageAlarmReporting }
            STATUS current
            DESCRIPTION "SmartMove Pair Invalid"
            --#SEVERITY CRITICAL
            ::= { smartMovePairInvalid 1 }

        -- 1.3.6.1.4.1.2011.2.251.20.1.2.2.15.633.10.2
        smartMovePairInvalid-Resume NOTIFICATION-TYPE
            OBJECTS { hwStorageAlarmReporting }
            STATUS current
            DESCRIPTION "Recover: SmartMove Pair Invalid"
            --#SEVERITY INFORMATIONAL
            ::= { smartMovePairInvalid 2 }

        -- 1.3.6.1.4.1.2011.2.251.20.1.2.2.15.633.11
        smartMoveFileSystemPairIsDisconnectedUnexpectedly OBJECT IDENTIFIER ::= { smartmove 11 }

        -- 1.3.6.1.4.1.2011.2.251.20.1.2.2.15.633.11.1
        smartMoveFileSystemPairIsDisconnectedUnexpectedly-Fault NOTIFICATION-TYPE
            OBJECTS { hwStorageAlarmReporting }
            STATUS current
            DESCRIPTION "SmartMove File System Pair Is Disconnected Unexpectedly"
            --#SEVERITY MAJOR
            ::= { smartMoveFileSystemPairIsDisconnectedUnexpectedly 1 }

        -- 1.3.6.1.4.1.2011.2.251.20.1.2.2.15.633.11.2
        smartMoveFileSystemPairIsDisconnectedUnexpectedly-Resume NOTIFICATION-TYPE
            OBJECTS { hwStorageAlarmReporting }
            STATUS current
            DESCRIPTION "Recover: SmartMove File System Pair Is Disconnected Unexpectedly"
            --#SEVERITY INFORMATIONAL
            ::= { smartMoveFileSystemPairIsDisconnectedUnexpectedly 2 }

        -- 1.3.6.1.4.1.2011.2.251.20.1.2.2.15.633.12
        smartMoveFileSystemPairConfigurationsAreDisconnectedUnexpectedly OBJECT IDENTIFIER ::= { smartmove 12 }

        -- 1.3.6.1.4.1.2011.2.251.20.1.2.2.15.633.12.1
        smartMoveFileSystemPairConfigurationsAreDisconnectedUnexpectedly-Fault NOTIFICATION-TYPE
            OBJECTS { hwStorageAlarmReporting }
            STATUS current
            DESCRIPTION "SmartMove File System Pair Configurations Are Disconnected Unexpectedly"
            --#SEVERITY MAJOR
            ::= { smartMoveFileSystemPairConfigurationsAreDisconnectedUnexpectedly 1 }

        -- 1.3.6.1.4.1.2011.2.251.20.1.2.2.15.633.12.2
        smartMoveFileSystemPairConfigurationsAreDisconnectedUnexpectedly-Resume NOTIFICATION-TYPE
            OBJECTS { hwStorageAlarmReporting }
            STATUS current
            DESCRIPTION "Recover: SmartMove File System Pair Configurations Are Disconnected Unexpectedly"
            --#SEVERITY INFORMATIONAL
            ::= { smartMoveFileSystemPairConfigurationsAreDisconnectedUnexpectedly 2 }

        -- 1.3.6.1.4.1.2011.2.251.20.1.2.2.15.633.14
        smartMoveDomainIsRecovery OBJECT IDENTIFIER ::= { smartmove 14 }

        -- 1.3.6.1.4.1.2011.2.251.20.1.2.2.15.633.14.1
        smartMoveDomainIsRecovery-Fault NOTIFICATION-TYPE
            OBJECTS { hwStorageAlarmReporting }
            STATUS current
            DESCRIPTION "SmartMove Domain Is In The Recovering State For A Long Time"
            --#SEVERITY WARNING
            ::= { smartMoveDomainIsRecovery 1 }

        -- 1.3.6.1.4.1.2011.2.251.20.1.2.2.15.633.14.2
        smartMoveDomainIsRecovery-Resume NOTIFICATION-TYPE
            OBJECTS { hwStorageAlarmReporting }
            STATUS current
            DESCRIPTION "Recover: SmartMove Domain Is In The Recovering State For A Long Time"
            --#SEVERITY INFORMATIONAL
            ::= { smartMoveDomainIsRecovery 2 }

        -- 1.3.6.1.4.1.2011.2.251.20.1.2.2.15.678
        vswitch OBJECT IDENTIFIER ::= { oidBasedTrap 678 }

        -- 1.3.6.1.4.1.2011.2.251.20.1.2.2.15.678.1
        cloudVxLANNetworkConfigurationsDoNotMeetRedundancyRequirements OBJECT IDENTIFIER ::= { vswitch 1 }

        -- 1.3.6.1.4.1.2011.2.251.20.1.2.2.15.678.1.1
        cloudVxLANNetworkConfigurationsDoNotMeetRedundancyRequirements-Fault NOTIFICATION-TYPE
            OBJECTS { hwStorageAlarmReporting }
            STATUS current
            DESCRIPTION "CloudVxLAN Network Configurations Do Not Meet Redundancy Requirements"
            --#SEVERITY MAJOR
            ::= { cloudVxLANNetworkConfigurationsDoNotMeetRedundancyRequirements 1 }

        -- 1.3.6.1.4.1.2011.2.251.20.1.2.2.15.678.1.2
        cloudVxLANNetworkConfigurationsDoNotMeetRedundancyRequirements-Resume NOTIFICATION-TYPE
            OBJECTS { hwStorageAlarmReporting }
            STATUS current
            DESCRIPTION "Recover: CloudVxLAN Network Configurations Do Not Meet Redundancy Requirements"
            --#SEVERITY INFORMATIONAL
            ::= { cloudVxLANNetworkConfigurationsDoNotMeetRedundancyRequirements 2 }

        -- 1.3.6.1.4.1.2011.2.251.20.1.2.2.15.756
        box OBJECT IDENTIFIER ::= { oidBasedTrap 756 }

        -- 1.3.6.1.4.1.2011.2.251.20.1.2.2.15.756.1
        boxCpldComponentIsFaulty OBJECT IDENTIFIER ::= { box 1 }

        -- 1.3.6.1.4.1.2011.2.251.20.1.2.2.15.756.1.1
        boxCpldComponentIsFaulty-Fault NOTIFICATION-TYPE
            OBJECTS { hwStorageAlarmReporting }
            STATUS current
            DESCRIPTION "A CPLD Module In The Box Is Faulty"
            --#SEVERITY WARNING
            ::= { boxCpldComponentIsFaulty 1 }

        -- 1.3.6.1.4.1.2011.2.251.20.1.2.2.15.756.1.2
        boxCpldComponentIsFaulty-Resume NOTIFICATION-TYPE
            OBJECTS { hwStorageAlarmReporting }
            STATUS current
            DESCRIPTION "Recover: A CPLD Module In The Box Is Faulty"
            --#SEVERITY INFORMATIONAL
            ::= { boxCpldComponentIsFaulty 2 }

        -- 1.3.6.1.4.1.2011.2.251.20.1.2.2.15.756.90
        riserCardTypeIsIllegal OBJECT IDENTIFIER ::= { box 90 }

        -- 1.3.6.1.4.1.2011.2.251.20.1.2.2.15.756.90.1
        riserCardTypeIsIllegal-Fault NOTIFICATION-TYPE
            OBJECTS { hwStorageAlarmReporting }
            STATUS current
            DESCRIPTION "Invalid Box Type"
            --#SEVERITY MAJOR
            ::= { riserCardTypeIsIllegal 1 }

        -- 1.3.6.1.4.1.2011.2.251.20.1.2.2.15.756.90.2
        riserCardTypeIsIllegal-Resume NOTIFICATION-TYPE
            OBJECTS { hwStorageAlarmReporting }
            STATUS current
            DESCRIPTION "Recover: Invalid Box Type"
            --#SEVERITY INFORMATIONAL
            ::= { riserCardTypeIsIllegal 2 }

        -- 1.3.6.1.4.1.2011.2.251.20.1.2.2.15.756.91
        riserCardIsRemoved OBJECT IDENTIFIER ::= { box 91 }

        -- 1.3.6.1.4.1.2011.2.251.20.1.2.2.15.756.91.1
        riserCardIsRemoved-Fault NOTIFICATION-TYPE
            OBJECTS { hwStorageAlarmReporting }
            STATUS current
            DESCRIPTION "The Box Is Removed"
            --#SEVERITY MAJOR
            ::= { riserCardIsRemoved 1 }

        -- 1.3.6.1.4.1.2011.2.251.20.1.2.2.15.756.91.2
        riserCardIsRemoved-Resume NOTIFICATION-TYPE
            OBJECTS { hwStorageAlarmReporting }
            STATUS current
            DESCRIPTION "Recover: The Box Is Removed"
            --#SEVERITY INFORMATIONAL
            ::= { riserCardIsRemoved 2 }

        -- 1.3.6.1.4.1.2011.2.251.20.1.2.2.15.756.92
        riserCardTypeIsUnrecognizable OBJECT IDENTIFIER ::= { box 92 }

        -- 1.3.6.1.4.1.2011.2.251.20.1.2.2.15.756.92.1
        riserCardTypeIsUnrecognizable-Fault NOTIFICATION-TYPE
            OBJECTS { hwStorageAlarmReporting }
            STATUS current
            DESCRIPTION "The Box Type Cannot Be Identified"
            --#SEVERITY MAJOR
            ::= { riserCardTypeIsUnrecognizable 1 }

        -- 1.3.6.1.4.1.2011.2.251.20.1.2.2.15.756.92.2
        riserCardTypeIsUnrecognizable-Resume NOTIFICATION-TYPE
            OBJECTS { hwStorageAlarmReporting }
            STATUS current
            DESCRIPTION "Recover: The Box Type Cannot Be Identified"
            --#SEVERITY INFORMATIONAL
            ::= { riserCardTypeIsUnrecognizable 2 }

        -- 1.3.6.1.4.1.2011.2.251.20.1.2.2.15.822
        performancemanagement OBJECT IDENTIFIER ::= { oidBasedTrap 822 }

        -- 1.3.6.1.4.1.2011.2.251.20.1.2.2.15.822.1
        warnAvgCpuUsageThreshAlarm OBJECT IDENTIFIER ::= { performancemanagement 1 }

        -- 1.3.6.1.4.1.2011.2.251.20.1.2.2.15.822.1.1
        warnAvgCpuUsageThreshAlarm-Fault NOTIFICATION-TYPE
            OBJECTS { hwStorageAlarmReporting }
            STATUS current
            DESCRIPTION "Average CPU Utilization Exceeded The Threshold"
            --#SEVERITY WARNING
            ::= { warnAvgCpuUsageThreshAlarm 1 }

        -- 1.3.6.1.4.1.2011.2.251.20.1.2.2.15.822.1.2
        warnAvgCpuUsageThreshAlarm-Resume NOTIFICATION-TYPE
            OBJECTS { hwStorageAlarmReporting }
            STATUS current
            DESCRIPTION "Recover: Average CPU Utilization Exceeded The Threshold"
            --#SEVERITY INFORMATIONAL
            ::= { warnAvgCpuUsageThreshAlarm 2 }

        -- 1.3.6.1.4.1.2011.2.251.20.1.2.2.15.822.2
        warnUsageThreshAlarm OBJECT IDENTIFIER ::= { performancemanagement 2 }

        -- 1.3.6.1.4.1.2011.2.251.20.1.2.2.15.822.2.1
        warnUsageThreshAlarm-Fault NOTIFICATION-TYPE
            OBJECTS { hwStorageAlarmReporting }
            STATUS current
            DESCRIPTION "Utilization Exceeded The Threshold"
            --#SEVERITY WARNING
            ::= { warnUsageThreshAlarm 1 }

        -- 1.3.6.1.4.1.2011.2.251.20.1.2.2.15.822.2.2
        warnUsageThreshAlarm-Resume NOTIFICATION-TYPE
            OBJECTS { hwStorageAlarmReporting }
            STATUS current
            DESCRIPTION "Recover: Utilization Exceeded The Threshold"
            --#SEVERITY INFORMATIONAL
            ::= { warnUsageThreshAlarm 2 }

        -- 1.3.6.1.4.1.2011.2.251.20.1.2.2.15.822.4
        warnAvgIORespTimeThreshAlarm OBJECT IDENTIFIER ::= { performancemanagement 4 }

        -- 1.3.6.1.4.1.2011.2.251.20.1.2.2.15.822.4.1
        warnAvgIORespTimeThreshAlarm-Fault NOTIFICATION-TYPE
            OBJECTS { hwStorageAlarmReporting }
            STATUS current
            DESCRIPTION "Average IO Response Time Exceeded The Threshold"
            --#SEVERITY WARNING
            ::= { warnAvgIORespTimeThreshAlarm 1 }

        -- 1.3.6.1.4.1.2011.2.251.20.1.2.2.15.822.4.2
        warnAvgIORespTimeThreshAlarm-Resume NOTIFICATION-TYPE
            OBJECTS { hwStorageAlarmReporting }
            STATUS current
            DESCRIPTION "Recover: Average IO Response Time Exceeded The Threshold"
            --#SEVERITY INFORMATIONAL
            ::= { warnAvgIORespTimeThreshAlarm 2 }

        -- 1.3.6.1.4.1.2011.2.251.20.1.2.2.15.822.7
        warnTimeSinceLastSyncThreshAlarm OBJECT IDENTIFIER ::= { performancemanagement 7 }

        -- 1.3.6.1.4.1.2011.2.251.20.1.2.2.15.822.7.1
        warnTimeSinceLastSyncThreshAlarm-Fault NOTIFICATION-TYPE
            OBJECTS { hwStorageAlarmReporting }
            STATUS current
            DESCRIPTION "Time Since Last Synchronization Exceeded The Threshold"
            --#SEVERITY WARNING
            ::= { warnTimeSinceLastSyncThreshAlarm 1 }

        -- 1.3.6.1.4.1.2011.2.251.20.1.2.2.15.822.7.2
        warnTimeSinceLastSyncThreshAlarm-Resume NOTIFICATION-TYPE
            OBJECTS { hwStorageAlarmReporting }
            STATUS current
            DESCRIPTION "Recover: Time Since Last Synchronization Exceeded The Threshold"
            --#SEVERITY INFORMATIONAL
            ::= { warnTimeSinceLastSyncThreshAlarm 2 }

        -- 1.3.6.1.4.1.2011.2.251.20.1.2.2.15.822.8
        criticalAvgCpuUsageThreshAlarm OBJECT IDENTIFIER ::= { performancemanagement 8 }

        -- 1.3.6.1.4.1.2011.2.251.20.1.2.2.15.822.8.1
        criticalAvgCpuUsageThreshAlarm-Fault NOTIFICATION-TYPE
            OBJECTS { hwStorageAlarmReporting }
            STATUS current
            DESCRIPTION "Average CPU Utilization Exceeded The Threshold"
            --#SEVERITY CRITICAL
            ::= { criticalAvgCpuUsageThreshAlarm 1 }

        -- 1.3.6.1.4.1.2011.2.251.20.1.2.2.15.822.8.2
        criticalAvgCpuUsageThreshAlarm-Resume NOTIFICATION-TYPE
            OBJECTS { hwStorageAlarmReporting }
            STATUS current
            DESCRIPTION "Recover: Average CPU Utilization Exceeded The Threshold"
            --#SEVERITY INFORMATIONAL
            ::= { criticalAvgCpuUsageThreshAlarm 2 }

        -- 1.3.6.1.4.1.2011.2.251.20.1.2.2.15.822.9
        criticalUsageThreshAlarm OBJECT IDENTIFIER ::= { performancemanagement 9 }

        -- 1.3.6.1.4.1.2011.2.251.20.1.2.2.15.822.9.1
        criticalUsageThreshAlarm-Fault NOTIFICATION-TYPE
            OBJECTS { hwStorageAlarmReporting }
            STATUS current
            DESCRIPTION "Utilization Exceeded The Threshold"
            --#SEVERITY CRITICAL
            ::= { criticalUsageThreshAlarm 1 }

        -- 1.3.6.1.4.1.2011.2.251.20.1.2.2.15.822.9.2
        criticalUsageThreshAlarm-Resume NOTIFICATION-TYPE
            OBJECTS { hwStorageAlarmReporting }
            STATUS current
            DESCRIPTION "Recover: Utilization Exceeded The Threshold"
            --#SEVERITY INFORMATIONAL
            ::= { criticalUsageThreshAlarm 2 }

        -- 1.3.6.1.4.1.2011.2.251.20.1.2.2.15.822.11
        criticalAvgIORespThreshAlarm OBJECT IDENTIFIER ::= { performancemanagement 11 }

        -- 1.3.6.1.4.1.2011.2.251.20.1.2.2.15.822.11.1
        criticalAvgIORespThreshAlarm-Fault NOTIFICATION-TYPE
            OBJECTS { hwStorageAlarmReporting }
            STATUS current
            DESCRIPTION "Average IO Response Time Exceeded The Threshold"
            --#SEVERITY CRITICAL
            ::= { criticalAvgIORespThreshAlarm 1 }

        -- 1.3.6.1.4.1.2011.2.251.20.1.2.2.15.822.11.2
        criticalAvgIORespThreshAlarm-Resume NOTIFICATION-TYPE
            OBJECTS { hwStorageAlarmReporting }
            STATUS current
            DESCRIPTION "Recover: Average IO Response Time Exceeded The Threshold"
            --#SEVERITY INFORMATIONAL
            ::= { criticalAvgIORespThreshAlarm 2 }

        -- 1.3.6.1.4.1.2011.2.251.20.1.2.2.15.822.14
        criticalTimeSinceSyncThreshAlarm OBJECT IDENTIFIER ::= { performancemanagement 14 }

        -- 1.3.6.1.4.1.2011.2.251.20.1.2.2.15.822.14.1
        criticalTimeSinceSyncThreshAlarm-Fault NOTIFICATION-TYPE
            OBJECTS { hwStorageAlarmReporting }
            STATUS current
            DESCRIPTION "Time Since Last Synchronization Exceeded The Threshold"
            --#SEVERITY CRITICAL
            ::= { criticalTimeSinceSyncThreshAlarm 1 }

        -- 1.3.6.1.4.1.2011.2.251.20.1.2.2.15.822.14.2
        criticalTimeSinceSyncThreshAlarm-Resume NOTIFICATION-TYPE
            OBJECTS { hwStorageAlarmReporting }
            STATUS current
            DESCRIPTION "Recover: Time Since Last Synchronization Exceeded The Threshold"
            --#SEVERITY INFORMATIONAL
            ::= { criticalTimeSinceSyncThreshAlarm 2 }

        -- 1.3.6.1.4.1.2011.2.251.20.1.2.2.15.822.15
        majorAvgCpuUsageThreshAlarm OBJECT IDENTIFIER ::= { performancemanagement 15 }

        -- 1.3.6.1.4.1.2011.2.251.20.1.2.2.15.822.15.1
        majorAvgCpuUsageThreshAlarm-Fault NOTIFICATION-TYPE
            OBJECTS { hwStorageAlarmReporting }
            STATUS current
            DESCRIPTION "Average CPU Utilization Exceeded The Threshold"
            --#SEVERITY MAJOR
            ::= { majorAvgCpuUsageThreshAlarm 1 }

        -- 1.3.6.1.4.1.2011.2.251.20.1.2.2.15.822.15.2
        majorAvgCpuUsageThreshAlarm-Resume NOTIFICATION-TYPE
            OBJECTS { hwStorageAlarmReporting }
            STATUS current
            DESCRIPTION "Recover: Average CPU Utilization Exceeded The Threshold"
            --#SEVERITY INFORMATIONAL
            ::= { majorAvgCpuUsageThreshAlarm 2 }

        -- 1.3.6.1.4.1.2011.2.251.20.1.2.2.15.822.16
        majorUsageThreshAlarm OBJECT IDENTIFIER ::= { performancemanagement 16 }

        -- 1.3.6.1.4.1.2011.2.251.20.1.2.2.15.822.16.1
        majorUsageThreshAlarm-Fault NOTIFICATION-TYPE
            OBJECTS { hwStorageAlarmReporting }
            STATUS current
            DESCRIPTION "Utilization Exceeded The Threshold"
            --#SEVERITY MAJOR
            ::= { majorUsageThreshAlarm 1 }

        -- 1.3.6.1.4.1.2011.2.251.20.1.2.2.15.822.16.2
        majorUsageThreshAlarm-Resume NOTIFICATION-TYPE
            OBJECTS { hwStorageAlarmReporting }
            STATUS current
            DESCRIPTION "Recover: Utilization Exceeded The Threshold"
            --#SEVERITY INFORMATIONAL
            ::= { majorUsageThreshAlarm 2 }

        -- 1.3.6.1.4.1.2011.2.251.20.1.2.2.15.822.18
        majorAvgIORespTimeThreshAlarm OBJECT IDENTIFIER ::= { performancemanagement 18 }

        -- 1.3.6.1.4.1.2011.2.251.20.1.2.2.15.822.18.1
        majorAvgIORespTimeThreshAlarm-Fault NOTIFICATION-TYPE
            OBJECTS { hwStorageAlarmReporting }
            STATUS current
            DESCRIPTION "Average IO Response Time Exceeded The Threshold"
            --#SEVERITY MAJOR
            ::= { majorAvgIORespTimeThreshAlarm 1 }

        -- 1.3.6.1.4.1.2011.2.251.20.1.2.2.15.822.18.2
        majorAvgIORespTimeThreshAlarm-Resume NOTIFICATION-TYPE
            OBJECTS { hwStorageAlarmReporting }
            STATUS current
            DESCRIPTION "Recover: Average IO Response Time Exceeded The Threshold"
            --#SEVERITY INFORMATIONAL
            ::= { majorAvgIORespTimeThreshAlarm 2 }

        -- 1.3.6.1.4.1.2011.2.251.20.1.2.2.15.822.21
        majorTimeSinceSyncThreshAlarm OBJECT IDENTIFIER ::= { performancemanagement 21 }

        -- 1.3.6.1.4.1.2011.2.251.20.1.2.2.15.822.21.1
        majorTimeSinceSyncThreshAlarm-Fault NOTIFICATION-TYPE
            OBJECTS { hwStorageAlarmReporting }
            STATUS current
            DESCRIPTION "Time Since Last Synchronization Exceeded The Threshold"
            --#SEVERITY MAJOR
            ::= { majorTimeSinceSyncThreshAlarm 1 }

        -- 1.3.6.1.4.1.2011.2.251.20.1.2.2.15.822.21.2
        majorTimeSinceSyncThreshAlarm-Resume NOTIFICATION-TYPE
            OBJECTS { hwStorageAlarmReporting }
            STATUS current
            DESCRIPTION "Recover: Time Since Last Synchronization Exceeded The Threshold"
            --#SEVERITY INFORMATIONAL
            ::= { majorTimeSinceSyncThreshAlarm 2 }

        -- 1.3.6.1.4.1.2011.2.251.20.1.2.2.15.822.37
        warnMemberdiskUsageThreshAlarm OBJECT IDENTIFIER ::= { performancemanagement 37 }

        -- 1.3.6.1.4.1.2011.2.251.20.1.2.2.15.822.37.1
        warnMemberdiskUsageThreshAlarm-Fault NOTIFICATION-TYPE
            OBJECTS { hwStorageAlarmReporting }
            STATUS current
            DESCRIPTION "The Average Usage Of Member Disks Exceeds The Threshold"
            --#SEVERITY WARNING
            ::= { warnMemberdiskUsageThreshAlarm 1 }

        -- 1.3.6.1.4.1.2011.2.251.20.1.2.2.15.822.37.2
        warnMemberdiskUsageThreshAlarm-Resume NOTIFICATION-TYPE
            OBJECTS { hwStorageAlarmReporting }
            STATUS current
            DESCRIPTION "Recover: The Average Usage Of Member Disks Exceeds The Threshold"
            --#SEVERITY INFORMATIONAL
            ::= { warnMemberdiskUsageThreshAlarm 2 }

        -- 1.3.6.1.4.1.2011.2.251.20.1.2.2.15.822.38
        majorMemberdiskUsageThreshAlarm OBJECT IDENTIFIER ::= { performancemanagement 38 }

        -- 1.3.6.1.4.1.2011.2.251.20.1.2.2.15.822.38.1
        majorMemberdiskUsageThreshAlarm-Fault NOTIFICATION-TYPE
            OBJECTS { hwStorageAlarmReporting }
            STATUS current
            DESCRIPTION "The Average Usage Of Member Disks Exceeds The Threshold"
            --#SEVERITY MAJOR
            ::= { majorMemberdiskUsageThreshAlarm 1 }

        -- 1.3.6.1.4.1.2011.2.251.20.1.2.2.15.822.38.2
        majorMemberdiskUsageThreshAlarm-Resume NOTIFICATION-TYPE
            OBJECTS { hwStorageAlarmReporting }
            STATUS current
            DESCRIPTION "Recover: The Average Usage Of Member Disks Exceeds The Threshold"
            --#SEVERITY INFORMATIONAL
            ::= { majorMemberdiskUsageThreshAlarm 2 }

        -- 1.3.6.1.4.1.2011.2.251.20.1.2.2.15.822.39
        criticalUsageThreshAlarm1 OBJECT IDENTIFIER ::= { performancemanagement 39 }

        -- 1.3.6.1.4.1.2011.2.251.20.1.2.2.15.822.39.1
        criticalUsageThreshAlarm1-Fault NOTIFICATION-TYPE
            OBJECTS { hwStorageAlarmReporting }
            STATUS current
            DESCRIPTION "The Average Usage Of Member Disks Exceeds The Threshold"
            --#SEVERITY CRITICAL
            ::= { criticalUsageThreshAlarm1 1 }

        -- 1.3.6.1.4.1.2011.2.251.20.1.2.2.15.822.39.2
        criticalUsageThreshAlarm1-Resume NOTIFICATION-TYPE
            OBJECTS { hwStorageAlarmReporting }
            STATUS current
            DESCRIPTION "Recover: The Average Usage Of Member Disks Exceeds The Threshold"
            --#SEVERITY INFORMATIONAL
            ::= { criticalUsageThreshAlarm1 2 }

        -- 1.3.6.1.4.1.2011.2.251.20.1.2.2.15.822.40
        theUnmapCommandBandwidthForWritingDataToDisksExceedsTheThreshold2 OBJECT IDENTIFIER ::= { performancemanagement 40 }

        -- 1.3.6.1.4.1.2011.2.251.20.1.2.2.15.822.40.1
        theUnmapCommandBandwidthForWritingDataToDisksExceedsTheThreshold2-Fault NOTIFICATION-TYPE
            OBJECTS { hwStorageAlarmReporting }
            STATUS current
            DESCRIPTION "The Unmap Command Bandwidth For Writing Data To Disks Exceeds The Threshold"
            --#SEVERITY WARNING
            ::= { theUnmapCommandBandwidthForWritingDataToDisksExceedsTheThreshold2 1 }

        -- 1.3.6.1.4.1.2011.2.251.20.1.2.2.15.822.40.2
        theUnmapCommandBandwidthForWritingDataToDisksExceedsTheThreshold2-Resume NOTIFICATION-TYPE
            OBJECTS { hwStorageAlarmReporting }
            STATUS current
            DESCRIPTION "Recover: The Unmap Command Bandwidth For Writing Data To Disks Exceeds The Threshold"
            --#SEVERITY INFORMATIONAL
            ::= { theUnmapCommandBandwidthForWritingDataToDisksExceedsTheThreshold2 2 }

        -- 1.3.6.1.4.1.2011.2.251.20.1.2.2.15.822.41
        theFullCopyCommandBandwidthOfWritingDataToDisksExceedsTheThreshold1 OBJECT IDENTIFIER ::= { performancemanagement 41 }

        -- 1.3.6.1.4.1.2011.2.251.20.1.2.2.15.822.41.1
        theFullCopyCommandBandwidthOfWritingDataToDisksExceedsTheThreshold1-Fault NOTIFICATION-TYPE
            OBJECTS { hwStorageAlarmReporting }
            STATUS current
            DESCRIPTION "The Full Copy Command Bandwidth Of Writing Data To Disks Exceeds The Threshold"
            --#SEVERITY WARNING
            ::= { theFullCopyCommandBandwidthOfWritingDataToDisksExceedsTheThreshold1 1 }

        -- 1.3.6.1.4.1.2011.2.251.20.1.2.2.15.822.41.2
        theFullCopyCommandBandwidthOfWritingDataToDisksExceedsTheThreshold1-Resume NOTIFICATION-TYPE
            OBJECTS { hwStorageAlarmReporting }
            STATUS current
            DESCRIPTION "Recover: The Full Copy Command Bandwidth Of Writing Data To Disks Exceeds The Threshold"
            --#SEVERITY INFORMATIONAL
            ::= { theFullCopyCommandBandwidthOfWritingDataToDisksExceedsTheThreshold1 2 }

        -- 1.3.6.1.4.1.2011.2.251.20.1.2.2.15.822.42
        theOdxCommandWriteBandwidthExceedsTheThreshold OBJECT IDENTIFIER ::= { performancemanagement 42 }

        -- 1.3.6.1.4.1.2011.2.251.20.1.2.2.15.822.42.1
        theOdxCommandWriteBandwidthExceedsTheThreshold-Fault NOTIFICATION-TYPE
            OBJECTS { hwStorageAlarmReporting }
            STATUS current
            DESCRIPTION "The Odx Command Write Bandwidth Exceeds The Threshold"
            --#SEVERITY WARNING
            ::= { theOdxCommandWriteBandwidthExceedsTheThreshold 1 }

        -- 1.3.6.1.4.1.2011.2.251.20.1.2.2.15.822.42.2
        theOdxCommandWriteBandwidthExceedsTheThreshold-Resume NOTIFICATION-TYPE
            OBJECTS { hwStorageAlarmReporting }
            STATUS current
            DESCRIPTION "Recover: The Odx Command Write Bandwidth Exceeds The Threshold"
            --#SEVERITY INFORMATIONAL
            ::= { theOdxCommandWriteBandwidthExceedsTheThreshold 2 }

        -- 1.3.6.1.4.1.2011.2.251.20.1.2.2.15.822.43
        theUnmapCommandBandwidthForWritingDataToDisksExceedsTheThreshold1 OBJECT IDENTIFIER ::= { performancemanagement 43 }

        -- 1.3.6.1.4.1.2011.2.251.20.1.2.2.15.822.43.1
        theUnmapCommandBandwidthForWritingDataToDisksExceedsTheThreshold1-Fault NOTIFICATION-TYPE
            OBJECTS { hwStorageAlarmReporting }
            STATUS current
            DESCRIPTION "The Unmap Command Bandwidth For Writing Data To Disks Exceeds The Threshold"
            --#SEVERITY MAJOR
            ::= { theUnmapCommandBandwidthForWritingDataToDisksExceedsTheThreshold1 1 }

        -- 1.3.6.1.4.1.2011.2.251.20.1.2.2.15.822.43.2
        theUnmapCommandBandwidthForWritingDataToDisksExceedsTheThreshold1-Resume NOTIFICATION-TYPE
            OBJECTS { hwStorageAlarmReporting }
            STATUS current
            DESCRIPTION "Recover: The Unmap Command Bandwidth For Writing Data To Disks Exceeds The Threshold"
            --#SEVERITY INFORMATIONAL
            ::= { theUnmapCommandBandwidthForWritingDataToDisksExceedsTheThreshold1 2 }

        -- 1.3.6.1.4.1.2011.2.251.20.1.2.2.15.822.44
        theUnmapCommandBandwidthForWritingDataToDisksExceedsTheThreshold OBJECT IDENTIFIER ::= { performancemanagement 44 }

        -- 1.3.6.1.4.1.2011.2.251.20.1.2.2.15.822.44.1
        theUnmapCommandBandwidthForWritingDataToDisksExceedsTheThreshold-Fault NOTIFICATION-TYPE
            OBJECTS { hwStorageAlarmReporting }
            STATUS current
            DESCRIPTION "The Unmap Command Bandwidth For Writing Data To Disks Exceeds The Threshold"
            --#SEVERITY CRITICAL
            ::= { theUnmapCommandBandwidthForWritingDataToDisksExceedsTheThreshold 1 }

        -- 1.3.6.1.4.1.2011.2.251.20.1.2.2.15.822.44.2
        theUnmapCommandBandwidthForWritingDataToDisksExceedsTheThreshold-Resume NOTIFICATION-TYPE
            OBJECTS { hwStorageAlarmReporting }
            STATUS current
            DESCRIPTION "Recover: The Unmap Command Bandwidth For Writing Data To Disks Exceeds The Threshold"
            --#SEVERITY INFORMATIONAL
            ::= { theUnmapCommandBandwidthForWritingDataToDisksExceedsTheThreshold 2 }

        -- 1.3.6.1.4.1.2011.2.251.20.1.2.2.15.822.45
        theFullCopyCommandBandwidthOfWritingDataToDisksExceedsTheThreshold OBJECT IDENTIFIER ::= { performancemanagement 45 }

        -- 1.3.6.1.4.1.2011.2.251.20.1.2.2.15.822.45.1
        theFullCopyCommandBandwidthOfWritingDataToDisksExceedsTheThreshold-Fault NOTIFICATION-TYPE
            OBJECTS { hwStorageAlarmReporting }
            STATUS current
            DESCRIPTION "The Full Copy Command Bandwidth Of Writing Data To Disks Exceeds The Threshold"
            --#SEVERITY MAJOR
            ::= { theFullCopyCommandBandwidthOfWritingDataToDisksExceedsTheThreshold 1 }

        -- 1.3.6.1.4.1.2011.2.251.20.1.2.2.15.822.45.2
        theFullCopyCommandBandwidthOfWritingDataToDisksExceedsTheThreshold-Resume NOTIFICATION-TYPE
            OBJECTS { hwStorageAlarmReporting }
            STATUS current
            DESCRIPTION "Recover: The Full Copy Command Bandwidth Of Writing Data To Disks Exceeds The Threshold"
            --#SEVERITY INFORMATIONAL
            ::= { theFullCopyCommandBandwidthOfWritingDataToDisksExceedsTheThreshold 2 }

        -- 1.3.6.1.4.1.2011.2.251.20.1.2.2.15.822.46
        theFullCopyCommandBandwidthOfWritingDataToDisksExceedsTheThreshold2 OBJECT IDENTIFIER ::= { performancemanagement 46 }

        -- 1.3.6.1.4.1.2011.2.251.20.1.2.2.15.822.46.1
        theFullCopyCommandBandwidthOfWritingDataToDisksExceedsTheThreshold2-Fault NOTIFICATION-TYPE
            OBJECTS { hwStorageAlarmReporting }
            STATUS current
            DESCRIPTION "The Full Copy Command Bandwidth Of Writing Data To Disks Exceeds The Threshold"
            --#SEVERITY CRITICAL
            ::= { theFullCopyCommandBandwidthOfWritingDataToDisksExceedsTheThreshold2 1 }

        -- 1.3.6.1.4.1.2011.2.251.20.1.2.2.15.822.46.2
        theFullCopyCommandBandwidthOfWritingDataToDisksExceedsTheThreshold2-Resume NOTIFICATION-TYPE
            OBJECTS { hwStorageAlarmReporting }
            STATUS current
            DESCRIPTION "Recover: The Full Copy Command Bandwidth Of Writing Data To Disks Exceeds The Threshold"
            --#SEVERITY INFORMATIONAL
            ::= { theFullCopyCommandBandwidthOfWritingDataToDisksExceedsTheThreshold2 2 }

        -- 1.3.6.1.4.1.2011.2.251.20.1.2.2.15.822.47
        theOdxCommandWriteBandwidthExceedsTheThreshold1 OBJECT IDENTIFIER ::= { performancemanagement 47 }

        -- 1.3.6.1.4.1.2011.2.251.20.1.2.2.15.822.47.1
        theOdxCommandWriteBandwidthExceedsTheThreshold1-Fault NOTIFICATION-TYPE
            OBJECTS { hwStorageAlarmReporting }
            STATUS current
            DESCRIPTION "The Odx Command Write Bandwidth Exceeds The Threshold"
            --#SEVERITY MAJOR
            ::= { theOdxCommandWriteBandwidthExceedsTheThreshold1 1 }

        -- 1.3.6.1.4.1.2011.2.251.20.1.2.2.15.822.47.2
        theOdxCommandWriteBandwidthExceedsTheThreshold1-Resume NOTIFICATION-TYPE
            OBJECTS { hwStorageAlarmReporting }
            STATUS current
            DESCRIPTION "Recover: The Odx Command Write Bandwidth Exceeds The Threshold"
            --#SEVERITY INFORMATIONAL
            ::= { theOdxCommandWriteBandwidthExceedsTheThreshold1 2 }

        -- 1.3.6.1.4.1.2011.2.251.20.1.2.2.15.822.48
        theOdxCommandWriteBandwidthExceedsTheThreshold2 OBJECT IDENTIFIER ::= { performancemanagement 48 }

        -- 1.3.6.1.4.1.2011.2.251.20.1.2.2.15.822.48.1
        theOdxCommandWriteBandwidthExceedsTheThreshold2-Fault NOTIFICATION-TYPE
            OBJECTS { hwStorageAlarmReporting }
            STATUS current
            DESCRIPTION "The Odx Command Write Bandwidth Exceeds The Threshold"
            --#SEVERITY CRITICAL
            ::= { theOdxCommandWriteBandwidthExceedsTheThreshold2 1 }

        -- 1.3.6.1.4.1.2011.2.251.20.1.2.2.15.822.48.2
        theOdxCommandWriteBandwidthExceedsTheThreshold2-Resume NOTIFICATION-TYPE
            OBJECTS { hwStorageAlarmReporting }
            STATUS current
            DESCRIPTION "Recover: The Odx Command Write Bandwidth Exceeds The Threshold"
            --#SEVERITY INFORMATIONAL
            ::= { theOdxCommandWriteBandwidthExceedsTheThreshold2 2 }

        -- 1.3.6.1.4.1.2011.2.251.20.1.2.2.15.822.49
        dataOnTheSecondaryEndIsEarlierThanThatOnThePrimaryEnd2 OBJECT IDENTIFIER ::= { performancemanagement 49 }

        -- 1.3.6.1.4.1.2011.2.251.20.1.2.2.15.822.49.1
        dataOnTheSecondaryEndIsEarlierThanThatOnThePrimaryEnd2-Fault NOTIFICATION-TYPE
            OBJECTS { hwStorageAlarmReporting }
            STATUS current
            DESCRIPTION "Data On The Secondary End Is Earlier Than That On The Primary End"
            --#SEVERITY WARNING
            ::= { dataOnTheSecondaryEndIsEarlierThanThatOnThePrimaryEnd2 1 }

        -- 1.3.6.1.4.1.2011.2.251.20.1.2.2.15.822.49.2
        dataOnTheSecondaryEndIsEarlierThanThatOnThePrimaryEnd2-Resume NOTIFICATION-TYPE
            OBJECTS { hwStorageAlarmReporting }
            STATUS current
            DESCRIPTION "Recover: Data On The Secondary End Is Earlier Than That On The Primary End"
            --#SEVERITY INFORMATIONAL
            ::= { dataOnTheSecondaryEndIsEarlierThanThatOnThePrimaryEnd2 2 }

        -- 1.3.6.1.4.1.2011.2.251.20.1.2.2.15.822.50
        dataOnTheSecondaryEndIsEarlierThanThatOnThePrimaryEnd1 OBJECT IDENTIFIER ::= { performancemanagement 50 }

        -- 1.3.6.1.4.1.2011.2.251.20.1.2.2.15.822.50.1
        dataOnTheSecondaryEndIsEarlierThanThatOnThePrimaryEnd1-Fault NOTIFICATION-TYPE
            OBJECTS { hwStorageAlarmReporting }
            STATUS current
            DESCRIPTION "Data On The Secondary End Is Earlier Than That On The Primary End"
            --#SEVERITY MAJOR
            ::= { dataOnTheSecondaryEndIsEarlierThanThatOnThePrimaryEnd1 1 }

        -- 1.3.6.1.4.1.2011.2.251.20.1.2.2.15.822.50.2
        dataOnTheSecondaryEndIsEarlierThanThatOnThePrimaryEnd1-Resume NOTIFICATION-TYPE
            OBJECTS { hwStorageAlarmReporting }
            STATUS current
            DESCRIPTION "Recover: Data On The Secondary End Is Earlier Than That On The Primary End"
            --#SEVERITY INFORMATIONAL
            ::= { dataOnTheSecondaryEndIsEarlierThanThatOnThePrimaryEnd1 2 }

        -- 1.3.6.1.4.1.2011.2.251.20.1.2.2.15.822.51
        dataOnTheSecondaryEndIsEarlierThanThatOnThePrimaryEnd OBJECT IDENTIFIER ::= { performancemanagement 51 }

        -- 1.3.6.1.4.1.2011.2.251.20.1.2.2.15.822.51.1
        dataOnTheSecondaryEndIsEarlierThanThatOnThePrimaryEnd-Fault NOTIFICATION-TYPE
            OBJECTS { hwStorageAlarmReporting }
            STATUS current
            DESCRIPTION "Data On The Secondary End Is Earlier Than That On The Primary End"
            --#SEVERITY CRITICAL
            ::= { dataOnTheSecondaryEndIsEarlierThanThatOnThePrimaryEnd 1 }

        -- 1.3.6.1.4.1.2011.2.251.20.1.2.2.15.822.51.2
        dataOnTheSecondaryEndIsEarlierThanThatOnThePrimaryEnd-Resume NOTIFICATION-TYPE
            OBJECTS { hwStorageAlarmReporting }
            STATUS current
            DESCRIPTION "Recover: Data On The Secondary End Is Earlier Than That On The Primary End"
            --#SEVERITY INFORMATIONAL
            ::= { dataOnTheSecondaryEndIsEarlierThanThatOnThePrimaryEnd 2 }

        -- 1.3.6.1.4.1.2011.2.251.20.1.2.2.15.822.52
        fluctuationDetectionAlarm OBJECT IDENTIFIER ::= { performancemanagement 52 }

        -- 1.3.6.1.4.1.2011.2.251.20.1.2.2.15.822.52.1
        fluctuationDetectionAlarm-Fault NOTIFICATION-TYPE
            OBJECTS { hwStorageAlarmReporting }
            STATUS current
            DESCRIPTION "Fluctuation Detection Alarm"
            --#SEVERITY WARNING
            ::= { fluctuationDetectionAlarm 1 }

        -- 1.3.6.1.4.1.2011.2.251.20.1.2.2.15.822.52.2
        fluctuationDetectionAlarm-Resume NOTIFICATION-TYPE
            OBJECTS { hwStorageAlarmReporting }
            STATUS current
            DESCRIPTION "Recover: Fluctuation Detection Alarm"
            --#SEVERITY INFORMATIONAL
            ::= { fluctuationDetectionAlarm 2 }

        -- 1.3.6.1.4.1.2011.2.251.20.1.2.2.15.822.308
        exceedThresholdWarning OBJECT IDENTIFIER ::= { performancemanagement 308 }

        -- 1.3.6.1.4.1.2011.2.251.20.1.2.2.15.822.308.1
        exceedThresholdWarning-Fault NOTIFICATION-TYPE
            OBJECTS { hwStorageAlarmReporting }
            STATUS current
            DESCRIPTION "The Performance Indicator Exceeded The Threshold"
            --#SEVERITY WARNING
            ::= { exceedThresholdWarning 1 }

        -- 1.3.6.1.4.1.2011.2.251.20.1.2.2.15.822.308.2
        exceedThresholdWarning-Resume NOTIFICATION-TYPE
            OBJECTS { hwStorageAlarmReporting }
            STATUS current
            DESCRIPTION "Recover: The Performance Indicator Exceeded The Threshold"
            --#SEVERITY INFORMATIONAL
            ::= { exceedThresholdWarning 2 }

        -- 1.3.6.1.4.1.2011.2.251.20.1.2.2.15.822.309
        exceedThresholdMajor OBJECT IDENTIFIER ::= { performancemanagement 309 }

        -- 1.3.6.1.4.1.2011.2.251.20.1.2.2.15.822.309.1
        exceedThresholdMajor-Fault NOTIFICATION-TYPE
            OBJECTS { hwStorageAlarmReporting }
            STATUS current
            DESCRIPTION "The Performance Indicator Exceeded The Threshold"
            --#SEVERITY MAJOR
            ::= { exceedThresholdMajor 1 }

        -- 1.3.6.1.4.1.2011.2.251.20.1.2.2.15.822.309.2
        exceedThresholdMajor-Resume NOTIFICATION-TYPE
            OBJECTS { hwStorageAlarmReporting }
            STATUS current
            DESCRIPTION "Recover: The Performance Indicator Exceeded The Threshold"
            --#SEVERITY INFORMATIONAL
            ::= { exceedThresholdMajor 2 }

        -- 1.3.6.1.4.1.2011.2.251.20.1.2.2.15.822.310
        exceedThresholdCritical OBJECT IDENTIFIER ::= { performancemanagement 310 }

        -- 1.3.6.1.4.1.2011.2.251.20.1.2.2.15.822.310.1
        exceedThresholdCritical-Fault NOTIFICATION-TYPE
            OBJECTS { hwStorageAlarmReporting }
            STATUS current
            DESCRIPTION "The Performance Indicator Exceeded The Threshold"
            --#SEVERITY CRITICAL
            ::= { exceedThresholdCritical 1 }

        -- 1.3.6.1.4.1.2011.2.251.20.1.2.2.15.822.310.2
        exceedThresholdCritical-Resume NOTIFICATION-TYPE
            OBJECTS { hwStorageAlarmReporting }
            STATUS current
            DESCRIPTION "Recover: The Performance Indicator Exceeded The Threshold"
            --#SEVERITY INFORMATIONAL
            ::= { exceedThresholdCritical 2 }

        -- 1.3.6.1.4.1.2011.2.251.20.1.2.2.15.823
        serveragent OBJECT IDENTIFIER ::= { oidBasedTrap 823 }

        -- 1.3.6.1.4.1.2011.2.251.20.1.2.2.15.823.1
        theCAServerIsUnavailable OBJECT IDENTIFIER ::= { serveragent 1 }

        -- 1.3.6.1.4.1.2011.2.251.20.1.2.2.15.823.1.1
        theCAServerIsUnavailable-Fault NOTIFICATION-TYPE
            OBJECTS { hwStorageAlarmReporting }
            STATUS current
            DESCRIPTION "The CA Server Is Unavailable"
            --#SEVERITY WARNING
            ::= { theCAServerIsUnavailable 1 }

        -- 1.3.6.1.4.1.2011.2.251.20.1.2.2.15.823.1.2
        theCAServerIsUnavailable-Resume NOTIFICATION-TYPE
            OBJECTS { hwStorageAlarmReporting }
            STATUS current
            DESCRIPTION "Recover: The CA Server Is Unavailable"
            --#SEVERITY INFORMATIONAL
            ::= { theCAServerIsUnavailable 2 }

        -- 1.3.6.1.4.1.2011.2.251.20.1.2.2.15.823.2
        serverIsUnavailable OBJECT IDENTIFIER ::= { serveragent 2 }

        -- 1.3.6.1.4.1.2011.2.251.20.1.2.2.15.823.2.1
        serverIsUnavailable-Fault NOTIFICATION-TYPE
            OBJECTS { hwStorageAlarmReporting }
            STATUS current
            DESCRIPTION "Server Is Unavailable"
            --#SEVERITY WARNING
            ::= { serverIsUnavailable 1 }

        -- 1.3.6.1.4.1.2011.2.251.20.1.2.2.15.823.2.2
        serverIsUnavailable-Resume NOTIFICATION-TYPE
            OBJECTS { hwStorageAlarmReporting }
            STATUS current
            DESCRIPTION "Recover: Server Is Unavailable"
            --#SEVERITY INFORMATIONAL
            ::= { serverIsUnavailable 2 }

        -- 1.3.6.1.4.1.2011.2.251.20.1.2.2.15.823.3
        theSMTPServerIsUnavailable OBJECT IDENTIFIER ::= { serveragent 3 }

        -- 1.3.6.1.4.1.2011.2.251.20.1.2.2.15.823.3.1
        theSMTPServerIsUnavailable-Fault NOTIFICATION-TYPE
            OBJECTS { hwStorageAlarmReporting }
            STATUS current
            DESCRIPTION "The SMTP Server Is Unavailable"
            --#SEVERITY WARNING
            ::= { theSMTPServerIsUnavailable 1 }

        -- 1.3.6.1.4.1.2011.2.251.20.1.2.2.15.823.3.2
        theSMTPServerIsUnavailable-Resume NOTIFICATION-TYPE
            OBJECTS { hwStorageAlarmReporting }
            STATUS current
            DESCRIPTION "Recover: The SMTP Server Is Unavailable"
            --#SEVERITY INFORMATIONAL
            ::= { theSMTPServerIsUnavailable 2 }

        -- 1.3.6.1.4.1.2011.2.251.20.1.2.2.15.823.4
        syslogServerIsUnavailable OBJECT IDENTIFIER ::= { serveragent 4 }

        -- 1.3.6.1.4.1.2011.2.251.20.1.2.2.15.823.4.1
        syslogServerIsUnavailable-Fault NOTIFICATION-TYPE
            OBJECTS { hwStorageAlarmReporting }
            STATUS current
            DESCRIPTION "Syslog Server Is Unavailable"
            --#SEVERITY WARNING
            ::= { syslogServerIsUnavailable 1 }

        -- 1.3.6.1.4.1.2011.2.251.20.1.2.2.15.823.4.2
        syslogServerIsUnavailable-Resume NOTIFICATION-TYPE
            OBJECTS { hwStorageAlarmReporting }
            STATUS current
            DESCRIPTION "Recover: Syslog Server Is Unavailable"
            --#SEVERITY INFORMATIONAL
            ::= { syslogServerIsUnavailable 2 }

        -- 1.3.6.1.4.1.2011.2.251.20.1.2.2.15.823.5
        alarmDumpServerIsUnavailable OBJECT IDENTIFIER ::= { serveragent 5 }

        -- 1.3.6.1.4.1.2011.2.251.20.1.2.2.15.823.5.1
        alarmDumpServerIsUnavailable-Fault NOTIFICATION-TYPE
            OBJECTS { hwStorageAlarmReporting }
            STATUS current
            DESCRIPTION "Alarm Dump Server Is Unavailable"
            --#SEVERITY WARNING
            ::= { alarmDumpServerIsUnavailable 1 }

        -- 1.3.6.1.4.1.2011.2.251.20.1.2.2.15.823.5.2
        alarmDumpServerIsUnavailable-Resume NOTIFICATION-TYPE
            OBJECTS { hwStorageAlarmReporting }
            STATUS current
            DESCRIPTION "Recover: Alarm Dump Server Is Unavailable"
            --#SEVERITY INFORMATIONAL
            ::= { alarmDumpServerIsUnavailable 2 }

        -- 1.3.6.1.4.1.2011.2.251.20.1.2.2.15.823.6
        performanceDumpServerIsUnavailable OBJECT IDENTIFIER ::= { serveragent 6 }

        -- 1.3.6.1.4.1.2011.2.251.20.1.2.2.15.823.6.1
        performanceDumpServerIsUnavailable-Fault NOTIFICATION-TYPE
            OBJECTS { hwStorageAlarmReporting }
            STATUS current
            DESCRIPTION "Performance Dump Server Is Unavailable"
            --#SEVERITY WARNING
            ::= { performanceDumpServerIsUnavailable 1 }

        -- 1.3.6.1.4.1.2011.2.251.20.1.2.2.15.823.6.2
        performanceDumpServerIsUnavailable-Resume NOTIFICATION-TYPE
            OBJECTS { hwStorageAlarmReporting }
            STATUS current
            DESCRIPTION "Recover: Performance Dump Server Is Unavailable"
            --#SEVERITY INFORMATIONAL
            ::= { performanceDumpServerIsUnavailable 2 }

        -- 1.3.6.1.4.1.2011.2.251.20.1.2.2.15.823.7
        lDAPServerIsUnavailable OBJECT IDENTIFIER ::= { serveragent 7 }

        -- 1.3.6.1.4.1.2011.2.251.20.1.2.2.15.823.7.1
        lDAPServerIsUnavailable-Fault NOTIFICATION-TYPE
            OBJECTS { hwStorageAlarmReporting }
            STATUS current
            DESCRIPTION "LDAP Server Is Unavailable"
            --#SEVERITY WARNING
            ::= { lDAPServerIsUnavailable 1 }

        -- 1.3.6.1.4.1.2011.2.251.20.1.2.2.15.823.7.2
        lDAPServerIsUnavailable-Resume NOTIFICATION-TYPE
            OBJECTS { hwStorageAlarmReporting }
            STATUS current
            DESCRIPTION "Recover: LDAP Server Is Unavailable"
            --#SEVERITY INFORMATIONAL
            ::= { lDAPServerIsUnavailable 2 }

        -- 1.3.6.1.4.1.2011.2.251.20.1.2.2.15.823.8
        keyFileBackupServerIsUnavailable OBJECT IDENTIFIER ::= { serveragent 8 }

        -- 1.3.6.1.4.1.2011.2.251.20.1.2.2.15.823.8.1
        keyFileBackupServerIsUnavailable-Fault NOTIFICATION-TYPE
            OBJECTS { hwStorageAlarmReporting }
            STATUS current
            DESCRIPTION "Key File Backup Server Is Unavailable"
            --#SEVERITY WARNING
            ::= { keyFileBackupServerIsUnavailable 1 }

        -- 1.3.6.1.4.1.2011.2.251.20.1.2.2.15.823.8.2
        keyFileBackupServerIsUnavailable-Resume NOTIFICATION-TYPE
            OBJECTS { hwStorageAlarmReporting }
            STATUS current
            DESCRIPTION "Recover: Key File Backup Server Is Unavailable"
            --#SEVERITY INFORMATIONAL
            ::= { keyFileBackupServerIsUnavailable 2 }

        -- 1.3.6.1.4.1.2011.2.251.20.1.2.2.15.823.10
        sSOServerIsUnavailable OBJECT IDENTIFIER ::= { serveragent 10 }

        -- 1.3.6.1.4.1.2011.2.251.20.1.2.2.15.823.10.1
        sSOServerIsUnavailable-Fault NOTIFICATION-TYPE
            OBJECTS { hwStorageAlarmReporting }
            STATUS current
            DESCRIPTION "SSO Server Is Unavailable"
            --#SEVERITY MAJOR
            ::= { sSOServerIsUnavailable 1 }

        -- 1.3.6.1.4.1.2011.2.251.20.1.2.2.15.823.10.2
        sSOServerIsUnavailable-Resume NOTIFICATION-TYPE
            OBJECTS { hwStorageAlarmReporting }
            STATUS current
            DESCRIPTION "Recover: SSO Server Is Unavailable"
            --#SEVERITY INFORMATIONAL
            ::= { sSOServerIsUnavailable 2 }

        -- 1.3.6.1.4.1.2011.2.251.20.1.2.2.15.823.11
        theRADIUSServerIsUnavailable OBJECT IDENTIFIER ::= { serveragent 11 }

        -- 1.3.6.1.4.1.2011.2.251.20.1.2.2.15.823.11.1
        theRADIUSServerIsUnavailable-Fault NOTIFICATION-TYPE
            OBJECTS { hwStorageAlarmReporting }
            STATUS current
            DESCRIPTION "The RADIUS Server Is Unavailable"
            --#SEVERITY MAJOR
            ::= { theRADIUSServerIsUnavailable 1 }

        -- 1.3.6.1.4.1.2011.2.251.20.1.2.2.15.823.11.2
        theRADIUSServerIsUnavailable-Resume NOTIFICATION-TYPE
            OBJECTS { hwStorageAlarmReporting }
            STATUS current
            DESCRIPTION "Recover: The RADIUS Server Is Unavailable"
            --#SEVERITY INFORMATIONAL
            ::= { theRADIUSServerIsUnavailable 2 }

        -- 1.3.6.1.4.1.2011.2.251.20.1.2.2.15.823.12
        serverLinkIsDown OBJECT IDENTIFIER ::= { serveragent 12 }

        -- 1.3.6.1.4.1.2011.2.251.20.1.2.2.15.823.12.1
        serverLinkIsDown-Fault NOTIFICATION-TYPE
            OBJECTS { hwStorageAlarmReporting }
            STATUS current
            DESCRIPTION "Server Link Is Down"
            --#SEVERITY CRITICAL
            ::= { serverLinkIsDown 1 }

        -- 1.3.6.1.4.1.2011.2.251.20.1.2.2.15.823.12.2
        serverLinkIsDown-Resume NOTIFICATION-TYPE
            OBJECTS { hwStorageAlarmReporting }
            STATUS current
            DESCRIPTION "Recover: Server Link Is Down"
            --#SEVERITY INFORMATIONAL
            ::= { serverLinkIsDown 2 }

        -- 1.3.6.1.4.1.2011.2.251.20.1.2.2.15.6004
        infrastructure OBJECT IDENTIFIER ::= { oidBasedTrap 6004 }

        -- 1.3.6.1.4.1.2011.2.251.20.1.2.2.15.6004.22
        smartDedupeAndSmartCompressionAccelerationModuleIsFaulty OBJECT IDENTIFIER ::= { infrastructure 22 }

        -- 1.3.6.1.4.1.2011.2.251.20.1.2.2.15.6004.22.1
        smartDedupeAndSmartCompressionAccelerationModuleIsFaulty-Fault NOTIFICATION-TYPE
            OBJECTS { hwStorageAlarmReporting }
            STATUS current
            DESCRIPTION "Failed To Connect The Data Reduction Acceleration Module"
            --#SEVERITY MAJOR
            ::= { smartDedupeAndSmartCompressionAccelerationModuleIsFaulty 1 }

        -- 1.3.6.1.4.1.2011.2.251.20.1.2.2.15.6004.22.2
        smartDedupeAndSmartCompressionAccelerationModuleIsFaulty-Resume NOTIFICATION-TYPE
            OBJECTS { hwStorageAlarmReporting }
            STATUS current
            DESCRIPTION "Recover: Failed To Connect The Data Reduction Acceleration Module"
            --#SEVERITY INFORMATIONAL
            ::= { smartDedupeAndSmartCompressionAccelerationModuleIsFaulty 2 }

        -- 1.3.6.1.4.1.2011.2.251.20.1.2.2.15.8001
        dme OBJECT IDENTIFIER ::= { oidBasedTrap 8001 }

        -- 1.3.6.1.4.1.2011.2.251.20.1.2.2.15.8001.14
        smartmobilityExclusionWithAntiRansomware OBJECT IDENTIFIER ::= { dme 14 }

        -- 1.3.6.1.4.1.2011.2.251.20.1.2.2.15.8001.14.1
        smartmobilityExclusionWithAntiRansomware-Fault NOTIFICATION-TYPE
            OBJECTS { hwStorageAlarmReporting }
            STATUS current
            DESCRIPTION "The SmartMobility Feature Is Exclusive With The Ransomware Protection Feature And Is Enabled For The File System"
            --#SEVERITY WARNING
            ::= { smartmobilityExclusionWithAntiRansomware 1 }

        -- 1.3.6.1.4.1.2011.2.251.20.1.2.2.15.8001.14.2
        smartmobilityExclusionWithAntiRansomware-Resume NOTIFICATION-TYPE
            OBJECTS { hwStorageAlarmReporting }
            STATUS current
            DESCRIPTION "Recover: The SmartMobility Feature Is Exclusive With The Ransomware Protection Feature And Is Enabled For The File System"
            --#SEVERITY INFORMATIONAL
            ::= { smartmobilityExclusionWithAntiRansomware 2 }

        -- 1.3.6.1.4.1.2011.2.251.20.1.2.2.15.8002
        dee OBJECT IDENTIFIER ::= { oidBasedTrap 8002 }

        -- 1.3.6.1.4.1.2011.2.251.20.1.2.2.15.8002.2
        failedToDeleteAFileSystemShare OBJECT IDENTIFIER ::= { dee 2 }

        -- 1.3.6.1.4.1.2011.2.251.20.1.2.2.15.8002.2.1
        failedToDeleteAFileSystemShare-Fault NOTIFICATION-TYPE
            OBJECTS { hwStorageAlarmReporting }
            STATUS current
            DESCRIPTION "Failed To Delete A File System Share"
            --#SEVERITY WARNING
            ::= { failedToDeleteAFileSystemShare 1 }

        -- 1.3.6.1.4.1.2011.2.251.20.1.2.2.15.8002.2.2
        failedToDeleteAFileSystemShare-Resume NOTIFICATION-TYPE
            OBJECTS { hwStorageAlarmReporting }
            STATUS current
            DESCRIPTION "Recover: Failed To Delete A File System Share"
            --#SEVERITY INFORMATIONAL
            ::= { failedToDeleteAFileSystemShare 2 }

        -- 1.3.6.1.4.1.2011.2.251.20.1.2.2.15.8002.8
        failedToDeleteTheFileSystemSnapshot OBJECT IDENTIFIER ::= { dee 8 }

        -- 1.3.6.1.4.1.2011.2.251.20.1.2.2.15.8002.8.1
        failedToDeleteTheFileSystemSnapshot-Fault NOTIFICATION-TYPE
            OBJECTS { hwStorageAlarmReporting }
            STATUS current
            DESCRIPTION "Failed To Delete The File System Snapshot"
            --#SEVERITY WARNING
            ::= { failedToDeleteTheFileSystemSnapshot 1 }

        -- 1.3.6.1.4.1.2011.2.251.20.1.2.2.15.8002.8.2
        failedToDeleteTheFileSystemSnapshot-Resume NOTIFICATION-TYPE
            OBJECTS { hwStorageAlarmReporting }
            STATUS current
            DESCRIPTION "Recover: Failed To Delete The File System Snapshot"
            --#SEVERITY INFORMATIONAL
            ::= { failedToDeleteTheFileSystemSnapshot 2 }

        -- 1.3.6.1.4.1.2011.2.251.20.1.2.2.15.8002.9
        failedToDeleteAFileSystem OBJECT IDENTIFIER ::= { dee 9 }

        -- 1.3.6.1.4.1.2011.2.251.20.1.2.2.15.8002.9.1
        failedToDeleteAFileSystem-Fault NOTIFICATION-TYPE
            OBJECTS { hwStorageAlarmReporting }
            STATUS current
            DESCRIPTION "Failed To Delete A File System"
            --#SEVERITY WARNING
            ::= { failedToDeleteAFileSystem 1 }

        -- 1.3.6.1.4.1.2011.2.251.20.1.2.2.15.8002.9.2
        failedToDeleteAFileSystem-Resume NOTIFICATION-TYPE
            OBJECTS { hwStorageAlarmReporting }
            STATUS current
            DESCRIPTION "Recover: Failed To Delete A File System"
            --#SEVERITY INFORMATIONAL
            ::= { failedToDeleteAFileSystem 2 }

        -- 1.3.6.1.4.1.2011.2.251.20.1.2.2.15.8002.10
        failedToPerformRollbackUsingTheFileSystemSnapshot OBJECT IDENTIFIER ::= { dee 10 }

        -- 1.3.6.1.4.1.2011.2.251.20.1.2.2.15.8002.10.1
        failedToPerformRollbackUsingTheFileSystemSnapshot-Fault NOTIFICATION-TYPE
            OBJECTS { hwStorageAlarmReporting }
            STATUS current
            DESCRIPTION "Failed To Perform Rollback Using The File System Snapshot"
            --#SEVERITY MAJOR
            ::= { failedToPerformRollbackUsingTheFileSystemSnapshot 1 }

        -- 1.3.6.1.4.1.2011.2.251.20.1.2.2.15.8002.10.2
        failedToPerformRollbackUsingTheFileSystemSnapshot-Resume NOTIFICATION-TYPE
            OBJECTS { hwStorageAlarmReporting }
            STATUS current
            DESCRIPTION "Recover: Failed To Perform Rollback Using The File System Snapshot"
            --#SEVERITY INFORMATIONAL
            ::= { failedToPerformRollbackUsingTheFileSystemSnapshot 2 }

        -- 1.3.6.1.4.1.2011.2.251.20.1.2.2.15.8002.15
        resourceIsInfected OBJECT IDENTIFIER ::= { dee 15 }

        -- 1.3.6.1.4.1.2011.2.251.20.1.2.2.15.8002.15.1
        resourceIsInfected-Fault NOTIFICATION-TYPE
            OBJECTS { hwStorageAlarmReporting }
            STATUS current
            DESCRIPTION "Copy Infected By Ransomware"
            --#SEVERITY MAJOR
            ::= { resourceIsInfected 1 }

        -- 1.3.6.1.4.1.2011.2.251.20.1.2.2.15.8002.15.2
        resourceIsInfected-Resume NOTIFICATION-TYPE
            OBJECTS { hwStorageAlarmReporting }
            STATUS current
            DESCRIPTION "Recover: Copy Infected By Ransomware"
            --#SEVERITY INFORMATIONAL
            ::= { resourceIsInfected 2 }

        -- 1.3.6.1.4.1.2011.2.251.20.1.2.2.15.8002.16
        failedToCancelApplyingTheFileNameExtensionFilteringRuleAssociatedWithTheVStore OBJECT IDENTIFIER ::= { dee 16 }

        -- 1.3.6.1.4.1.2011.2.251.20.1.2.2.15.8002.16.1
        failedToCancelApplyingTheFileNameExtensionFilteringRuleAssociatedWithTheVStore-Fault NOTIFICATION-TYPE
            OBJECTS { hwStorageAlarmReporting }
            STATUS current
            DESCRIPTION "Failed To Cancel Applying The File Name Extension Filtering Rule Associated With The VStore"
            --#SEVERITY WARNING
            ::= { failedToCancelApplyingTheFileNameExtensionFilteringRuleAssociatedWithTheVStore 1 }

        -- 1.3.6.1.4.1.2011.2.251.20.1.2.2.15.8002.16.2
        failedToCancelApplyingTheFileNameExtensionFilteringRuleAssociatedWithTheVStore-Resume NOTIFICATION-TYPE
            OBJECTS { hwStorageAlarmReporting }
            STATUS current
            DESCRIPTION "Recover: Failed To Cancel Applying The File Name Extension Filtering Rule Associated With The VStore"
            --#SEVERITY INFORMATIONAL
            ::= { failedToCancelApplyingTheFileNameExtensionFilteringRuleAssociatedWithTheVStore 2 }

        -- 1.3.6.1.4.1.2011.2.251.20.1.2.2.15.8002.17
        failedToApplyTheFileNameExtensionFilteringRuleAssociatedWithTheVStore OBJECT IDENTIFIER ::= { dee 17 }

        -- 1.3.6.1.4.1.2011.2.251.20.1.2.2.15.8002.17.1
        failedToApplyTheFileNameExtensionFilteringRuleAssociatedWithTheVStore-Fault NOTIFICATION-TYPE
            OBJECTS { hwStorageAlarmReporting }
            STATUS current
            DESCRIPTION "Failed To Apply The File Name Extension Filtering Rule Associated With The VStore"
            --#SEVERITY WARNING
            ::= { failedToApplyTheFileNameExtensionFilteringRuleAssociatedWithTheVStore 1 }

        -- 1.3.6.1.4.1.2011.2.251.20.1.2.2.15.8002.17.2
        failedToApplyTheFileNameExtensionFilteringRuleAssociatedWithTheVStore-Resume NOTIFICATION-TYPE
            OBJECTS { hwStorageAlarmReporting }
            STATUS current
            DESCRIPTION "Recover: Failed To Apply The File Name Extension Filtering Rule Associated With The VStore"
            --#SEVERITY INFORMATIONAL
            ::= { failedToApplyTheFileNameExtensionFilteringRuleAssociatedWithTheVStore 2 }

        -- 1.3.6.1.4.1.2011.2.251.20.1.2.2.15.8002.18
        nasInfected OBJECT IDENTIFIER ::= { dee 18 }

        -- 1.3.6.1.4.1.2011.2.251.20.1.2.2.15.8002.18.1
        nasInfected-Fault NOTIFICATION-TYPE
            OBJECTS { hwStorageAlarmReporting }
            STATUS current
            DESCRIPTION "File System Of A VStore Infected By Ransomware"
            --#SEVERITY MAJOR
            ::= { nasInfected 1 }

        -- 1.3.6.1.4.1.2011.2.251.20.1.2.2.15.8002.18.2
        nasInfected-Resume NOTIFICATION-TYPE
            OBJECTS { hwStorageAlarmReporting }
            STATUS current
            DESCRIPTION "Recover: File System Of A VStore Infected By Ransomware"
            --#SEVERITY INFORMATIONAL
            ::= { nasInfected 2 }

        -- 1.3.6.1.4.1.2011.2.251.20.1.2.2.15.8002.19
        intelligentDetectionAbnormal OBJECT IDENTIFIER ::= { dee 19 }

        -- 1.3.6.1.4.1.2011.2.251.20.1.2.2.15.8002.19.1
        intelligentDetectionAbnormal-Fault NOTIFICATION-TYPE
            OBJECTS { hwStorageAlarmReporting }
            STATUS current
            DESCRIPTION "An Exception Occurred During Intelligent Ransomware Detection"
            --#SEVERITY WARNING
            ::= { intelligentDetectionAbnormal 1 }

        -- 1.3.6.1.4.1.2011.2.251.20.1.2.2.15.8002.19.2
        intelligentDetectionAbnormal-Resume NOTIFICATION-TYPE
            OBJECTS { hwStorageAlarmReporting }
            STATUS current
            DESCRIPTION "Recover: An Exception Occurred During Intelligent Ransomware Detection"
            --#SEVERITY INFORMATIONAL
            ::= { intelligentDetectionAbnormal 2 }

        -- 1.3.6.1.4.1.2011.2.251.20.1.2.2.15.8002.20
        theNumberOfIndexJobsReachesTheUpperLimit OBJECT IDENTIFIER ::= { dee 20 }

        -- 1.3.6.1.4.1.2011.2.251.20.1.2.2.15.8002.20.1
        theNumberOfIndexJobsReachesTheUpperLimit-Fault NOTIFICATION-TYPE
            OBJECTS { hwStorageAlarmReporting }
            STATUS current
            DESCRIPTION "The Number Of Index Jobs Reaches The Upper Limit"
            --#SEVERITY WARNING
            ::= { theNumberOfIndexJobsReachesTheUpperLimit 1 }

        -- 1.3.6.1.4.1.2011.2.251.20.1.2.2.15.8002.20.2
        theNumberOfIndexJobsReachesTheUpperLimit-Resume NOTIFICATION-TYPE
            OBJECTS { hwStorageAlarmReporting }
            STATUS current
            DESCRIPTION "Recover: The Number Of Index Jobs Reaches The Upper Limit"
            --#SEVERITY INFORMATIONAL
            ::= { theNumberOfIndexJobsReachesTheUpperLimit 2 }

        -- 1.3.6.1.4.1.2011.2.251.20.1.2.2.15.8002.21
        failedToCreateACopyIndex OBJECT IDENTIFIER ::= { dee 21 }

        -- 1.3.6.1.4.1.2011.2.251.20.1.2.2.15.8002.21.1
        failedToCreateACopyIndex-Fault NOTIFICATION-TYPE
            OBJECTS { hwStorageAlarmReporting }
            STATUS current
            DESCRIPTION "Failed To Create A Copy Index"
            --#SEVERITY MAJOR
            ::= { failedToCreateACopyIndex 1 }

        -- 1.3.6.1.4.1.2011.2.251.20.1.2.2.15.8002.21.2
        failedToCreateACopyIndex-Resume NOTIFICATION-TYPE
            OBJECTS { hwStorageAlarmReporting }
            STATUS current
            DESCRIPTION "Recover: Failed To Create A Copy Index"
            --#SEVERITY INFORMATIONAL
            ::= { failedToCreateACopyIndex 2 }

        -- 1.3.6.1.4.1.2011.2.251.20.1.2.2.15.8002.30
        fileNameExtensionFilteringRulesCannotBeConfiguredForTheSecondaryFileSystemOfTheVStore OBJECT IDENTIFIER ::= { dee 30 }

        -- 1.3.6.1.4.1.2011.2.251.20.1.2.2.15.8002.30.1
        fileNameExtensionFilteringRulesCannotBeConfiguredForTheSecondaryFileSystemOfTheVStore-Fault NOTIFICATION-TYPE
            OBJECTS { hwStorageAlarmReporting }
            STATUS current
            DESCRIPTION "File Name Extension Filtering Rules Cannot Be Configured For The Secondary File System Of The VStore"
            --#SEVERITY WARNING
            ::= { fileNameExtensionFilteringRulesCannotBeConfiguredForTheSecondaryFileSystemOfTheVStore 1 }

        -- 1.3.6.1.4.1.2011.2.251.20.1.2.2.15.8002.30.2
        fileNameExtensionFilteringRulesCannotBeConfiguredForTheSecondaryFileSystemOfTheVStore-Resume NOTIFICATION-TYPE
            OBJECTS { hwStorageAlarmReporting }
            STATUS current
            DESCRIPTION "Recover: File Name Extension Filtering Rules Cannot Be Configured For The Secondary File System Of The VStore"
            --#SEVERITY INFORMATIONAL
            ::= { fileNameExtensionFilteringRulesCannotBeConfiguredForTheSecondaryFileSystemOfTheVStore 2 }

        -- 1.3.6.1.4.1.2011.2.251.20.1.2.2.15.8002.38
        failedToDeployHoneyfiles OBJECT IDENTIFIER ::= { dee 38 }

        -- 1.3.6.1.4.1.2011.2.251.20.1.2.2.15.8002.38.1
        failedToDeployHoneyfiles-Fault NOTIFICATION-TYPE
            OBJECTS { hwStorageAlarmReporting }
            STATUS current
            DESCRIPTION "Failed To Deploy Honeyfiles"
            --#SEVERITY WARNING
            ::= { failedToDeployHoneyfiles 1 }

        -- 1.3.6.1.4.1.2011.2.251.20.1.2.2.15.8002.38.2
        failedToDeployHoneyfiles-Resume NOTIFICATION-TYPE
            OBJECTS { hwStorageAlarmReporting }
            STATUS current
            DESCRIPTION "Recover: Failed To Deploy Honeyfiles"
            --#SEVERITY INFORMATIONAL
            ::= { failedToDeployHoneyfiles 2 }

        -- 1.3.6.1.4.1.2011.2.251.20.1.2.2.15.8002.39
        fileSystemShareConfigurationIsAbnormal OBJECT IDENTIFIER ::= { dee 39 }

        -- 1.3.6.1.4.1.2011.2.251.20.1.2.2.15.8002.39.1
        fileSystemShareConfigurationIsAbnormal-Fault NOTIFICATION-TYPE
            OBJECTS { hwStorageAlarmReporting }
            STATUS current
            DESCRIPTION "File System Share Configuration Is Abnormal"
            --#SEVERITY WARNING
            ::= { fileSystemShareConfigurationIsAbnormal 1 }

        -- 1.3.6.1.4.1.2011.2.251.20.1.2.2.15.8002.39.2
        fileSystemShareConfigurationIsAbnormal-Resume NOTIFICATION-TYPE
            OBJECTS { hwStorageAlarmReporting }
            STATUS current
            DESCRIPTION "Recover: File System Share Configuration Is Abnormal"
            --#SEVERITY INFORMATIONAL
            ::= { fileSystemShareConfigurationIsAbnormal 2 }

        -- 1.3.6.1.4.1.2011.2.251.20.1.2.2.15.8002.40
        antiRansomwareDetectFailedDueToSnapshotNotExists OBJECT IDENTIFIER ::= { dee 40 }

        -- 1.3.6.1.4.1.2011.2.251.20.1.2.2.15.8002.40.1
        antiRansomwareDetectFailedDueToSnapshotNotExists-Fault NOTIFICATION-TYPE
            OBJECTS { hwStorageAlarmReporting }
            STATUS current
            DESCRIPTION "An Exception Occurred During Intelligent Ransomware Detection Because The Snapshot Does Not Exist"
            --#SEVERITY WARNING
            ::= { antiRansomwareDetectFailedDueToSnapshotNotExists 1 }

        -- 1.3.6.1.4.1.2011.2.251.20.1.2.2.15.8002.40.2
        antiRansomwareDetectFailedDueToSnapshotNotExists-Resume NOTIFICATION-TYPE
            OBJECTS { hwStorageAlarmReporting }
            STATUS current
            DESCRIPTION "Recover: An Exception Occurred During Intelligent Ransomware Detection Because The Snapshot Does Not Exist"
            --#SEVERITY INFORMATIONAL
            ::= { antiRansomwareDetectFailedDueToSnapshotNotExists 2 }

        -- 1.3.6.1.4.1.2011.2.251.20.1.2.2.15.8002.43
        lunInfected OBJECT IDENTIFIER ::= { dee 43 }

        -- 1.3.6.1.4.1.2011.2.251.20.1.2.2.15.8002.43.1
        lunInfected-Fault NOTIFICATION-TYPE
            OBJECTS { hwStorageAlarmReporting }
            STATUS current
            DESCRIPTION "Ransomware Infection Is Detected In A LUN Of The VStore"
            --#SEVERITY MAJOR
            ::= { lunInfected 1 }

        -- 1.3.6.1.4.1.2011.2.251.20.1.2.2.15.8002.43.2
        lunInfected-Resume NOTIFICATION-TYPE
            OBJECTS { hwStorageAlarmReporting }
            STATUS current
            DESCRIPTION "Recover: Ransomware Infection Is Detected In A LUN Of The VStore"
            --#SEVERITY INFORMATIONAL
            ::= { lunInfected 2 }

        -- 1.3.6.1.4.1.2011.2.251.20.1.2.2.15.8002.49
        enableRansomwareFileInterceptionFaulty OBJECT IDENTIFIER ::= { dee 49 }

        -- 1.3.6.1.4.1.2011.2.251.20.1.2.2.15.8002.49.1
        enableRansomwareFileInterceptionFaulty-Fault NOTIFICATION-TYPE
            OBJECTS { hwStorageAlarmReporting }
            STATUS current
            DESCRIPTION "An Exception Occurred When Ransomware File Interception Was Being Enabled For The VStore"
            --#SEVERITY WARNING
            ::= { enableRansomwareFileInterceptionFaulty 1 }

        -- 1.3.6.1.4.1.2011.2.251.20.1.2.2.15.8002.49.2
        enableRansomwareFileInterceptionFaulty-Resume NOTIFICATION-TYPE
            OBJECTS { hwStorageAlarmReporting }
            STATUS current
            DESCRIPTION "Recover: An Exception Occurred When Ransomware File Interception Was Being Enabled For The VStore"
            --#SEVERITY INFORMATIONAL
            ::= { enableRansomwareFileInterceptionFaulty 2 }

        -- 1.3.6.1.4.1.2011.2.251.20.1.2.2.15.8002.50
        disableRansomwareFileInterceptionFaulty OBJECT IDENTIFIER ::= { dee 50 }

        -- 1.3.6.1.4.1.2011.2.251.20.1.2.2.15.8002.50.1
        disableRansomwareFileInterceptionFaulty-Fault NOTIFICATION-TYPE
            OBJECTS { hwStorageAlarmReporting }
            STATUS current
            DESCRIPTION "An Exception Occurred When Ransomware File Interception Was Being Disabled For The VStore"
            --#SEVERITY WARNING
            ::= { disableRansomwareFileInterceptionFaulty 1 }

        -- 1.3.6.1.4.1.2011.2.251.20.1.2.2.15.8002.50.2
        disableRansomwareFileInterceptionFaulty-Resume NOTIFICATION-TYPE
            OBJECTS { hwStorageAlarmReporting }
            STATUS current
            DESCRIPTION "Recover: An Exception Occurred When Ransomware File Interception Was Being Disabled For The VStore"
            --#SEVERITY INFORMATIONAL
            ::= { disableRansomwareFileInterceptionFaulty 2 }

        -- 1.3.6.1.4.1.2011.2.251.20.1.2.2.15.8003
        dps OBJECT IDENTIFIER ::= { oidBasedTrap 8003 }

        -- 1.3.6.1.4.1.2011.2.251.20.1.2.2.15.8003.13
        jobFailed OBJECT IDENTIFIER ::= { dps 13 }

        -- 1.3.6.1.4.1.2011.2.251.20.1.2.2.15.8003.13.1
        jobFailed-Fault NOTIFICATION-TYPE
            OBJECTS { hwStorageAlarmReporting }
            STATUS current
            DESCRIPTION "Job Failed"
            --#SEVERITY MAJOR
            ::= { jobFailed 1 }

        -- 1.3.6.1.4.1.2011.2.251.20.1.2.2.15.8003.13.2
        jobFailed-Resume NOTIFICATION-TYPE
            OBJECTS { hwStorageAlarmReporting }
            STATUS current
            DESCRIPTION "Recover: Job Failed"
            --#SEVERITY INFORMATIONAL
            ::= { jobFailed 2 }

        -- 1.3.6.1.4.1.2011.2.251.20.1.2.2.15.8005
        dpcc OBJECT IDENTIFIER ::= { oidBasedTrap 8005 }

        -- 1.3.6.1.4.1.2011.2.251.20.1.2.2.15.8005.9
        abnormalLogLevel OBJECT IDENTIFIER ::= { dpcc 9 }

        -- 1.3.6.1.4.1.2011.2.251.20.1.2.2.15.8005.9.1
        abnormalLogLevel-Fault NOTIFICATION-TYPE
            OBJECTS { hwStorageAlarmReporting }
            STATUS current
            DESCRIPTION "Abnormal Log Level"
            --#SEVERITY WARNING
            ::= { abnormalLogLevel 1 }

        -- 1.3.6.1.4.1.2011.2.251.20.1.2.2.15.8005.9.2
        abnormalLogLevel-Resume NOTIFICATION-TYPE
            OBJECTS { hwStorageAlarmReporting }
            STATUS current
            DESCRIPTION "Recover: Abnormal Log Level"
            --#SEVERITY INFORMATIONAL
            ::= { abnormalLogLevel 2 }

        -- 1.3.6.1.4.1.2011.2.251.20.1.2.2.15.8005.10
        memoryUsageExceedsTheThreshold OBJECT IDENTIFIER ::= { dpcc 10 }

        -- 1.3.6.1.4.1.2011.2.251.20.1.2.2.15.8005.10.1
        memoryUsageExceedsTheThreshold-Fault NOTIFICATION-TYPE
            OBJECTS { hwStorageAlarmReporting }
            STATUS current
            DESCRIPTION "Memory Usage Exceeds The Threshold"
            --#SEVERITY WARNING
            ::= { memoryUsageExceedsTheThreshold 1 }

        -- 1.3.6.1.4.1.2011.2.251.20.1.2.2.15.8005.10.2
        memoryUsageExceedsTheThreshold-Resume NOTIFICATION-TYPE
            OBJECTS { hwStorageAlarmReporting }
            STATUS current
            DESCRIPTION "Recover: Memory Usage Exceeds The Threshold"
            --#SEVERITY INFORMATIONAL
            ::= { memoryUsageExceedsTheThreshold 2 }

        -- 1.3.6.1.4.1.2011.2.251.20.1.2.2.15.8005.11
        containerRunsAbnormally OBJECT IDENTIFIER ::= { dpcc 11 }

        -- 1.3.6.1.4.1.2011.2.251.20.1.2.2.15.8005.11.1
        containerRunsAbnormally-Fault NOTIFICATION-TYPE
            OBJECTS { hwStorageAlarmReporting }
            STATUS current
            DESCRIPTION "The Container Runs Abnormally"
            --#SEVERITY MAJOR
            ::= { containerRunsAbnormally 1 }

        -- 1.3.6.1.4.1.2011.2.251.20.1.2.2.15.8005.11.2
        containerRunsAbnormally-Resume NOTIFICATION-TYPE
            OBJECTS { hwStorageAlarmReporting }
            STATUS current
            DESCRIPTION "Recover: The Container Runs Abnormally"
            --#SEVERITY INFORMATIONAL
            ::= { containerRunsAbnormally 2 }

        -- 1.3.6.1.4.1.2011.2.251.20.1.2.2.15.8005.12
        cpuUsageExceedsTheThreshold OBJECT IDENTIFIER ::= { dpcc 12 }

        -- 1.3.6.1.4.1.2011.2.251.20.1.2.2.15.8005.12.1
        cpuUsageExceedsTheThreshold-Fault NOTIFICATION-TYPE
            OBJECTS { hwStorageAlarmReporting }
            STATUS current
            DESCRIPTION "The CPU Usage Exceeds The Threshold"
            --#SEVERITY WARNING
            ::= { cpuUsageExceedsTheThreshold 1 }

        -- 1.3.6.1.4.1.2011.2.251.20.1.2.2.15.8005.12.2
        cpuUsageExceedsTheThreshold-Resume NOTIFICATION-TYPE
            OBJECTS { hwStorageAlarmReporting }
            STATUS current
            DESCRIPTION "Recover: The CPU Usage Exceeds The Threshold"
            --#SEVERITY INFORMATIONAL
            ::= { cpuUsageExceedsTheThreshold 2 }

        -- 1.3.6.1.4.1.2011.2.251.20.1.2.2.15.8005.13
        builtinPersistentVolumeCapacityUsageExceedsTheThreshold OBJECT IDENTIFIER ::= { dpcc 13 }

        -- 1.3.6.1.4.1.2011.2.251.20.1.2.2.15.8005.13.1
        builtinPersistentVolumeCapacityUsageExceedsTheThreshold-Fault NOTIFICATION-TYPE
            OBJECTS { hwStorageAlarmReporting }
            STATUS current
            DESCRIPTION "Builtin Persistent Volume Capacity Usage Exceeds The Threshold"
            --#SEVERITY WARNING
            ::= { builtinPersistentVolumeCapacityUsageExceedsTheThreshold 1 }

        -- 1.3.6.1.4.1.2011.2.251.20.1.2.2.15.8005.13.2
        builtinPersistentVolumeCapacityUsageExceedsTheThreshold-Resume NOTIFICATION-TYPE
            OBJECTS { hwStorageAlarmReporting }
            STATUS current
            DESCRIPTION "Recover: Builtin Persistent Volume Capacity Usage Exceeds The Threshold"
            --#SEVERITY INFORMATIONAL
            ::= { builtinPersistentVolumeCapacityUsageExceedsTheThreshold 2 }

        -- 1.3.6.1.4.1.2011.2.251.20.1.2.2.15.15361
        hypermetro OBJECT IDENTIFIER ::= { oidBasedTrap 15361 }

        -- 1.3.6.1.4.1.2011.2.251.20.1.2.2.15.15361.1
        hyperMetroIsUnavailable OBJECT IDENTIFIER ::= { hypermetro 1 }

        -- 1.3.6.1.4.1.2011.2.251.20.1.2.2.15.15361.1.1
        hyperMetroIsUnavailable-Fault NOTIFICATION-TYPE
            OBJECTS { hwStorageAlarmReporting }
            STATUS current
            DESCRIPTION "HyperMetro Is Unavailable"
            --#SEVERITY CRITICAL
            ::= { hyperMetroIsUnavailable 1 }

        -- 1.3.6.1.4.1.2011.2.251.20.1.2.2.15.15361.1.2
        hyperMetroIsUnavailable-Resume NOTIFICATION-TYPE
            OBJECTS { hwStorageAlarmReporting }
            STATUS current
            DESCRIPTION "Recover: HyperMetro Is Unavailable"
            --#SEVERITY INFORMATIONAL
            ::= { hyperMetroIsUnavailable 2 }

        -- 1.3.6.1.4.1.2011.2.251.20.1.2.2.15.15361.2
        hostIncorrectAccessForHyperMetroPair OBJECT IDENTIFIER ::= { hypermetro 2 }

        -- 1.3.6.1.4.1.2011.2.251.20.1.2.2.15.15361.2.1
        hostIncorrectAccessForHyperMetroPair-Fault NOTIFICATION-TYPE
            OBJECTS { hwStorageAlarmReporting }
            STATUS current
            DESCRIPTION "The Host Has An Incorrect Access Permission"
            --#SEVERITY CRITICAL
            ::= { hostIncorrectAccessForHyperMetroPair 1 }

        -- 1.3.6.1.4.1.2011.2.251.20.1.2.2.15.15361.2.2
        hostIncorrectAccessForHyperMetroPair-Resume NOTIFICATION-TYPE
            OBJECTS { hwStorageAlarmReporting }
            STATUS current
            DESCRIPTION "Recover: The Host Has An Incorrect Access Permission"
            --#SEVERITY INFORMATIONAL
            ::= { hostIncorrectAccessForHyperMetroPair 2 }

        -- 1.3.6.1.4.1.2011.2.251.20.1.2.2.15.15361.6
        oneStorageArrayOfAHyperMetroPairIsIsolated OBJECT IDENTIFIER ::= { hypermetro 6 }

        -- 1.3.6.1.4.1.2011.2.251.20.1.2.2.15.15361.6.1
        oneStorageArrayOfAHyperMetroPairIsIsolated-Fault NOTIFICATION-TYPE
            OBJECTS { hwStorageAlarmReporting }
            STATUS current
            DESCRIPTION "One Storage Array Of A HyperMetro Pair Is Isolated"
            --#SEVERITY MAJOR
            ::= { oneStorageArrayOfAHyperMetroPairIsIsolated 1 }

        -- 1.3.6.1.4.1.2011.2.251.20.1.2.2.15.15361.6.2
        oneStorageArrayOfAHyperMetroPairIsIsolated-Resume NOTIFICATION-TYPE
            OBJECTS { hwStorageAlarmReporting }
            STATUS current
            DESCRIPTION "Recover: One Storage Array Of A HyperMetro Pair Is Isolated"
            --#SEVERITY INFORMATIONAL
            ::= { oneStorageArrayOfAHyperMetroPairIsIsolated 2 }

        -- 1.3.6.1.4.1.2011.2.251.20.1.2.2.15.15361.9
        registerIncorrectAccessForPair OBJECT IDENTIFIER ::= { hypermetro 9 }

        -- 1.3.6.1.4.1.2011.2.251.20.1.2.2.15.15361.9.1
        registerIncorrectAccessForPair-Fault NOTIFICATION-TYPE
            OBJECTS { hwStorageAlarmReporting }
            STATUS current
            DESCRIPTION "HyperMetro Arbitration Information Conflicts With The Existing Information"
            --#SEVERITY MAJOR
            ::= { registerIncorrectAccessForPair 1 }

        -- 1.3.6.1.4.1.2011.2.251.20.1.2.2.15.15361.9.2
        registerIncorrectAccessForPair-Resume NOTIFICATION-TYPE
            OBJECTS { hwStorageAlarmReporting }
            STATUS current
            DESCRIPTION "Recover: HyperMetro Arbitration Information Conflicts With The Existing Information"
            --#SEVERITY INFORMATIONAL
            ::= { registerIncorrectAccessForPair 2 }

        -- 1.3.6.1.4.1.2011.2.251.20.1.2.2.15.15361.14
        hyperMetroIsDisconnected3 OBJECT IDENTIFIER ::= { hypermetro 14 }

        -- 1.3.6.1.4.1.2011.2.251.20.1.2.2.15.15361.14.1
        hyperMetroIsDisconnected3-Fault NOTIFICATION-TYPE
            OBJECTS { hwStorageAlarmReporting }
            STATUS current
            DESCRIPTION "The HyperMetro Pair Is Interrupted And The Local LUN Cannot Provide Services"
            --#SEVERITY MAJOR
            ::= { hyperMetroIsDisconnected3 1 }

        -- 1.3.6.1.4.1.2011.2.251.20.1.2.2.15.15361.14.2
        hyperMetroIsDisconnected3-Resume NOTIFICATION-TYPE
            OBJECTS { hwStorageAlarmReporting }
            STATUS current
            DESCRIPTION "Recover: The HyperMetro Pair Is Interrupted And The Local LUN Cannot Provide Services"
            --#SEVERITY INFORMATIONAL
            ::= { hyperMetroIsDisconnected3 2 }

        -- 1.3.6.1.4.1.2011.2.251.20.1.2.2.15.15361.15
        hyperMetroIsDisconnected2 OBJECT IDENTIFIER ::= { hypermetro 15 }

        -- 1.3.6.1.4.1.2011.2.251.20.1.2.2.15.15361.15.1
        hyperMetroIsDisconnected2-Fault NOTIFICATION-TYPE
            OBJECTS { hwStorageAlarmReporting }
            STATUS current
            DESCRIPTION "The HyperMetro Pair Is Interrupted And The Local LUN Continues To Provide Services"
            --#SEVERITY MAJOR
            ::= { hyperMetroIsDisconnected2 1 }

        -- 1.3.6.1.4.1.2011.2.251.20.1.2.2.15.15361.15.2
        hyperMetroIsDisconnected2-Resume NOTIFICATION-TYPE
            OBJECTS { hwStorageAlarmReporting }
            STATUS current
            DESCRIPTION "Recover: The HyperMetro Pair Is Interrupted And The Local LUN Continues To Provide Services"
            --#SEVERITY INFORMATIONAL
            ::= { hyperMetroIsDisconnected2 2 }

        -- 1.3.6.1.4.1.2011.2.251.20.1.2.2.15.15361.29
        theLocalArrayHasHyperMetroLUNsThatAreNotMappedToTheHost OBJECT IDENTIFIER ::= { hypermetro 29 }

        -- 1.3.6.1.4.1.2011.2.251.20.1.2.2.15.15361.29.1
        theLocalArrayHasHyperMetroLUNsThatAreNotMappedToTheHost-Fault NOTIFICATION-TYPE
            OBJECTS { hwStorageAlarmReporting }
            STATUS current
            DESCRIPTION "The Local Array Has HyperMetro LUNs That Are Not Mapped To The Host"
            --#SEVERITY WARNING
            ::= { theLocalArrayHasHyperMetroLUNsThatAreNotMappedToTheHost 1 }

        -- 1.3.6.1.4.1.2011.2.251.20.1.2.2.15.15361.29.2
        theLocalArrayHasHyperMetroLUNsThatAreNotMappedToTheHost-Resume NOTIFICATION-TYPE
            OBJECTS { hwStorageAlarmReporting }
            STATUS current
            DESCRIPTION "Recover: The Local Array Has HyperMetro LUNs That Are Not Mapped To The Host"
            --#SEVERITY INFORMATIONAL
            ::= { theLocalArrayHasHyperMetroLUNsThatAreNotMappedToTheHost 2 }

        -- 1.3.6.1.4.1.2011.2.251.20.1.2.2.15.15361.33
        hyperMetroPairAutoDisconnect1 OBJECT IDENTIFIER ::= { hypermetro 33 }

        -- 1.3.6.1.4.1.2011.2.251.20.1.2.2.15.15361.33.1
        hyperMetroPairAutoDisconnect1-Fault NOTIFICATION-TYPE
            OBJECTS { hwStorageAlarmReporting }
            STATUS current
            DESCRIPTION "A HyperMetro Pair Is Automatically Disconnected And The Local LUN Cannot Provide Services"
            --#SEVERITY WARNING
            ::= { hyperMetroPairAutoDisconnect1 1 }

        -- 1.3.6.1.4.1.2011.2.251.20.1.2.2.15.15361.33.2
        hyperMetroPairAutoDisconnect1-Resume NOTIFICATION-TYPE
            OBJECTS { hwStorageAlarmReporting }
            STATUS current
            DESCRIPTION "Recover: A HyperMetro Pair Is Automatically Disconnected And The Local LUN Cannot Provide Services"
            --#SEVERITY INFORMATIONAL
            ::= { hyperMetroPairAutoDisconnect1 2 }

        -- 1.3.6.1.4.1.2011.2.251.20.1.2.2.15.15361.34
        hyperMetroPairAutoDisconnect OBJECT IDENTIFIER ::= { hypermetro 34 }

        -- 1.3.6.1.4.1.2011.2.251.20.1.2.2.15.15361.34.1
        hyperMetroPairAutoDisconnect-Fault NOTIFICATION-TYPE
            OBJECTS { hwStorageAlarmReporting }
            STATUS current
            DESCRIPTION "A HyperMetro Pair Is Automatically Disconnected And The Local LUN Continues To Provide Services"
            --#SEVERITY WARNING
            ::= { hyperMetroPairAutoDisconnect 1 }

        -- 1.3.6.1.4.1.2011.2.251.20.1.2.2.15.15361.34.2
        hyperMetroPairAutoDisconnect-Resume NOTIFICATION-TYPE
            OBJECTS { hwStorageAlarmReporting }
            STATUS current
            DESCRIPTION "Recover: A HyperMetro Pair Is Automatically Disconnected And The Local LUN Continues To Provide Services"
            --#SEVERITY INFORMATIONAL
            ::= { hyperMetroPairAutoDisconnect 2 }

        -- 1.3.6.1.4.1.2011.2.251.20.1.2.2.15.15361.35
        hyperMetroIsDisconnected OBJECT IDENTIFIER ::= { hypermetro 35 }

        -- 1.3.6.1.4.1.2011.2.251.20.1.2.2.15.15361.35.1
        hyperMetroIsDisconnected-Fault NOTIFICATION-TYPE
            OBJECTS { hwStorageAlarmReporting }
            STATUS current
            DESCRIPTION "The HyperMetro Pair Is Interrupted And The Local LUN Cannot Provide Services"
            --#SEVERITY MAJOR
            ::= { hyperMetroIsDisconnected 1 }

        -- 1.3.6.1.4.1.2011.2.251.20.1.2.2.15.15361.35.2
        hyperMetroIsDisconnected-Resume NOTIFICATION-TYPE
            OBJECTS { hwStorageAlarmReporting }
            STATUS current
            DESCRIPTION "Recover: The HyperMetro Pair Is Interrupted And The Local LUN Cannot Provide Services"
            --#SEVERITY INFORMATIONAL
            ::= { hyperMetroIsDisconnected 2 }

        -- 1.3.6.1.4.1.2011.2.251.20.1.2.2.15.15361.36
        hyperMetroIsDisconnected1 OBJECT IDENTIFIER ::= { hypermetro 36 }

        -- 1.3.6.1.4.1.2011.2.251.20.1.2.2.15.15361.36.1
        hyperMetroIsDisconnected1-Fault NOTIFICATION-TYPE
            OBJECTS { hwStorageAlarmReporting }
            STATUS current
            DESCRIPTION "The HyperMetro Pair Is Interrupted And The Local LUN Continues To Provide Services"
            --#SEVERITY MAJOR
            ::= { hyperMetroIsDisconnected1 1 }

        -- 1.3.6.1.4.1.2011.2.251.20.1.2.2.15.15361.36.2
        hyperMetroIsDisconnected1-Resume NOTIFICATION-TYPE
            OBJECTS { hwStorageAlarmReporting }
            STATUS current
            DESCRIPTION "Recover: The HyperMetro Pair Is Interrupted And The Local LUN Continues To Provide Services"
            --#SEVERITY INFORMATIONAL
            ::= { hyperMetroIsDisconnected1 2 }

        -- 1.3.6.1.4.1.2011.2.251.20.1.2.2.15.15361.37
        failedToStartTheHyperMetroService OBJECT IDENTIFIER ::= { hypermetro 37 }

        -- 1.3.6.1.4.1.2011.2.251.20.1.2.2.15.15361.37.1
        failedToStartTheHyperMetroService-Fault NOTIFICATION-TYPE
            OBJECTS { hwStorageAlarmReporting }
            STATUS current
            DESCRIPTION "Failed To Start The HyperMetro Service"
            --#SEVERITY WARNING
            ::= { failedToStartTheHyperMetroService 1 }

        -- 1.3.6.1.4.1.2011.2.251.20.1.2.2.15.15361.37.2
        failedToStartTheHyperMetroService-Resume NOTIFICATION-TYPE
            OBJECTS { hwStorageAlarmReporting }
            STATUS current
            DESCRIPTION "Recover: Failed To Start The HyperMetro Service"
            --#SEVERITY INFORMATIONAL
            ::= { failedToStartTheHyperMetroService 2 }

        -- 1.3.6.1.4.1.2011.2.251.20.1.2.2.15.15361.38
        hyperMetroIsInterruptedAndTheLocalFileSystemCannotProvideServices OBJECT IDENTIFIER ::= { hypermetro 38 }

        -- 1.3.6.1.4.1.2011.2.251.20.1.2.2.15.15361.38.1
        hyperMetroIsInterruptedAndTheLocalFileSystemCannotProvideServices-Fault NOTIFICATION-TYPE
            OBJECTS { hwStorageAlarmReporting }
            STATUS current
            DESCRIPTION "HyperMetro Is Interrupted And The Local File System Cannot Provide Services"
            --#SEVERITY MAJOR
            ::= { hyperMetroIsInterruptedAndTheLocalFileSystemCannotProvideServices 1 }

        -- 1.3.6.1.4.1.2011.2.251.20.1.2.2.15.15361.38.2
        hyperMetroIsInterruptedAndTheLocalFileSystemCannotProvideServices-Resume NOTIFICATION-TYPE
            OBJECTS { hwStorageAlarmReporting }
            STATUS current
            DESCRIPTION "Recover: HyperMetro Is Interrupted And The Local File System Cannot Provide Services"
            --#SEVERITY INFORMATIONAL
            ::= { hyperMetroIsInterruptedAndTheLocalFileSystemCannotProvideServices 2 }

        -- 1.3.6.1.4.1.2011.2.251.20.1.2.2.15.15361.39
        theLocalFileSystemContinuesToProvideServicesWhenHyperMetroIsInterrupted OBJECT IDENTIFIER ::= { hypermetro 39 }

        -- 1.3.6.1.4.1.2011.2.251.20.1.2.2.15.15361.39.1
        theLocalFileSystemContinuesToProvideServicesWhenHyperMetroIsInterrupted-Fault NOTIFICATION-TYPE
            OBJECTS { hwStorageAlarmReporting }
            STATUS current
            DESCRIPTION "The Local File System Continues To Provide Services When HyperMetro Is Interrupted"
            --#SEVERITY MAJOR
            ::= { theLocalFileSystemContinuesToProvideServicesWhenHyperMetroIsInterrupted 1 }

        -- 1.3.6.1.4.1.2011.2.251.20.1.2.2.15.15361.39.2
        theLocalFileSystemContinuesToProvideServicesWhenHyperMetroIsInterrupted-Resume NOTIFICATION-TYPE
            OBJECTS { hwStorageAlarmReporting }
            STATUS current
            DESCRIPTION "Recover: The Local File System Continues To Provide Services When HyperMetro Is Interrupted"
            --#SEVERITY INFORMATIONAL
            ::= { theLocalFileSystemContinuesToProvideServicesWhenHyperMetroIsInterrupted 2 }

        -- 1.3.6.1.4.1.2011.2.251.20.1.2.2.15.15361.40
        nasHyperMetraClusterProtectWrite OBJECT IDENTIFIER ::= { hypermetro 40 }

        -- 1.3.6.1.4.1.2011.2.251.20.1.2.2.15.15361.40.1
        nasHyperMetraClusterProtectWrite-Fault NOTIFICATION-TYPE
            OBJECTS { hwStorageAlarmReporting }
            STATUS current
            DESCRIPTION "The File System HyperMetro Domain Is In The Write Protection Status"
            --#SEVERITY MAJOR
            ::= { nasHyperMetraClusterProtectWrite 1 }

        -- 1.3.6.1.4.1.2011.2.251.20.1.2.2.15.15361.40.2
        nasHyperMetraClusterProtectWrite-Resume NOTIFICATION-TYPE
            OBJECTS { hwStorageAlarmReporting }
            STATUS current
            DESCRIPTION "Recover: The File System HyperMetro Domain Is In The Write Protection Status"
            --#SEVERITY INFORMATIONAL
            ::= { nasHyperMetraClusterProtectWrite 2 }

        -- 1.3.6.1.4.1.2011.2.251.20.1.2.2.15.15361.43
        failedToStartTheServiceOfAFileSystemHyperMetroPair OBJECT IDENTIFIER ::= { hypermetro 43 }

        -- 1.3.6.1.4.1.2011.2.251.20.1.2.2.15.15361.43.1
        failedToStartTheServiceOfAFileSystemHyperMetroPair-Fault NOTIFICATION-TYPE
            OBJECTS { hwStorageAlarmReporting }
            STATUS current
            DESCRIPTION "Failed To Start The Service Of A File System HyperMetro Pair"
            --#SEVERITY WARNING
            ::= { failedToStartTheServiceOfAFileSystemHyperMetroPair 1 }

        -- 1.3.6.1.4.1.2011.2.251.20.1.2.2.15.15361.43.2
        failedToStartTheServiceOfAFileSystemHyperMetroPair-Resume NOTIFICATION-TYPE
            OBJECTS { hwStorageAlarmReporting }
            STATUS current
            DESCRIPTION "Recover: Failed To Start The Service Of A File System HyperMetro Pair"
            --#SEVERITY INFORMATIONAL
            ::= { failedToStartTheServiceOfAFileSystemHyperMetroPair 2 }

        -- 1.3.6.1.4.1.2011.2.251.20.1.2.2.15.15361.44
        hyperMetroPairConfigurationsAreDisconnected OBJECT IDENTIFIER ::= { hypermetro 44 }

        -- 1.3.6.1.4.1.2011.2.251.20.1.2.2.15.15361.44.1
        hyperMetroPairConfigurationsAreDisconnected-Fault NOTIFICATION-TYPE
            OBJECTS { hwStorageAlarmReporting }
            STATUS current
            DESCRIPTION "HyperMetro Pair Configurations Are Disconnected"
            --#SEVERITY MAJOR
            ::= { hyperMetroPairConfigurationsAreDisconnected 1 }

        -- 1.3.6.1.4.1.2011.2.251.20.1.2.2.15.15361.44.2
        hyperMetroPairConfigurationsAreDisconnected-Resume NOTIFICATION-TYPE
            OBJECTS { hwStorageAlarmReporting }
            STATUS current
            DESCRIPTION "Recover: HyperMetro Pair Configurations Are Disconnected"
            --#SEVERITY INFORMATIONAL
            ::= { hyperMetroPairConfigurationsAreDisconnected 2 }

        -- 1.3.6.1.4.1.2011.2.251.20.1.2.2.15.15361.45
        nasHyperMetroIsUnavailable OBJECT IDENTIFIER ::= { hypermetro 45 }

        -- 1.3.6.1.4.1.2011.2.251.20.1.2.2.15.15361.45.1
        nasHyperMetroIsUnavailable-Fault NOTIFICATION-TYPE
            OBJECTS { hwStorageAlarmReporting }
            STATUS current
            DESCRIPTION "The File System HyperMetro Pair Is Unavailable"
            --#SEVERITY CRITICAL
            ::= { nasHyperMetroIsUnavailable 1 }

        -- 1.3.6.1.4.1.2011.2.251.20.1.2.2.15.15361.45.2
        nasHyperMetroIsUnavailable-Resume NOTIFICATION-TYPE
            OBJECTS { hwStorageAlarmReporting }
            STATUS current
            DESCRIPTION "Recover: The File System HyperMetro Pair Is Unavailable"
            --#SEVERITY INFORMATIONAL
            ::= { nasHyperMetroIsUnavailable 2 }

        -- 1.3.6.1.4.1.2011.2.251.20.1.2.2.15.15361.47
        nvmeClusterReservationCommandFailed OBJECT IDENTIFIER ::= { hypermetro 47 }

        -- 1.3.6.1.4.1.2011.2.251.20.1.2.2.15.15361.47.1
        nvmeClusterReservationCommandFailed-Fault NOTIFICATION-TYPE
            OBJECTS { hwStorageAlarmReporting }
            STATUS current
            DESCRIPTION "The Host Fails To Deliver The NVMe Cluster Reservation Command"
            --#SEVERITY MAJOR
            ::= { nvmeClusterReservationCommandFailed 1 }

        -- 1.3.6.1.4.1.2011.2.251.20.1.2.2.15.15361.47.2
        nvmeClusterReservationCommandFailed-Resume NOTIFICATION-TYPE
            OBJECTS { hwStorageAlarmReporting }
            STATUS current
            DESCRIPTION "Recover: The Host Fails To Deliver The NVMe Cluster Reservation Command"
            --#SEVERITY INFORMATIONAL
            ::= { nvmeClusterReservationCommandFailed 2 }

        -- 1.3.6.1.4.1.2011.2.251.20.1.2.2.15.15362
        hypermetrodomain OBJECT IDENTIFIER ::= { oidBasedTrap 15362 }

        -- 1.3.6.1.4.1.2011.2.251.20.1.2.2.15.15362.0
        hyperMetroDomainIsUnavailable OBJECT IDENTIFIER ::= { hypermetrodomain 0 }

        -- 1.3.6.1.4.1.2011.2.251.20.1.2.2.15.15362.0.1
        hyperMetroDomainIsUnavailable-Fault NOTIFICATION-TYPE
            OBJECTS { hwStorageAlarmReporting }
            STATUS current
            DESCRIPTION "The HyperMetro Domain Is Unavailable"
            --#SEVERITY CRITICAL
            ::= { hyperMetroDomainIsUnavailable 1 }

        -- 1.3.6.1.4.1.2011.2.251.20.1.2.2.15.15362.0.2
        hyperMetroDomainIsUnavailable-Resume NOTIFICATION-TYPE
            OBJECTS { hwStorageAlarmReporting }
            STATUS current
            DESCRIPTION "Recover: The HyperMetro Domain Is Unavailable"
            --#SEVERITY INFORMATIONAL
            ::= { hyperMetroDomainIsUnavailable 2 }

        -- 1.3.6.1.4.1.2011.2.251.20.1.2.2.15.15362.4
        theHyperMetroDomainIsFaulty OBJECT IDENTIFIER ::= { hypermetrodomain 4 }

        -- 1.3.6.1.4.1.2011.2.251.20.1.2.2.15.15362.4.1
        theHyperMetroDomainIsFaulty-Fault NOTIFICATION-TYPE
            OBJECTS { hwStorageAlarmReporting }
            STATUS current
            DESCRIPTION "The HyperMetro Domain Is Faulty"
            --#SEVERITY MAJOR
            ::= { theHyperMetroDomainIsFaulty 1 }

        -- 1.3.6.1.4.1.2011.2.251.20.1.2.2.15.15362.4.2
        theHyperMetroDomainIsFaulty-Resume NOTIFICATION-TYPE
            OBJECTS { hwStorageAlarmReporting }
            STATUS current
            DESCRIPTION "Recover: The HyperMetro Domain Is Faulty"
            --#SEVERITY INFORMATIONAL
            ::= { theHyperMetroDomainIsFaulty 2 }

        -- 1.3.6.1.4.1.2011.2.251.20.1.2.2.15.15362.6
        hyperMetroDomainIsRecovery OBJECT IDENTIFIER ::= { hypermetrodomain 6 }

        -- 1.3.6.1.4.1.2011.2.251.20.1.2.2.15.15362.6.1
        hyperMetroDomainIsRecovery-Fault NOTIFICATION-TYPE
            OBJECTS { hwStorageAlarmReporting }
            STATUS current
            DESCRIPTION "HyperMetro Domain Is In The Recovering State For A Long Time"
            --#SEVERITY WARNING
            ::= { hyperMetroDomainIsRecovery 1 }

        -- 1.3.6.1.4.1.2011.2.251.20.1.2.2.15.15362.6.2
        hyperMetroDomainIsRecovery-Resume NOTIFICATION-TYPE
            OBJECTS { hwStorageAlarmReporting }
            STATUS current
            DESCRIPTION "Recover: HyperMetro Domain Is In The Recovering State For A Long Time"
            --#SEVERITY INFORMATIONAL
            ::= { hyperMetroDomainIsRecovery 2 }

        -- 1.3.6.1.4.1.2011.2.251.20.1.2.2.15.15362.40
        hyperMetroDomainIsDisconnected1 OBJECT IDENTIFIER ::= { hypermetrodomain 40 }

        -- 1.3.6.1.4.1.2011.2.251.20.1.2.2.15.15362.40.1
        hyperMetroDomainIsDisconnected1-Fault NOTIFICATION-TYPE
            OBJECTS { hwStorageAlarmReporting }
            STATUS current
            DESCRIPTION "The Local End Cannot Provide Services When The HyperMetro Domain Is Disconnected"
            --#SEVERITY CRITICAL
            ::= { hyperMetroDomainIsDisconnected1 1 }

        -- 1.3.6.1.4.1.2011.2.251.20.1.2.2.15.15362.40.2
        hyperMetroDomainIsDisconnected1-Resume NOTIFICATION-TYPE
            OBJECTS { hwStorageAlarmReporting }
            STATUS current
            DESCRIPTION "Recover: The Local End Cannot Provide Services When The HyperMetro Domain Is Disconnected"
            --#SEVERITY INFORMATIONAL
            ::= { hyperMetroDomainIsDisconnected1 2 }

        -- 1.3.6.1.4.1.2011.2.251.20.1.2.2.15.15362.41
        hyperMetroDomainIsDisconnected OBJECT IDENTIFIER ::= { hypermetrodomain 41 }

        -- 1.3.6.1.4.1.2011.2.251.20.1.2.2.15.15362.41.1
        hyperMetroDomainIsDisconnected-Fault NOTIFICATION-TYPE
            OBJECTS { hwStorageAlarmReporting }
            STATUS current
            DESCRIPTION "The Local End Continues To Provide Services When The HyperMetro Domain Is Disconnected"
            --#SEVERITY MAJOR
            ::= { hyperMetroDomainIsDisconnected 1 }

        -- 1.3.6.1.4.1.2011.2.251.20.1.2.2.15.15362.41.2
        hyperMetroDomainIsDisconnected-Resume NOTIFICATION-TYPE
            OBJECTS { hwStorageAlarmReporting }
            STATUS current
            DESCRIPTION "Recover: The Local End Continues To Provide Services When The HyperMetro Domain Is Disconnected"
            --#SEVERITY INFORMATIONAL
            ::= { hyperMetroDomainIsDisconnected 2 }

        -- 1.3.6.1.4.1.2011.2.251.20.1.2.2.15.15363
        quorumserver OBJECT IDENTIFIER ::= { oidBasedTrap 15363 }

        -- 1.3.6.1.4.1.2011.2.251.20.1.2.2.15.15363.2
        noBackupLinkForCps OBJECT IDENTIFIER ::= { quorumserver 2 }

        -- 1.3.6.1.4.1.2011.2.251.20.1.2.2.15.15363.2.1
        noBackupLinkForCps-Fault NOTIFICATION-TYPE
            OBJECTS { hwStorageAlarmReporting }
            STATUS current
            DESCRIPTION "No Backup Links Available"
            --#SEVERITY WARNING
            ::= { noBackupLinkForCps 1 }

        -- 1.3.6.1.4.1.2011.2.251.20.1.2.2.15.15363.2.2
        noBackupLinkForCps-Resume NOTIFICATION-TYPE
            OBJECTS { hwStorageAlarmReporting }
            STATUS current
            DESCRIPTION "Recover: No Backup Links Available"
            --#SEVERITY INFORMATIONAL
            ::= { noBackupLinkForCps 2 }

        -- 1.3.6.1.4.1.2011.2.251.20.1.2.2.15.15363.4
        quorumServerDisconnected OBJECT IDENTIFIER ::= { quorumserver 4 }

        -- 1.3.6.1.4.1.2011.2.251.20.1.2.2.15.15363.4.1
        quorumServerDisconnected-Fault NOTIFICATION-TYPE
            OBJECTS { hwStorageAlarmReporting }
            STATUS current
            DESCRIPTION "Quorum Server Is Disconnected From The Storage Array"
            --#SEVERITY MAJOR
            ::= { quorumServerDisconnected 1 }

        -- 1.3.6.1.4.1.2011.2.251.20.1.2.2.15.15363.4.2
        quorumServerDisconnected-Resume NOTIFICATION-TYPE
            OBJECTS { hwStorageAlarmReporting }
            STATUS current
            DESCRIPTION "Recover: Quorum Server Is Disconnected From The Storage Array"
            --#SEVERITY INFORMATIONAL
            ::= { quorumServerDisconnected 2 }

        -- 1.3.6.1.4.1.2011.2.251.20.1.2.2.15.15363.8
        certificateOfAQuorumServerHasExpired OBJECT IDENTIFIER ::= { quorumserver 8 }

        -- 1.3.6.1.4.1.2011.2.251.20.1.2.2.15.15363.8.1
        certificateOfAQuorumServerHasExpired-Fault NOTIFICATION-TYPE
            OBJECTS { hwStorageAlarmReporting }
            STATUS current
            DESCRIPTION "Certificate Of A Quorum Server Has Expired"
            --#SEVERITY CRITICAL
            ::= { certificateOfAQuorumServerHasExpired 1 }

        -- 1.3.6.1.4.1.2011.2.251.20.1.2.2.15.15363.8.2
        certificateOfAQuorumServerHasExpired-Resume NOTIFICATION-TYPE
            OBJECTS { hwStorageAlarmReporting }
            STATUS current
            DESCRIPTION "Recover: Certificate Of A Quorum Server Has Expired"
            --#SEVERITY INFORMATIONAL
            ::= { certificateOfAQuorumServerHasExpired 2 }

        -- 1.3.6.1.4.1.2011.2.251.20.1.2.2.15.15363.9
        cACertificateOfAQuorumServerHasExpired OBJECT IDENTIFIER ::= { quorumserver 9 }

        -- 1.3.6.1.4.1.2011.2.251.20.1.2.2.15.15363.9.1
        cACertificateOfAQuorumServerHasExpired-Fault NOTIFICATION-TYPE
            OBJECTS { hwStorageAlarmReporting }
            STATUS current
            DESCRIPTION "CA Certificate Of A Quorum Server Has Expired"
            --#SEVERITY CRITICAL
            ::= { cACertificateOfAQuorumServerHasExpired 1 }

        -- 1.3.6.1.4.1.2011.2.251.20.1.2.2.15.15363.9.2
        cACertificateOfAQuorumServerHasExpired-Resume NOTIFICATION-TYPE
            OBJECTS { hwStorageAlarmReporting }
            STATUS current
            DESCRIPTION "Recover: CA Certificate Of A Quorum Server Has Expired"
            --#SEVERITY INFORMATIONAL
            ::= { cACertificateOfAQuorumServerHasExpired 2 }

        -- 1.3.6.1.4.1.2011.2.251.20.1.2.2.15.15363.10
        theCertificateOfQuorumServerIsAboutToExpire OBJECT IDENTIFIER ::= { quorumserver 10 }

        -- 1.3.6.1.4.1.2011.2.251.20.1.2.2.15.15363.10.1
        theCertificateOfQuorumServerIsAboutToExpire-Fault NOTIFICATION-TYPE
            OBJECTS { hwStorageAlarmReporting }
            STATUS current
            DESCRIPTION "Certificate Of A Quorum Server Is About To Expire"
            --#SEVERITY MAJOR
            ::= { theCertificateOfQuorumServerIsAboutToExpire 1 }

        -- 1.3.6.1.4.1.2011.2.251.20.1.2.2.15.15363.10.2
        theCertificateOfQuorumServerIsAboutToExpire-Resume NOTIFICATION-TYPE
            OBJECTS { hwStorageAlarmReporting }
            STATUS current
            DESCRIPTION "Recover: Certificate Of A Quorum Server Is About To Expire"
            --#SEVERITY INFORMATIONAL
            ::= { theCertificateOfQuorumServerIsAboutToExpire 2 }

        -- 1.3.6.1.4.1.2011.2.251.20.1.2.2.15.15363.11
        cACertificateOfAQuorumServerIsAboutToExpire OBJECT IDENTIFIER ::= { quorumserver 11 }

        -- 1.3.6.1.4.1.2011.2.251.20.1.2.2.15.15363.11.1
        cACertificateOfAQuorumServerIsAboutToExpire-Fault NOTIFICATION-TYPE
            OBJECTS { hwStorageAlarmReporting }
            STATUS current
            DESCRIPTION "CA Certificate Of A Quorum Server Is About To Expire"
            --#SEVERITY MAJOR
            ::= { cACertificateOfAQuorumServerIsAboutToExpire 1 }

        -- 1.3.6.1.4.1.2011.2.251.20.1.2.2.15.15363.11.2
        cACertificateOfAQuorumServerIsAboutToExpire-Resume NOTIFICATION-TYPE
            OBJECTS { hwStorageAlarmReporting }
            STATUS current
            DESCRIPTION "Recover: CA Certificate Of A Quorum Server Is About To Expire"
            --#SEVERITY INFORMATIONAL
            ::= { cACertificateOfAQuorumServerIsAboutToExpire 2 }

        -- 1.3.6.1.4.1.2011.2.251.20.1.2.2.15.15364
        hypermetroconsistencygroup OBJECT IDENTIFIER ::= { oidBasedTrap 15364 }

        -- 1.3.6.1.4.1.2011.2.251.20.1.2.2.15.15364.2
        hyperMetroGroupIsUnavailable OBJECT IDENTIFIER ::= { hypermetroconsistencygroup 2 }

        -- 1.3.6.1.4.1.2011.2.251.20.1.2.2.15.15364.2.1
        hyperMetroGroupIsUnavailable-Fault NOTIFICATION-TYPE
            OBJECTS { hwStorageAlarmReporting }
            STATUS current
            DESCRIPTION "HyperMetro Consistency Group Is Unavailable"
            --#SEVERITY CRITICAL
            ::= { hyperMetroGroupIsUnavailable 1 }

        -- 1.3.6.1.4.1.2011.2.251.20.1.2.2.15.15364.2.2
        hyperMetroGroupIsUnavailable-Resume NOTIFICATION-TYPE
            OBJECTS { hwStorageAlarmReporting }
            STATUS current
            DESCRIPTION "Recover: HyperMetro Consistency Group Is Unavailable"
            --#SEVERITY INFORMATIONAL
            ::= { hyperMetroGroupIsUnavailable 2 }

        -- 1.3.6.1.4.1.2011.2.251.20.1.2.2.15.15364.3
        hostIncorrectAccessForHyperMetroGroup OBJECT IDENTIFIER ::= { hypermetroconsistencygroup 3 }

        -- 1.3.6.1.4.1.2011.2.251.20.1.2.2.15.15364.3.1
        hostIncorrectAccessForHyperMetroGroup-Fault NOTIFICATION-TYPE
            OBJECTS { hwStorageAlarmReporting }
            STATUS current
            DESCRIPTION "The Host Has An Incorrect Access Permission For HyperMetro Consistency Group"
            --#SEVERITY CRITICAL
            ::= { hostIncorrectAccessForHyperMetroGroup 1 }

        -- 1.3.6.1.4.1.2011.2.251.20.1.2.2.15.15364.3.2
        hostIncorrectAccessForHyperMetroGroup-Resume NOTIFICATION-TYPE
            OBJECTS { hwStorageAlarmReporting }
            STATUS current
            DESCRIPTION "Recover: The Host Has An Incorrect Access Permission For HyperMetro Consistency Group"
            --#SEVERITY INFORMATIONAL
            ::= { hostIncorrectAccessForHyperMetroGroup 2 }

        -- 1.3.6.1.4.1.2011.2.251.20.1.2.2.15.15364.4
        registerIncorrectAccessForGroup OBJECT IDENTIFIER ::= { hypermetroconsistencygroup 4 }

        -- 1.3.6.1.4.1.2011.2.251.20.1.2.2.15.15364.4.1
        registerIncorrectAccessForGroup-Fault NOTIFICATION-TYPE
            OBJECTS { hwStorageAlarmReporting }
            STATUS current
            DESCRIPTION "The HyperMetro Consistency Group Arbitration Information Conflicts With The Existing Information"
            --#SEVERITY MAJOR
            ::= { registerIncorrectAccessForGroup 1 }

        -- 1.3.6.1.4.1.2011.2.251.20.1.2.2.15.15364.4.2
        registerIncorrectAccessForGroup-Resume NOTIFICATION-TYPE
            OBJECTS { hwStorageAlarmReporting }
            STATUS current
            DESCRIPTION "Recover: The HyperMetro Consistency Group Arbitration Information Conflicts With The Existing Information"
            --#SEVERITY INFORMATIONAL
            ::= { registerIncorrectAccessForGroup 2 }

        -- 1.3.6.1.4.1.2011.2.251.20.1.2.2.15.15364.10
        oneStorageArrayOfAHyperMetroConsistencyGroupIsIsolated OBJECT IDENTIFIER ::= { hypermetroconsistencygroup 10 }

        -- 1.3.6.1.4.1.2011.2.251.20.1.2.2.15.15364.10.1
        oneStorageArrayOfAHyperMetroConsistencyGroupIsIsolated-Fault NOTIFICATION-TYPE
            OBJECTS { hwStorageAlarmReporting }
            STATUS current
            DESCRIPTION "One Storage Array Of A HyperMetro Consistency Group Is Isolated"
            --#SEVERITY MAJOR
            ::= { oneStorageArrayOfAHyperMetroConsistencyGroupIsIsolated 1 }

        -- 1.3.6.1.4.1.2011.2.251.20.1.2.2.15.15364.10.2
        oneStorageArrayOfAHyperMetroConsistencyGroupIsIsolated-Resume NOTIFICATION-TYPE
            OBJECTS { hwStorageAlarmReporting }
            STATUS current
            DESCRIPTION "Recover: One Storage Array Of A HyperMetro Consistency Group Is Isolated"
            --#SEVERITY INFORMATIONAL
            ::= { oneStorageArrayOfAHyperMetroConsistencyGroupIsIsolated 2 }

        -- 1.3.6.1.4.1.2011.2.251.20.1.2.2.15.15364.11
        hyperMetroGroupIsDisconnected1 OBJECT IDENTIFIER ::= { hypermetroconsistencygroup 11 }

        -- 1.3.6.1.4.1.2011.2.251.20.1.2.2.15.15364.11.1
        hyperMetroGroupIsDisconnected1-Fault NOTIFICATION-TYPE
            OBJECTS { hwStorageAlarmReporting }
            STATUS current
            DESCRIPTION "The HyperMetro Consistency Group Is Disconnected And Member LUNs In The Local Consistency Group Cannot Provide Services"
            --#SEVERITY MAJOR
            ::= { hyperMetroGroupIsDisconnected1 1 }

        -- 1.3.6.1.4.1.2011.2.251.20.1.2.2.15.15364.11.2
        hyperMetroGroupIsDisconnected1-Resume NOTIFICATION-TYPE
            OBJECTS { hwStorageAlarmReporting }
            STATUS current
            DESCRIPTION "Recover: The HyperMetro Consistency Group Is Disconnected And Member LUNs In The Local Consistency Group Cannot Provide Services"
            --#SEVERITY INFORMATIONAL
            ::= { hyperMetroGroupIsDisconnected1 2 }

        -- 1.3.6.1.4.1.2011.2.251.20.1.2.2.15.15364.12
        hyperMetroGroupIsDisconnected OBJECT IDENTIFIER ::= { hypermetroconsistencygroup 12 }

        -- 1.3.6.1.4.1.2011.2.251.20.1.2.2.15.15364.12.1
        hyperMetroGroupIsDisconnected-Fault NOTIFICATION-TYPE
            OBJECTS { hwStorageAlarmReporting }
            STATUS current
            DESCRIPTION "The HyperMetro Consistency Group Is Disconnected And Member LUNs In The Local Consistency Group Continue To Provide Services"
            --#SEVERITY MAJOR
            ::= { hyperMetroGroupIsDisconnected 1 }

        -- 1.3.6.1.4.1.2011.2.251.20.1.2.2.15.15364.12.2
        hyperMetroGroupIsDisconnected-Resume NOTIFICATION-TYPE
            OBJECTS { hwStorageAlarmReporting }
            STATUS current
            DESCRIPTION "Recover: The HyperMetro Consistency Group Is Disconnected And Member LUNs In The Local Consistency Group Continue To Provide Services"
            --#SEVERITY INFORMATIONAL
            ::= { hyperMetroGroupIsDisconnected 2 }

        -- 1.3.6.1.4.1.2011.2.251.20.1.2.2.15.15364.13
        failedToStartTheHyperMetroConsistencyGroupService OBJECT IDENTIFIER ::= { hypermetroconsistencygroup 13 }

        -- 1.3.6.1.4.1.2011.2.251.20.1.2.2.15.15364.13.1
        failedToStartTheHyperMetroConsistencyGroupService-Fault NOTIFICATION-TYPE
            OBJECTS { hwStorageAlarmReporting }
            STATUS current
            DESCRIPTION "Failed To Start The HyperMetro Consistency Group Service"
            --#SEVERITY WARNING
            ::= { failedToStartTheHyperMetroConsistencyGroupService 1 }

        -- 1.3.6.1.4.1.2011.2.251.20.1.2.2.15.15364.13.2
        failedToStartTheHyperMetroConsistencyGroupService-Resume NOTIFICATION-TYPE
            OBJECTS { hwStorageAlarmReporting }
            STATUS current
            DESCRIPTION "Recover: Failed To Start The HyperMetro Consistency Group Service"
            --#SEVERITY INFORMATIONAL
            ::= { failedToStartTheHyperMetroConsistencyGroupService 2 }

        -- 1.3.6.1.4.1.2011.2.251.20.1.2.2.15.15364.16
        hyperMetroGroupIsDisconnected3 OBJECT IDENTIFIER ::= { hypermetroconsistencygroup 16 }

        -- 1.3.6.1.4.1.2011.2.251.20.1.2.2.15.15364.16.1
        hyperMetroGroupIsDisconnected3-Fault NOTIFICATION-TYPE
            OBJECTS { hwStorageAlarmReporting }
            STATUS current
            DESCRIPTION "The HyperMetro Consistency Group Is Disconnected And Member LUNs In The Local Consistency Group Cannot Provide Services"
            --#SEVERITY MAJOR
            ::= { hyperMetroGroupIsDisconnected3 1 }

        -- 1.3.6.1.4.1.2011.2.251.20.1.2.2.15.15364.16.2
        hyperMetroGroupIsDisconnected3-Resume NOTIFICATION-TYPE
            OBJECTS { hwStorageAlarmReporting }
            STATUS current
            DESCRIPTION "Recover: The HyperMetro Consistency Group Is Disconnected And Member LUNs In The Local Consistency Group Cannot Provide Services"
            --#SEVERITY INFORMATIONAL
            ::= { hyperMetroGroupIsDisconnected3 2 }

        -- 1.3.6.1.4.1.2011.2.251.20.1.2.2.15.15364.17
        hyperMetroGroupIsDisconnected2 OBJECT IDENTIFIER ::= { hypermetroconsistencygroup 17 }

        -- 1.3.6.1.4.1.2011.2.251.20.1.2.2.15.15364.17.1
        hyperMetroGroupIsDisconnected2-Fault NOTIFICATION-TYPE
            OBJECTS { hwStorageAlarmReporting }
            STATUS current
            DESCRIPTION "The HyperMetro Consistency Group Is Disconnected And Member LUNs In The Local Consistency Group Continue To Provide Services"
            --#SEVERITY MAJOR
            ::= { hyperMetroGroupIsDisconnected2 1 }

        -- 1.3.6.1.4.1.2011.2.251.20.1.2.2.15.15364.17.2
        hyperMetroGroupIsDisconnected2-Resume NOTIFICATION-TYPE
            OBJECTS { hwStorageAlarmReporting }
            STATUS current
            DESCRIPTION "Recover: The HyperMetro Consistency Group Is Disconnected And Member LUNs In The Local Consistency Group Continue To Provide Services"
            --#SEVERITY INFORMATIONAL
            ::= { hyperMetroGroupIsDisconnected2 2 }

        -- 1.3.6.1.4.1.2011.2.251.20.1.2.2.15.15366
        hypermetrovstorepair OBJECT IDENTIFIER ::= { oidBasedTrap 15366 }

        -- 1.3.6.1.4.1.2011.2.251.20.1.2.2.15.15366.5
        theHyperMetroVStorePairIsInPreferredWorkingModeForALongTime OBJECT IDENTIFIER ::= { hypermetrovstorepair 5 }

        -- 1.3.6.1.4.1.2011.2.251.20.1.2.2.15.15366.5.1
        theHyperMetroVStorePairIsInPreferredWorkingModeForALongTime-Fault NOTIFICATION-TYPE
            OBJECTS { hwStorageAlarmReporting }
            STATUS current
            DESCRIPTION "The HyperMetro VStore Pair Is In Preferred Working Mode For A Long Time"
            --#SEVERITY WARNING
            ::= { theHyperMetroVStorePairIsInPreferredWorkingModeForALongTime 1 }

        -- 1.3.6.1.4.1.2011.2.251.20.1.2.2.15.15366.5.2
        theHyperMetroVStorePairIsInPreferredWorkingModeForALongTime-Resume NOTIFICATION-TYPE
            OBJECTS { hwStorageAlarmReporting }
            STATUS current
            DESCRIPTION "Recover: The HyperMetro VStore Pair Is In Preferred Working Mode For A Long Time"
            --#SEVERITY INFORMATIONAL
            ::= { theHyperMetroVStorePairIsInPreferredWorkingModeForALongTime 2 }

        -- 1.3.6.1.4.1.2011.2.251.20.1.2.2.15.16386
        nasprotocol OBJECT IDENTIFIER ::= { oidBasedTrap 16386 }

        -- 1.3.6.1.4.1.2011.2.251.20.1.2.2.15.16386.5
        clientConnectionReachUpperLimit OBJECT IDENTIFIER ::= { nasprotocol 5 }

        -- 1.3.6.1.4.1.2011.2.251.20.1.2.2.15.16386.5.1
        clientConnectionReachUpperLimit-Fault NOTIFICATION-TYPE
            OBJECTS { hwStorageAlarmReporting }
            STATUS current
            DESCRIPTION "The Number Of NAS Client Connections On A Controller Reaches The Upper Limit"
            --#SEVERITY WARNING
            ::= { clientConnectionReachUpperLimit 1 }

        -- 1.3.6.1.4.1.2011.2.251.20.1.2.2.15.16386.5.2
        clientConnectionReachUpperLimit-Resume NOTIFICATION-TYPE
            OBJECTS { hwStorageAlarmReporting }
            STATUS current
            DESCRIPTION "Recover: The Number Of NAS Client Connections On A Controller Reaches The Upper Limit"
            --#SEVERITY INFORMATIONAL
            ::= { clientConnectionReachUpperLimit 2 }

        -- 1.3.6.1.4.1.2011.2.251.20.1.2.2.15.16386.8
        smb2ShareNumReachUpperLimit OBJECT IDENTIFIER ::= { nasprotocol 8 }

        -- 1.3.6.1.4.1.2011.2.251.20.1.2.2.15.16386.8.1
        smb2ShareNumReachUpperLimit-Fault NOTIFICATION-TYPE
            OBJECTS { hwStorageAlarmReporting }
            STATUS current
            DESCRIPTION "The Number Of Share Connections For The SMB2 Protocol Reaches The Upper Limit"
            --#SEVERITY MAJOR
            ::= { smb2ShareNumReachUpperLimit 1 }

        -- 1.3.6.1.4.1.2011.2.251.20.1.2.2.15.16386.8.2
        smb2ShareNumReachUpperLimit-Resume NOTIFICATION-TYPE
            OBJECTS { hwStorageAlarmReporting }
            STATUS current
            DESCRIPTION "Recover: The Number Of Share Connections For The SMB2 Protocol Reaches The Upper Limit"
            --#SEVERITY INFORMATIONAL
            ::= { smb2ShareNumReachUpperLimit 2 }

        -- 1.3.6.1.4.1.2011.2.251.20.1.2.2.15.16386.41
        servicePortConflict OBJECT IDENTIFIER ::= { nasprotocol 41 }

        -- 1.3.6.1.4.1.2011.2.251.20.1.2.2.15.16386.41.1
        servicePortConflict-Fault NOTIFICATION-TYPE
            OBJECTS { hwStorageAlarmReporting }
            STATUS current
            DESCRIPTION "A Service Port Conflicts"
            --#SEVERITY MAJOR
            ::= { servicePortConflict 1 }

        -- 1.3.6.1.4.1.2011.2.251.20.1.2.2.15.16386.41.2
        servicePortConflict-Resume NOTIFICATION-TYPE
            OBJECTS { hwStorageAlarmReporting }
            STATUS current
            DESCRIPTION "Recover: A Service Port Conflicts"
            --#SEVERITY INFORMATIONAL
            ::= { servicePortConflict 2 }

        -- 1.3.6.1.4.1.2011.2.251.20.1.2.2.15.16386.42
        ldapServiceUnavailable OBJECT IDENTIFIER ::= { nasprotocol 42 }

        -- 1.3.6.1.4.1.2011.2.251.20.1.2.2.15.16386.42.1
        ldapServiceUnavailable-Fault NOTIFICATION-TYPE
            OBJECTS { hwStorageAlarmReporting }
            STATUS current
            DESCRIPTION "LDAP Domain Service Is Unavailable"
            --#SEVERITY MAJOR
            ::= { ldapServiceUnavailable 1 }

        -- 1.3.6.1.4.1.2011.2.251.20.1.2.2.15.16386.42.2
        ldapServiceUnavailable-Resume NOTIFICATION-TYPE
            OBJECTS { hwStorageAlarmReporting }
            STATUS current
            DESCRIPTION "Recover: LDAP Domain Service Is Unavailable"
            --#SEVERITY INFORMATIONAL
            ::= { ldapServiceUnavailable 2 }

        -- 1.3.6.1.4.1.2011.2.251.20.1.2.2.15.16386.43
        nisServiceUnavailable OBJECT IDENTIFIER ::= { nasprotocol 43 }

        -- 1.3.6.1.4.1.2011.2.251.20.1.2.2.15.16386.43.1
        nisServiceUnavailable-Fault NOTIFICATION-TYPE
            OBJECTS { hwStorageAlarmReporting }
            STATUS current
            DESCRIPTION "NIS Domain Service Is Unavailable"
            --#SEVERITY MAJOR
            ::= { nisServiceUnavailable 1 }

        -- 1.3.6.1.4.1.2011.2.251.20.1.2.2.15.16386.43.2
        nisServiceUnavailable-Resume NOTIFICATION-TYPE
            OBJECTS { hwStorageAlarmReporting }
            STATUS current
            DESCRIPTION "Recover: NIS Domain Service Is Unavailable"
            --#SEVERITY INFORMATIONAL
            ::= { nisServiceUnavailable 2 }

        -- 1.3.6.1.4.1.2011.2.251.20.1.2.2.15.16386.44
        adDomainServiceUnavailable OBJECT IDENTIFIER ::= { nasprotocol 44 }

        -- 1.3.6.1.4.1.2011.2.251.20.1.2.2.15.16386.44.1
        adDomainServiceUnavailable-Fault NOTIFICATION-TYPE
            OBJECTS { hwStorageAlarmReporting }
            STATUS current
            DESCRIPTION "AD Domain Service Is Unavailable"
            --#SEVERITY MAJOR
            ::= { adDomainServiceUnavailable 1 }

        -- 1.3.6.1.4.1.2011.2.251.20.1.2.2.15.16386.44.2
        adDomainServiceUnavailable-Resume NOTIFICATION-TYPE
            OBJECTS { hwStorageAlarmReporting }
            STATUS current
            DESCRIPTION "Recover: AD Domain Service Is Unavailable"
            --#SEVERITY INFORMATIONAL
            ::= { adDomainServiceUnavailable 2 }

        -- 1.3.6.1.4.1.2011.2.251.20.1.2.2.15.16386.45
        domainDNSServiceUnavailable OBJECT IDENTIFIER ::= { nasprotocol 45 }

        -- 1.3.6.1.4.1.2011.2.251.20.1.2.2.15.16386.45.1
        domainDNSServiceUnavailable-Fault NOTIFICATION-TYPE
            OBJECTS { hwStorageAlarmReporting }
            STATUS current
            DESCRIPTION "DNS Service Is Unavailable"
            --#SEVERITY MAJOR
            ::= { domainDNSServiceUnavailable 1 }

        -- 1.3.6.1.4.1.2011.2.251.20.1.2.2.15.16386.45.2
        domainDNSServiceUnavailable-Resume NOTIFICATION-TYPE
            OBJECTS { hwStorageAlarmReporting }
            STATUS current
            DESCRIPTION "Recover: DNS Service Is Unavailable"
            --#SEVERITY INFORMATIONAL
            ::= { domainDNSServiceUnavailable 2 }

        -- 1.3.6.1.4.1.2011.2.251.20.1.2.2.15.16386.46
        fileLockNumReachUpperLimit2 OBJECT IDENTIFIER ::= { nasprotocol 46 }

        -- 1.3.6.1.4.1.2011.2.251.20.1.2.2.15.16386.46.1
        fileLockNumReachUpperLimit2-Fault NOTIFICATION-TYPE
            OBJECTS { hwStorageAlarmReporting }
            STATUS current
            DESCRIPTION "The Number Of Files Opened On A Single Controller For The NAS Protocol Reaches The Upper Limit"
            --#SEVERITY MAJOR
            ::= { fileLockNumReachUpperLimit2 1 }

        -- 1.3.6.1.4.1.2011.2.251.20.1.2.2.15.16386.46.2
        fileLockNumReachUpperLimit2-Resume NOTIFICATION-TYPE
            OBJECTS { hwStorageAlarmReporting }
            STATUS current
            DESCRIPTION "Recover: The Number Of Files Opened On A Single Controller For The NAS Protocol Reaches The Upper Limit"
            --#SEVERITY INFORMATIONAL
            ::= { fileLockNumReachUpperLimit2 2 }

        -- 1.3.6.1.4.1.2011.2.251.20.1.2.2.15.16386.47
        fileLockNumReachUpperLimit1 OBJECT IDENTIFIER ::= { nasprotocol 47 }

        -- 1.3.6.1.4.1.2011.2.251.20.1.2.2.15.16386.47.1
        fileLockNumReachUpperLimit1-Fault NOTIFICATION-TYPE
            OBJECTS { hwStorageAlarmReporting }
            STATUS current
            DESCRIPTION "The Number Of File Open Locks For The NAS Protocol Reaches The Upper Limit"
            --#SEVERITY MAJOR
            ::= { fileLockNumReachUpperLimit1 1 }

        -- 1.3.6.1.4.1.2011.2.251.20.1.2.2.15.16386.47.2
        fileLockNumReachUpperLimit1-Resume NOTIFICATION-TYPE
            OBJECTS { hwStorageAlarmReporting }
            STATUS current
            DESCRIPTION "Recover: The Number Of File Open Locks For The NAS Protocol Reaches The Upper Limit"
            --#SEVERITY INFORMATIONAL
            ::= { fileLockNumReachUpperLimit1 2 }

        -- 1.3.6.1.4.1.2011.2.251.20.1.2.2.15.16386.51
        fileLockNumReachUpperLimit OBJECT IDENTIFIER ::= { nasprotocol 51 }

        -- 1.3.6.1.4.1.2011.2.251.20.1.2.2.15.16386.51.1
        fileLockNumReachUpperLimit-Fault NOTIFICATION-TYPE
            OBJECTS { hwStorageAlarmReporting }
            STATUS current
            DESCRIPTION "The Number Of File Range Locks For The NAS Protocol Reaches The Upper Limit"
            --#SEVERITY MAJOR
            ::= { fileLockNumReachUpperLimit 1 }

        -- 1.3.6.1.4.1.2011.2.251.20.1.2.2.15.16386.51.2
        fileLockNumReachUpperLimit-Resume NOTIFICATION-TYPE
            OBJECTS { hwStorageAlarmReporting }
            STATUS current
            DESCRIPTION "Recover: The Number Of File Range Locks For The NAS Protocol Reaches The Upper Limit"
            --#SEVERITY INFORMATIONAL
            ::= { fileLockNumReachUpperLimit 2 }

        -- 1.3.6.1.4.1.2011.2.251.20.1.2.2.15.16386.52
        theNumberOfLockRescResourcesForTheNASProtocolReachesTheUpperLimit OBJECT IDENTIFIER ::= { nasprotocol 52 }

        -- 1.3.6.1.4.1.2011.2.251.20.1.2.2.15.16386.52.1
        theNumberOfLockRescResourcesForTheNASProtocolReachesTheUpperLimit-Fault NOTIFICATION-TYPE
            OBJECTS { hwStorageAlarmReporting }
            STATUS current
            DESCRIPTION "The Number Of LockResc Resources For The NAS Protocol Reaches The Upper Limit"
            --#SEVERITY MAJOR
            ::= { theNumberOfLockRescResourcesForTheNASProtocolReachesTheUpperLimit 1 }

        -- 1.3.6.1.4.1.2011.2.251.20.1.2.2.15.16386.52.2
        theNumberOfLockRescResourcesForTheNASProtocolReachesTheUpperLimit-Resume NOTIFICATION-TYPE
            OBJECTS { hwStorageAlarmReporting }
            STATUS current
            DESCRIPTION "Recover: The Number Of LockResc Resources For The NAS Protocol Reaches The Upper Limit"
            --#SEVERITY INFORMATIONAL
            ::= { theNumberOfLockRescResourcesForTheNASProtocolReachesTheUpperLimit 2 }

        -- 1.3.6.1.4.1.2011.2.251.20.1.2.2.15.16386.53
        theNumberOfPublicResourceEntryLocksForTheNASProtocolReachesTheUpperLimit OBJECT IDENTIFIER ::= { nasprotocol 53 }

        -- 1.3.6.1.4.1.2011.2.251.20.1.2.2.15.16386.53.1
        theNumberOfPublicResourceEntryLocksForTheNASProtocolReachesTheUpperLimit-Fault NOTIFICATION-TYPE
            OBJECTS { hwStorageAlarmReporting }
            STATUS current
            DESCRIPTION "The Number Of Public Resource Entry Locks For The NAS Protocol Reaches The Upper Limit"
            --#SEVERITY MAJOR
            ::= { theNumberOfPublicResourceEntryLocksForTheNASProtocolReachesTheUpperLimit 1 }

        -- 1.3.6.1.4.1.2011.2.251.20.1.2.2.15.16386.53.2
        theNumberOfPublicResourceEntryLocksForTheNASProtocolReachesTheUpperLimit-Resume NOTIFICATION-TYPE
            OBJECTS { hwStorageAlarmReporting }
            STATUS current
            DESCRIPTION "Recover: The Number Of Public Resource Entry Locks For The NAS Protocol Reaches The Upper Limit"
            --#SEVERITY INFORMATIONAL
            ::= { theNumberOfPublicResourceEntryLocksForTheNASProtocolReachesTheUpperLimit 2 }

        -- 1.3.6.1.4.1.2011.2.251.20.1.2.2.15.16386.54
        theNumberOfPublicResourceNameLocksForTheNASProtocolReachesTheUpperLimit OBJECT IDENTIFIER ::= { nasprotocol 54 }

        -- 1.3.6.1.4.1.2011.2.251.20.1.2.2.15.16386.54.1
        theNumberOfPublicResourceNameLocksForTheNASProtocolReachesTheUpperLimit-Fault NOTIFICATION-TYPE
            OBJECTS { hwStorageAlarmReporting }
            STATUS current
            DESCRIPTION "The Number Of Public Resource Name Locks For The NAS Protocol Reaches The Upper Limit"
            --#SEVERITY MAJOR
            ::= { theNumberOfPublicResourceNameLocksForTheNASProtocolReachesTheUpperLimit 1 }

        -- 1.3.6.1.4.1.2011.2.251.20.1.2.2.15.16386.54.2
        theNumberOfPublicResourceNameLocksForTheNASProtocolReachesTheUpperLimit-Resume NOTIFICATION-TYPE
            OBJECTS { hwStorageAlarmReporting }
            STATUS current
            DESCRIPTION "Recover: The Number Of Public Resource Name Locks For The NAS Protocol Reaches The Upper Limit"
            --#SEVERITY INFORMATIONAL
            ::= { theNumberOfPublicResourceNameLocksForTheNASProtocolReachesTheUpperLimit 2 }

        -- 1.3.6.1.4.1.2011.2.251.20.1.2.2.15.16386.55
        theNumberOfBlockReqBlockLocksForTheNASProtocolReachesTheUpperLimit OBJECT IDENTIFIER ::= { nasprotocol 55 }

        -- 1.3.6.1.4.1.2011.2.251.20.1.2.2.15.16386.55.1
        theNumberOfBlockReqBlockLocksForTheNASProtocolReachesTheUpperLimit-Fault NOTIFICATION-TYPE
            OBJECTS { hwStorageAlarmReporting }
            STATUS current
            DESCRIPTION "The Number Of BlockReq Block Locks For The NAS Protocol Reaches The Upper Limit"
            --#SEVERITY MAJOR
            ::= { theNumberOfBlockReqBlockLocksForTheNASProtocolReachesTheUpperLimit 1 }

        -- 1.3.6.1.4.1.2011.2.251.20.1.2.2.15.16386.55.2
        theNumberOfBlockReqBlockLocksForTheNASProtocolReachesTheUpperLimit-Resume NOTIFICATION-TYPE
            OBJECTS { hwStorageAlarmReporting }
            STATUS current
            DESCRIPTION "Recover: The Number Of BlockReq Block Locks For The NAS Protocol Reaches The Upper Limit"
            --#SEVERITY INFORMATIONAL
            ::= { theNumberOfBlockReqBlockLocksForTheNASProtocolReachesTheUpperLimit 2 }

        -- 1.3.6.1.4.1.2011.2.251.20.1.2.2.15.16386.56
        theNumberOfSessionsForTheSMB2ProtocolReachesTheUpperLimit OBJECT IDENTIFIER ::= { nasprotocol 56 }

        -- 1.3.6.1.4.1.2011.2.251.20.1.2.2.15.16386.56.1
        theNumberOfSessionsForTheSMB2ProtocolReachesTheUpperLimit-Fault NOTIFICATION-TYPE
            OBJECTS { hwStorageAlarmReporting }
            STATUS current
            DESCRIPTION "The Number Of Sessions For The SMB2 Protocol Reaches The Upper Limit"
            --#SEVERITY MAJOR
            ::= { theNumberOfSessionsForTheSMB2ProtocolReachesTheUpperLimit 1 }

        -- 1.3.6.1.4.1.2011.2.251.20.1.2.2.15.16386.56.2
        theNumberOfSessionsForTheSMB2ProtocolReachesTheUpperLimit-Resume NOTIFICATION-TYPE
            OBJECTS { hwStorageAlarmReporting }
            STATUS current
            DESCRIPTION "Recover: The Number Of Sessions For The SMB2 Protocol Reaches The Upper Limit"
            --#SEVERITY INFORMATIONAL
            ::= { theNumberOfSessionsForTheSMB2ProtocolReachesTheUpperLimit 2 }

        -- 1.3.6.1.4.1.2011.2.251.20.1.2.2.15.16386.62
        adDomainServerNetworkAbnormal1 OBJECT IDENTIFIER ::= { nasprotocol 62 }

        -- 1.3.6.1.4.1.2011.2.251.20.1.2.2.15.16386.62.1
        adDomainServerNetworkAbnormal1-Fault NOTIFICATION-TYPE
            OBJECTS { hwStorageAlarmReporting }
            STATUS current
            DESCRIPTION "The Communication Network Of The AD Domain Server Is Abnormal"
            --#SEVERITY WARNING
            ::= { adDomainServerNetworkAbnormal1 1 }

        -- 1.3.6.1.4.1.2011.2.251.20.1.2.2.15.16386.62.2
        adDomainServerNetworkAbnormal1-Resume NOTIFICATION-TYPE
            OBJECTS { hwStorageAlarmReporting }
            STATUS current
            DESCRIPTION "Recover: The Communication Network Of The AD Domain Server Is Abnormal"
            --#SEVERITY INFORMATIONAL
            ::= { adDomainServerNetworkAbnormal1 2 }

        -- 1.3.6.1.4.1.2011.2.251.20.1.2.2.15.16386.63
        domainDNSServerNetworkAbnormal1 OBJECT IDENTIFIER ::= { nasprotocol 63 }

        -- 1.3.6.1.4.1.2011.2.251.20.1.2.2.15.16386.63.1
        domainDNSServerNetworkAbnormal1-Fault NOTIFICATION-TYPE
            OBJECTS { hwStorageAlarmReporting }
            STATUS current
            DESCRIPTION "The DNS Server Communication Network Is Abnormal"
            --#SEVERITY WARNING
            ::= { domainDNSServerNetworkAbnormal1 1 }

        -- 1.3.6.1.4.1.2011.2.251.20.1.2.2.15.16386.63.2
        domainDNSServerNetworkAbnormal1-Resume NOTIFICATION-TYPE
            OBJECTS { hwStorageAlarmReporting }
            STATUS current
            DESCRIPTION "Recover: The DNS Server Communication Network Is Abnormal"
            --#SEVERITY INFORMATIONAL
            ::= { domainDNSServerNetworkAbnormal1 2 }

        -- 1.3.6.1.4.1.2011.2.251.20.1.2.2.15.16386.64
        ldapServerNetworkAbnormal1 OBJECT IDENTIFIER ::= { nasprotocol 64 }

        -- 1.3.6.1.4.1.2011.2.251.20.1.2.2.15.16386.64.1
        ldapServerNetworkAbnormal1-Fault NOTIFICATION-TYPE
            OBJECTS { hwStorageAlarmReporting }
            STATUS current
            DESCRIPTION "The Communication Network Of The LDAP Domain Server Is Abnormal"
            --#SEVERITY WARNING
            ::= { ldapServerNetworkAbnormal1 1 }

        -- 1.3.6.1.4.1.2011.2.251.20.1.2.2.15.16386.64.2
        ldapServerNetworkAbnormal1-Resume NOTIFICATION-TYPE
            OBJECTS { hwStorageAlarmReporting }
            STATUS current
            DESCRIPTION "Recover: The Communication Network Of The LDAP Domain Server Is Abnormal"
            --#SEVERITY INFORMATIONAL
            ::= { ldapServerNetworkAbnormal1 2 }

        -- 1.3.6.1.4.1.2011.2.251.20.1.2.2.15.16386.68
        nisServerNetworkAbnormal1 OBJECT IDENTIFIER ::= { nasprotocol 68 }

        -- 1.3.6.1.4.1.2011.2.251.20.1.2.2.15.16386.68.1
        nisServerNetworkAbnormal1-Fault NOTIFICATION-TYPE
            OBJECTS { hwStorageAlarmReporting }
            STATUS current
            DESCRIPTION "The Communication Network Of The NIS Domain Server Is Abnormal"
            --#SEVERITY WARNING
            ::= { nisServerNetworkAbnormal1 1 }

        -- 1.3.6.1.4.1.2011.2.251.20.1.2.2.15.16386.68.2
        nisServerNetworkAbnormal1-Resume NOTIFICATION-TYPE
            OBJECTS { hwStorageAlarmReporting }
            STATUS current
            DESCRIPTION "Recover: The Communication Network Of The NIS Domain Server Is Abnormal"
            --#SEVERITY INFORMATIONAL
            ::= { nisServerNetworkAbnormal1 2 }

        -- 1.3.6.1.4.1.2011.2.251.20.1.2.2.15.16386.73
        domainDNSServerNetworkAbnormal OBJECT IDENTIFIER ::= { nasprotocol 73 }

        -- 1.3.6.1.4.1.2011.2.251.20.1.2.2.15.16386.73.1
        domainDNSServerNetworkAbnormal-Fault NOTIFICATION-TYPE
            OBJECTS { hwStorageAlarmReporting }
            STATUS current
            DESCRIPTION "The Communication Network With The DNS Server Is Abnormal"
            --#SEVERITY WARNING
            ::= { domainDNSServerNetworkAbnormal 1 }

        -- 1.3.6.1.4.1.2011.2.251.20.1.2.2.15.16386.73.2
        domainDNSServerNetworkAbnormal-Resume NOTIFICATION-TYPE
            OBJECTS { hwStorageAlarmReporting }
            STATUS current
            DESCRIPTION "Recover: The Communication Network With The DNS Server Is Abnormal"
            --#SEVERITY INFORMATIONAL
            ::= { domainDNSServerNetworkAbnormal 2 }

        -- 1.3.6.1.4.1.2011.2.251.20.1.2.2.15.16386.74
        ldapServerNetworkAbnormal OBJECT IDENTIFIER ::= { nasprotocol 74 }

        -- 1.3.6.1.4.1.2011.2.251.20.1.2.2.15.16386.74.1
        ldapServerNetworkAbnormal-Fault NOTIFICATION-TYPE
            OBJECTS { hwStorageAlarmReporting }
            STATUS current
            DESCRIPTION "The Communication Network With The LDAP Domain Server Is Abnormal"
            --#SEVERITY WARNING
            ::= { ldapServerNetworkAbnormal 1 }

        -- 1.3.6.1.4.1.2011.2.251.20.1.2.2.15.16386.74.2
        ldapServerNetworkAbnormal-Resume NOTIFICATION-TYPE
            OBJECTS { hwStorageAlarmReporting }
            STATUS current
            DESCRIPTION "Recover: The Communication Network With The LDAP Domain Server Is Abnormal"
            --#SEVERITY INFORMATIONAL
            ::= { ldapServerNetworkAbnormal 2 }

        -- 1.3.6.1.4.1.2011.2.251.20.1.2.2.15.16386.75
        nisServerNetworkAbnormal OBJECT IDENTIFIER ::= { nasprotocol 75 }

        -- 1.3.6.1.4.1.2011.2.251.20.1.2.2.15.16386.75.1
        nisServerNetworkAbnormal-Fault NOTIFICATION-TYPE
            OBJECTS { hwStorageAlarmReporting }
            STATUS current
            DESCRIPTION "The Communication Network With The NIS Domain Server Is Abnormal"
            --#SEVERITY WARNING
            ::= { nisServerNetworkAbnormal 1 }

        -- 1.3.6.1.4.1.2011.2.251.20.1.2.2.15.16386.75.2
        nisServerNetworkAbnormal-Resume NOTIFICATION-TYPE
            OBJECTS { hwStorageAlarmReporting }
            STATUS current
            DESCRIPTION "Recover: The Communication Network With The NIS Domain Server Is Abnormal"
            --#SEVERITY INFORMATIONAL
            ::= { nisServerNetworkAbnormal 2 }

        -- 1.3.6.1.4.1.2011.2.251.20.1.2.2.15.16386.76
        adDomainServerNetworkAbnormal OBJECT IDENTIFIER ::= { nasprotocol 76 }

        -- 1.3.6.1.4.1.2011.2.251.20.1.2.2.15.16386.76.1
        adDomainServerNetworkAbnormal-Fault NOTIFICATION-TYPE
            OBJECTS { hwStorageAlarmReporting }
            STATUS current
            DESCRIPTION "The Communication Network With The AD Domain Server Is Abnormal"
            --#SEVERITY WARNING
            ::= { adDomainServerNetworkAbnormal 1 }

        -- 1.3.6.1.4.1.2011.2.251.20.1.2.2.15.16386.76.2
        adDomainServerNetworkAbnormal-Resume NOTIFICATION-TYPE
            OBJECTS { hwStorageAlarmReporting }
            STATUS current
            DESCRIPTION "Recover: The Communication Network With The AD Domain Server Is Abnormal"
            --#SEVERITY INFORMATIONAL
            ::= { adDomainServerNetworkAbnormal 2 }

        -- 1.3.6.1.4.1.2011.2.251.20.1.2.2.15.16386.77
        theNumberOfOpenedSMB2SharesHasReachedTheUpperLimit OBJECT IDENTIFIER ::= { nasprotocol 77 }

        -- 1.3.6.1.4.1.2011.2.251.20.1.2.2.15.16386.77.1
        theNumberOfOpenedSMB2SharesHasReachedTheUpperLimit-Fault NOTIFICATION-TYPE
            OBJECTS { hwStorageAlarmReporting }
            STATUS current
            DESCRIPTION "The Number Of Opened SMB2 Shares Has Reached The Upper Limit"
            --#SEVERITY MAJOR
            ::= { theNumberOfOpenedSMB2SharesHasReachedTheUpperLimit 1 }

        -- 1.3.6.1.4.1.2011.2.251.20.1.2.2.15.16386.77.2
        theNumberOfOpenedSMB2SharesHasReachedTheUpperLimit-Resume NOTIFICATION-TYPE
            OBJECTS { hwStorageAlarmReporting }
            STATUS current
            DESCRIPTION "Recover: The Number Of Opened SMB2 Shares Has Reached The Upper Limit"
            --#SEVERITY INFORMATIONAL
            ::= { theNumberOfOpenedSMB2SharesHasReachedTheUpperLimit 2 }

        -- 1.3.6.1.4.1.2011.2.251.20.1.2.2.15.16386.82
        theDNSServiceIsAbnormal1 OBJECT IDENTIFIER ::= { nasprotocol 82 }

        -- 1.3.6.1.4.1.2011.2.251.20.1.2.2.15.16386.82.1
        theDNSServiceIsAbnormal1-Fault NOTIFICATION-TYPE
            OBJECTS { hwStorageAlarmReporting }
            STATUS current
            DESCRIPTION "The DNS Service Is Abnormal"
            --#SEVERITY WARNING
            ::= { theDNSServiceIsAbnormal1 1 }

        -- 1.3.6.1.4.1.2011.2.251.20.1.2.2.15.16386.82.2
        theDNSServiceIsAbnormal1-Resume NOTIFICATION-TYPE
            OBJECTS { hwStorageAlarmReporting }
            STATUS current
            DESCRIPTION "Recover: The DNS Service Is Abnormal"
            --#SEVERITY INFORMATIONAL
            ::= { theDNSServiceIsAbnormal1 2 }

        -- 1.3.6.1.4.1.2011.2.251.20.1.2.2.15.16386.84
        clientConcurrencyReachUpperLimit OBJECT IDENTIFIER ::= { nasprotocol 84 }

        -- 1.3.6.1.4.1.2011.2.251.20.1.2.2.15.16386.84.1
        clientConcurrencyReachUpperLimit-Fault NOTIFICATION-TYPE
            OBJECTS { hwStorageAlarmReporting }
            STATUS current
            DESCRIPTION "The Number Of Concurrent NAS Clients On The Controller Reaches The Upper Limit"
            --#SEVERITY WARNING
            ::= { clientConcurrencyReachUpperLimit 1 }

        -- 1.3.6.1.4.1.2011.2.251.20.1.2.2.15.16386.84.2
        clientConcurrencyReachUpperLimit-Resume NOTIFICATION-TYPE
            OBJECTS { hwStorageAlarmReporting }
            STATUS current
            DESCRIPTION "Recover: The Number Of Concurrent NAS Clients On The Controller Reaches The Upper Limit"
            --#SEVERITY INFORMATIONAL
            ::= { clientConcurrencyReachUpperLimit 2 }

        -- 1.3.6.1.4.1.2011.2.251.20.1.2.2.15.16386.95
        smbHardCryptFaulty OBJECT IDENTIFIER ::= { nasprotocol 95 }

        -- 1.3.6.1.4.1.2011.2.251.20.1.2.2.15.16386.95.1
        smbHardCryptFaulty-Fault NOTIFICATION-TYPE
            OBJECTS { hwStorageAlarmReporting }
            STATUS current
            DESCRIPTION "SMB Hard Encryption And Decryption Fault"
            --#SEVERITY MAJOR
            ::= { smbHardCryptFaulty 1 }

        -- 1.3.6.1.4.1.2011.2.251.20.1.2.2.15.16386.95.2
        smbHardCryptFaulty-Resume NOTIFICATION-TYPE
            OBJECTS { hwStorageAlarmReporting }
            STATUS current
            DESCRIPTION "Recover: SMB Hard Encryption And Decryption Fault"
            --#SEVERITY INFORMATIONAL
            ::= { smbHardCryptFaulty 2 }

        -- 1.3.6.1.4.1.2011.2.251.20.1.2.2.15.16386.96
        adDomainServiceAbnormal OBJECT IDENTIFIER ::= { nasprotocol 96 }

        -- 1.3.6.1.4.1.2011.2.251.20.1.2.2.15.16386.96.1
        adDomainServiceAbnormal-Fault NOTIFICATION-TYPE
            OBJECTS { hwStorageAlarmReporting }
            STATUS current
            DESCRIPTION "The AD Domain Service Is Abnormal"
            --#SEVERITY WARNING
            ::= { adDomainServiceAbnormal 1 }

        -- 1.3.6.1.4.1.2011.2.251.20.1.2.2.15.16386.96.2
        adDomainServiceAbnormal-Resume NOTIFICATION-TYPE
            OBJECTS { hwStorageAlarmReporting }
            STATUS current
            DESCRIPTION "Recover: The AD Domain Service Is Abnormal"
            --#SEVERITY INFORMATIONAL
            ::= { adDomainServiceAbnormal 2 }

        -- 1.3.6.1.4.1.2011.2.251.20.1.2.2.15.16386.97
        theDNSServiceIsAbnormal OBJECT IDENTIFIER ::= { nasprotocol 97 }

        -- 1.3.6.1.4.1.2011.2.251.20.1.2.2.15.16386.97.1
        theDNSServiceIsAbnormal-Fault NOTIFICATION-TYPE
            OBJECTS { hwStorageAlarmReporting }
            STATUS current
            DESCRIPTION "The DNS Service Is Abnormal"
            --#SEVERITY WARNING
            ::= { theDNSServiceIsAbnormal 1 }

        -- 1.3.6.1.4.1.2011.2.251.20.1.2.2.15.16386.97.2
        theDNSServiceIsAbnormal-Resume NOTIFICATION-TYPE
            OBJECTS { hwStorageAlarmReporting }
            STATUS current
            DESCRIPTION "Recover: The DNS Service Is Abnormal"
            --#SEVERITY INFORMATIONAL
            ::= { theDNSServiceIsAbnormal 2 }

        -- 1.3.6.1.4.1.2011.2.251.20.1.2.2.15.16386.107
        theRemoteS3DeviceOfSmartMobilityRespondsSlowly OBJECT IDENTIFIER ::= { nasprotocol 107 }

        -- 1.3.6.1.4.1.2011.2.251.20.1.2.2.15.16386.107.1
        theRemoteS3DeviceOfSmartMobilityRespondsSlowly-Fault NOTIFICATION-TYPE
            OBJECTS { hwStorageAlarmReporting }
            STATUS current
            DESCRIPTION "The Remote S3 Device Of SmartMobility Responds Slowly"
            --#SEVERITY WARNING
            ::= { theRemoteS3DeviceOfSmartMobilityRespondsSlowly 1 }

        -- 1.3.6.1.4.1.2011.2.251.20.1.2.2.15.16386.107.2
        theRemoteS3DeviceOfSmartMobilityRespondsSlowly-Resume NOTIFICATION-TYPE
            OBJECTS { hwStorageAlarmReporting }
            STATUS current
            DESCRIPTION "Recover: The Remote S3 Device Of SmartMobility Responds Slowly"
            --#SEVERITY INFORMATIONAL
            ::= { theRemoteS3DeviceOfSmartMobilityRespondsSlowly 2 }

        -- 1.3.6.1.4.1.2011.2.251.20.1.2.2.15.16386.108
        theLDAPCRLHasExpired OBJECT IDENTIFIER ::= { nasprotocol 108 }

        -- 1.3.6.1.4.1.2011.2.251.20.1.2.2.15.16386.108.1
        theLDAPCRLHasExpired-Fault NOTIFICATION-TYPE
            OBJECTS { hwStorageAlarmReporting }
            STATUS current
            DESCRIPTION "The LDAP CRL Has Expired"
            --#SEVERITY WARNING
            ::= { theLDAPCRLHasExpired 1 }

        -- 1.3.6.1.4.1.2011.2.251.20.1.2.2.15.16386.108.2
        theLDAPCRLHasExpired-Resume NOTIFICATION-TYPE
            OBJECTS { hwStorageAlarmReporting }
            STATUS current
            DESCRIPTION "Recover: The LDAP CRL Has Expired"
            --#SEVERITY INFORMATIONAL
            ::= { theLDAPCRLHasExpired 2 }

        -- 1.3.6.1.4.1.2011.2.251.20.1.2.2.15.16386.109
        clientNfsORdmaConnMax OBJECT IDENTIFIER ::= { nasprotocol 109 }

        -- 1.3.6.1.4.1.2011.2.251.20.1.2.2.15.16386.109.1
        clientNfsORdmaConnMax-Fault NOTIFICATION-TYPE
            OBJECTS { hwStorageAlarmReporting }
            STATUS current
            DESCRIPTION "The Number Of Used QPs of A RoCE NIC On A Controller Reaches The Upper Limit"
            --#SEVERITY WARNING
            ::= { clientNfsORdmaConnMax 1 }

        -- 1.3.6.1.4.1.2011.2.251.20.1.2.2.15.16386.109.2
        clientNfsORdmaConnMax-Resume NOTIFICATION-TYPE
            OBJECTS { hwStorageAlarmReporting }
            STATUS current
            DESCRIPTION "Recover: The Number Of Used QPs of A RoCE NIC On A Controller Reaches The Upper Limit"
            --#SEVERITY INFORMATIONAL
            ::= { clientNfsORdmaConnMax 2 }

        -- 1.3.6.1.4.1.2011.2.251.20.1.2.2.15.16386.110
        theBranchcacheFunctionIsUnavailable OBJECT IDENTIFIER ::= { nasprotocol 110 }

        -- 1.3.6.1.4.1.2011.2.251.20.1.2.2.15.16386.110.1
        theBranchcacheFunctionIsUnavailable-Fault NOTIFICATION-TYPE
            OBJECTS { hwStorageAlarmReporting }
            STATUS current
            DESCRIPTION "The Branchcache Function Is Unavailable"
            --#SEVERITY MAJOR
            ::= { theBranchcacheFunctionIsUnavailable 1 }

        -- 1.3.6.1.4.1.2011.2.251.20.1.2.2.15.16386.110.2
        theBranchcacheFunctionIsUnavailable-Resume NOTIFICATION-TYPE
            OBJECTS { hwStorageAlarmReporting }
            STATUS current
            DESCRIPTION "Recover: The Branchcache Function Is Unavailable"
            --#SEVERITY INFORMATIONAL
            ::= { theBranchcacheFunctionIsUnavailable 2 }

        -- 1.3.6.1.4.1.2011.2.251.20.1.2.2.15.16386.111
        pwdOfResUserHasExpired OBJECT IDENTIFIER ::= { nasprotocol 111 }

        -- 1.3.6.1.4.1.2011.2.251.20.1.2.2.15.16386.111.1
        pwdOfResUserHasExpired-Fault NOTIFICATION-TYPE
            OBJECTS { hwStorageAlarmReporting }
            STATUS current
            DESCRIPTION "The Password Of A Windows User Has Expired"
            --#SEVERITY MAJOR
            ::= { pwdOfResUserHasExpired 1 }

        -- 1.3.6.1.4.1.2011.2.251.20.1.2.2.15.16386.111.2
        pwdOfResUserHasExpired-Resume NOTIFICATION-TYPE
            OBJECTS { hwStorageAlarmReporting }
            STATUS current
            DESCRIPTION "Recover: The Password Of A Windows User Has Expired"
            --#SEVERITY INFORMATIONAL
            ::= { pwdOfResUserHasExpired 2 }

        -- 1.3.6.1.4.1.2011.2.251.20.1.2.2.15.16386.112
        thisAlarmIsGeneratedWhenPacketControlOccurs OBJECT IDENTIFIER ::= { nasprotocol 112 }

        -- 1.3.6.1.4.1.2011.2.251.20.1.2.2.15.16386.112.1
        thisAlarmIsGeneratedWhenPacketControlOccurs-Fault NOTIFICATION-TYPE
            OBJECTS { hwStorageAlarmReporting }
            STATUS current
            DESCRIPTION "This Alarm Is Generated When Packet Control Occurs"
            --#SEVERITY MAJOR
            ::= { thisAlarmIsGeneratedWhenPacketControlOccurs 1 }

        -- 1.3.6.1.4.1.2011.2.251.20.1.2.2.15.16386.112.2
        thisAlarmIsGeneratedWhenPacketControlOccurs-Resume NOTIFICATION-TYPE
            OBJECTS { hwStorageAlarmReporting }
            STATUS current
            DESCRIPTION "Recover: This Alarm Is Generated When Packet Control Occurs"
            --#SEVERITY INFORMATIONAL
            ::= { thisAlarmIsGeneratedWhenPacketControlOccurs 2 }

        -- 1.3.6.1.4.1.2011.2.251.20.1.2.2.15.16386.113
        windowsUserHasBeenLocked OBJECT IDENTIFIER ::= { nasprotocol 113 }

        -- 1.3.6.1.4.1.2011.2.251.20.1.2.2.15.16386.113.1
        windowsUserHasBeenLocked-Fault NOTIFICATION-TYPE
            OBJECTS { hwStorageAlarmReporting }
            STATUS current
            DESCRIPTION "A Windows User Has Been Locked"
            --#SEVERITY MAJOR
            ::= { windowsUserHasBeenLocked 1 }

        -- 1.3.6.1.4.1.2011.2.251.20.1.2.2.15.16386.113.2
        windowsUserHasBeenLocked-Resume NOTIFICATION-TYPE
            OBJECTS { hwStorageAlarmReporting }
            STATUS current
            DESCRIPTION "Recover: A Windows User Has Been Locked"
            --#SEVERITY INFORMATIONAL
            ::= { windowsUserHasBeenLocked 2 }

        -- 1.3.6.1.4.1.2011.2.251.20.1.2.2.15.16386.114
        pwdOfResUserIsAboutToExpire OBJECT IDENTIFIER ::= { nasprotocol 114 }

        -- 1.3.6.1.4.1.2011.2.251.20.1.2.2.15.16386.114.1
        pwdOfResUserIsAboutToExpire-Fault NOTIFICATION-TYPE
            OBJECTS { hwStorageAlarmReporting }
            STATUS current
            DESCRIPTION "The Password Of A Windows User Is About To Expire"
            --#SEVERITY WARNING
            ::= { pwdOfResUserIsAboutToExpire 1 }

        -- 1.3.6.1.4.1.2011.2.251.20.1.2.2.15.16386.114.2
        pwdOfResUserIsAboutToExpire-Resume NOTIFICATION-TYPE
            OBJECTS { hwStorageAlarmReporting }
            STATUS current
            DESCRIPTION "Recover: The Password Of A Windows User Is About To Expire"
            --#SEVERITY INFORMATIONAL
            ::= { pwdOfResUserIsAboutToExpire 2 }

        -- 1.3.6.1.4.1.2011.2.251.20.1.2.2.15.16386.115
        windowsUserIsAboutToBeLocked OBJECT IDENTIFIER ::= { nasprotocol 115 }

        -- 1.3.6.1.4.1.2011.2.251.20.1.2.2.15.16386.115.1
        windowsUserIsAboutToBeLocked-Fault NOTIFICATION-TYPE
            OBJECTS { hwStorageAlarmReporting }
            STATUS current
            DESCRIPTION "A Windows User Is About To Be Locked"
            --#SEVERITY WARNING
            ::= { windowsUserIsAboutToBeLocked 1 }

        -- 1.3.6.1.4.1.2011.2.251.20.1.2.2.15.16386.115.2
        windowsUserIsAboutToBeLocked-Resume NOTIFICATION-TYPE
            OBJECTS { hwStorageAlarmReporting }
            STATUS current
            DESCRIPTION "Recover: A Windows User Is About To Be Locked"
            --#SEVERITY INFORMATIONAL
            ::= { windowsUserIsAboutToBeLocked 2 }

        -- 1.3.6.1.4.1.2011.2.251.20.1.2.2.15.16386.116
        largeClusterLdapServerNetworkAbnormal OBJECT IDENTIFIER ::= { nasprotocol 116 }

        -- 1.3.6.1.4.1.2011.2.251.20.1.2.2.15.16386.116.1
        largeClusterLdapServerNetworkAbnormal-Fault NOTIFICATION-TYPE
            OBJECTS { hwStorageAlarmReporting }
            STATUS current
            DESCRIPTION "The Communication Network With The LDAP Domain Server Is Abnormal"
            --#SEVERITY WARNING
            ::= { largeClusterLdapServerNetworkAbnormal 1 }

        -- 1.3.6.1.4.1.2011.2.251.20.1.2.2.15.16386.116.2
        largeClusterLdapServerNetworkAbnormal-Resume NOTIFICATION-TYPE
            OBJECTS { hwStorageAlarmReporting }
            STATUS current
            DESCRIPTION "Recover: The Communication Network With The LDAP Domain Server Is Abnormal"
            --#SEVERITY INFORMATIONAL
            ::= { largeClusterLdapServerNetworkAbnormal 2 }

        -- 1.3.6.1.4.1.2011.2.251.20.1.2.2.15.16386.117
        largeClusterDnsServerNetworkAbnormal OBJECT IDENTIFIER ::= { nasprotocol 117 }

        -- 1.3.6.1.4.1.2011.2.251.20.1.2.2.15.16386.117.1
        largeClusterDnsServerNetworkAbnormal-Fault NOTIFICATION-TYPE
            OBJECTS { hwStorageAlarmReporting }
            STATUS current
            DESCRIPTION "The Communication Network With The DNS Server Is Abnormal"
            --#SEVERITY WARNING
            ::= { largeClusterDnsServerNetworkAbnormal 1 }

        -- 1.3.6.1.4.1.2011.2.251.20.1.2.2.15.16386.117.2
        largeClusterDnsServerNetworkAbnormal-Resume NOTIFICATION-TYPE
            OBJECTS { hwStorageAlarmReporting }
            STATUS current
            DESCRIPTION "Recover: The Communication Network With The DNS Server Is Abnormal"
            --#SEVERITY INFORMATIONAL
            ::= { largeClusterDnsServerNetworkAbnormal 2 }

        -- 1.3.6.1.4.1.2011.2.251.20.1.2.2.15.16386.118
        clusterRestrict OBJECT IDENTIFIER ::= { nasprotocol 118 }

        -- 1.3.6.1.4.1.2011.2.251.20.1.2.2.15.16386.118.1
        clusterRestrict-Fault NOTIFICATION-TYPE
            OBJECTS { hwStorageAlarmReporting }
            STATUS current
            DESCRIPTION "This Alarm Is Generated When An Array Enters Silent Management And Control"
            --#SEVERITY CRITICAL
            ::= { clusterRestrict 1 }

        -- 1.3.6.1.4.1.2011.2.251.20.1.2.2.15.16386.118.2
        clusterRestrict-Resume NOTIFICATION-TYPE
            OBJECTS { hwStorageAlarmReporting }
            STATUS current
            DESCRIPTION "Recover: This Alarm Is Generated When An Array Enters Silent Management And Control"
            --#SEVERITY INFORMATIONAL
            ::= { clusterRestrict 2 }

        -- 1.3.6.1.4.1.2011.2.251.20.1.2.2.15.16386.119
        clusterRestrictFailed OBJECT IDENTIFIER ::= { nasprotocol 119 }

        -- 1.3.6.1.4.1.2011.2.251.20.1.2.2.15.16386.119.1
        clusterRestrictFailed-Fault NOTIFICATION-TYPE
            OBJECTS { hwStorageAlarmReporting }
            STATUS current
            DESCRIPTION "This Alarm Is Generated When An Array Failed To Enter Silent Management And Control"
            --#SEVERITY CRITICAL
            ::= { clusterRestrictFailed 1 }

        -- 1.3.6.1.4.1.2011.2.251.20.1.2.2.15.16386.119.2
        clusterRestrictFailed-Resume NOTIFICATION-TYPE
            OBJECTS { hwStorageAlarmReporting }
            STATUS current
            DESCRIPTION "Recover: This Alarm Is Generated When An Array Failed To Enter Silent Management And Control"
            --#SEVERITY INFORMATIONAL
            ::= { clusterRestrictFailed 2 }

        -- 1.3.6.1.4.1.2011.2.251.20.1.2.2.15.16386.120
        largeClusterNisServerNetworkAbnormal OBJECT IDENTIFIER ::= { nasprotocol 120 }

        -- 1.3.6.1.4.1.2011.2.251.20.1.2.2.15.16386.120.1
        largeClusterNisServerNetworkAbnormal-Fault NOTIFICATION-TYPE
            OBJECTS { hwStorageAlarmReporting }
            STATUS current
            DESCRIPTION "Communication Network Of The NIS Server Is Abnormal"
            --#SEVERITY WARNING
            ::= { largeClusterNisServerNetworkAbnormal 1 }

        -- 1.3.6.1.4.1.2011.2.251.20.1.2.2.15.16386.120.2
        largeClusterNisServerNetworkAbnormal-Resume NOTIFICATION-TYPE
            OBJECTS { hwStorageAlarmReporting }
            STATUS current
            DESCRIPTION "Recover: Communication Network Of The NIS Server Is Abnormal"
            --#SEVERITY INFORMATIONAL
            ::= { largeClusterNisServerNetworkAbnormal 2 }

        -- 1.3.6.1.4.1.2011.2.251.20.1.2.2.15.16386.126
        dataturboConnectionReachUpperLimit OBJECT IDENTIFIER ::= { nasprotocol 126 }

        -- 1.3.6.1.4.1.2011.2.251.20.1.2.2.15.16386.126.1
        dataturboConnectionReachUpperLimit-Fault NOTIFICATION-TYPE
            OBJECTS { hwStorageAlarmReporting }
            STATUS current
            DESCRIPTION "The Number Of DataTurbo Links On The Controller Is About To Reach The Upper Limit"
            --#SEVERITY WARNING
            ::= { dataturboConnectionReachUpperLimit 1 }

        -- 1.3.6.1.4.1.2011.2.251.20.1.2.2.15.16386.126.2
        dataturboConnectionReachUpperLimit-Resume NOTIFICATION-TYPE
            OBJECTS { hwStorageAlarmReporting }
            STATUS current
            DESCRIPTION "Recover: The Number Of DataTurbo Links On The Controller Is About To Reach The Upper Limit"
            --#SEVERITY INFORMATIONAL
            ::= { dataturboConnectionReachUpperLimit 2 }

        -- 1.3.6.1.4.1.2011.2.251.20.1.2.2.15.16442
        vstore OBJECT IDENTIFIER ::= { oidBasedTrap 16442 }

        -- 1.3.6.1.4.1.2011.2.251.20.1.2.2.15.16442.1
        vstoreQuotaNotEnough OBJECT IDENTIFIER ::= { vstore 1 }

        -- 1.3.6.1.4.1.2011.2.251.20.1.2.2.15.16442.1.1
        vstoreQuotaNotEnough-Fault NOTIFICATION-TYPE
            OBJECTS { hwStorageAlarmReporting }
            STATUS current
            DESCRIPTION "The VStore Quota Capacity Has Reached The Threshold"
            --#SEVERITY MAJOR
            ::= { vstoreQuotaNotEnough 1 }

        -- 1.3.6.1.4.1.2011.2.251.20.1.2.2.15.16442.1.2
        vstoreQuotaNotEnough-Resume NOTIFICATION-TYPE
            OBJECTS { hwStorageAlarmReporting }
            STATUS current
            DESCRIPTION "Recover: The VStore Quota Capacity Has Reached The Threshold"
            --#SEVERITY INFORMATIONAL
            ::= { vstoreQuotaNotEnough 2 }

        -- 1.3.6.1.4.1.2011.2.251.20.1.2.2.15.16452
        nfsservice OBJECT IDENTIFIER ::= { oidBasedTrap 16452 }

        -- 1.3.6.1.4.1.2011.2.251.20.1.2.2.15.16452.29
        theNumberOfClientRelatedResourcesHasReachedTheUpperLimit OBJECT IDENTIFIER ::= { nfsservice 29 }

        -- 1.3.6.1.4.1.2011.2.251.20.1.2.2.15.16452.29.1
        theNumberOfClientRelatedResourcesHasReachedTheUpperLimit-Fault NOTIFICATION-TYPE
            OBJECTS { hwStorageAlarmReporting }
            STATUS current
            DESCRIPTION "The Number Of Client Related Resources Has Reached The Upper Limit"
            --#SEVERITY MAJOR
            ::= { theNumberOfClientRelatedResourcesHasReachedTheUpperLimit 1 }

        -- 1.3.6.1.4.1.2011.2.251.20.1.2.2.15.16452.29.2
        theNumberOfClientRelatedResourcesHasReachedTheUpperLimit-Resume NOTIFICATION-TYPE
            OBJECTS { hwStorageAlarmReporting }
            STATUS current
            DESCRIPTION "Recover: The Number Of Client Related Resources Has Reached The Upper Limit"
            --#SEVERITY INFORMATIONAL
            ::= { theNumberOfClientRelatedResourcesHasReachedTheUpperLimit 2 }

        -- 1.3.6.1.4.1.2011.2.251.20.1.2.2.15.16453
        cifsservice OBJECT IDENTIFIER ::= { oidBasedTrap 16453 }

        -- 1.3.6.1.4.1.2011.2.251.20.1.2.2.15.16453.46
        resourcesUsedByTheClientAreAboutToExceedTheSpecification OBJECT IDENTIFIER ::= { cifsservice 46 }

        -- 1.3.6.1.4.1.2011.2.251.20.1.2.2.15.16453.46.1
        resourcesUsedByTheClientAreAboutToExceedTheSpecification-Fault NOTIFICATION-TYPE
            OBJECTS { hwStorageAlarmReporting }
            STATUS current
            DESCRIPTION "Resources Used By The Client Are About To Exceed The Specification"
            --#SEVERITY WARNING
            ::= { resourcesUsedByTheClientAreAboutToExceedTheSpecification 1 }

        -- 1.3.6.1.4.1.2011.2.251.20.1.2.2.15.16453.46.2
        resourcesUsedByTheClientAreAboutToExceedTheSpecification-Resume NOTIFICATION-TYPE
            OBJECTS { hwStorageAlarmReporting }
            STATUS current
            DESCRIPTION "Recover: Resources Used By The Client Are About To Exceed The Specification"
            --#SEVERITY INFORMATIONAL
            ::= { resourcesUsedByTheClientAreAboutToExceedTheSpecification 2 }

        -- 1.3.6.1.4.1.2011.2.251.20.1.2.2.15.16458
        filesystemquota OBJECT IDENTIFIER ::= { oidBasedTrap 16458 }

        -- 1.3.6.1.4.1.2011.2.251.20.1.2.2.15.16458.16
        quotaNumIsExceed OBJECT IDENTIFIER ::= { filesystemquota 16 }

        -- 1.3.6.1.4.1.2011.2.251.20.1.2.2.15.16458.16.1
        quotaNumIsExceed-Fault NOTIFICATION-TYPE
            OBJECTS { hwStorageAlarmReporting }
            STATUS current
            DESCRIPTION "The Number Of Configured File System Quotas Exceeds 85% Of The Threshold"
            --#SEVERITY MAJOR
            ::= { quotaNumIsExceed 1 }

        -- 1.3.6.1.4.1.2011.2.251.20.1.2.2.15.16458.16.2
        quotaNumIsExceed-Resume NOTIFICATION-TYPE
            OBJECTS { hwStorageAlarmReporting }
            STATUS current
            DESCRIPTION "Recover: The Number Of Configured File System Quotas Exceeds 85% Of The Threshold"
            --#SEVERITY INFORMATIONAL
            ::= { quotaNumIsExceed 2 }

        -- 1.3.6.1.4.1.2011.2.251.20.1.2.2.15.16458.21
        fsQuotaSoftCapAlarmDirType OBJECT IDENTIFIER ::= { filesystemquota 21 }

        -- 1.3.6.1.4.1.2011.2.251.20.1.2.2.15.16458.21.1
        fsQuotaSoftCapAlarmDirType-Fault NOTIFICATION-TYPE
            OBJECTS { hwStorageAlarmReporting }
            STATUS current
            DESCRIPTION "Used Resource Of A File System Quota Exceeds The Soft Quota"
            --#SEVERITY MAJOR
            ::= { fsQuotaSoftCapAlarmDirType 1 }

        -- 1.3.6.1.4.1.2011.2.251.20.1.2.2.15.16458.21.2
        fsQuotaSoftCapAlarmDirType-Resume NOTIFICATION-TYPE
            OBJECTS { hwStorageAlarmReporting }
            STATUS current
            DESCRIPTION "Recover: Used Resource Of A File System Quota Exceeds The Soft Quota"
            --#SEVERITY INFORMATIONAL
            ::= { fsQuotaSoftCapAlarmDirType 2 }

        -- 1.3.6.1.4.1.2011.2.251.20.1.2.2.15.16458.22
        fsQuotaSoftCapAlarmGrpUsrType OBJECT IDENTIFIER ::= { filesystemquota 22 }

        -- 1.3.6.1.4.1.2011.2.251.20.1.2.2.15.16458.22.1
        fsQuotaSoftCapAlarmGrpUsrType-Fault NOTIFICATION-TYPE
            OBJECTS { hwStorageAlarmReporting }
            STATUS current
            DESCRIPTION "Used Resource Of A File System Quota Exceeds The Soft Quota"
            --#SEVERITY MAJOR
            ::= { fsQuotaSoftCapAlarmGrpUsrType 1 }

        -- 1.3.6.1.4.1.2011.2.251.20.1.2.2.15.16458.22.2
        fsQuotaSoftCapAlarmGrpUsrType-Resume NOTIFICATION-TYPE
            OBJECTS { hwStorageAlarmReporting }
            STATUS current
            DESCRIPTION "Recover: Used Resource Of A File System Quota Exceeds The Soft Quota"
            --#SEVERITY INFORMATIONAL
            ::= { fsQuotaSoftCapAlarmGrpUsrType 2 }

        -- 1.3.6.1.4.1.2011.2.251.20.1.2.2.15.16458.23
        fsQuotaHardCapAlarmDirType OBJECT IDENTIFIER ::= { filesystemquota 23 }

        -- 1.3.6.1.4.1.2011.2.251.20.1.2.2.15.16458.23.1
        fsQuotaHardCapAlarmDirType-Fault NOTIFICATION-TYPE
            OBJECTS { hwStorageAlarmReporting }
            STATUS current
            DESCRIPTION "Used Resource Of A File System Quota Reaches The Hard Quota"
            --#SEVERITY MAJOR
            ::= { fsQuotaHardCapAlarmDirType 1 }

        -- 1.3.6.1.4.1.2011.2.251.20.1.2.2.15.16458.23.2
        fsQuotaHardCapAlarmDirType-Resume NOTIFICATION-TYPE
            OBJECTS { hwStorageAlarmReporting }
            STATUS current
            DESCRIPTION "Recover: Used Resource Of A File System Quota Reaches The Hard Quota"
            --#SEVERITY INFORMATIONAL
            ::= { fsQuotaHardCapAlarmDirType 2 }

        -- 1.3.6.1.4.1.2011.2.251.20.1.2.2.15.16458.25
        fsQuotaHardCapAlarmUsrGrpType OBJECT IDENTIFIER ::= { filesystemquota 25 }

        -- 1.3.6.1.4.1.2011.2.251.20.1.2.2.15.16458.25.1
        fsQuotaHardCapAlarmUsrGrpType-Fault NOTIFICATION-TYPE
            OBJECTS { hwStorageAlarmReporting }
            STATUS current
            DESCRIPTION "Used Resource Of A File System Quota Reaches The Hard Quota"
            --#SEVERITY MAJOR
            ::= { fsQuotaHardCapAlarmUsrGrpType 1 }

        -- 1.3.6.1.4.1.2011.2.251.20.1.2.2.15.16458.25.2
        fsQuotaHardCapAlarmUsrGrpType-Resume NOTIFICATION-TYPE
            OBJECTS { hwStorageAlarmReporting }
            STATUS current
            DESCRIPTION "Recover: Used Resource Of A File System Quota Reaches The Hard Quota"
            --#SEVERITY INFORMATIONAL
            ::= { fsQuotaHardCapAlarmUsrGrpType 2 }

        -- 1.3.6.1.4.1.2011.2.251.20.1.2.2.15.16458.27
        fsQuotaCapAlarm OBJECT IDENTIFIER ::= { filesystemquota 27 }

        -- 1.3.6.1.4.1.2011.2.251.20.1.2.2.15.16458.27.1
        fsQuotaCapAlarm-Fault NOTIFICATION-TYPE
            OBJECTS { hwStorageAlarmReporting }
            STATUS current
            DESCRIPTION "The Number Of Configured File System Quotas Exceeds The Threshold"
            --#SEVERITY MAJOR
            ::= { fsQuotaCapAlarm 1 }

        -- 1.3.6.1.4.1.2011.2.251.20.1.2.2.15.16458.27.2
        fsQuotaCapAlarm-Resume NOTIFICATION-TYPE
            OBJECTS { hwStorageAlarmReporting }
            STATUS current
            DESCRIPTION "Recover: The Number Of Configured File System Quotas Exceeds The Threshold"
            --#SEVERITY INFORMATIONAL
            ::= { fsQuotaCapAlarm 2 }

        -- 1.3.6.1.4.1.2011.2.251.20.1.2.2.15.16458.19969
        usedResourceOfAFileSystemDirQuotaExceedsTheSoftQuota OBJECT IDENTIFIER ::= { filesystemquota 19969 }

        -- 1.3.6.1.4.1.2011.2.251.20.1.2.2.15.16458.19969.1
        usedResourceOfAFileSystemDirQuotaExceedsTheSoftQuota-Fault NOTIFICATION-TYPE
            OBJECTS { hwStorageAlarmReporting }
            STATUS current
            DESCRIPTION "Used Resource Of A File System Quota Exceeds The Soft Quota"
            --#SEVERITY MAJOR
            ::= { usedResourceOfAFileSystemDirQuotaExceedsTheSoftQuota 1 }

        -- 1.3.6.1.4.1.2011.2.251.20.1.2.2.15.16458.19969.2
        usedResourceOfAFileSystemDirQuotaExceedsTheSoftQuota-Resume NOTIFICATION-TYPE
            OBJECTS { hwStorageAlarmReporting }
            STATUS current
            DESCRIPTION "Recover: Used Resource Of A File System Quota Exceeds The Soft Quota"
            --#SEVERITY INFORMATIONAL
            ::= { usedResourceOfAFileSystemDirQuotaExceedsTheSoftQuota 2 }

        -- 1.3.6.1.4.1.2011.2.251.20.1.2.2.15.16458.19970
        usedResourceOfAFileSystemGrpUsrQuotaExceedsTheSoftQuota OBJECT IDENTIFIER ::= { filesystemquota 19970 }

        -- 1.3.6.1.4.1.2011.2.251.20.1.2.2.15.16458.19970.1
        usedResourceOfAFileSystemGrpUsrQuotaExceedsTheSoftQuota-Fault NOTIFICATION-TYPE
            OBJECTS { hwStorageAlarmReporting }
            STATUS current
            DESCRIPTION "Used Resource Of A File System Quota Exceeds The Soft Quota"
            --#SEVERITY MAJOR
            ::= { usedResourceOfAFileSystemGrpUsrQuotaExceedsTheSoftQuota 1 }

        -- 1.3.6.1.4.1.2011.2.251.20.1.2.2.15.16458.19970.2
        usedResourceOfAFileSystemGrpUsrQuotaExceedsTheSoftQuota-Resume NOTIFICATION-TYPE
            OBJECTS { hwStorageAlarmReporting }
            STATUS current
            DESCRIPTION "Recover: Used Resource Of A File System Quota Exceeds The Soft Quota"
            --#SEVERITY INFORMATIONAL
            ::= { usedResourceOfAFileSystemGrpUsrQuotaExceedsTheSoftQuota 2 }

        -- 1.3.6.1.4.1.2011.2.251.20.1.2.2.15.16458.19971
        usedResourceOfAFileSystemDirQuotaReachesTheHardQuota OBJECT IDENTIFIER ::= { filesystemquota 19971 }

        -- 1.3.6.1.4.1.2011.2.251.20.1.2.2.15.16458.19971.1
        usedResourceOfAFileSystemDirQuotaReachesTheHardQuota-Fault NOTIFICATION-TYPE
            OBJECTS { hwStorageAlarmReporting }
            STATUS current
            DESCRIPTION "Used Resource Of A File System Quota Reaches The Hard Quota"
            --#SEVERITY MAJOR
            ::= { usedResourceOfAFileSystemDirQuotaReachesTheHardQuota 1 }

        -- 1.3.6.1.4.1.2011.2.251.20.1.2.2.15.16458.19971.2
        usedResourceOfAFileSystemDirQuotaReachesTheHardQuota-Resume NOTIFICATION-TYPE
            OBJECTS { hwStorageAlarmReporting }
            STATUS current
            DESCRIPTION "Recover: Used Resource Of A File System Quota Reaches The Hard Quota"
            --#SEVERITY INFORMATIONAL
            ::= { usedResourceOfAFileSystemDirQuotaReachesTheHardQuota 2 }

        -- 1.3.6.1.4.1.2011.2.251.20.1.2.2.15.16458.19972
        usedResourceOfAFileSystemGrpUsrQuotaReachesTheHardQuota OBJECT IDENTIFIER ::= { filesystemquota 19972 }

        -- 1.3.6.1.4.1.2011.2.251.20.1.2.2.15.16458.19972.1
        usedResourceOfAFileSystemGrpUsrQuotaReachesTheHardQuota-Fault NOTIFICATION-TYPE
            OBJECTS { hwStorageAlarmReporting }
            STATUS current
            DESCRIPTION "Used Resource Of A File System Quota Reaches The Hard Quota"
            --#SEVERITY MAJOR
            ::= { usedResourceOfAFileSystemGrpUsrQuotaReachesTheHardQuota 1 }

        -- 1.3.6.1.4.1.2011.2.251.20.1.2.2.15.16458.19972.2
        usedResourceOfAFileSystemGrpUsrQuotaReachesTheHardQuota-Resume NOTIFICATION-TYPE
            OBJECTS { hwStorageAlarmReporting }
            STATUS current
            DESCRIPTION "Recover: Used Resource Of A File System Quota Reaches The Hard Quota"
            --#SEVERITY INFORMATIONAL
            ::= { usedResourceOfAFileSystemGrpUsrQuotaReachesTheHardQuota 2 }

        -- 1.3.6.1.4.1.2011.2.251.20.1.2.2.15.16459
        objectservice OBJECT IDENTIFIER ::= { oidBasedTrap 16459 }

        -- 1.3.6.1.4.1.2011.2.251.20.1.2.2.15.16459.1
        akskIsAboutToExpire OBJECT IDENTIFIER ::= { objectservice 1 }

        -- 1.3.6.1.4.1.2011.2.251.20.1.2.2.15.16459.1.1
        akskIsAboutToExpire-Fault NOTIFICATION-TYPE
            OBJECTS { hwStorageAlarmReporting }
            STATUS current
            DESCRIPTION "Object Service Access Key Is About To Expire"
            --#SEVERITY WARNING
            ::= { akskIsAboutToExpire 1 }

        -- 1.3.6.1.4.1.2011.2.251.20.1.2.2.15.16459.1.2
        akskIsAboutToExpire-Resume NOTIFICATION-TYPE
            OBJECTS { hwStorageAlarmReporting }
            STATUS current
            DESCRIPTION "Recover: Object Service Access Key Is About To Expire"
            --#SEVERITY INFORMATIONAL
            ::= { akskIsAboutToExpire 2 }

        -- 1.3.6.1.4.1.2011.2.251.20.1.2.2.15.16459.2
        akskHasExpired OBJECT IDENTIFIER ::= { objectservice 2 }

        -- 1.3.6.1.4.1.2011.2.251.20.1.2.2.15.16459.2.1
        akskHasExpired-Fault NOTIFICATION-TYPE
            OBJECTS { hwStorageAlarmReporting }
            STATUS current
            DESCRIPTION "Object Service Access Key Has Expired"
            --#SEVERITY MAJOR
            ::= { akskHasExpired 1 }

        -- 1.3.6.1.4.1.2011.2.251.20.1.2.2.15.16459.2.2
        akskHasExpired-Resume NOTIFICATION-TYPE
            OBJECTS { hwStorageAlarmReporting }
            STATUS current
            DESCRIPTION "Recover: Object Service Access Key Has Expired"
            --#SEVERITY INFORMATIONAL
            ::= { akskHasExpired 2 }

        -- 1.3.6.1.4.1.2011.2.251.20.1.2.2.15.16459.3
        setUpHTTPSConnFaulty OBJECT IDENTIFIER ::= { objectservice 3 }

        -- 1.3.6.1.4.1.2011.2.251.20.1.2.2.15.16459.3.1
        setUpHTTPSConnFaulty-Fault NOTIFICATION-TYPE
            OBJECTS { hwStorageAlarmReporting }
            STATUS current
            DESCRIPTION "HTTPS Connections Failed To Be Established For The Object Service"
            --#SEVERITY WARNING
            ::= { setUpHTTPSConnFaulty 1 }

        -- 1.3.6.1.4.1.2011.2.251.20.1.2.2.15.16459.3.2
        setUpHTTPSConnFaulty-Resume NOTIFICATION-TYPE
            OBJECTS { hwStorageAlarmReporting }
            STATUS current
            DESCRIPTION "Recover: HTTPS Connections Failed To Be Established For The Object Service"
            --#SEVERITY INFORMATIONAL
            ::= { setUpHTTPSConnFaulty 2 }

        -- 1.3.6.1.4.1.2011.2.251.20.1.2.2.15.16459.4
        obsHTTPSConnReachUpperLimit OBJECT IDENTIFIER ::= { objectservice 4 }

        -- 1.3.6.1.4.1.2011.2.251.20.1.2.2.15.16459.4.1
        obsHTTPSConnReachUpperLimit-Fault NOTIFICATION-TYPE
            OBJECTS { hwStorageAlarmReporting }
            STATUS current
            DESCRIPTION "Number Of HTTPS Connections Of The Object Service On The Controller Is About To Reach The Upper Limit"
            --#SEVERITY WARNING
            ::= { obsHTTPSConnReachUpperLimit 1 }

        -- 1.3.6.1.4.1.2011.2.251.20.1.2.2.15.16459.4.2
        obsHTTPSConnReachUpperLimit-Resume NOTIFICATION-TYPE
            OBJECTS { hwStorageAlarmReporting }
            STATUS current
            DESCRIPTION "Recover: Number Of HTTPS Connections Of The Object Service On The Controller Is About To Reach The Upper Limit"
            --#SEVERITY INFORMATIONAL
            ::= { obsHTTPSConnReachUpperLimit 2 }

        -- 1.3.6.1.4.1.2011.2.251.20.1.2.2.15.20480
        certificatemanagement OBJECT IDENTIFIER ::= { oidBasedTrap 20480 }

        -- 1.3.6.1.4.1.2011.2.251.20.1.2.2.15.20480.1
        certificateExpiredWithDeadline OBJECT IDENTIFIER ::= { certificatemanagement 1 }

        -- 1.3.6.1.4.1.2011.2.251.20.1.2.2.15.20480.1.1
        certificateExpiredWithDeadline-Fault NOTIFICATION-TYPE
            OBJECTS { hwStorageAlarmReporting }
            STATUS current
            DESCRIPTION "A Certificate Has Expired"
            --#SEVERITY CRITICAL
            ::= { certificateExpiredWithDeadline 1 }

        -- 1.3.6.1.4.1.2011.2.251.20.1.2.2.15.20480.1.2
        certificateExpiredWithDeadline-Resume NOTIFICATION-TYPE
            OBJECTS { hwStorageAlarmReporting }
            STATUS current
            DESCRIPTION "Recover: A Certificate Has Expired"
            --#SEVERITY INFORMATIONAL
            ::= { certificateExpiredWithDeadline 2 }

        -- 1.3.6.1.4.1.2011.2.251.20.1.2.2.15.20480.2
        certificateWillExpireWithTime OBJECT IDENTIFIER ::= { certificatemanagement 2 }

        -- 1.3.6.1.4.1.2011.2.251.20.1.2.2.15.20480.2.1
        certificateWillExpireWithTime-Fault NOTIFICATION-TYPE
            OBJECTS { hwStorageAlarmReporting }
            STATUS current
            DESCRIPTION "A Certificate Is About To Expire"
            --#SEVERITY MAJOR
            ::= { certificateWillExpireWithTime 1 }

        -- 1.3.6.1.4.1.2011.2.251.20.1.2.2.15.20480.2.2
        certificateWillExpireWithTime-Resume NOTIFICATION-TYPE
            OBJECTS { hwStorageAlarmReporting }
            STATUS current
            DESCRIPTION "Recover: A Certificate Is About To Expire"
            --#SEVERITY INFORMATIONAL
            ::= { certificateWillExpireWithTime 2 }

        -- 1.3.6.1.4.1.2011.2.251.20.1.2.2.15.20480.3
        tenantCertificateHasExpired OBJECT IDENTIFIER ::= { certificatemanagement 3 }

        -- 1.3.6.1.4.1.2011.2.251.20.1.2.2.15.20480.3.1
        tenantCertificateHasExpired-Fault NOTIFICATION-TYPE
            OBJECTS { hwStorageAlarmReporting }
            STATUS current
            DESCRIPTION "A Certificate Has Expired"
            --#SEVERITY CRITICAL
            ::= { tenantCertificateHasExpired 1 }

        -- 1.3.6.1.4.1.2011.2.251.20.1.2.2.15.20480.3.2
        tenantCertificateHasExpired-Resume NOTIFICATION-TYPE
            OBJECTS { hwStorageAlarmReporting }
            STATUS current
            DESCRIPTION "Recover: A Certificate Has Expired"
            --#SEVERITY INFORMATIONAL
            ::= { tenantCertificateHasExpired 2 }

        -- 1.3.6.1.4.1.2011.2.251.20.1.2.2.15.20480.4
        tenantCertificateWillExpire OBJECT IDENTIFIER ::= { certificatemanagement 4 }

        -- 1.3.6.1.4.1.2011.2.251.20.1.2.2.15.20480.4.1
        tenantCertificateWillExpire-Fault NOTIFICATION-TYPE
            OBJECTS { hwStorageAlarmReporting }
            STATUS current
            DESCRIPTION "A Certificate Is About To Expire"
            --#SEVERITY MAJOR
            ::= { tenantCertificateWillExpire 1 }

        -- 1.3.6.1.4.1.2011.2.251.20.1.2.2.15.20480.4.2
        tenantCertificateWillExpire-Resume NOTIFICATION-TYPE
            OBJECTS { hwStorageAlarmReporting }
            STATUS current
            DESCRIPTION "Recover: A Certificate Is About To Expire"
            --#SEVERITY INFORMATIONAL
            ::= { tenantCertificateWillExpire 2 }

        -- 1.3.6.1.4.1.2011.2.251.20.1.2.2.15.20480.6
        crlExpired OBJECT IDENTIFIER ::= { certificatemanagement 6 }

        -- 1.3.6.1.4.1.2011.2.251.20.1.2.2.15.20480.6.1
        crlExpired-Fault NOTIFICATION-TYPE
            OBJECTS { hwStorageAlarmReporting }
            STATUS current
            DESCRIPTION "A Certificate Revocation List Has Expired"
            --#SEVERITY MAJOR
            ::= { crlExpired 1 }

        -- 1.3.6.1.4.1.2011.2.251.20.1.2.2.15.20480.6.2
        crlExpired-Resume NOTIFICATION-TYPE
            OBJECTS { hwStorageAlarmReporting }
            STATUS current
            DESCRIPTION "Recover: A Certificate Revocation List Has Expired"
            --#SEVERITY INFORMATIONAL
            ::= { crlExpired 2 }

        -- 1.3.6.1.4.1.2011.2.251.20.1.2.2.15.20480.10
        tenantCRLHasExpired OBJECT IDENTIFIER ::= { certificatemanagement 10 }

        -- 1.3.6.1.4.1.2011.2.251.20.1.2.2.15.20480.10.1
        tenantCRLHasExpired-Fault NOTIFICATION-TYPE
            OBJECTS { hwStorageAlarmReporting }
            STATUS current
            DESCRIPTION "A Certificate Revocation List Has Expired"
            --#SEVERITY MAJOR
            ::= { tenantCRLHasExpired 1 }

        -- 1.3.6.1.4.1.2011.2.251.20.1.2.2.15.20480.10.2
        tenantCRLHasExpired-Resume NOTIFICATION-TYPE
            OBJECTS { hwStorageAlarmReporting }
            STATUS current
            DESCRIPTION "Recover: A Certificate Revocation List Has Expired"
            --#SEVERITY INFORMATIONAL
            ::= { tenantCRLHasExpired 2 }

        -- 1.3.6.1.4.1.2011.2.251.20.1.2.2.15.20480.13
        theCACertificateIsAboutToExpire OBJECT IDENTIFIER ::= { certificatemanagement 13 }

        -- 1.3.6.1.4.1.2011.2.251.20.1.2.2.15.20480.13.1
        theCACertificateIsAboutToExpire-Fault NOTIFICATION-TYPE
            OBJECTS { hwStorageAlarmReporting }
            STATUS current
            DESCRIPTION "A CA Certificate Is About To Expire"
            --#SEVERITY MAJOR
            ::= { theCACertificateIsAboutToExpire 1 }

        -- 1.3.6.1.4.1.2011.2.251.20.1.2.2.15.20480.13.2
        theCACertificateIsAboutToExpire-Resume NOTIFICATION-TYPE
            OBJECTS { hwStorageAlarmReporting }
            STATUS current
            DESCRIPTION "Recover: A CA Certificate Is About To Expire"
            --#SEVERITY INFORMATIONAL
            ::= { theCACertificateIsAboutToExpire 2 }

        -- 1.3.6.1.4.1.2011.2.251.20.1.2.2.15.20480.14
        theCACertificateHasExpired OBJECT IDENTIFIER ::= { certificatemanagement 14 }

        -- 1.3.6.1.4.1.2011.2.251.20.1.2.2.15.20480.14.1
        theCACertificateHasExpired-Fault NOTIFICATION-TYPE
            OBJECTS { hwStorageAlarmReporting }
            STATUS current
            DESCRIPTION "A CA Certificate Has Expired"
            --#SEVERITY CRITICAL
            ::= { theCACertificateHasExpired 1 }

        -- 1.3.6.1.4.1.2011.2.251.20.1.2.2.15.20480.14.2
        theCACertificateHasExpired-Resume NOTIFICATION-TYPE
            OBJECTS { hwStorageAlarmReporting }
            STATUS current
            DESCRIPTION "Recover: A CA Certificate Has Expired"
            --#SEVERITY INFORMATIONAL
            ::= { theCACertificateHasExpired 2 }

        -- 1.3.6.1.4.1.2011.2.251.20.1.2.2.15.20480.19
        theCACertificateOfAVstoreIsAboutToExpire OBJECT IDENTIFIER ::= { certificatemanagement 19 }

        -- 1.3.6.1.4.1.2011.2.251.20.1.2.2.15.20480.19.1
        theCACertificateOfAVstoreIsAboutToExpire-Fault NOTIFICATION-TYPE
            OBJECTS { hwStorageAlarmReporting }
            STATUS current
            DESCRIPTION "The CA Certificate Of A Vstore Is About To Expire"
            --#SEVERITY MAJOR
            ::= { theCACertificateOfAVstoreIsAboutToExpire 1 }

        -- 1.3.6.1.4.1.2011.2.251.20.1.2.2.15.20480.19.2
        theCACertificateOfAVstoreIsAboutToExpire-Resume NOTIFICATION-TYPE
            OBJECTS { hwStorageAlarmReporting }
            STATUS current
            DESCRIPTION "Recover: The CA Certificate Of A Vstore Is About To Expire"
            --#SEVERITY INFORMATIONAL
            ::= { theCACertificateOfAVstoreIsAboutToExpire 2 }

        -- 1.3.6.1.4.1.2011.2.251.20.1.2.2.15.20480.35
        theCACertificateOfAVstoreHasExpired OBJECT IDENTIFIER ::= { certificatemanagement 35 }

        -- 1.3.6.1.4.1.2011.2.251.20.1.2.2.15.20480.35.1
        theCACertificateOfAVstoreHasExpired-Fault NOTIFICATION-TYPE
            OBJECTS { hwStorageAlarmReporting }
            STATUS current
            DESCRIPTION "The CA Certificate Of A Vstore Has Expired"
            --#SEVERITY CRITICAL
            ::= { theCACertificateOfAVstoreHasExpired 1 }

        -- 1.3.6.1.4.1.2011.2.251.20.1.2.2.15.20480.35.2
        theCACertificateOfAVstoreHasExpired-Resume NOTIFICATION-TYPE
            OBJECTS { hwStorageAlarmReporting }
            STATUS current
            DESCRIPTION "Recover: The CA Certificate Of A Vstore Has Expired"
            --#SEVERITY INFORMATIONAL
            ::= { theCACertificateOfAVstoreHasExpired 2 }

        -- 1.3.6.1.4.1.2011.2.251.20.1.2.2.15.20480.36
        certificateExpired OBJECT IDENTIFIER ::= { certificatemanagement 36 }

        -- 1.3.6.1.4.1.2011.2.251.20.1.2.2.15.20480.36.1
        certificateExpired-Fault NOTIFICATION-TYPE
            OBJECTS { hwStorageAlarmReporting }
            STATUS current
            DESCRIPTION "A Certificate Has Expired"
            --#SEVERITY CRITICAL
            ::= { certificateExpired 1 }

        -- 1.3.6.1.4.1.2011.2.251.20.1.2.2.15.20480.36.2
        certificateExpired-Resume NOTIFICATION-TYPE
            OBJECTS { hwStorageAlarmReporting }
            STATUS current
            DESCRIPTION "Recover: A Certificate Has Expired"
            --#SEVERITY INFORMATIONAL
            ::= { certificateExpired 2 }

        -- 1.3.6.1.4.1.2011.2.251.20.1.2.2.15.20480.37
        certificateWillExpire OBJECT IDENTIFIER ::= { certificatemanagement 37 }

        -- 1.3.6.1.4.1.2011.2.251.20.1.2.2.15.20480.37.1
        certificateWillExpire-Fault NOTIFICATION-TYPE
            OBJECTS { hwStorageAlarmReporting }
            STATUS current
            DESCRIPTION "A Certificate Is About To Expire"
            --#SEVERITY MAJOR
            ::= { certificateWillExpire 1 }

        -- 1.3.6.1.4.1.2011.2.251.20.1.2.2.15.20480.37.2
        certificateWillExpire-Resume NOTIFICATION-TYPE
            OBJECTS { hwStorageAlarmReporting }
            STATUS current
            DESCRIPTION "Recover: A Certificate Is About To Expire"
            --#SEVERITY INFORMATIONAL
            ::= { certificateWillExpire 2 }

        -- 1.3.6.1.4.1.2011.2.251.20.1.2.2.15.20480.351
        thereIsNoCACertificateForDiskAuthenticationOnTheArray OBJECT IDENTIFIER ::= { certificatemanagement 351 }

        -- 1.3.6.1.4.1.2011.2.251.20.1.2.2.15.20480.351.1
        thereIsNoCACertificateForDiskAuthenticationOnTheArray-Fault NOTIFICATION-TYPE
            OBJECTS { hwStorageAlarmReporting }
            STATUS current
            DESCRIPTION "There Is No CA Certificate For Disk Authentication On The Array"
            --#SEVERITY CRITICAL
            ::= { thereIsNoCACertificateForDiskAuthenticationOnTheArray 1 }

        -- 1.3.6.1.4.1.2011.2.251.20.1.2.2.15.20480.351.2
        thereIsNoCACertificateForDiskAuthenticationOnTheArray-Resume NOTIFICATION-TYPE
            OBJECTS { hwStorageAlarmReporting }
            STATUS current
            DESCRIPTION "Recover: There Is No CA Certificate For Disk Authentication On The Array"
            --#SEVERITY INFORMATIONAL
            ::= { thereIsNoCACertificateForDiskAuthenticationOnTheArray 2 }

        -- 1.3.6.1.4.1.2011.2.251.20.1.2.2.15.50000
        storageunit OBJECT IDENTIFIER ::= { oidBasedTrap 50000 }

        -- 1.3.6.1.4.1.2011.2.251.20.1.2.2.15.50000.1
        storageUnitIsDisconnected OBJECT IDENTIFIER ::= { storageunit 1 }

        -- 1.3.6.1.4.1.2011.2.251.20.1.2.2.15.50000.1.1
        storageUnitIsDisconnected-Fault NOTIFICATION-TYPE
            OBJECTS { hwStorageAlarmReporting }
            STATUS current
            DESCRIPTION "A Storage Unit Is Disconnected"
            --#SEVERITY MAJOR
            ::= { storageUnitIsDisconnected 1 }

        -- 1.3.6.1.4.1.2011.2.251.20.1.2.2.15.50000.1.2
        storageUnitIsDisconnected-Resume NOTIFICATION-TYPE
            OBJECTS { hwStorageAlarmReporting }
            STATUS current
            DESCRIPTION "Recover: A Storage Unit Is Disconnected"
            --#SEVERITY INFORMATIONAL
            ::= { storageUnitIsDisconnected 2 }

        -- 1.3.6.1.4.1.2011.2.251.20.1.2.2.15.50000.2
        storageUnitInaccessible OBJECT IDENTIFIER ::= { storageunit 2 }

        -- 1.3.6.1.4.1.2011.2.251.20.1.2.2.15.50000.2.1
        storageUnitInaccessible-Fault NOTIFICATION-TYPE
            OBJECTS { hwStorageAlarmReporting }
            STATUS current
            DESCRIPTION "Failed To Access The Storage Unit"
            --#SEVERITY WARNING
            ::= { storageUnitInaccessible 1 }

        -- 1.3.6.1.4.1.2011.2.251.20.1.2.2.15.50000.2.2
        storageUnitInaccessible-Resume NOTIFICATION-TYPE
            OBJECTS { hwStorageAlarmReporting }
            STATUS current
            DESCRIPTION "Recover: Failed To Access The Storage Unit"
            --#SEVERITY INFORMATIONAL
            ::= { storageUnitInaccessible 2 }

        -- 1.3.6.1.4.1.2011.2.251.20.1.2.2.15.50000.3
        theCapacityOfAStorageUnitInAStoragePoolIsInsufficient OBJECT IDENTIFIER ::= { storageunit 3 }

        -- 1.3.6.1.4.1.2011.2.251.20.1.2.2.15.50000.3.1
        theCapacityOfAStorageUnitInAStoragePoolIsInsufficient-Fault NOTIFICATION-TYPE
            OBJECTS { hwStorageAlarmReporting }
            STATUS current
            DESCRIPTION "The Capacity Of A Storage Unit In A Storage Pool Is Insufficient"
            --#SEVERITY MAJOR
            ::= { theCapacityOfAStorageUnitInAStoragePoolIsInsufficient 1 }

        -- 1.3.6.1.4.1.2011.2.251.20.1.2.2.15.50000.3.2
        theCapacityOfAStorageUnitInAStoragePoolIsInsufficient-Resume NOTIFICATION-TYPE
            OBJECTS { hwStorageAlarmReporting }
            STATUS current
            DESCRIPTION "Recover: The Capacity Of A Storage Unit In A Storage Pool Is Insufficient"
            --#SEVERITY INFORMATIONAL
            ::= { theCapacityOfAStorageUnitInAStoragePoolIsInsufficient 2 }

        -- 1.3.6.1.4.1.2011.2.251.20.1.2.2.15.50001
        repository OBJECT IDENTIFIER ::= { oidBasedTrap 50001 }

        -- 1.3.6.1.4.1.2011.2.251.20.1.2.2.15.50001.1
        insufficientRepositorySpace OBJECT IDENTIFIER ::= { repository 1 }

        -- 1.3.6.1.4.1.2011.2.251.20.1.2.2.15.50001.1.1
        insufficientRepositorySpace-Fault NOTIFICATION-TYPE
            OBJECTS { hwStorageAlarmReporting }
            STATUS current
            DESCRIPTION "Insufficient Repository Space"
            --#SEVERITY MAJOR
            ::= { insufficientRepositorySpace 1 }

        -- 1.3.6.1.4.1.2011.2.251.20.1.2.2.15.50001.1.2
        insufficientRepositorySpace-Resume NOTIFICATION-TYPE
            OBJECTS { hwStorageAlarmReporting }
            STATUS current
            DESCRIPTION "Recover: Insufficient Repository Space"
            --#SEVERITY INFORMATIONAL
            ::= { insufficientRepositorySpace 2 }

        -- 1.3.6.1.4.1.2011.2.251.20.1.2.2.15.50001.2
        repositoryUsageExceedsTheThreshold OBJECT IDENTIFIER ::= { repository 2 }

        -- 1.3.6.1.4.1.2011.2.251.20.1.2.2.15.50001.2.1
        repositoryUsageExceedsTheThreshold-Fault NOTIFICATION-TYPE
            OBJECTS { hwStorageAlarmReporting }
            STATUS current
            DESCRIPTION "Repository Usage Exceeds The Threshold"
            --#SEVERITY WARNING
            ::= { repositoryUsageExceedsTheThreshold 1 }

        -- 1.3.6.1.4.1.2011.2.251.20.1.2.2.15.50001.2.2
        repositoryUsageExceedsTheThreshold-Resume NOTIFICATION-TYPE
            OBJECTS { hwStorageAlarmReporting }
            STATUS current
            DESCRIPTION "Recover: Repository Usage Exceeds The Threshold"
            --#SEVERITY INFORMATIONAL
            ::= { repositoryUsageExceedsTheThreshold 2 }

        -- 1.3.6.1.4.1.2011.2.251.20.1.2.2.15.50011
        job OBJECT IDENTIFIER ::= { oidBasedTrap 50011 }

        -- 1.3.6.1.4.1.2011.2.251.20.1.2.2.15.50011.1
        theNumberOfTasksReachesTheThreshold OBJECT IDENTIFIER ::= { job 1 }

        -- 1.3.6.1.4.1.2011.2.251.20.1.2.2.15.50011.1.1
        theNumberOfTasksReachesTheThreshold-Fault NOTIFICATION-TYPE
            OBJECTS { hwStorageAlarmReporting }
            STATUS current
            DESCRIPTION "The Number Of Tasks Reaches The Threshold"
            --#SEVERITY WARNING
            ::= { theNumberOfTasksReachesTheThreshold 1 }

        -- 1.3.6.1.4.1.2011.2.251.20.1.2.2.15.50011.1.2
        theNumberOfTasksReachesTheThreshold-Resume NOTIFICATION-TYPE
            OBJECTS { hwStorageAlarmReporting }
            STATUS current
            DESCRIPTION "Recover: The Number Of Tasks Reaches The Threshold"
            --#SEVERITY INFORMATIONAL
            ::= { theNumberOfTasksReachesTheThreshold 2 }

        -- 1.3.6.1.4.1.2011.2.251.20.1.2.2.15.50011.2
        theNumberOfTasksReachesTheUpperLimit OBJECT IDENTIFIER ::= { job 2 }

        -- 1.3.6.1.4.1.2011.2.251.20.1.2.2.15.50011.2.1
        theNumberOfTasksReachesTheUpperLimit-Fault NOTIFICATION-TYPE
            OBJECTS { hwStorageAlarmReporting }
            STATUS current
            DESCRIPTION "The Number Of Tasks Reaches The Upper Limit"
            --#SEVERITY MAJOR
            ::= { theNumberOfTasksReachesTheUpperLimit 1 }

        -- 1.3.6.1.4.1.2011.2.251.20.1.2.2.15.50011.2.2
        theNumberOfTasksReachesTheUpperLimit-Resume NOTIFICATION-TYPE
            OBJECTS { hwStorageAlarmReporting }
            STATUS current
            DESCRIPTION "Recover: The Number Of Tasks Reaches The Upper Limit"
            --#SEVERITY INFORMATIONAL
            ::= { theNumberOfTasksReachesTheUpperLimit 2 }

        -- 1.3.6.1.4.1.2011.2.251.20.1.2.2.15.50012
        backupimage OBJECT IDENTIFIER ::= { oidBasedTrap 50012 }

        -- 1.3.6.1.4.1.2011.2.251.20.1.2.2.15.50012.5
        theNumberOfBackupImagesIsAboutToReachTheUpperLimit OBJECT IDENTIFIER ::= { backupimage 5 }

        -- 1.3.6.1.4.1.2011.2.251.20.1.2.2.15.50012.5.1
        theNumberOfBackupImagesIsAboutToReachTheUpperLimit-Fault NOTIFICATION-TYPE
            OBJECTS { hwStorageAlarmReporting }
            STATUS current
            DESCRIPTION "The Number Of Backup Images Is About To Reach The Upper Limit Supported By The System"
            --#SEVERITY WARNING
            ::= { theNumberOfBackupImagesIsAboutToReachTheUpperLimit 1 }

        -- 1.3.6.1.4.1.2011.2.251.20.1.2.2.15.50012.5.2
        theNumberOfBackupImagesIsAboutToReachTheUpperLimit-Resume NOTIFICATION-TYPE
            OBJECTS { hwStorageAlarmReporting }
            STATUS current
            DESCRIPTION "Recover: The Number Of Backup Images Is About To Reach The Upper Limit Supported By The System"
            --#SEVERITY INFORMATIONAL
            ::= { theNumberOfBackupImagesIsAboutToReachTheUpperLimit 2 }

        -- 1.3.6.1.4.1.2011.2.251.20.1.2.2.15.50029
        systemtime OBJECT IDENTIFIER ::= { oidBasedTrap 50029 }

        -- 1.3.6.1.4.1.2011.2.251.20.1.2.2.15.50029.1
        nTPFailedToSynchronizeTime OBJECT IDENTIFIER ::= { systemtime 1 }

        -- 1.3.6.1.4.1.2011.2.251.20.1.2.2.15.50029.1.1
        nTPFailedToSynchronizeTime-Fault NOTIFICATION-TYPE
            OBJECTS { hwStorageAlarmReporting }
            STATUS current
            DESCRIPTION "NTP Failed To Synchronize Time"
            --#SEVERITY WARNING
            ::= { nTPFailedToSynchronizeTime 1 }

        -- 1.3.6.1.4.1.2011.2.251.20.1.2.2.15.50029.1.2
        nTPFailedToSynchronizeTime-Resume NOTIFICATION-TYPE
            OBJECTS { hwStorageAlarmReporting }
            STATUS current
            DESCRIPTION "Recover: NTP Failed To Synchronize Time"
            --#SEVERITY INFORMATIONAL
            ::= { nTPFailedToSynchronizeTime 2 }

        -- 1.3.6.1.4.1.2011.2.251.20.1.2.2.15.57435
        chsagent OBJECT IDENTIFIER ::= { oidBasedTrap 57435 }

        -- 1.3.6.1.4.1.2011.2.251.20.1.2.2.15.57435.4
        dMEIQFailedToConnectToTheRemoteServer OBJECT IDENTIFIER ::= { chsagent 4 }

        -- 1.3.6.1.4.1.2011.2.251.20.1.2.2.15.57435.4.1
        dMEIQFailedToConnectToTheRemoteServer-Fault NOTIFICATION-TYPE
            OBJECTS { hwStorageAlarmReporting }
            STATUS current
            DESCRIPTION "DME IQ Failed To Connect To The Remote Server"
            --#SEVERITY WARNING
            ::= { dMEIQFailedToConnectToTheRemoteServer 1 }

        -- 1.3.6.1.4.1.2011.2.251.20.1.2.2.15.57435.4.2
        dMEIQFailedToConnectToTheRemoteServer-Resume NOTIFICATION-TYPE
            OBJECTS { hwStorageAlarmReporting }
            STATUS current
            DESCRIPTION "Recover: DME IQ Failed To Connect To The Remote Server"
            --#SEVERITY INFORMATIONAL
            ::= { dMEIQFailedToConnectToTheRemoteServer 2 }

        -- 1.3.6.1.4.1.2011.2.251.20.1.2.2.15.57508
        drstar OBJECT IDENTIFIER ::= { oidBasedTrap 57508 }

        -- 1.3.6.1.4.1.2011.2.251.20.1.2.2.15.57508.2
        drStarIsInvalid OBJECT IDENTIFIER ::= { drstar 2 }

        -- 1.3.6.1.4.1.2011.2.251.20.1.2.2.15.57508.2.1
        drStarIsInvalid-Fault NOTIFICATION-TYPE
            OBJECTS { hwStorageAlarmReporting }
            STATUS current
            DESCRIPTION "DR Star Is Invalid"
            --#SEVERITY CRITICAL
            ::= { drStarIsInvalid 1 }

        -- 1.3.6.1.4.1.2011.2.251.20.1.2.2.15.57508.2.2
        drStarIsInvalid-Resume NOTIFICATION-TYPE
            OBJECTS { hwStorageAlarmReporting }
            STATUS current
            DESCRIPTION "Recover: DR Star Is Invalid"
            --#SEVERITY INFORMATIONAL
            ::= { drStarIsInvalid 2 }

        -- 1.3.6.1.4.1.2011.2.251.20.1.2.2.15.57802
        fsmigration OBJECT IDENTIFIER ::= { oidBasedTrap 57802 }

        -- 1.3.6.1.4.1.2011.2.251.20.1.2.2.15.57802.5
        aFileSystemMigrationTaskIsFaulty OBJECT IDENTIFIER ::= { fsmigration 5 }

        -- 1.3.6.1.4.1.2011.2.251.20.1.2.2.15.57802.5.1
        aFileSystemMigrationTaskIsFaulty-Fault NOTIFICATION-TYPE
            OBJECTS { hwStorageAlarmReporting }
            STATUS current
            DESCRIPTION "A File System Migration Task Is Faulty"
            --#SEVERITY MAJOR
            ::= { aFileSystemMigrationTaskIsFaulty 1 }

        -- 1.3.6.1.4.1.2011.2.251.20.1.2.2.15.57802.5.2
        aFileSystemMigrationTaskIsFaulty-Resume NOTIFICATION-TYPE
            OBJECTS { hwStorageAlarmReporting }
            STATUS current
            DESCRIPTION "Recover: A File System Migration Task Is Faulty"
            --#SEVERITY INFORMATIONAL
            ::= { aFileSystemMigrationTaskIsFaulty 2 }

        -- 1.3.6.1.4.1.2011.2.251.20.1.2.2.15.57802.6
        theNumberOfSynchronizationTimesOfTheFileSystemMigrationTaskHasReachedTheUpperLimit OBJECT IDENTIFIER ::= { fsmigration 6 }

        -- 1.3.6.1.4.1.2011.2.251.20.1.2.2.15.57802.6.1
        theNumberOfSynchronizationTimesOfTheFileSystemMigrationTaskHasReachedTheUpperLimit-Fault NOTIFICATION-TYPE
            OBJECTS { hwStorageAlarmReporting }
            STATUS current
            DESCRIPTION "The Number Of Synchronization Times Of The File System Migration Task Has Reached The Upper Limit"
            --#SEVERITY MAJOR
            ::= { theNumberOfSynchronizationTimesOfTheFileSystemMigrationTaskHasReachedTheUpperLimit 1 }

        -- 1.3.6.1.4.1.2011.2.251.20.1.2.2.15.57802.6.2
        theNumberOfSynchronizationTimesOfTheFileSystemMigrationTaskHasReachedTheUpperLimit-Resume NOTIFICATION-TYPE
            OBJECTS { hwStorageAlarmReporting }
            STATUS current
            DESCRIPTION "Recover: The Number Of Synchronization Times Of The File System Migration Task Has Reached The Upper Limit"
            --#SEVERITY INFORMATIONAL
            ::= { theNumberOfSynchronizationTimesOfTheFileSystemMigrationTaskHasReachedTheUpperLimit 2 }

        -- 1.3.6.1.4.1.2011.2.251.20.1.2.2.15.57802.7
        theNASMigrationLinkIsDisconnectedProactively OBJECT IDENTIFIER ::= { fsmigration 7 }

        -- 1.3.6.1.4.1.2011.2.251.20.1.2.2.15.57802.7.1
        theNASMigrationLinkIsDisconnectedProactively-Fault NOTIFICATION-TYPE
            OBJECTS { hwStorageAlarmReporting }
            STATUS current
            DESCRIPTION "The NAS Migration Link Is Disconnected Proactively"
            --#SEVERITY WARNING
            ::= { theNASMigrationLinkIsDisconnectedProactively 1 }

        -- 1.3.6.1.4.1.2011.2.251.20.1.2.2.15.57802.7.2
        theNASMigrationLinkIsDisconnectedProactively-Resume NOTIFICATION-TYPE
            OBJECTS { hwStorageAlarmReporting }
            STATUS current
            DESCRIPTION "Recover: The NAS Migration Link Is Disconnected Proactively"
            --#SEVERITY INFORMATIONAL
            ::= { theNASMigrationLinkIsDisconnectedProactively 2 }

        -- 1.3.6.1.4.1.2011.2.251.20.1.2.2.15.57802.8
        thereIsNoFreeSpaceInTheLogFileSystem OBJECT IDENTIFIER ::= { fsmigration 8 }

        -- 1.3.6.1.4.1.2011.2.251.20.1.2.2.15.57802.8.1
        thereIsNoFreeSpaceInTheLogFileSystem-Fault NOTIFICATION-TYPE
            OBJECTS { hwStorageAlarmReporting }
            STATUS current
            DESCRIPTION "There Is No Free Space In The Log File System"
            --#SEVERITY WARNING
            ::= { thereIsNoFreeSpaceInTheLogFileSystem 1 }

        -- 1.3.6.1.4.1.2011.2.251.20.1.2.2.15.57802.8.2
        thereIsNoFreeSpaceInTheLogFileSystem-Resume NOTIFICATION-TYPE
            OBJECTS { hwStorageAlarmReporting }
            STATUS current
            DESCRIPTION "Recover: There Is No Free Space In The Log File System"
            --#SEVERITY INFORMATIONAL
            ::= { thereIsNoFreeSpaceInTheLogFileSystem 2 }

        -- 1.3.6.1.4.1.2011.2.251.20.1.2.2.15.57884
        containerservice OBJECT IDENTIFIER ::= { oidBasedTrap 57884 }

        -- 1.3.6.1.4.1.2011.2.251.20.1.2.2.15.57884.6
        failedToStartTheContainerServiceOnTheController OBJECT IDENTIFIER ::= { containerservice 6 }

        -- 1.3.6.1.4.1.2011.2.251.20.1.2.2.15.57884.6.1
        failedToStartTheContainerServiceOnTheController-Fault NOTIFICATION-TYPE
            OBJECTS { hwStorageAlarmReporting }
            STATUS current
            DESCRIPTION "Failed To Start The Container Service On The Controller"
            --#SEVERITY WARNING
            ::= { failedToStartTheContainerServiceOnTheController 1 }

        -- 1.3.6.1.4.1.2011.2.251.20.1.2.2.15.57884.6.2
        failedToStartTheContainerServiceOnTheController-Resume NOTIFICATION-TYPE
            OBJECTS { hwStorageAlarmReporting }
            STATUS current
            DESCRIPTION "Recover: Failed To Start The Container Service On The Controller"
            --#SEVERITY INFORMATIONAL
            ::= { failedToStartTheContainerServiceOnTheController 2 }

        -- 1.3.6.1.4.1.2011.2.251.20.1.2.2.15.57884.8
        containerRootDirectoryIsFaulty OBJECT IDENTIFIER ::= { containerservice 8 }

        -- 1.3.6.1.4.1.2011.2.251.20.1.2.2.15.57884.8.1
        containerRootDirectoryIsFaulty-Fault NOTIFICATION-TYPE
            OBJECTS { hwStorageAlarmReporting }
            STATUS current
            DESCRIPTION "Container Root Directory Is Faulty"
            --#SEVERITY WARNING
            ::= { containerRootDirectoryIsFaulty 1 }

        -- 1.3.6.1.4.1.2011.2.251.20.1.2.2.15.57884.8.2
        containerRootDirectoryIsFaulty-Resume NOTIFICATION-TYPE
            OBJECTS { hwStorageAlarmReporting }
            STATUS current
            DESCRIPTION "Recover: Container Root Directory Is Faulty"
            --#SEVERITY INFORMATIONAL
            ::= { containerRootDirectoryIsFaulty 2 }

        -- 1.3.6.1.4.1.2011.2.251.20.1.2.2.15.57884.9
        theContainerServiceProcessOnTheControllerIsAbnormal OBJECT IDENTIFIER ::= { containerservice 9 }

        -- 1.3.6.1.4.1.2011.2.251.20.1.2.2.15.57884.9.1
        theContainerServiceProcessOnTheControllerIsAbnormal-Fault NOTIFICATION-TYPE
            OBJECTS { hwStorageAlarmReporting }
            STATUS current
            DESCRIPTION "The Container Service Process On The Controller Is Abnormal"
            --#SEVERITY MAJOR
            ::= { theContainerServiceProcessOnTheControllerIsAbnormal 1 }

        -- 1.3.6.1.4.1.2011.2.251.20.1.2.2.15.57884.9.2
        theContainerServiceProcessOnTheControllerIsAbnormal-Resume NOTIFICATION-TYPE
            OBJECTS { hwStorageAlarmReporting }
            STATUS current
            DESCRIPTION "Recover: The Container Service Process On The Controller Is Abnormal"
            --#SEVERITY INFORMATIONAL
            ::= { theContainerServiceProcessOnTheControllerIsAbnormal 2 }

        -- 1.3.6.1.4.1.2011.2.251.20.1.2.2.15.57885
        containerapplication OBJECT IDENTIFIER ::= { oidBasedTrap 57885 }

        -- 1.3.6.1.4.1.2011.2.251.20.1.2.2.15.57885.1
        failedToActivateTheComponent OBJECT IDENTIFIER ::= { containerapplication 1 }

        -- 1.3.6.1.4.1.2011.2.251.20.1.2.2.15.57885.1.1
        failedToActivateTheComponent-Fault NOTIFICATION-TYPE
            OBJECTS { hwStorageAlarmReporting }
            STATUS current
            DESCRIPTION "Failed To Activate The Component"
            --#SEVERITY WARNING
            ::= { failedToActivateTheComponent 1 }

        -- 1.3.6.1.4.1.2011.2.251.20.1.2.2.15.57885.1.2
        failedToActivateTheComponent-Resume NOTIFICATION-TYPE
            OBJECTS { hwStorageAlarmReporting }
            STATUS current
            DESCRIPTION "Recover: Failed To Activate The Component"
            --#SEVERITY INFORMATIONAL
            ::= { failedToActivateTheComponent 2 }

        -- 1.3.6.1.4.1.2011.2.251.20.1.2.2.15.57885.2
        failedToUninstallTheComponent OBJECT IDENTIFIER ::= { containerapplication 2 }

        -- 1.3.6.1.4.1.2011.2.251.20.1.2.2.15.57885.2.1
        failedToUninstallTheComponent-Fault NOTIFICATION-TYPE
            OBJECTS { hwStorageAlarmReporting }
            STATUS current
            DESCRIPTION "Failed To Uninstall The Component"
            --#SEVERITY WARNING
            ::= { failedToUninstallTheComponent 1 }

        -- 1.3.6.1.4.1.2011.2.251.20.1.2.2.15.57885.2.2
        failedToUninstallTheComponent-Resume NOTIFICATION-TYPE
            OBJECTS { hwStorageAlarmReporting }
            STATUS current
            DESCRIPTION "Recover: Failed To Uninstall The Component"
            --#SEVERITY INFORMATIONAL
            ::= { failedToUninstallTheComponent 2 }

        -- 1.3.6.1.4.1.2011.2.251.20.1.2.2.15.57886
        containerpod OBJECT IDENTIFIER ::= { oidBasedTrap 57886 }

        -- 1.3.6.1.4.1.2011.2.251.20.1.2.2.15.57886.1
        podIsAbnormal OBJECT IDENTIFIER ::= { containerpod 1 }

        -- 1.3.6.1.4.1.2011.2.251.20.1.2.2.15.57886.1.1
        podIsAbnormal-Fault NOTIFICATION-TYPE
            OBJECTS { hwStorageAlarmReporting }
            STATUS current
            DESCRIPTION "Pod Is Abnormal"
            --#SEVERITY MAJOR
            ::= { podIsAbnormal 1 }

        -- 1.3.6.1.4.1.2011.2.251.20.1.2.2.15.57886.1.2
        podIsAbnormal-Resume NOTIFICATION-TYPE
            OBJECTS { hwStorageAlarmReporting }
            STATUS current
            DESCRIPTION "Recover: Pod Is Abnormal"
            --#SEVERITY INFORMATIONAL
            ::= { podIsAbnormal 2 }

        -- 1.3.6.1.4.1.2011.2.251.20.1.2.2.15.57886.5
        theContainerPodDirectoryIsFaulty OBJECT IDENTIFIER ::= { containerpod 5 }

        -- 1.3.6.1.4.1.2011.2.251.20.1.2.2.15.57886.5.1
        theContainerPodDirectoryIsFaulty-Fault NOTIFICATION-TYPE
            OBJECTS { hwStorageAlarmReporting }
            STATUS current
            DESCRIPTION "The Container Pod Directory Is Faulty"
            --#SEVERITY WARNING
            ::= { theContainerPodDirectoryIsFaulty 1 }

        -- 1.3.6.1.4.1.2011.2.251.20.1.2.2.15.57886.5.2
        theContainerPodDirectoryIsFaulty-Resume NOTIFICATION-TYPE
            OBJECTS { hwStorageAlarmReporting }
            STATUS current
            DESCRIPTION "Recover: The Container Pod Directory Is Faulty"
            --#SEVERITY INFORMATIONAL
            ::= { theContainerPodDirectoryIsFaulty 2 }

        -- 1.3.6.1.4.1.2011.2.251.20.1.2.2.15.60002
        storagecluster OBJECT IDENTIFIER ::= { oidBasedTrap 60002 }

        -- 1.3.6.1.4.1.2011.2.251.20.1.2.2.15.60002.37
        updateArbtrationFail OBJECT IDENTIFIER ::= { storagecluster 37 }

        -- 1.3.6.1.4.1.2011.2.251.20.1.2.2.15.60002.37.1
        updateArbtrationFail-Fault NOTIFICATION-TYPE
            OBJECTS { hwStorageAlarmReporting }
            STATUS current
            DESCRIPTION "Failed To Update CCDB Arbitration Information"
            --#SEVERITY MAJOR
            ::= { updateArbtrationFail 1 }

        -- 1.3.6.1.4.1.2011.2.251.20.1.2.2.15.60002.37.2
        updateArbtrationFail-Resume NOTIFICATION-TYPE
            OBJECTS { hwStorageAlarmReporting }
            STATUS current
            DESCRIPTION "Recover: Failed To Update CCDB Arbitration Information"
            --#SEVERITY INFORMATIONAL
            ::= { updateArbtrationFail 2 }

        -- 1.3.6.1.4.1.2011.2.251.20.1.2.2.15.60002.13335
        cCDBClusterBackupFailed OBJECT IDENTIFIER ::= { storagecluster 13335 }

        -- 1.3.6.1.4.1.2011.2.251.20.1.2.2.15.60002.13335.1
        cCDBClusterBackupFailed-Fault NOTIFICATION-TYPE
            OBJECTS { hwStorageAlarmReporting }
            STATUS current
            DESCRIPTION "CCDB Cluster Backup Failed"
            --#SEVERITY MAJOR
            ::= { cCDBClusterBackupFailed 1 }

        -- 1.3.6.1.4.1.2011.2.251.20.1.2.2.15.60002.13335.2
        cCDBClusterBackupFailed-Resume NOTIFICATION-TYPE
            OBJECTS { hwStorageAlarmReporting }
            STATUS current
            DESCRIPTION "Recover: CCDB Cluster Backup Failed"
            --#SEVERITY INFORMATIONAL
            ::= { cCDBClusterBackupFailed 2 }

        -- 1.3.6.1.4.1.2011.2.251.20.1.2.2.15.60002.13341
        ccdbBackupFailed OBJECT IDENTIFIER ::= { storagecluster 13341 }

        -- 1.3.6.1.4.1.2011.2.251.20.1.2.2.15.60002.13341.1
        ccdbBackupFailed-Fault NOTIFICATION-TYPE
            OBJECTS { hwStorageAlarmReporting }
            STATUS current
            DESCRIPTION "CCDB Database Backup Failed In The HyperScale Cluster"
            --#SEVERITY MAJOR
            ::= { ccdbBackupFailed 1 }

        -- 1.3.6.1.4.1.2011.2.251.20.1.2.2.15.60002.13341.2
        ccdbBackupFailed-Resume NOTIFICATION-TYPE
            OBJECTS { hwStorageAlarmReporting }
            STATUS current
            DESCRIPTION "Recover: CCDB Database Backup Failed In The HyperScale Cluster"
            --#SEVERITY INFORMATIONAL
            ::= { ccdbBackupFailed 2 }


    END
--
-- HUAWEI-STORAGE-OID-BASED-TRAP-MIB.mib
--
