-- OPTIX-GLOBAL-PM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-PM-MIB DEFINITIONS ::= BEGIN
    IMPORTS
        optixCommonGlobal
            FROM OPTIX-OID-MIB
        PerformanceEventType,ValidflagType,ObjType,AlarmEventType,AlmDataSrvEffType,AlmDataNtfcnCdeType
            FROM OPTIX-GLOBAL-TC-MIB
        OBJECT-GROUP,MODULE-COMPLIANCE
            FROM SNMPv2-CONF
        Integer32,Unsigned32,OBJECT-TYPE,MODULE-IDENTITY
            FROM SNMPv2-SMI
        DateAndTime,DisplayString
            FROM SNMPv2-TC
        ;

    optixGlobalPM MODULE-IDENTITY
        LAST-UPDATED "200805240500Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Data performance module"
        REVISION "200805240500Z"
        DESCRIPTION
            "The initial version"
        ::={ optixCommonGlobal 10 }

    -- 1.3.6.1.4.1.2011.2.25.3.40.10.10
    pmHistCtr OBJECT IDENTIFIER ::= { optixGlobalPM 10 }

    -- 1.3.6.1.4.1.2011.2.25.3.40.10.10.10
    pmHistCtrTable OBJECT-TYPE
        SYNTAX SEQUENCE OF PmHistCtrEntry
        MAX-ACCESS not-accessible
        STATUS current
        DESCRIPTION
            "Indicates the historical control table of data performance."
        ::= { pmHistCtr 10 }

    -- 1.3.6.1.4.1.2011.2.25.3.40.10.10.10.1
    pmHistCtrEntry OBJECT-TYPE
        SYNTAX PmHistCtrEntry
        MAX-ACCESS not-accessible
        STATUS current
        DESCRIPTION
            "Indicates entry node in the historical control table of data performance."
        INDEX{ pmHistCtrPeriod }
        ::= { pmHistCtrTable 1 }

    PmHistCtrEntry ::=
        SEQUENCE {
            pmHistCtrPeriod
                INTEGER,
            pmHistCtrRecNum
                INTEGER,
            pmHistCtrInterval
                INTEGER,
            pmHistCtrEnableFlag
                INTEGER
        }

    -- 1.3.6.1.4.1.2011.2.25.3.40.10.10.10.1.1
    pmHistCtrPeriod OBJECT-TYPE
        SYNTAX INTEGER
        {
            period30s(17),
            period30m(18),
            periodPrdvar(19),
            periodPrdvar2(20)
        }
        MAX-ACCESS read-only
        STATUS current
        DESCRIPTION
            "Indicates the history data performance period."
        ::= { pmHistCtrEntry 1 }

    -- 1.3.6.1.4.1.2011.2.25.3.40.10.10.10.1.2
    pmHistCtrRecNum OBJECT-TYPE
        SYNTAX INTEGER
        MAX-ACCESS read-write
        STATUS current
        DESCRIPTION
            "Indicates the number of registers in a history data performance period."
        ::= { pmHistCtrEntry 2 }

    -- 1.3.6.1.4.1.2011.2.25.3.40.10.10.10.1.3
    pmHistCtrInterval OBJECT-TYPE
        SYNTAX INTEGER
        MAX-ACCESS read-write
        STATUS current
        DESCRIPTION
            "Indicates the interval between two history data performance periods."
        ::= { pmHistCtrEntry 3 }

    -- 1.3.6.1.4.1.2011.2.25.3.40.10.10.10.1.4
    pmHistCtrEnableFlag OBJECT-TYPE
        SYNTAX INTEGER
        {
            enable(1),
            disable(0)
        }
        MAX-ACCESS read-write
        STATUS current
        DESCRIPTION
            "Indicates the enable/diable status of the history data performance period."
        ::= { pmHistCtrEntry 4 }

END
