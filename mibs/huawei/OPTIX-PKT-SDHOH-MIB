-- OPTIX-PKT-SDHOH-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-SDHOH-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        ;

    optixPktSdhOh MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of sdh tunnel"
        REVISION "201204200000Z"
        DESCRIPTION
            "The initial revision of this MIB module1."
        ::={ optixProvisionPtn 34 }

    -- 1.3.6.1.4.1.2011.2.25.4.50.34.1
    optixPktSdhOhGroup OBJECT IDENTIFIER ::= { optixPktSdhOh 1 }

    -- 1.3.6.1.4.1.2011.2.25.4.50.34.1.1
    optixPktSdhPortOhTable OBJECT-TYPE
        SYNTAX SEQUENCE OF OptixPktSdhPortOhEntry
        MAX-ACCESS not-accessible
        STATUS current
        DESCRIPTION
            "This table describes the SDH port configurations."
        ::= { optixPktSdhOhGroup 1 }

    -- 1.3.6.1.4.1.2011.2.25.4.50.34.1.1.1
    optixPktSdhPortOhEntry OBJECT-TYPE
        SYNTAX OptixPktSdhPortOhEntry
        MAX-ACCESS not-accessible
        STATUS current
        DESCRIPTION
            "This entry describes the SDH port configurations."
        INDEX{ optixLogBoardId,optixLogSubCardId,optixPktSdhPortId }
        ::= { optixPktSdhPortOhTable 1 }

    OptixPktSdhPortOhEntry ::=
        SEQUENCE {
            optixPktSdhPortId
                Unsigned32,
            optixPktSdhSRJ0Mode
                INTEGER,
            optixPktSdhSRJ0Value
                OCTET STRING,
            optixPktSdhSTJ0Mode
                INTEGER,
            optixPktSdhSTJ0Value
                OCTET STRING,
            optixPktSdhRJ0Mode
                Unsigned32,
            optixPktSdhRJ0Value
                OCTET STRING,
            optixPktSdhLoopMode
                INTEGER,
            optixPktSdhLaserStatus
                INTEGER,
            optixPktSdhLSRStatus
                INTEGER,
            optixPktSdhLSRDistance
                Unsigned32,
            optixPktSdhAisCheck
                INTEGER
        }

    -- 1.3.6.1.4.1.2011.2.25.4.50.34.1.1.1.1
    optixPktSdhPortId OBJECT-TYPE
        SYNTAX Unsigned32
        MAX-ACCESS not-accessible
        STATUS current
        DESCRIPTION
            "This object indicates the port number of theSDH port."
        ::= { optixPktSdhPortOhEntry 1 }

    -- 1.3.6.1.4.1.2011.2.25.4.50.34.1.1.1.2
    optixPktSdhSRJ0Mode OBJECT-TYPE
        SYNTAX INTEGER
        {
            sdh(0),
            sdhcrc(1),
            singlecharacter(3)
        }
        MAX-ACCESS read-write
        STATUS current
        DESCRIPTION
            "This object indicates the J0 byte to be actual received mode. 0: sdh, 1: sdhcrc, 3: singlecharacter"
        ::= { optixPktSdhPortOhEntry 2 }

    -- 1.3.6.1.4.1.2011.2.25.4.50.34.1.1.1.3
    optixPktSdhSRJ0Value OBJECT-TYPE
        SYNTAX OCTET STRING (SIZE(0..32))
        MAX-ACCESS read-write
        STATUS current
        DESCRIPTION
            "This object indicates the value of J0 byte to be received."
        ::= { optixPktSdhPortOhEntry 3 }

    -- 1.3.6.1.4.1.2011.2.25.4.50.34.1.1.1.4
    optixPktSdhSTJ0Mode OBJECT-TYPE
        SYNTAX INTEGER
        {
            sdh(0),
            sdhcrc(1),
            singlecharacter(3)
        }
        MAX-ACCESS read-write
        STATUS current
        DESCRIPTION
            "This object indicates the mode of the J0 byte to be sent. 0: sdh, 1: sdhcrc, 3: singlecharacter"
        ::= { optixPktSdhPortOhEntry 4 }

    -- 1.3.6.1.4.1.2011.2.25.4.50.34.1.1.1.5
    optixPktSdhSTJ0Value OBJECT-TYPE
        SYNTAX OCTET STRING (SIZE(0..32))
        MAX-ACCESS read-write
        STATUS current
        DESCRIPTION
            "This object indicates the value of J0 byte to be sended condignly."
        ::= { optixPktSdhPortOhEntry 5 }

    -- 1.3.6.1.4.1.2011.2.25.4.50.34.1.1.1.6
    optixPktSdhRJ0Mode OBJECT-TYPE
        SYNTAX Unsigned32
        MAX-ACCESS read-only
        STATUS current
        DESCRIPTION
            "This object indicates the actual received J0 byte mode."
        ::= { optixPktSdhPortOhEntry 6 }

    -- 1.3.6.1.4.1.2011.2.25.4.50.34.1.1.1.7
    optixPktSdhRJ0Value OBJECT-TYPE
        SYNTAX OCTET STRING (SIZE(0..32))
        MAX-ACCESS read-only
        STATUS current
        DESCRIPTION
            "This object indicates the value of actual received J0 byte."
        ::= { optixPktSdhPortOhEntry 7 }

    -- 1.3.6.1.4.1.2011.2.25.4.50.34.1.1.1.8
    optixPktSdhLoopMode OBJECT-TYPE
        SYNTAX INTEGER
        {
            noloop(0),
            loopin(1),
            loopout(2)
        }
        MAX-ACCESS read-write
        STATUS current
        DESCRIPTION
            "This object indicates the loopback mode of the optical port. 0: noloop, 1: inloop, 2: outloop"
        ::= { optixPktSdhPortOhEntry 8 }

    -- 1.3.6.1.4.1.2011.2.25.4.50.34.1.1.1.9
    optixPktSdhLaserStatus OBJECT-TYPE
        SYNTAX INTEGER
        {
            open(1),
            close(0)
        }
        MAX-ACCESS read-write
        STATUS current
        DESCRIPTION
            "This object indicates theenable status of the laser. 1: open, 0: close"
        ::= { optixPktSdhPortOhEntry 9 }

    -- 1.3.6.1.4.1.2011.2.25.4.50.34.1.1.1.10
    optixPktSdhLSRStatus OBJECT-TYPE
        SYNTAX INTEGER
        {
            onLine(1),
            offLine(0)
        }
        MAX-ACCESS read-only
        STATUS current
        DESCRIPTION
            "This object indicates the online information of the laser with the hot swapping function. 1: onLine, 0: offLine"
        ::= { optixPktSdhPortOhEntry 10 }

    -- 1.3.6.1.4.1.2011.2.25.4.50.34.1.1.1.11
    optixPktSdhLSRDistance OBJECT-TYPE
        SYNTAX Unsigned32
        MAX-ACCESS read-only
        STATUS current
        DESCRIPTION
            "This object indicates the transmission distance of the laser."
        ::= { optixPktSdhPortOhEntry 11 }

    -- 1.3.6.1.4.1.2011.2.25.4.50.34.1.1.1.12
    optixPktSdhAisCheck OBJECT-TYPE
        SYNTAX INTEGER
        {
            disable(0),
            enable(1)
        }
        MAX-ACCESS read-write
        STATUS current
        DESCRIPTION
            "This object indicates the status of the Ais alarm."
        ::= { optixPktSdhPortOhEntry 12 }

    -- 1.3.6.1.4.1.2011.2.25.4.50.34.1.2
    optixPktSdhVC4OhTable OBJECT-TYPE
        SYNTAX SEQUENCE OF OptixPktSdhVC4OhEntry
        MAX-ACCESS not-accessible
        STATUS current
        DESCRIPTION
            "This table describes the SDH VC4 channel configurations."
        ::= { optixPktSdhOhGroup 2 }

    -- 1.3.6.1.4.1.2011.2.25.4.50.34.1.2.1
    optixPktSdhVC4OhEntry OBJECT-TYPE
        SYNTAX OptixPktSdhVC4OhEntry
        MAX-ACCESS not-accessible
        STATUS current
        DESCRIPTION
            "Thisentry describes the SDH VC4 channel configurations."
        INDEX{ optixLogBoardId,optixLogSubCardId,optixPktSdhPortId,optixPktSdhVC4HP }
        ::= { optixPktSdhVC4OhTable 1 }

    OptixPktSdhVC4OhEntry ::=
        SEQUENCE {
            optixPktSdhVC4HP
                Unsigned32,
            optixPktSdhSTJ1Mode
                INTEGER,
            optixPktSdhSTJ1Value
                OCTET STRING,
            optixPktSdhSRJ1Mode
                INTEGER,
            optixPktSdhSRJ1Value
                OCTET STRING,
            optixPktSdhRJ1Mode
                Unsigned32,
            optixPktSdhRJ1Value
                OCTET STRING,
            optixPktSdhSTC2Value
                INTEGER,
            optixPktSdhSRC2Value
                INTEGER,
            optixPktSdhRC2Value
                Unsigned32
        }

    -- 1.3.6.1.4.1.2011.2.25.4.50.34.1.2.1.1
    optixPktSdhVC4HP OBJECT-TYPE
        SYNTAX Unsigned32
        MAX-ACCESS not-accessible
        STATUS current
        DESCRIPTION
            "This object indicates the high-order VC4 channel ID."
        ::= { optixPktSdhVC4OhEntry 1 }

    -- 1.3.6.1.4.1.2011.2.25.4.50.34.1.2.1.2
    optixPktSdhSTJ1Mode OBJECT-TYPE
        SYNTAX INTEGER
        {
            sdh(0),
            sdhcrc(1),
            sonet(2),
            singlecharacter(3)
        }
        MAX-ACCESS read-write
        STATUS current
        DESCRIPTION
            "This object indicates the J1 byte to be transmitted mode condignly. 0: sdh, 1: sdhcrc, 2: sonet, 3: singlecharacter"
        ::= { optixPktSdhVC4OhEntry 2 }

    -- 1.3.6.1.4.1.2011.2.25.4.50.34.1.2.1.3
    optixPktSdhSTJ1Value OBJECT-TYPE
        SYNTAX OCTET STRING (SIZE(0..64))
        MAX-ACCESS read-write
        STATUS current
        DESCRIPTION
            "This object indicates the value of J1 byte to be actual transmitted."
        ::= { optixPktSdhVC4OhEntry 3 }

    -- 1.3.6.1.4.1.2011.2.25.4.50.34.1.2.1.4
    optixPktSdhSRJ1Mode OBJECT-TYPE
        SYNTAX INTEGER
        {
            sdh(0),
            sdhcrc(1),
            sonet(2),
            singlecharacter(3)
        }
        MAX-ACCESS read-write
        STATUS current
        DESCRIPTION
            "This object indicates the J1 byte to be received mode. 0: sdh, 1: sdhcrc, 2: sonet, 3: singlecharacter"
        ::= { optixPktSdhVC4OhEntry 4 }

    -- 1.3.6.1.4.1.2011.2.25.4.50.34.1.2.1.5
    optixPktSdhSRJ1Value OBJECT-TYPE
        SYNTAX OCTET STRING (SIZE(0..64))
        MAX-ACCESS read-write
        STATUS current
        DESCRIPTION
            "This object indicates the value of J1 byte to be received condignly."
        ::= { optixPktSdhVC4OhEntry 5 }

    -- 1.3.6.1.4.1.2011.2.25.4.50.34.1.2.1.6
    optixPktSdhRJ1Mode OBJECT-TYPE
        SYNTAX Unsigned32
        MAX-ACCESS read-only
        STATUS current
        DESCRIPTION
            "This object indicates the actual received J1 byte mode. 0: sdh, 1: sdhcrc, 2: sonet, 3: singlecharacter"
        ::= { optixPktSdhVC4OhEntry 6 }

    -- 1.3.6.1.4.1.2011.2.25.4.50.34.1.2.1.7
    optixPktSdhRJ1Value OBJECT-TYPE
        SYNTAX OCTET STRING (SIZE(0..64))
        MAX-ACCESS read-only
        STATUS current
        DESCRIPTION
            "This object indicates the value of the actual received J1 byte."
        ::= { optixPktSdhVC4OhEntry 7 }

    -- 1.3.6.1.4.1.2011.2.25.4.50.34.1.2.1.8
    optixPktSdhSTC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-write
        STATUS current
        DESCRIPTION
            "This object indicates the value ofC2 byte to be transmitted condignly. 0: uneq, 1: unsp, 2: tugs, 3: tulock, 4: asyn, 5: develop, 18: a140, 19: atm, 20: man, 21: fddi, 22: ppp, 23: resvp1, 24: laps, 25: resvp2, 26: enet, 27: gfp, 207: resv, 225: resvn1, 252: resvn2, 254: test, 255: ais"
        ::= { optixPktSdhVC4OhEntry 8 }

    -- 1.3.6.1.4.1.2011.2.25.4.50.34.1.2.1.9
    optixPktSdhSRC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-write
        STATUS current
        DESCRIPTION
            "This object indicates the value ofC2 byte to be received condignly. 0: uneq, 1: unsp, 2: tugs, 3: tulock, 4: asyn, 5: develop, 18: a140, 19: atm, 20: man, 21: fddi, 22: ppp, 23: resvp1, 24: laps, 25: resvp2, 26: enet, 27: gfp, 207: resv, 225: resvn1, 252: resvn2, 254: test, 255: ais"
        ::= { optixPktSdhVC4OhEntry 9 }

    -- 1.3.6.1.4.1.2011.2.25.4.50.34.1.2.1.10
    optixPktSdhRC2Value OBJECT-TYPE
        SYNTAX Unsigned32
        MAX-ACCESS read-only
        STATUS current
        DESCRIPTION
            "This object indicates the value of actual received C2 byte."
        ::= { optixPktSdhVC4OhEntry 10 }

    -- 1.3.6.1.4.1.2011.2.25.4.50.34.1.3
    optixPktSdhVC12OhTable OBJECT-TYPE
        SYNTAX SEQUENCE OF OptixPktSdhVC12OhEntry
        MAX-ACCESS not-accessible
        STATUS current
        DESCRIPTION
            "This table describes the SDH VC12 channel configurations."
        ::= { optixPktSdhOhGroup 3 }

    -- 1.3.6.1.4.1.2011.2.25.4.50.34.1.3.1
    optixPktSdhVC12OhEntry OBJECT-TYPE
        SYNTAX OptixPktSdhVC12OhEntry
        MAX-ACCESS not-accessible
        STATUS current
        DESCRIPTION
            "Thisentry describes the SDH VC12 channel configurations."
        INDEX{ optixLogBoardId,optixLogSubCardId,optixPktSdhPortId,optixPktSdhVC4HP,optixPktSdhVC12SerType,optixPktSdhVC12LP }
        ::= { optixPktSdhVC12OhTable 1 }

    OptixPktSdhVC12OhEntry ::=
        SEQUENCE {
            optixPktSdhVC12SerType
                Unsigned32,
            optixPktSdhVC12LP
                Unsigned32,
            optixPktSdhVC12LoopMode
                INTEGER
        }

    -- 1.3.6.1.4.1.2011.2.25.4.50.34.1.3.1.1
    optixPktSdhVC12SerType OBJECT-TYPE
        SYNTAX Unsigned32
        MAX-ACCESS not-accessible
        STATUS current
        DESCRIPTION
            "This object indicates the service type."
        ::= { optixPktSdhVC12OhEntry 1 }

    -- 1.3.6.1.4.1.2011.2.25.4.50.34.1.3.1.2
    optixPktSdhVC12LP OBJECT-TYPE
        SYNTAX Unsigned32
        MAX-ACCESS not-accessible
        STATUS current
        DESCRIPTION
            "This object indicates the loopback low-order channel ID of the VC12 channels."
        ::= { optixPktSdhVC12OhEntry 2 }

    -- 1.3.6.1.4.1.2011.2.25.4.50.34.1.3.1.3
    optixPktSdhVC12LoopMode OBJECT-TYPE
        SYNTAX INTEGER
        {
            noloop(0),
            inloop(1),
            outloop(2)
        }
        MAX-ACCESS read-write
        STATUS current
        DESCRIPTION
            "This object indicates the VC12 loopback mode of the optical port. 0: noloop, 1: inloop, 2: outloop"
        ::= { optixPktSdhVC12OhEntry 3 }

    -- 1.3.6.1.4.1.2011.2.25.4.50.34.1.4
    optixPktSdhVC12OhJVTable OBJECT-TYPE
        SYNTAX SEQUENCE OF OptixPktSdhVC12OhJVEntry
        MAX-ACCESS not-accessible
        STATUS current
        DESCRIPTION
            "This table contains basic configuration information of SDH VC12 tunnel"
        ::= { optixPktSdhOhGroup 4 }

    -- 1.3.6.1.4.1.2011.2.25.4.50.34.1.4.1
    optixPktSdhVC12OhJVEntry OBJECT-TYPE
        SYNTAX OptixPktSdhVC12OhJVEntry
        MAX-ACCESS not-accessible
        STATUS current
        DESCRIPTION
            "Thisentry describes basic configuration information of SDH VC12 tunnel"
        INDEX{ optixLogBoardId,optixLogSubCardId,optixPktSdhPortId,optixPktSdhVC4HP,optixPktSdhVC12LP }
        ::= { optixPktSdhVC12OhJVTable 1 }

    OptixPktSdhVC12OhJVEntry ::=
        SEQUENCE {
            optixPktSdhSTJ2Mode
                INTEGER,
            optixPktSdhSTJ2Value
                OCTET STRING,
            optixPktSdhSRJ2Mode
                INTEGER,
            optixPktSdhSRJ2Value
                OCTET STRING,
            optixPktSdhRJ2Mode
                Unsigned32,
            optixPktSdhRJ2Value
                OCTET STRING,
            optixPktSdhSTV5Value
                Unsigned32,
            optixPktSdhSRV5Value
                Unsigned32,
            optixPktSdhRV5Value
                Unsigned32,
            optixPktSdhRetimingMode
                INTEGER,
            optixPktSdhVc12Frm
                INTEGER,
            optixPktSdhVC12UserSlotNum
                INTEGER
        }

    -- 1.3.6.1.4.1.2011.2.25.4.50.34.1.4.1.1
    optixPktSdhSTJ2Mode OBJECT-TYPE
        SYNTAX INTEGER
        {
            sdh(0),
            singlecharacter(3)
        }
        MAX-ACCESS read-write
        STATUS current
        DESCRIPTION
            "This object indicates the mode of the J2 byte to be transmitted. 0: sdh, 3: singlecharacter"
        ::= { optixPktSdhVC12OhJVEntry 1 }

    -- 1.3.6.1.4.1.2011.2.25.4.50.34.1.4.1.2
    optixPktSdhSTJ2Value OBJECT-TYPE
        SYNTAX OCTET STRING (SIZE(0..64))
        MAX-ACCESS read-write
        STATUS current
        DESCRIPTION
            "This object indicates the value of J2 byte to be transmitted condignly. 0: sdh, 3: singlecharacter"
        ::= { optixPktSdhVC12OhJVEntry 2 }

    -- 1.3.6.1.4.1.2011.2.25.4.50.34.1.4.1.3
    optixPktSdhSRJ2Mode OBJECT-TYPE
        SYNTAX INTEGER
        {
            sdh(0),
            singlecharacter(3)
        }
        MAX-ACCESS read-write
        STATUS current
        DESCRIPTION
            "This object indicates the J2 byte to be received mode condignly."
        ::= { optixPktSdhVC12OhJVEntry 3 }

    -- 1.3.6.1.4.1.2011.2.25.4.50.34.1.4.1.4
    optixPktSdhSRJ2Value OBJECT-TYPE
        SYNTAX OCTET STRING (SIZE(0..64))
        MAX-ACCESS read-write
        STATUS current
        DESCRIPTION
            "This object indicates the value of J2 byte to be received condignly."
        ::= { optixPktSdhVC12OhJVEntry 4 }

    -- 1.3.6.1.4.1.2011.2.25.4.50.34.1.4.1.5
    optixPktSdhRJ2Mode OBJECT-TYPE
        SYNTAX Unsigned32
        MAX-ACCESS read-only
        STATUS current
        DESCRIPTION
            "This object indicates the actual received J2 byte mode."
        ::= { optixPktSdhVC12OhJVEntry 5 }

    -- 1.3.6.1.4.1.2011.2.25.4.50.34.1.4.1.6
    optixPktSdhRJ2Value OBJECT-TYPE
        SYNTAX OCTET STRING (SIZE(0..64))
        MAX-ACCESS read-only
        STATUS current
        DESCRIPTION
            "This object indicates the value of the actual received J2 byte."
        ::= { optixPktSdhVC12OhJVEntry 6 }

    -- 1.3.6.1.4.1.2011.2.25.4.50.34.1.4.1.7
    optixPktSdhSTV5Value OBJECT-TYPE
        SYNTAX Unsigned32
        MAX-ACCESS read-write
        STATUS current
        DESCRIPTION
            "This object indicates the mode of the V5 byte to be sent."
        ::= { optixPktSdhVC12OhJVEntry 7 }

    -- 1.3.6.1.4.1.2011.2.25.4.50.34.1.4.1.8
    optixPktSdhSRV5Value OBJECT-TYPE
        SYNTAX Unsigned32
        MAX-ACCESS read-write
        STATUS current
        DESCRIPTION
            "This object indicates the value of the V5 byte to be received."
        ::= { optixPktSdhVC12OhJVEntry 8 }

    -- 1.3.6.1.4.1.2011.2.25.4.50.34.1.4.1.9
    optixPktSdhRV5Value OBJECT-TYPE
        SYNTAX Unsigned32
        MAX-ACCESS read-only
        STATUS current
        DESCRIPTION
            "This object indicates the value of the actual received V5 byte."
        ::= { optixPktSdhVC12OhJVEntry 9 }

    -- 1.3.6.1.4.1.2011.2.25.4.50.34.1.4.1.10
    optixPktSdhRetimingMode OBJECT-TYPE
        SYNTAX INTEGER
        {
            master(0),
            slave(1)
        }
        MAX-ACCESS read-write
        STATUS current
        DESCRIPTION
            "This object indicates the retiming mode."
        ::= { optixPktSdhVC12OhJVEntry 10 }

    -- 1.3.6.1.4.1.2011.2.25.4.50.34.1.4.1.11
    optixPktSdhVc12Frm OBJECT-TYPE
        SYNTAX INTEGER
        {
            unframe(0),
            doubleFrame(1),
            crc4Multiframe(2)
        }
        MAX-ACCESS read-write
        STATUS current
        DESCRIPTION
            "This object indicates the E1 frame format of VC-12 channels."
        ::= { optixPktSdhVC12OhJVEntry 11 }

    -- 1.3.6.1.4.1.2011.2.25.4.50.34.1.4.1.12
    optixPktSdhVC12UserSlotNum OBJECT-TYPE
        SYNTAX INTEGER
        {
            snmp30(30),
            snmp31(31)
        }
        MAX-ACCESS read-write
        STATUS current
        DESCRIPTION
            "This object indicates the number of free timeslots for VC-12 channel users."
        ::= { optixPktSdhVC12OhJVEntry 12 }

    -- 1.3.6.1.4.1.2011.2.25.4.50.34.1.5
    optixPktSdhSwitchCESTable OBJECT-TYPE
        SYNTAX SEQUENCE OF OptixPktSdhSwitchCESEntry
        MAX-ACCESS not-accessible
        STATUS current
        DESCRIPTION
            "This table allows TDM boards to support SDH/CES mode switching."
        ::= { optixPktSdhOhGroup 5 }

    -- 1.3.6.1.4.1.2011.2.25.4.50.34.1.5.1
    optixPktSdhSwitchCESEntry OBJECT-TYPE
        SYNTAX OptixPktSdhSwitchCESEntry
        MAX-ACCESS not-accessible
        STATUS current
        DESCRIPTION
            "This node describes an entity of the function that allows TDM boards to support SDH/CES mode switching."
        INDEX{ optixPktSdhPortSrvMod }
        ::= { optixPktSdhSwitchCESTable 1 }

    OptixPktSdhSwitchCESEntry ::=
        SEQUENCE {
            optixPktSdhPortSrvMod
                INTEGER
        }

    -- 1.3.6.1.4.1.2011.2.25.4.50.34.1.5.1.1
    optixPktSdhPortSrvMod OBJECT-TYPE
        SYNTAX INTEGER
        {
            sdh(0),
            ces(1)
        }
        MAX-ACCESS not-accessible
        STATUS current
        DESCRIPTION
            "The port mode for SDH STM-1 services. 0: SDH, 1: CES"
        ::= { optixPktSdhSwitchCESEntry 1 }

END
