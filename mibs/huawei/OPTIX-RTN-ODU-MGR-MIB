-- OPTIX-RTN-ODU-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-ODU-MGR-MIB DEFINITIONS ::= BEGIN
    IMPORTS
        OBJECT-GROUP,MODULE-COMPLIANCE
            FROM SNMPv2-CONF
        Unsigned32,Integer32,OBJECT-TYPE,MODULE-IDENTITY,NOTIFICATION-TYPE
            FROM SNMPv2-SMI
        TEXTUAL-CONVENTION
            FROM SNMPv2-TC
        optixProvisionRtn
            FROM OPTIX-OID-MIB
        optixRtnIFPortlist
	    FROM OPTIX-RTN-GENNERAL-MIB
        ;

    optixRtnOduMgr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query RF unit parameters for a radio link, including the RF unit frequency, power, and working status."
        REVISION "201204160935Z"
        DESCRIPTION
            "The initial revision of this MIB module1."
        ::={ optixProvisionRtn 4 }

    OPTIXRtnCombineMode ::= TEXTUAL-CONVENTION
        STATUS current
        DESCRIPTION
            "Indicates the combine mode of a RFU-SD board."
        SYNTAX INTEGER
        {
            main(0),
            slave(1),
            combine(2)
        }

    OPTIXRtnFiberEqualState ::= TEXTUAL-CONVENTION
        STATUS current
        DESCRIPTION
            "Indicates RFU-SD fiber equal state."
        SYNTAX INTEGER
        {
            start(1)
        }

    OPTIXRtnOduWorkStateType ::= TEXTUAL-CONVENTION
        STATUS current
        DESCRIPTION
            "Indicates the working status of RF unit. Values: 0: muted 1: unmuted"
        SYNTAX INTEGER
        {
            mute(0),
            unmute(1)
        }

    OPTIXRtnOduPortBandWidthType ::= TEXTUAL-CONVENTION
        STATUS current
        DESCRIPTION
            "Describes the channel spacing supported by an IF board. Values: 10: 250M; 11: 500M; 12:750M; 18:1000M; 26:1500M; 27:2000M"
        SYNTAX INTEGER
        {
            bw7M(2),
            bw14M(3),
            bw28M(4),
            bw40M(5),
            bw56M(6),
            bwFCC30M(7),
            bwFCC40M(8),
            bwFCC50M(9),
            bw112M(23),
	    bw80M(34)
        }

    OPTIXRtnOduBandWidthType ::= TEXTUAL-CONVENTION
        STATUS current
        DESCRIPTION
            "Describes the channel spacing supported by an IF board. Values: 10: 250M; 11: 500M; 12:750M; 18:1000M; 26:1500M; 27:2000M"
        SYNTAX INTEGER
        {  
        	bw3P5M(1),
        	bw7M(2),
        	bw14M(3),
        	bw28M(4),
        	bw40M(5),
        	bw56M(6),
        	bwFCC30M(7),
        	bwFCC40M(8),
        	bwFCC50M(9),
                bw250M(10),
                bw500M(11),
                bw750M(12),
                bw62P5M(16),
                bw125M(17),
		bw1000M(18),
		bw200M(22),
        	bwFCC10M(24),
        	bwFCC20M(25),
		bw1500M(26),
		bw2000M(27),
        	bwFCC60M(28)
        }
    -- 1.3.6.1.4.1.2011.2.25.4.40.4.10
    optixODU OBJECT IDENTIFIER ::= { optixRtnOduMgr 10 }

    -- 1.3.6.1.4.1.2011.2.25.4.40.4.10.10
    optixRtnOduIndexTable OBJECT-TYPE
        SYNTAX SEQUENCE OF OptixRtnOduIndexEntry
        MAX-ACCESS not-accessible
        STATUS current
        DESCRIPTION
            "Serves as the public index table for attribute tables related to an RF unit."
        ::= { optixODU 10 }

    -- 1.3.6.1.4.1.2011.2.25.4.40.4.10.10.1
    optixRtnOduIndexEntry OBJECT-TYPE
        SYNTAX OptixRtnOduIndexEntry
        MAX-ACCESS not-accessible
        STATUS current
        DESCRIPTION
            "Indicates the index entry for an RF unit."
        INDEX{ optixRtnOduIndex1,optixRtnOduIndex2 }
        ::= { optixRtnOduIndexTable 1 }

    OptixRtnOduIndexEntry ::=
        SEQUENCE {
            optixRtnOduIndex1
                Unsigned32,
            optixRtnOduIndex2
                Unsigned32,
            optixRtnOduIndex3
                Unsigned32,
            optixRtnOduIndex4
                Unsigned32
        }

    -- 1.3.6.1.4.1.2011.2.25.4.40.4.10.10.1.1
    optixRtnOduIndex1 OBJECT-TYPE
        SYNTAX Unsigned32
        MAX-ACCESS not-accessible
        STATUS current
        DESCRIPTION
            "Indicates the RF unit board ID."
        ::= { optixRtnOduIndexEntry 1 }

    -- 1.3.6.1.4.1.2011.2.25.4.40.4.10.10.1.2
    optixRtnOduIndex2 OBJECT-TYPE
        SYNTAX Unsigned32
        MAX-ACCESS read-only
        STATUS current
        DESCRIPTION
            "Indicates the subboard ID."
        ::= { optixRtnOduIndexEntry 2 }

    -- 1.3.6.1.4.1.2011.2.25.4.40.4.10.10.1.3
    optixRtnOduIndex3 OBJECT-TYPE
        SYNTAX Unsigned32
        MAX-ACCESS read-only
        STATUS current
        DESCRIPTION
            "Indicates the Port ID."
        ::= { optixRtnOduIndexEntry 3 }
		
    -- 1.3.6.1.4.1.2011.2.25.4.40.4.10.10.1.4
    optixRtnOduIndex4 OBJECT-TYPE
        SYNTAX Unsigned32
        MAX-ACCESS not-accessible
        STATUS current
        DESCRIPTION
            "Indicates the freqency point."
        ::= { optixRtnOduIndexEntry 4 }
		
    -- 1.3.6.1.4.1.2011.2.25.4.40.4.10.17
    optixRtnOduGeneralAttrExtTable OBJECT-TYPE
        SYNTAX SEQUENCE OF OptixRtnOduGeneralAttrExtEntry
        MAX-ACCESS not-accessible
        STATUS current
        DESCRIPTION
            "Indicates the table of general attributes of an ODU."
        ::= { optixODU 17 }

    -- 1.3.6.1.4.1.2011.2.25.4.40.4.10.17.1
    optixRtnOduGeneralAttrExtEntry OBJECT-TYPE
        SYNTAX OptixRtnOduGeneralAttrExtEntry
        MAX-ACCESS not-accessible
        STATUS current
        DESCRIPTION
            "Indicates an entry of general attributes of an ODU."
        INDEX{ optixRtnOduIndex1,optixRtnOduIndex2 }
        ::= { optixRtnOduGeneralAttrExtTable 1 }

    OptixRtnOduGeneralAttrExtEntry ::=
        SEQUENCE {
            optixRtnOduFademarginAlmThExt
                Unsigned32,
            optixRtnOduCurrentFilterExt
                Unsigned32,
            optixRtnOduAllFilterListInfoExt
                OCTET STRING,
            optixRtnOduLoopModeExt
                INTEGER
        }

    -- 1.3.6.1.4.1.2011.2.25.4.40.4.10.17.1.1
    optixRtnOduFademarginAlmThExt OBJECT-TYPE
        SYNTAX Unsigned32
        MAX-ACCESS read-write
        STATUS current
        DESCRIPTION
            "Indicates the alarming threshold in the unit of 0.1 dB."
        ::= { optixRtnOduGeneralAttrExtEntry 1 }

    -- 1.3.6.1.4.1.2011.2.25.4.40.4.10.17.1.2
    optixRtnOduCurrentFilterExt OBJECT-TYPE
        SYNTAX Unsigned32
        MAX-ACCESS read-write
        STATUS current
        DESCRIPTION
            "Indicates the filter, expressed in KHz."
        ::= { optixRtnOduGeneralAttrExtEntry 2 }

    -- 1.3.6.1.4.1.2011.2.25.4.40.4.10.17.1.3
    optixRtnOduAllFilterListInfoExt OBJECT-TYPE
        SYNTAX OCTET STRING
        MAX-ACCESS read-only
        STATUS current
        DESCRIPTION
            "Indicates the supported filter list. Every 4 bytes represent a filter, expressed in KHz."
        ::= { optixRtnOduGeneralAttrExtEntry 3 }

    -- 1.3.6.1.4.1.2011.2.25.4.40.4.10.17.1.4
    optixRtnOduLoopModeExt OBJECT-TYPE
        SYNTAX INTEGER
        {
            noloop(0),
            inloop(1),
            masterinloop(3),
            slaveinloop(4)
        }
        MAX-ACCESS read-write
        STATUS current
        DESCRIPTION
            "Indicates the loop mode(360 or 380 or 380H or 380hn or 380a or 380ax not support this node):
	    0:no loop
	    1:in loop
	    3:masterinloop
	    4:slaveinloop"
        ::= { optixRtnOduGeneralAttrExtEntry 4 }		

    -- 1.3.6.1.4.1.2011.2.25.4.40.4.10.18
    optixRtnOduPortGeneralAttrTable OBJECT-TYPE
        SYNTAX SEQUENCE OF OptixRtnOduPortGeneralAttrEntry
        MAX-ACCESS not-accessible
        STATUS current
        DESCRIPTION
            "Indicates the table of general attributes of an ODU(this node used only to 320 or 3202f)."
        ::= { optixODU 18 }

    -- 1.3.6.1.4.1.2011.2.25.4.40.4.10.18.1
    optixRtnOduPortGeneralAttrEntry OBJECT-TYPE
        SYNTAX OptixRtnOduPortGeneralAttrEntry
        MAX-ACCESS not-accessible
        STATUS current
        DESCRIPTION
            "Indicates an entry of general attributes of an ODU(this node used only to 320 or 3202f)."
        INDEX{ optixRtnOduIndex1,optixRtnOduIndex2,optixRtnOduIndex3 }
        ::= { optixRtnOduPortGeneralAttrTable 1 }

    OptixRtnOduPortGeneralAttrEntry ::=
        SEQUENCE {
            optixRtnOduPortFademarginAlmTh
                Unsigned32,
            optixRtnOduPortCurrentFilter
                Unsigned32,
            optixRtnOduPortAllFilterListInfo
                OCTET STRING,
            optixRtnOduPortLoopMode
                INTEGER
        }

    -- 1.3.6.1.4.1.2011.2.25.4.40.4.10.18.1.1
    optixRtnOduPortFademarginAlmTh OBJECT-TYPE
        SYNTAX Unsigned32
        MAX-ACCESS read-write
        STATUS current
        DESCRIPTION
            "Indicates the alarming threshold in the unit of 0.1 dB(this node used only to 320 or 3202f)."
        ::= { optixRtnOduPortGeneralAttrEntry 1 }

    -- 1.3.6.1.4.1.2011.2.25.4.40.4.10.18.1.2
    optixRtnOduPortCurrentFilter OBJECT-TYPE
        SYNTAX Unsigned32
        MAX-ACCESS read-write
        STATUS current
        DESCRIPTION
            "Indicates the filter, expressed in KHz(this node used only to 320 or 3202f)."
        ::= { optixRtnOduPortGeneralAttrEntry 2 }

    -- 1.3.6.1.4.1.2011.2.25.4.40.4.10.18.1.3
    optixRtnOduPortAllFilterListInfo OBJECT-TYPE
        SYNTAX OCTET STRING
        MAX-ACCESS read-only
        STATUS current
        DESCRIPTION
            "Indicates the supported filter list. Every 4 bytes represent a filter, expressed in KHz(this node used only to 320 or 3202f)."
        ::= { optixRtnOduPortGeneralAttrEntry 3 }

    -- 1.3.6.1.4.1.2011.2.25.4.40.4.10.18.1.4
    optixRtnOduPortLoopMode OBJECT-TYPE
        SYNTAX INTEGER
        {
            noloop(0),
            inloop(1)
        }
        MAX-ACCESS read-write
        STATUS current
        DESCRIPTION
            "Indicates the loop mode(this node used only to 320 or 3202f):
	    0:no loop
	    1:in loop
	    2:out loop"
        ::= { optixRtnOduPortGeneralAttrEntry 4 }
	
    -- 1.3.6.1.4.1.2011.2.25.4.40.4.10.13
    optixRtnOduFactoryInfoTable  OBJECT-TYPE
	SYNTAX SEQUENCE OF OptixRtnOduFactoryInfoEntry
	MAX-ACCESS not-accessible
	STATUS current
	DESCRIPTION
	    "Query ODU manufacturers information."
	::= { optixODU 13 }
    -- 1.3.6.1.4.1.2011.2.25.4.40.4.10.13.1	
    optixRtnOduFactoryInfoEntry	OBJECT-TYPE
	SYNTAX OptixRtnOduFactoryInfoEntry
	MAX-ACCESS not-accessible
	STATUS current
	DESCRIPTION
		"Query ODU manufacturers information."
	INDEX{ optixRtnOduIndex1,optixRtnOduIndex2 }
	::= { optixRtnOduFactoryInfoTable 1 }

    OptixRtnOduFactoryInfoEntry ::= 
	SEQUENCE {
		optixRtnOduFactoryInfo
	OCTET STRING
	}

    -- 1.3.6.1.4.1.2011.2.25.4.40.4.10.13.1.1	
    optixRtnOduFactoryInfo OBJECT-TYPE
	SYNTAX OCTET STRING
	MAX-ACCESS read-only
	STATUS current
	DESCRIPTION
		"Indicates the information of ODU manufacturers."
	::= { optixRtnOduFactoryInfoEntry 1 }

     -- 1.3.6.1.4.1.2011.2.25.4.40.4.10.16
     optixRtnOduPowerSwitchTable OBJECT-TYPE
        SYNTAX SEQUENCE OF OptixRtnOduPowerSwitchEntry
        MAX-ACCESS not-accessible
        STATUS current
        DESCRIPTION
            "Describes the RF unit transmit and receive frequencies."
        ::= { optixODU 16 }

    -- 1.3.6.1.4.1.2011.2.25.4.40.4.10.16.1
     optixRtnOduPowerSwitchEntry  OBJECT-TYPE
     	SYNTAX OptixRtnOduPowerSwitchEntry
        MAX-ACCESS not-accessible
        STATUS current
        DESCRIPTION
            "Indicates the parameter entry for power switch."
        INDEX{ optixRtnOduIndex1,optixRtnOduIndex2,optixRtnOduIndex3 }
        ::= { optixRtnOduPowerSwitchTable 1 }

    OptixRtnOduPowerSwitchEntry ::=
    	SEQUENCE{
    	    optixOduPowerSwitch
    	    	INTEGER	
    	}
  
    -- 1.3.6.1.4.1.2011.2.25.4.40.4.10.16.1.1
  	optixOduPowerSwitch OBJECT-TYPE
  	    SYNTAX INTEGER {
  	          disable(0),
  	          enable(1)
   	    }
        MAX-ACCESS read-write
        STATUS current
        DESCRIPTION
            "Indicates the transmit power switch"
        ::= { optixRtnOduPowerSwitchEntry 1 }

    -- 1.3.6.1.4.1.2011.2.25.4.40.4.10.27
    optixRtnOduFrequencyExtTable OBJECT-TYPE
        SYNTAX SEQUENCE OF OptixRtnOduFrequencyExtEntry
        MAX-ACCESS not-accessible
        STATUS current
        DESCRIPTION
            "Describes the RF unit transmit and receive frequencies."
        ::= { optixODU 27 }

    -- 1.3.6.1.4.1.2011.2.25.4.40.4.10.27.1
    optixRtnOduFrequencyExtEntry OBJECT-TYPE
        SYNTAX OptixRtnOduFrequencyExtEntry
        MAX-ACCESS not-accessible
        STATUS current
        DESCRIPTION
            "Indicates the parameter entry for the RF unit transmit and receive frequencies."
        INDEX{ optixRtnOduIndex1,optixRtnOduIndex2 }
        ::= { optixRtnOduFrequencyExtTable 1 }

    OptixRtnOduFrequencyExtEntry ::=
        SEQUENCE {
            optixRtnOduCfgTxFreqExt
                Unsigned32,
            optixRtnOduCfgTRSpacingExt
                Unsigned32,
            optixRtnOduActualTxFreqExt
                Unsigned32,
            optixRtnOduActualRxFreqExt
                Unsigned32,
            optixRtnOduMinTxFreqExt
                Unsigned32,
            optixRtnOduMaxTxFreqExt
                Unsigned32,
            optixRtnOduRealRTRSpacingExt
                Unsigned32,
            optixRtnOduTRSpacingInfoExt
                OCTET STRING
        }

    -- 1.3.6.1.4.1.2011.2.25.4.40.4.10.27.1.1
     optixRtnOduCfgTxFreqExt OBJECT-TYPE
        SYNTAX Unsigned32
        MAX-ACCESS read-write
        STATUS current
        DESCRIPTION
            "Indicates the transmit frequency of an RF unit. When frequencies of the transmitter/receiver at both ends match, signals can be transmitted and received successfully. Unit: kHz"
        ::= { optixRtnOduFrequencyExtEntry 1 }

    -- 1.3.6.1.4.1.2011.2.25.4.40.4.10.27.1.2
    optixRtnOduCfgTRSpacingExt OBJECT-TYPE
        SYNTAX Unsigned32
        MAX-ACCESS read-write
        STATUS current
        DESCRIPTION
            "Indicates the TR spacing of an RF unit board to avoid interference. Unit: kHz"
        ::= { optixRtnOduFrequencyExtEntry 2 }

    -- 1.3.6.1.4.1.2011.2.25.4.40.4.10.27.1.3
    optixRtnOduActualTxFreqExt OBJECT-TYPE
        SYNTAX Unsigned32
        MAX-ACCESS read-only
        STATUS current
        DESCRIPTION
            "Indicates the actual transmit frequency of an RF unit. Unit: kHz"
        ::= { optixRtnOduFrequencyExtEntry 3 }

    -- 1.3.6.1.4.1.2011.2.25.4.40.4.10.27.1.4
    optixRtnOduActualRxFreqExt OBJECT-TYPE
        SYNTAX Unsigned32
        MAX-ACCESS read-only
        STATUS current
        DESCRIPTION
            "Indicates the actual receive frequency of an RF unit. Unit: kHz"
        ::= { optixRtnOduFrequencyExtEntry 4 }

    -- 1.3.6.1.4.1.2011.2.25.4.40.4.10.27.1.5
    optixRtnOduMinTxFreqExt OBJECT-TYPE
        SYNTAX Unsigned32
        MAX-ACCESS read-only
        STATUS current
        DESCRIPTION
            "Indicates the minimum range of an RF unit frequency point. Unit: kHz"
        ::= { optixRtnOduFrequencyExtEntry 5 }

    -- 1.3.6.1.4.1.2011.2.25.4.40.4.10.27.1.6
    optixRtnOduMaxTxFreqExt OBJECT-TYPE
        SYNTAX Unsigned32
        MAX-ACCESS read-only
        STATUS current
        DESCRIPTION
            "Indicates the maximum range of an RF unit frequency point. Unit: kHz"
        ::= { optixRtnOduFrequencyExtEntry 6 }

    -- 1.3.6.1.4.1.2011.2.25.4.40.4.10.27.1.7
    optixRtnOduRealRTRSpacingExt OBJECT-TYPE
        SYNTAX Unsigned32
        MAX-ACCESS read-only
        STATUS current
        DESCRIPTION
            "Indicates the real TR spacing of an RF unit. Unit: kHz"
        ::= { optixRtnOduFrequencyExtEntry 7 }

    -- 1.3.6.1.4.1.2011.2.25.4.40.4.10.27.1.8
    optixRtnOduTRSpacingInfoExt OBJECT-TYPE
        SYNTAX OCTET STRING
        MAX-ACCESS read-only
        STATUS current
        DESCRIPTION
            "Indicates the TR spacing of an RF unit(Use only 360/380/380H/380hn/380a/380ax). Unit: kHz"
        ::= { optixRtnOduFrequencyExtEntry 8 }

    -- 1.3.6.1.4.1.2011.2.25.4.40.4.10.28
    optixRtnOduPortFrequencyTable OBJECT-TYPE
        SYNTAX SEQUENCE OF OptixRtnOduPortFrequencyEntry
        MAX-ACCESS not-accessible
        STATUS current
        DESCRIPTION
            "Describes the RF unit transmit and receive frequencies(this node used only to 320 or 3202f)."
        ::= { optixODU 28 }

    -- 1.3.6.1.4.1.2011.2.25.4.40.4.10.28.1
    optixRtnOduPortFrequencyEntry OBJECT-TYPE
        SYNTAX OptixRtnOduPortFrequencyEntry
        MAX-ACCESS not-accessible
        STATUS current
        DESCRIPTION
            "Indicates the parameter entry for the RF unit transmit and receive frequencies(this node used only to 320 or 3202f)."
        INDEX{ optixRtnOduIndex1,optixRtnOduIndex2,optixRtnOduIndex3 }
        ::= { optixRtnOduPortFrequencyTable 1 }

    OptixRtnOduPortFrequencyEntry ::=
        SEQUENCE {
            optixRtnOduPortCfgTxFreq
                Unsigned32,
            optixRtnOduPortCfgTRSpacing
                Unsigned32,
            optixRtnOduPortActualTxFreq
                Unsigned32,
            optixRtnOduPortActualRxFreq
                Unsigned32,
            optixRtnOduPortMinTxFreq
                Unsigned32,
            optixRtnOduPortMaxTxFreq
                Unsigned32,
            optixRtnOduPortRealRTRSpacing
                Unsigned32
        }

    -- 1.3.6.1.4.1.2011.2.25.4.40.4.10.28.1.1
    optixRtnOduPortCfgTxFreq OBJECT-TYPE
        SYNTAX Unsigned32
        MAX-ACCESS read-write
        STATUS current
        DESCRIPTION
            "Indicates the transmit frequency of an RF unit. When frequencies of the transmitter/receiver at both ends match, signals can be transmitted and received successfully(this node used only to 320 or 3202f). Unit: kHz"
        ::= { optixRtnOduPortFrequencyEntry 1 }

    -- 1.3.6.1.4.1.2011.2.25.4.40.4.10.28.1.2
    optixRtnOduPortCfgTRSpacing OBJECT-TYPE
        SYNTAX Unsigned32
        MAX-ACCESS read-write
        STATUS current
        DESCRIPTION
            "Indicates the TR spacing of an RF unit board to avoid interference(this node used only to 320 or 3202f). Unit: kHz"
        ::= { optixRtnOduPortFrequencyEntry 2 }

    -- 1.3.6.1.4.1.2011.2.25.4.40.4.10.28.1.3
    optixRtnOduPortActualTxFreq OBJECT-TYPE
        SYNTAX Unsigned32
        MAX-ACCESS read-only
        STATUS current
        DESCRIPTION
            "Indicates the actual transmit frequency of an RF unit(this node used only to 320 or 3202f). Unit: kHz"
        ::= { optixRtnOduPortFrequencyEntry 3 }

    -- 1.3.6.1.4.1.2011.2.25.4.40.4.10.28.1.4
    optixRtnOduPortActualRxFreq OBJECT-TYPE
        SYNTAX Unsigned32
        MAX-ACCESS read-only
        STATUS current
        DESCRIPTION
            "Indicates the actual receive frequency of an RF unit(this node used only to 320 or 3202f). Unit: kHz"
        ::= { optixRtnOduPortFrequencyEntry 4 }

    -- 1.3.6.1.4.1.2011.2.25.4.40.4.10.28.1.5
    optixRtnOduPortMinTxFreq OBJECT-TYPE
        SYNTAX Unsigned32
        MAX-ACCESS read-only
        STATUS current
        DESCRIPTION
            "Indicates the minimum range of an RF unit frequency point(this node used only to 320 or 3202f). Unit: kHz"
        ::= { optixRtnOduPortFrequencyEntry 5 }

    -- 1.3.6.1.4.1.2011.2.25.4.40.4.10.28.1.6
    optixRtnOduPortMaxTxFreq OBJECT-TYPE
        SYNTAX Unsigned32
        MAX-ACCESS read-only
        STATUS current
        DESCRIPTION
            "Indicates the maximum range of an RF unit frequency point(this node used only to 320 or 3202f). Unit: kHz"
        ::= { optixRtnOduPortFrequencyEntry 6 }

    -- 1.3.6.1.4.1.2011.2.25.4.40.4.10.28.1.7
    optixRtnOduPortRealRTRSpacing OBJECT-TYPE
        SYNTAX Unsigned32
        MAX-ACCESS read-only
        STATUS current
        DESCRIPTION
            "Indicates the real TR spacing of an RF unit(this node used only to 320 or 3202f). Unit: kHz"
        ::= { optixRtnOduPortFrequencyEntry 7 }

    --1.3.6.1.4.1.2011.2.25.4.40.4.10.23
    optixRtnOduAmTxpowerTable OBJECT-TYPE
    	 SYNTAX SEQUENCE OF OptixRtnOduAmTxpowerEntry
        MAX-ACCESS not-accessible
        STATUS current
        DESCRIPTION
            "Describes parameters of the txpower range."
        ::= { optixODU 23 }

    -- 1.3.6.1.4.1.2011.2.25.4.40.4.10.23.1
    optixRtnOduAmTxpowerEntry OBJECT-TYPE
    	SYNTAX OptixRtnOduAmTxpowerEntry
        MAX-ACCESS not-accessible
        STATUS current
        DESCRIPTION
            "Indicates the parameter entry for the txpower range."
        INDEX{ optixRtnOduIndex1,optixRtnOduIndex2,optixRtnOduIndex3 }
        ::= { optixRtnOduAmTxpowerTable 1 }
	
    OptixRtnOduAmTxpowerEntry ::=
    	SEQUENCE {
    	    optixRtnOduAcm
	            OCTET STRING
	    }
    
    -- 1.3.6.1.4.1.2011.2.25.4.40.4.10.23.1.1
    optixRtnOduAcm  OBJECT-TYPE
        SYNTAX  OCTET STRING 
	MAX-ACCESS read-only
        STATUS current
        DESCRIPTION
	    "this leaf sis AM modle."
	::={optixRtnOduAmTxpowerEntry 1}

    -- 1.3.6.1.4.1.2011.2.25.4.40.4.10.24
    optixRtnRegOduRslTable OBJECT-TYPE  
    	SYNTAX SEQUENCE OF OptixRtnRegOduRslEntry
        MAX-ACCESS   not-accessible
        STATUS current
        DESCRIPTION
            "DEscribes parameters of Min rsl."
        ::= { optixODU 24 }

    -- 1.3.6.1.4.1.2011.2.25.4.40.4.10.24.1
    optixRtnRegOduRslEntry  OBJECT-TYPE 
        SYNTAX OptixRtnRegOduRslEntry
        MAX-ACCESS not-accessible
        STATUS current
        DESCRIPTION
            "Indicates the parameter entry for the RF unit transmit and receive powers."
        INDEX{ optixRtnOduIndex1,optixRtnOduIndex2,optixRtnOduIndex3, optixRtnOduIndexRsl4 }
        ::= { optixRtnRegOduRslTable 1 }

	OptixRtnRegOduRslEntry ::=
	    SEQUENCE{
		optixRtnOduIndexRsl4
		    Unsigned32,
		optixRtnOduRsl
		    Integer32
		}
	
    -- 1.3.6.1.4.1.2011.2.25.4.40.4.10.24.1.4
    optixRtnOduIndexRsl4 OBJECT-TYPE
        SYNTAX   Unsigned32
        MAX-ACCESS not-accessible
        STATUS current
        DESCRIPTION
            "index  board id."
        ::= { optixRtnRegOduRslEntry 4 }
		  
    -- 1.3.6.1.4.1.2011.2.25.4.40.4.10.24.1.5
    optixRtnOduRsl OBJECT-TYPE
        SYNTAX   Integer32
        MAX-ACCESS read-only
        STATUS current
        DESCRIPTION
            "Describes parameters of the RF unit transmit and receive power."
        ::= { optixRtnRegOduRslEntry 5 }

    -- 1.3.6.1.4.1.2011.2.25.4.40.4.10.31
    optixRtnOduPowerExtTable OBJECT-TYPE
        SYNTAX SEQUENCE OF OptixRtnOduPowerExtEntry
        MAX-ACCESS not-accessible
        STATUS current
        DESCRIPTION
            "Describes parameters of the RF unit transmit and receive power."
        ::= { optixODU 31 }

    -- 1.3.6.1.4.1.2011.2.25.4.40.4.10.31.1
    optixRtnOduPowerExtEntry OBJECT-TYPE
        SYNTAX OptixRtnOduPowerExtEntry
        MAX-ACCESS not-accessible
        STATUS current
        DESCRIPTION
            "Indicates the parameter entry for the RF unit transmit and receive powers."
        INDEX{ optixRtnOduIndex1,optixRtnOduIndex2 }
        ::= { optixRtnOduPowerExtTable 1 }

    OptixRtnOduPowerExtEntry ::=
        SEQUENCE {
            optixRtnOduCfgTxPowerExt
                Integer32,
            optixRtnOduCfgToBeRxPowerExt
                Integer32,
            optixRtnOduTxPowerHighThExt
                Integer32,
            optixRtnOduTxPowerLowTHExt
                Integer32,
            optixRtnOduRxPowerHighThExt
                Integer32,
            optixRtnOduRxPowerLowTHExt
                Integer32,
            optixRtnOduCfgMaxTxpowerExt
                Integer32,
            optixRtnOduActualTxPowerExt
                Integer32,
            optixRtnOduActualRxPowerExt
                Integer32,
            optixRtnOduMaxTxpowerExt
                Integer32,
            optixRtnOduMinTxpowerExt
                Integer32
        }

    -- 1.3.6.1.4.1.2011.2.25.4.40.4.10.31.1.1
    optixRtnOduCfgTxPowerExt OBJECT-TYPE
        SYNTAX Integer32
        MAX-ACCESS read-write
        STATUS current
        DESCRIPTION
            "Indicates the transmit power of an RF port. Signed type Value range: -100 to +350 Unit: 0.1 dBm"
        DEFVAL{ 100 }
        ::= { optixRtnOduPowerExtEntry 1 }

    -- 1.3.6.1.4.1.2011.2.25.4.40.4.10.31.1.2
    optixRtnOduCfgToBeRxPowerExt OBJECT-TYPE
        SYNTAX Integer32
        MAX-ACCESS read-write
        STATUS current
        DESCRIPTION
            "Indicates the power expected to receive by an RF port. Unit: 0.1 dBm"
        ::= { optixRtnOduPowerExtEntry 2 }

    -- 1.3.6.1.4.1.2011.2.25.4.40.4.10.31.1.3
    optixRtnOduTxPowerHighThExt OBJECT-TYPE
        SYNTAX Integer32
        MAX-ACCESS read-write
        STATUS current
        DESCRIPTION
            "Indicates the upper threshold of the transmit power. Signed type The value range: -100 to +350 Unit: 0.1 dBm"
        DEFVAL{ 350 }
        ::= { optixRtnOduPowerExtEntry 3 }

    -- 1.3.6.1.4.1.2011.2.25.4.40.4.10.31.1.4
    optixRtnOduTxPowerLowTHExt OBJECT-TYPE
        SYNTAX Integer32
        MAX-ACCESS read-write
        STATUS current
        DESCRIPTION
            "Indicates the lower threshold of the transmit power. Signed type The value range: -100 to +350 Unit: 0.1 dBm"
        DEFVAL{ 350 }
        ::= { optixRtnOduPowerExtEntry 4 }

    -- 1.3.6.1.4.1.2011.2.25.4.40.4.10.31.1.5
    optixRtnOduRxPowerHighThExt OBJECT-TYPE
        SYNTAX Integer32
        MAX-ACCESS read-write
        STATUS current
        DESCRIPTION
            "Indicates the upper threshold of the receive power. Signed type Unit: 0.1 dBm"
        ::= { optixRtnOduPowerExtEntry 5 }

    -- 1.3.6.1.4.1.2011.2.25.4.40.4.10.31.1.6
    optixRtnOduRxPowerLowTHExt OBJECT-TYPE
        SYNTAX Integer32
        MAX-ACCESS read-write
        STATUS current
        DESCRIPTION
            "Indicates the lower threshold of the receive power. Signed type Unit: 0.1 dBm"
        ::= { optixRtnOduPowerExtEntry 6 }

    -- 1.3.6.1.4.1.2011.2.25.4.40.4.10.31.1.7
    optixRtnOduCfgMaxTxpowerExt OBJECT-TYPE
        SYNTAX Integer32
        MAX-ACCESS read-write
        STATUS current
        DESCRIPTION
            "Indicates the maximum transmit power of an RF unit board. When the ACM function is disabled, the maximum transmit power in the current mode is returned. When the ACM function is enabled, the maximum transmit power in the guaranteed capacity modulation mode is returned."
        ::= { optixRtnOduPowerExtEntry 7 }

    -- 1.3.6.1.4.1.2011.2.25.4.40.4.10.31.1.8
    optixRtnOduActualTxPowerExt OBJECT-TYPE
        SYNTAX Integer32
        MAX-ACCESS read-only
        STATUS current
        DESCRIPTION
            "Indicates the actual transmit power of an RF port. Signed type Unit: 0.1 dBm"
        ::= { optixRtnOduPowerExtEntry 8 }

    -- 1.3.6.1.4.1.2011.2.25.4.40.4.10.31.1.9
    optixRtnOduActualRxPowerExt OBJECT-TYPE
        SYNTAX Integer32
        MAX-ACCESS read-only
        STATUS current
        DESCRIPTION
            "Indicates the actual receive power of an RF port. Signed type Unit: 0.1 dBm"
        ::= { optixRtnOduPowerExtEntry 9 }

    -- 1.3.6.1.4.1.2011.2.25.4.40.4.10.31.1.10
    optixRtnOduMaxTxpowerExt OBJECT-TYPE
        SYNTAX Integer32
        MAX-ACCESS read-only
        STATUS current
        DESCRIPTION
            "Indicates the maximum value of the transmit power. Signed type Unit: 0.1 dBm"
        ::= { optixRtnOduPowerExtEntry 10 }

    -- 1.3.6.1.4.1.2011.2.25.4.40.4.10.31.1.11
    optixRtnOduMinTxpowerExt OBJECT-TYPE
        SYNTAX Integer32
        MAX-ACCESS read-only
        STATUS current
        DESCRIPTION
            "Indicates the minimum value of the transmit power. Signed type Unit: 0.1 dBm"
        ::= { optixRtnOduPowerExtEntry 11 }

    -- 1.3.6.1.4.1.2011.2.25.4.40.4.10.32
    optixRtnOduPortPowerTable OBJECT-TYPE
        SYNTAX SEQUENCE OF OptixRtnOduPortPowerEntry
        MAX-ACCESS not-accessible
        STATUS current
        DESCRIPTION
            "Describes parameters of the RF unit transmit and receive power(this node used only to 320 or 3202f)."
        ::= { optixODU 32 }

    -- 1.3.6.1.4.1.2011.2.25.4.40.4.10.30.1
    optixRtnOduPortPowerEntry OBJECT-TYPE
        SYNTAX OptixRtnOduPortPowerEntry
        MAX-ACCESS not-accessible
        STATUS current
        DESCRIPTION
            "Indicates the parameter entry for the RF unit transmit and receive powers(this node used only to 320 or 3202f)."
        INDEX{ optixRtnOduIndex1,optixRtnOduIndex2,optixRtnOduIndex3 }
        ::= { optixRtnOduPortPowerTable 1 }

    OptixRtnOduPortPowerEntry ::=
        SEQUENCE {
            optixRtnOduPortCfgTxPower
                Integer32,
            optixRtnOduPortCfgToBeRxPower
                Integer32,
            optixRtnOduPortTxPowerHighTh
                Integer32,
            optixRtnOduPortTxPowerLowTH
                Integer32,
            optixRtnOduPortRxPowerHighTh
                Integer32,
            optixRtnOduPortRxPowerLowTH
                Integer32,
            optixRtnOduPortCfgMaxTxpower
                Integer32,
            optixRtnOduPortActualTxPower
                Integer32,
            optixRtnOduPortActualRxPower
                Integer32,
            optixRtnOduPortMaxTxpower
                Integer32,
            optixRtnOduPortMinTxpower
                Integer32
        }

    -- 1.3.6.1.4.1.2011.2.25.4.40.4.10.32.1.1
    optixRtnOduPortCfgTxPower OBJECT-TYPE
        SYNTAX Integer32
        MAX-ACCESS read-write
        STATUS current
        DESCRIPTION
            "Indicates the transmit power of an RF port. Signed type Value range: -100 to +350 Unit: 0.1 dBm(this node used only to 320 or 3202f)."
        DEFVAL{ 100 }
        ::= { optixRtnOduPortPowerEntry 1 }

    -- 1.3.6.1.4.1.2011.2.25.4.40.4.10.32.1.2
    optixRtnOduPortCfgToBeRxPower OBJECT-TYPE
        SYNTAX Integer32
        MAX-ACCESS read-write
        STATUS current
        DESCRIPTION
            "Indicates the power expected to receive by an RF port. Unit: 0.1 dBm(this node used only to 320 or 3202f)."
        ::= { optixRtnOduPortPowerEntry 2 }

    -- 1.3.6.1.4.1.2011.2.25.4.40.4.10.32.1.3
    optixRtnOduPortTxPowerHighTh OBJECT-TYPE
        SYNTAX Integer32
        MAX-ACCESS read-write
        STATUS current
        DESCRIPTION
            "Indicates the upper threshold of the transmit power. Signed type The value range: -100 to +350 Unit: 0.1 dBm(this node used only to 320 or 3202f)."
        DEFVAL{ 350 }
        ::= { optixRtnOduPortPowerEntry 3 }

    -- 1.3.6.1.4.1.2011.2.25.4.40.4.10.32.1.4
    optixRtnOduPortTxPowerLowTH OBJECT-TYPE
        SYNTAX Integer32
        MAX-ACCESS read-write
        STATUS current
        DESCRIPTION
            "Indicates the lower threshold of the transmit power. Signed type The value range: -100 to +350 Unit: 0.1 dBm(this node used only to 320 or 3202f)."
        DEFVAL{ 350 }
        ::= { optixRtnOduPortPowerEntry 4 }

    -- 1.3.6.1.4.1.2011.2.25.4.40.4.10.32.1.5
    optixRtnOduPortRxPowerHighTh OBJECT-TYPE
        SYNTAX Integer32
        MAX-ACCESS read-write
        STATUS current
        DESCRIPTION
            "Indicates the upper threshold of the receive power. Signed type Unit: 0.1 dBm(this node used only to 320 or 3202f)."
        ::= { optixRtnOduPortPowerEntry 5 }

    -- 1.3.6.1.4.1.2011.2.25.4.40.4.10.32.1.6
    optixRtnOduPortRxPowerLowTH OBJECT-TYPE
        SYNTAX Integer32
        MAX-ACCESS read-write
        STATUS current
        DESCRIPTION
            "Indicates the lower threshold of the receive power. Signed type Unit: 0.1 dBm(this node used only to 320 or 3202f)"
        ::= { optixRtnOduPortPowerEntry 6 }

    -- 1.3.6.1.4.1.2011.2.25.4.40.4.10.32.1.7
    optixRtnOduPortCfgMaxTxpower OBJECT-TYPE
        SYNTAX Integer32
        MAX-ACCESS read-write
        STATUS current
        DESCRIPTION
            "Indicates the maximum transmit power of an RF unit board. When the ACM function is disabled, the maximum transmit power in the current mode is returned. When the ACM function is enabled, the maximum transmit power in the guaranteed capacity modulation mode is returned
(this node used only to 320 or 3202f)."
        ::= { optixRtnOduPortPowerEntry 7 }

    -- 1.3.6.1.4.1.2011.2.25.4.40.4.10.32.1.8
    optixRtnOduPortActualTxPower OBJECT-TYPE
        SYNTAX Integer32
        MAX-ACCESS read-only
        STATUS current
        DESCRIPTION
            "Indicates the actual transmit power of an RF port. Signed type Unit: 0.1 dBm(this node used only to 320 or 3202f)."
        ::= { optixRtnOduPortPowerEntry 8 }

    -- 1.3.6.1.4.1.2011.2.25.4.40.4.10.32.1.9
    optixRtnOduPortActualRxPower OBJECT-TYPE
        SYNTAX Integer32
        MAX-ACCESS read-only
        STATUS current
        DESCRIPTION
            "Indicates the actual receive power of an RF port. Signed type Unit: 0.1 dBm(this node used only to 320 or 3202f)."
        ::= { optixRtnOduPortPowerEntry 9 }

    -- 1.3.6.1.4.1.2011.2.25.4.40.4.10.32.1.10
    optixRtnOduPortMaxTxpower OBJECT-TYPE
        SYNTAX Integer32
        MAX-ACCESS read-only
        STATUS current
        DESCRIPTION
            "Indicates the maximum value of the actual transmit power. Signed type Unit: 0.1 dBm(this node used only to 320 or 3202f)."
        ::= { optixRtnOduPortPowerEntry 10 }

    -- 1.3.6.1.4.1.2011.2.25.4.40.4.10.32.1.11
    optixRtnOduPortMinTxpower OBJECT-TYPE
        SYNTAX Integer32
        MAX-ACCESS read-only
        STATUS current
        DESCRIPTION
            "Indicates the minimum value of the actual transmit power. Signed type Unit: 0.1 dBm(this node used only to 320 or 3202f)."
        ::= { optixRtnOduPortPowerEntry 11 }

    -- 1.3.6.1.4.1.2011.2.25.4.40.4.10.41
    optixRtnOduWorkStateExtTable OBJECT-TYPE
        SYNTAX SEQUENCE OF OptixRtnOduWorkStateExtEntry
        MAX-ACCESS not-accessible
        STATUS current
        DESCRIPTION
            "Indicates the current emission status of an RF unit board."
        ::= { optixODU 41 }

    -- 1.3.6.1.4.1.2011.2.25.4.40.4.10.41.1
    optixRtnOduWorkStateExtEntry OBJECT-TYPE
        SYNTAX OptixRtnOduWorkStateExtEntry
        MAX-ACCESS not-accessible
        STATUS current
        DESCRIPTION
            "Indicates the transmission status entry for an RF unit."
        INDEX{ optixRtnOduIndex1,optixRtnOduIndex2 }
        ::= { optixRtnOduWorkStateExtTable 1 }

    OptixRtnOduWorkStateExtEntry ::=
        SEQUENCE {
            optixRtnOduConfigWorkStateExt
                OPTIXRtnOduWorkStateType,
            optixRtnOduActualWorkStateExt
                INTEGER
        }

    -- 1.3.6.1.4.1.2011.2.25.4.40.4.10.41.1.1
    optixRtnOduConfigWorkStateExt OBJECT-TYPE
        SYNTAX OPTIXRtnOduWorkStateType
        MAX-ACCESS read-write
        STATUS current
        DESCRIPTION
            "Indicates the transmission status of an RF transmitter. Values: 0: muted 1: unmuted"
        DEFVAL{ 1 }
        ::= { optixRtnOduWorkStateExtEntry 1 }

    -- 1.3.6.1.4.1.2011.2.25.4.40.4.10.41.1.2
    optixRtnOduActualWorkStateExt OBJECT-TYPE
        SYNTAX INTEGER
        {
            mute(0),
            unmute(1)
        }
        MAX-ACCESS read-only
        STATUS current
        DESCRIPTION
            "Indicates the transmission actual status of an RF transmitter. Values: 0: muted 1: unmuted"
        ::= { optixRtnOduWorkStateExtEntry 2 }

    -- 1.3.6.1.4.1.2011.2.25.4.40.4.10.42
    optixRtnOduPortWorkStateTable OBJECT-TYPE
        SYNTAX SEQUENCE OF OptixRtnOduPortWorkStateEntry
        MAX-ACCESS not-accessible
        STATUS current
        DESCRIPTION
            "Indicates the current emission status of an RF unit board(this node used only to 320 or 3202f)."
        ::= { optixODU 42 }

    -- 1.3.6.1.4.1.2011.2.25.4.40.4.10.42.1
    optixRtnOduPortWorkStateEntry OBJECT-TYPE
        SYNTAX OptixRtnOduPortWorkStateEntry
        MAX-ACCESS not-accessible
        STATUS current
        DESCRIPTION
            "Indicates the transmission status entry for an RF unit(this node used only to 320 or 3202f)."
        INDEX{ optixRtnOduIndex1,optixRtnOduIndex2,optixRtnOduIndex3 }
        ::= { optixRtnOduPortWorkStateTable 1 }

    OptixRtnOduPortWorkStateEntry ::=
        SEQUENCE {
            optixRtnOduPortConfigWorkState
                OPTIXRtnOduWorkStateType,
            optixRtnOduPortActualWorkState
                OPTIXRtnOduWorkStateType
        }

    -- 1.3.6.1.4.1.2011.2.25.4.40.4.10.42.1.1
    optixRtnOduPortConfigWorkState OBJECT-TYPE
        SYNTAX OPTIXRtnOduWorkStateType
        MAX-ACCESS read-write
        STATUS current
        DESCRIPTION
            "Indicates the transmission status of an RF transmitter(this node used only to 320 or 3202f). Values: 0: muted 1: unmuted"
        DEFVAL{ 1 }
        ::= { optixRtnOduPortWorkStateEntry 1 }

    -- 1.3.6.1.4.1.2011.2.25.4.40.4.10.42.1.2
    optixRtnOduPortActualWorkState OBJECT-TYPE
        SYNTAX OPTIXRtnOduWorkStateType
        MAX-ACCESS read-only
        STATUS current
        DESCRIPTION
            "Indicates the transmission actual status of an RF transmitter(this node used only to 320 or 3202f). Values: 0: muted 1: unmuted"
        ::= { optixRtnOduPortWorkStateEntry 2 }

    -- 1.3.6.1.4.1.2011.2.25.4.40.4.10.43
    optixRtnRegOduLHFreqScanTable OBJECT-TYPE
	SYNTAX SEQUENCE OF OptixRtnRegOduLHFreqScanEntry
	MAX-ACCESS not-accessible
	STATUS current
	DESCRIPTION
	"Describes the information about RF unit, frequency scanning , and obtaining of interfering frequency."
	::= { optixODU 43 }  

    -- 1.3.6.1.4.1.2011.2.25.4.40.4.10.43.1
    optixRtnRegOduLHFreqScanEntry OBJECT-TYPE
        SYNTAX OptixRtnRegOduLHFreqScanEntry
        MAX-ACCESS not-accessible
        STATUS current
        DESCRIPTION
            "Indicates the parameter entry for RF unit frequency scanning."
        INDEX{ optixRtnOduIndex1,optixRtnOduIndex2,optixRtnOduIndex3}
        ::= { optixRtnRegOduLHFreqScanTable 1 }
	
    OptixRtnRegOduLHFreqScanEntry ::=
        SEQUENCE {
            optixRtnOduLHScanFreqInterference
                INTEGER,
            optixRtnOduLHScanFreqLeakage
                INTEGER,
            optixRtnOduLHScanFreqIntermodulation
                INTEGER,
            optixRtnOduLHScanFreqStaFreq
                INTEGER,
            optixRtnOduLHScanFreqEndFreq
                INTEGER,
            optixRtnOduLHScanFreqStep
                INTEGER,
            optixRtnOduLHScanFreqBandWidth
                INTEGER,
            optixRtnOduLHScanFreqNumber
                INTEGER,
            optixRtnOduLHScanFreqBids
                OCTET STRING
        }
	
	
    -- 1.3.6.1.4.1.2011.2.25.4.40.4.10.43.1.4
    optixRtnOduLHScanFreqInterference OBJECT-TYPE
        SYNTAX INTEGER
	{
	    no(0),
	    yes(1),
	    unknown(-1)	
	}
        MAX-ACCESS read-only
        STATUS current
        DESCRIPTION
            "Indicates the  information of Interference."
        ::= { optixRtnRegOduLHFreqScanEntry 4 }
 
    -- 1.3.6.1.4.1.2011.2.25.4.40.4.10.43.1.5
    optixRtnOduLHScanFreqLeakage OBJECT-TYPE
        SYNTAX INTEGER
	{
	    no(0),
	    yes(1),
	    unknown(-1)	
	}
        MAX-ACCESS read-only
        STATUS current
        DESCRIPTION
            "Indicates the  information of Leakage."
        ::= { optixRtnRegOduLHFreqScanEntry 5 }
	
    -- 1.3.6.1.4.1.2011.2.25.4.40.4.10.43.1.6
    optixRtnOduLHScanFreqIntermodulation OBJECT-TYPE
        SYNTAX INTEGER
	{
	    no(0),
	    yes(1),
	    unknown(-1)	
	}
        MAX-ACCESS read-only
        STATUS current
        DESCRIPTION
            "Indicates the  information of Intermodulation."
        ::= { optixRtnRegOduLHFreqScanEntry 6}

    -- 1.3.6.1.4.1.2011.2.25.4.40.4.10.43.1.7
    optixRtnOduLHScanFreqStaFreq OBJECT-TYPE
        SYNTAX INTEGER
        MAX-ACCESS read-write
        STATUS current
        DESCRIPTION
            "Indicates the  frequence of starting scanning ."
        ::= { optixRtnRegOduLHFreqScanEntry 7}
	
    -- 1.3.6.1.4.1.2011.2.25.4.40.4.10.43.1.8
    optixRtnOduLHScanFreqEndFreq OBJECT-TYPE
        SYNTAX INTEGER
        MAX-ACCESS read-write
        STATUS current
        DESCRIPTION
            "Indicates the  frequence of ending scanning."
        ::= { optixRtnRegOduLHFreqScanEntry 8}
	
    -- 1.3.6.1.4.1.2011.2.25.4.40.4.10.43.1.9
    optixRtnOduLHScanFreqStep OBJECT-TYPE
        SYNTAX INTEGER
	{
	    step1p5m(10),
	    step1p75m(11),
	    step3p5m(12),
	    step7m(13),
	    step14m(14)
	}
        MAX-ACCESS read-write
        STATUS current
        DESCRIPTION
            "Indicates the  step of scanning frequence."
        ::= { optixRtnRegOduLHFreqScanEntry 9}

    -- 1.3.6.1.4.1.2011.2.25.4.40.4.10.43.1.10
    optixRtnOduLHScanFreqBandWidth OBJECT-TYPE
        SYNTAX INTEGER
	{
	    bw3P5M(1),
            bw7M(2),
            bw14M(3),
            bw28M(4),
            bw40M(5),
            bw56M(6),
            bwFCC30M(7),
            bwFCC40M(8),
            bwFCC50M(9),
            bw250M(10),
            bw500M(11),
            bw750M(12),
            bw62P5M(16),
            bw125M(17),
            bw112M(23),
            bwFCC10M(24),
            bwFCC20M(25),
            bwFCC60M(28),
	    bw80M(34)
	}
        MAX-ACCESS read-write
        STATUS current
        DESCRIPTION
            "Indicates the  bandwidth of scanning frequence."
        ::= { optixRtnRegOduLHFreqScanEntry 10}	
	
    -- 1.3.6.1.4.1.2011.2.25.4.40.4.10.43.1.11
    optixRtnOduLHScanFreqNumber OBJECT-TYPE
        SYNTAX INTEGER
        MAX-ACCESS read-write
        STATUS current
        DESCRIPTION
            "Indicates the  number of scanning frequence."
        ::= { optixRtnRegOduLHFreqScanEntry 11}	
	
    -- 1.3.6.1.4.1.2011.2.25.4.40.4.10.43.1.12
    optixRtnOduLHScanFreqBids OBJECT-TYPE
        SYNTAX OCTET STRING
        MAX-ACCESS read-write
        STATUS current
        DESCRIPTION
            "Indicates the  board IDs of scanning frequence. format:number,bid1,bid2,...,"
        ::= { optixRtnRegOduLHFreqScanEntry 12}	

   -- 1.3.6.1.4.1.2011.2.25.4.40.4.10.44
    optixRtnRegOduLHFreqScanResultTable OBJECT-TYPE
	SYNTAX SEQUENCE OF OptixRtnRegOduLHFreqScanResultEntry
	MAX-ACCESS not-accessible
	STATUS current
	DESCRIPTION
	"Describes the information about RF unit, frequency scanning , and obtaining of interfering frequency."
	::= { optixODU 44 }  

    -- 1.3.6.1.4.1.2011.2.25.4.40.4.10.44.1
    optixRtnRegOduLHFreqScanResultEntry OBJECT-TYPE
        SYNTAX OptixRtnRegOduLHFreqScanResultEntry
        MAX-ACCESS not-accessible
        STATUS current
        DESCRIPTION
            "Indicates the parameter entry for RF unit frequency scanning."
        INDEX{ optixRtnOduIndex1,optixRtnOduIndex2,optixRtnOduIndex3,optixRtnOduIndex4}
        ::= { optixRtnRegOduLHFreqScanResultTable 1 }
	
    OptixRtnRegOduLHFreqScanResultEntry ::=
        SEQUENCE {
            optixRtnOduLHScanResultRxFreq
                INTEGER,
            optixRtnOduLHScanResultMainRsl
                INTEGER,
            optixRtnOduLHScanResultSlaveRsl
                INTEGER
        
        }
		
    -- 1.3.6.1.4.1.2011.2.25.4.40.4.10.44.1.5
    optixRtnOduLHScanResultRxFreq	OBJECT-TYPE			
  	SYNTAX INTEGER
        MAX-ACCESS read-only
        STATUS current
        DESCRIPTION
            "Indicates the Rx frequency of frequency scanning."
        ::= { optixRtnRegOduLHFreqScanResultEntry 5 }
	
    -- 1.3.6.1.4.1.2011.2.25.4.40.4.10.44.1.6
    optixRtnOduLHScanResultMainRsl	OBJECT-TYPE				
  	SYNTAX INTEGER
        MAX-ACCESS read-only
        STATUS current
        DESCRIPTION
            "Indicates the main Rsl of frequency scanning."
        ::= { optixRtnRegOduLHFreqScanResultEntry 6 }
	
    -- 1.3.6.1.4.1.2011.2.25.4.40.4.10.44.1.7
    optixRtnOduLHScanResultSlaveRsl	OBJECT-TYPE				
  	SYNTAX INTEGER
        MAX-ACCESS read-only
        STATUS current
        DESCRIPTION
            "Indicates the slave Rsl of frequency scanning."
        ::= { optixRtnRegOduLHFreqScanResultEntry 7 }

    -- 1.3.6.1.4.1.2011.2.25.4.40.4.10.51
    optixRtnOduFreqScanExtTable OBJECT-TYPE
        SYNTAX SEQUENCE OF OptixRtnOduFreqScanExtEntry
        MAX-ACCESS not-accessible
        STATUS current
        DESCRIPTION
            "Describes the information about RF unit start, frequency scanning stop, and obtaining of interfering frequency."
        ::= { optixODU 51 }

    -- 1.3.6.1.4.1.2011.2.25.4.40.4.10.51.1
    optixRtnOduFreqScanExtEntry OBJECT-TYPE
        SYNTAX OptixRtnOduFreqScanExtEntry
        MAX-ACCESS not-accessible
        STATUS current
        DESCRIPTION
            "Indicates the parameter entry for RF unit frequency scanning."
        INDEX{ optixRtnOduIndex1,optixRtnOduIndex2 }
        ::= { optixRtnOduFreqScanExtTable 1 }

    OptixRtnOduFreqScanExtEntry ::=
        SEQUENCE {
            optixRtnOduStartScanStartFreqExt
                Unsigned32,
            optixRtnOduStartScanEndFreqExt
                Unsigned32,
            optixRtnOduStartScanStepExt
                INTEGER,
            optixRtnOduStartScanBWidExt
                OPTIXRtnOduBandWidthType,
            optixRtnOduStopFreqScanExt
                INTEGER,
            optixRtnOduInterferenceFreqBwidExt
                OPTIXRtnOduBandWidthType,
            optixRtnOduInterferenceFreqLeftChannelExt
                INTEGER,
            optixRtnOduInterferenceFreqCfgChannelExt
                INTEGER,
            optixRtnOduInterferenceFreqRightChannelExt
                INTEGER
        }

    -- 1.3.6.1.4.1.2011.2.25.4.40.4.10.51.1.1
    optixRtnOduStartScanStartFreqExt OBJECT-TYPE
        SYNTAX Unsigned32
        MAX-ACCESS read-write
        STATUS current
        DESCRIPTION
            "Indicates the start frequency of frequency scanning. Unit:KHz"
        ::= { optixRtnOduFreqScanExtEntry 1 }

    -- 1.3.6.1.4.1.2011.2.25.4.40.4.10.51.1.2
    optixRtnOduStartScanEndFreqExt OBJECT-TYPE
        SYNTAX Unsigned32
        MAX-ACCESS read-write
        STATUS current
        DESCRIPTION
            "Indicates the end freqency of frequency scanning. Unit:KHz"
        ::= { optixRtnOduFreqScanExtEntry 2 }

    -- 1.3.6.1.4.1.2011.2.25.4.40.4.10.51.1.3
    optixRtnOduStartScanStepExt OBJECT-TYPE
        SYNTAX INTEGER
        {
            step15M(1),
            step31M(2),
            step62M(3),
            step1P5M(10),
            step1P75M(11),
            step3P5M(12),
            step7M(13),
            step14M(14)
        }
        MAX-ACCESS read-write
        STATUS current
        DESCRIPTION
            "Indicates the step of frequency scanning. Values for RTN300:1-15M,2-31M,3- 62M. Values for RTN900:11-1P5M,12-1P75M,13-3P5M,14-7M,15-14M"
        ::= { optixRtnOduFreqScanExtEntry 3 }

    -- 1.3.6.1.4.1.2011.2.25.4.40.4.10.51.1.4
    optixRtnOduStartScanBWidExt OBJECT-TYPE
        SYNTAX OPTIXRtnOduBandWidthType
        MAX-ACCESS read-write
        STATUS current
        DESCRIPTION
            "Indicates the bandwidth of frequency scanning,for calculating available frequencies."
        ::= { optixRtnOduFreqScanExtEntry 4 }

    -- 1.3.6.1.4.1.2011.2.25.4.40.4.10.51.1.5
    optixRtnOduStopFreqScanExt OBJECT-TYPE
        SYNTAX INTEGER
        {
            stop(0)
        }
        MAX-ACCESS read-write
        STATUS current
        DESCRIPTION
            "Indicates the stop of frequency scanning."
        DEFVAL{ stop }
        ::= { optixRtnOduFreqScanExtEntry 5 }

    -- 1.3.6.1.4.1.2011.2.25.4.40.4.10.51.1.6
    optixRtnOduInterferenceFreqBwidExt OBJECT-TYPE
        SYNTAX OPTIXRtnOduBandWidthType
        MAX-ACCESS read-only
        STATUS current
        DESCRIPTION
            "Indicates the configuration bandwidth."
        ::= { optixRtnOduFreqScanExtEntry 6 }

    -- 1.3.6.1.4.1.2011.2.25.4.40.4.10.51.1.7
    optixRtnOduInterferenceFreqLeftChannelExt OBJECT-TYPE
        SYNTAX INTEGER
        {
            stateUnknown(-1),
            stateNoInterference(0),
            stateInterference(1)
        }
        MAX-ACCESS read-only
        STATUS current
        DESCRIPTION
            "Indicates the left channel state of configuration frequency"
        ::= { optixRtnOduFreqScanExtEntry 7 }

    -- 1.3.6.1.4.1.2011.2.25.4.40.4.10.51.1.8
    optixRtnOduInterferenceFreqCfgChannelExt OBJECT-TYPE
        SYNTAX INTEGER
        {
            stateUnknown(-1),
            stateNoInterference(0),
            stateInterference(1)
        }
        MAX-ACCESS read-only
        STATUS current
        DESCRIPTION
            "Indicates the current channel state of configuration frequency."
        ::= { optixRtnOduFreqScanExtEntry 8 }

    -- 1.3.6.1.4.1.2011.2.25.4.40.4.10.51.1.9
    optixRtnOduInterferenceFreqRightChannelExt OBJECT-TYPE
        SYNTAX INTEGER
        {
            stateUnknown(-1),
            stateNoInterference(0),
            stateInterference(1)
        }
        MAX-ACCESS read-only
        STATUS current
        DESCRIPTION
            "Indicates the right channel state of configuration frequency."
        ::= { optixRtnOduFreqScanExtEntry 9 }

    -- 1.3.6.1.4.1.2011.2.25.4.40.4.10.52
    optixRtnOduPortFreqScanTable OBJECT-TYPE
        SYNTAX SEQUENCE OF OptixRtnOduPortFreqScanEntry
        MAX-ACCESS not-accessible
        STATUS current
        DESCRIPTION
            "Describes the information about RF unit start, frequency scanning stop, and obtaining of interfering frequency(this node used only to 320 or 3202f)."
        ::= { optixODU 52 }

    -- 1.3.6.1.4.1.2011.2.25.4.40.4.10.52.1
    optixRtnOduPortFreqScanEntry OBJECT-TYPE
        SYNTAX OptixRtnOduPortFreqScanEntry
        MAX-ACCESS not-accessible
        STATUS current
        DESCRIPTION
            "Indicates the parameter entry for RF unit frequency scanning(this node used only to 320 or 3202f)."
        INDEX{ optixRtnOduIndex1,optixRtnOduIndex2,optixRtnOduIndex3 }
        ::= { optixRtnOduPortFreqScanTable 1 }

    OptixRtnOduPortFreqScanEntry ::=
        SEQUENCE {
            optixRtnOduPortStartScanStartFreq
                Unsigned32,
            optixRtnOduPortStartScanEndFreq
                Unsigned32,
            optixRtnOduPortStartScanStep
                INTEGER,
            optixRtnOduPortStartScanBWid
                OPTIXRtnOduPortBandWidthType,
            optixRtnOduPortStopFreqScan
                INTEGER,
            optixRtnOduPortInterferenceFreqBwid
                OPTIXRtnOduPortBandWidthType,
            optixRtnOduPortInterferenceFreqLeftChannel
                INTEGER,
            optixRtnOduPortInterferenceFreqCfgChannel
                INTEGER,
            optixRtnOduPortInterferenceFreqRightChannel
                INTEGER
        }

    -- 1.3.6.1.4.1.2011.2.25.4.40.4.10.52.1.1
    optixRtnOduPortStartScanStartFreq OBJECT-TYPE
        SYNTAX Unsigned32
        MAX-ACCESS read-write
        STATUS current
        DESCRIPTION
            "Indicates the start frequency of frequency scanning(this node used only to 320 or 3202f). Unit:KHz"
        ::= { optixRtnOduPortFreqScanEntry 1 }

    -- 1.3.6.1.4.1.2011.2.25.4.40.4.10.52.1.2
    optixRtnOduPortStartScanEndFreq OBJECT-TYPE
        SYNTAX Unsigned32
        MAX-ACCESS read-write
        STATUS current
        DESCRIPTION
            "Indicates the end freqency of frequency scanning(this node used only to 320 or 3202f). Unit:KHz"
        ::= { optixRtnOduPortFreqScanEntry 2 }

    -- 1.3.6.1.4.1.2011.2.25.4.40.4.10.52.1.3
    optixRtnOduPortStartScanStep OBJECT-TYPE
        SYNTAX INTEGER
        {
            step1P5M(10),
            step1P75M(11),
            step3P5M(12),
            step7M(13),
            step14M(14)
        }
        MAX-ACCESS read-write
        STATUS current
        DESCRIPTION
            "Indicates the step of frequency scanning(this node used only to 320 or 3202f).
Values for RTN300:1-15M,2-31M,3- 62M. Values for RTN900:11-1P5M,12-1P75M,13-3P5M,14-7M,15-14M"
        ::= { optixRtnOduPortFreqScanEntry 3 }

    -- 1.3.6.1.4.1.2011.2.25.4.40.4.10.52.1.4
    optixRtnOduPortStartScanBWid OBJECT-TYPE
        SYNTAX OPTIXRtnOduPortBandWidthType
        MAX-ACCESS read-write
        STATUS current
        DESCRIPTION
            "Indicates the bandwidth of frequency scanning,for calculating available frequencies(this node used only to 320 or 3202f)."
        ::= { optixRtnOduPortFreqScanEntry 4 }

    -- 1.3.6.1.4.1.2011.2.25.4.40.4.10.52.1.5
    optixRtnOduPortStopFreqScan OBJECT-TYPE
        SYNTAX INTEGER
        {
            stop(0)
        }
        MAX-ACCESS read-write
        STATUS current
        DESCRIPTION
            "Indicates the stop of frequency scanning(this node used only to 320 or 3202f)."
        DEFVAL{ stop }
        ::= { optixRtnOduPortFreqScanEntry 5 }

    -- 1.3.6.1.4.1.2011.2.25.4.40.4.10.52.1.6
    optixRtnOduPortInterferenceFreqBwid OBJECT-TYPE
        SYNTAX OPTIXRtnOduPortBandWidthType
        MAX-ACCESS read-only
        STATUS current
        DESCRIPTION
            "Indicates the configuration bandwidth(this node used only to 320 or 3202f)."
        ::= { optixRtnOduPortFreqScanEntry 6 }

    -- 1.3.6.1.4.1.2011.2.25.4.40.4.10.52.1.7
    optixRtnOduPortInterferenceFreqLeftChannel OBJECT-TYPE
        SYNTAX INTEGER
        {
            stateUnknown(-1),
            stateNoInterference(0),
            stateInterference(1)
        }
        MAX-ACCESS read-only
        STATUS current
        DESCRIPTION
            "Indicates the left channel state of configuration frequency(this node used only to 320 or 3202f)."
        ::= { optixRtnOduPortFreqScanEntry 7 }

    -- 1.3.6.1.4.1.2011.2.25.4.40.4.10.52.1.8
    optixRtnOduPortInterferenceFreqCfgChannel OBJECT-TYPE
        SYNTAX INTEGER
        {
            stateUnknown(-1),
            stateNoInterference(0),
            stateInterference(1)
        }
        MAX-ACCESS read-only
        STATUS current
        DESCRIPTION
            "Indicates the current channel state of configuration frequency(this node used only to 320 or 3202f)."
        ::= { optixRtnOduPortFreqScanEntry 8 }

    -- 1.3.6.1.4.1.2011.2.25.4.40.4.10.52.1.9
    optixRtnOduPortInterferenceFreqRightChannel OBJECT-TYPE
        SYNTAX INTEGER
        {
            stateUnknown(-1),
            stateNoInterference(0),
            stateInterference(1)
        }
        MAX-ACCESS read-only
        STATUS current
        DESCRIPTION
            "Indicates the right channel state of configuration frequency(this node used only to 320 or 3202f)."
        ::= { optixRtnOduPortFreqScanEntry 9 }

    -- 1.3.6.1.4.1.2011.2.25.4.40.4.10.61
    optixRtnOduFreqScanAvailFreqExtTable OBJECT-TYPE
        SYNTAX SEQUENCE OF OptixRtnOduFreqScanAvailFreqExtEntry
        MAX-ACCESS not-accessible
        STATUS current
        DESCRIPTION
            "Describes Available frequencies of the RF unit frequency scanning."
        ::= { optixODU 61 }

    -- 1.3.6.1.4.1.2011.2.25.4.40.4.10.61.1
    optixRtnOduFreqScanAvailFreqExtEntry OBJECT-TYPE
        SYNTAX OptixRtnOduFreqScanAvailFreqExtEntry
        MAX-ACCESS not-accessible
        STATUS current
        DESCRIPTION
            "Indicates the parameter entry for the RF unit frequency scanning."
        INDEX{ optixRtnOduIndex1,optixRtnOduIndex2,optixRtnOduAvailFreqListExt }
        ::= { optixRtnOduFreqScanAvailFreqExtTable 1 }

    OptixRtnOduFreqScanAvailFreqExtEntry ::=
        SEQUENCE {
            optixRtnOduAvailFreqListExt
                Unsigned32,
            optixRtnOduGetAvailableBwidExt
                OPTIXRtnOduBandWidthType,
            optixRtnOduGetAvailableTxfreqsExt
                Unsigned32
        }

    -- 1.3.6.1.4.1.2011.2.25.4.40.4.10.61.1.1
    optixRtnOduAvailFreqListExt OBJECT-TYPE
        SYNTAX Unsigned32
        MAX-ACCESS not-accessible
        STATUS current
        DESCRIPTION
            "Indicates the list number of available frequencies."
        ::= { optixRtnOduFreqScanAvailFreqExtEntry 1 }

    -- 1.3.6.1.4.1.2011.2.25.4.40.4.10.61.1.2
    optixRtnOduGetAvailableBwidExt OBJECT-TYPE
        SYNTAX OPTIXRtnOduBandWidthType
        MAX-ACCESS read-only
        STATUS current
        DESCRIPTION
            "Indicates the bandwidth that inputted when starting the frequency scanning."
        ::= { optixRtnOduFreqScanAvailFreqExtEntry 2 }

    -- 1.3.6.1.4.1.2011.2.25.4.40.4.10.61.1.3
    optixRtnOduGetAvailableTxfreqsExt OBJECT-TYPE
        SYNTAX Unsigned32
        MAX-ACCESS read-only
        STATUS current
        DESCRIPTION
            "Indicates the available freqencies of frequency scanning. Unit:KHz"
        ::= { optixRtnOduFreqScanAvailFreqExtEntry 3 }

    -- 1.3.6.1.4.1.2011.2.25.4.40.4.10.62
    optixRtnOduPortFreqScanAvailFreqTable OBJECT-TYPE
        SYNTAX SEQUENCE OF OptixRtnOduPortFreqScanAvailFreqEntry
        MAX-ACCESS not-accessible
        STATUS current
        DESCRIPTION
            "Describes Available frequencies of the RF unit frequency scanning(this node used only to 320 or 3202f)."
        ::= { optixODU 62 }

    -- 1.3.6.1.4.1.2011.2.25.4.40.4.10.62.1
    optixRtnOduPortFreqScanAvailFreqEntry OBJECT-TYPE
        SYNTAX OptixRtnOduPortFreqScanAvailFreqEntry
        MAX-ACCESS not-accessible
        STATUS current
        DESCRIPTION
            "Indicates the parameter entry for the RF unit frequency scanning(this node used only to 320 or 3202f)."
        INDEX{ optixRtnOduIndex1,optixRtnOduIndex2,optixRtnOduIndex3,optixRtnOduPortAvailFreqList }
        ::= { optixRtnOduPortFreqScanAvailFreqTable 1 }

    OptixRtnOduPortFreqScanAvailFreqEntry ::=
        SEQUENCE {
            optixRtnOduPortAvailFreqList
                Unsigned32,
            optixRtnOduPortGetAvailableBwid
                OPTIXRtnOduPortBandWidthType,
            optixRtnOduPortGetAvailableTxfreqs
                Unsigned32
        }

    -- 1.3.6.1.4.1.2011.2.25.4.40.4.10.62.1.1
    optixRtnOduPortAvailFreqList OBJECT-TYPE
        SYNTAX Unsigned32
        MAX-ACCESS not-accessible
        STATUS current
        DESCRIPTION
            "Indicates the list number of available frequencies(this node used only to 320 or 3202f)."
        ::= { optixRtnOduPortFreqScanAvailFreqEntry 1 }

    -- 1.3.6.1.4.1.2011.2.25.4.40.4.10.62.1.2
    optixRtnOduPortGetAvailableBwid OBJECT-TYPE
        SYNTAX OPTIXRtnOduPortBandWidthType
        MAX-ACCESS read-only
        STATUS current
        DESCRIPTION
            "Indicates the bandwidth that inputted when starting the frequency scanning(this node used only to 320 or 3202f)."
        ::= { optixRtnOduPortFreqScanAvailFreqEntry 2 }

    -- 1.3.6.1.4.1.2011.2.25.4.40.4.10.62.1.3
    optixRtnOduPortGetAvailableTxfreqs OBJECT-TYPE
        SYNTAX Unsigned32
        MAX-ACCESS read-only
        STATUS current
        DESCRIPTION
            "Indicates the available freqencies of frequency scanning(this node used only to 320 or 3202f). Unit:KHz"
        ::= { optixRtnOduPortFreqScanAvailFreqEntry 3 }

    -- 1.3.6.1.4.1.2011.2.25.4.40.4.10.71
    optixRtnOduFreqScanResultExtTable OBJECT-TYPE
        SYNTAX SEQUENCE OF OptixRtnOduFreqScanResultExtEntry
        MAX-ACCESS not-accessible
        STATUS current
        DESCRIPTION
            "Describes result of the RF unit frequency scanning"
        ::= { optixODU 71 }

    -- 1.3.6.1.4.1.2011.2.25.4.40.4.10.71.1
    optixRtnOduFreqScanResultExtEntry OBJECT-TYPE
        SYNTAX OptixRtnOduFreqScanResultExtEntry
        MAX-ACCESS not-accessible
        STATUS current
        DESCRIPTION
            "Indicates the parameter entry for the RF unit frequency scanning."
        INDEX{ optixRtnOduIndex1,optixRtnOduIndex2,optixRtnOduScanResultListExt }
        ::= { optixRtnOduFreqScanResultExtTable 1 }

    OptixRtnOduFreqScanResultExtEntry ::=
        SEQUENCE {
            optixRtnOduScanResultListExt
                Unsigned32,
            optixRtnOduScanResultRxFreqExt
                Unsigned32,
            optixRtnOduScanResultRxRslExt
                Integer32
        }

    -- 1.3.6.1.4.1.2011.2.25.4.40.4.10.71.1.1
    optixRtnOduScanResultListExt OBJECT-TYPE
        SYNTAX Unsigned32
        MAX-ACCESS not-accessible
        STATUS current
        DESCRIPTION
            "Indicates the list of RF scanning results."
        ::= { optixRtnOduFreqScanResultExtEntry 1 }

    -- 1.3.6.1.4.1.2011.2.25.4.40.4.10.71.1.2
    optixRtnOduScanResultRxFreqExt OBJECT-TYPE
        SYNTAX Unsigned32
        MAX-ACCESS read-only
        STATUS current
        DESCRIPTION
            "Indicates the receive freqencies of frequency scanning. Unit:KHz"
        ::= { optixRtnOduFreqScanResultExtEntry 2 }

    -- 1.3.6.1.4.1.2011.2.25.4.40.4.10.71.1.3
    optixRtnOduScanResultRxRslExt OBJECT-TYPE
        SYNTAX Integer32
        MAX-ACCESS read-only
        STATUS current
        DESCRIPTION
            "Indicates the receive power of frequency scanning. Unit:0.1 dBm"
        ::= { optixRtnOduFreqScanResultExtEntry 3 }

    -- 1.3.6.1.4.1.2011.2.25.4.40.4.10.72
    optixRtnOduPortFreqScanResultTable OBJECT-TYPE
        SYNTAX SEQUENCE OF OptixRtnOduPortFreqScanResultEntry
        MAX-ACCESS not-accessible
        STATUS current
        DESCRIPTION
            "Describes result of the RF unit frequency scanning(this node used only to 320 or 3202f)."
        ::= { optixODU 72 }

    -- 1.3.6.1.4.1.2011.2.25.4.40.4.10.72.1
    optixRtnOduPortFreqScanResultEntry OBJECT-TYPE
        SYNTAX OptixRtnOduPortFreqScanResultEntry
        MAX-ACCESS not-accessible
        STATUS current
        DESCRIPTION
            "Indicates the parameter entry for the RF unit frequency scanning(this node used only to 320 or 3202f)."
        INDEX{ optixRtnOduIndex1,optixRtnOduIndex2,optixRtnOduIndex3,optixRtnOduPortScanResultList }
        ::= { optixRtnOduPortFreqScanResultTable 1 }

    OptixRtnOduPortFreqScanResultEntry ::=
        SEQUENCE {
            optixRtnOduPortScanResultList
                Unsigned32,
            optixRtnOduPortScanResultRxFreq
                Unsigned32,
            optixRtnOduPortScanResultRxRsl
                Integer32
        }

    -- 1.3.6.1.4.1.2011.2.25.4.40.4.10.72.1.1
    optixRtnOduPortScanResultList OBJECT-TYPE
        SYNTAX Unsigned32
        MAX-ACCESS not-accessible
        STATUS current
        DESCRIPTION
            "Indicates the list of RF scanning results(this node used only to 320 or 3202f)."
        ::= { optixRtnOduPortFreqScanResultEntry 1 }

    -- 1.3.6.1.4.1.2011.2.25.4.40.4.10.72.1.2
    optixRtnOduPortScanResultRxFreq OBJECT-TYPE
        SYNTAX Unsigned32
        MAX-ACCESS read-only
        STATUS current
        DESCRIPTION
            "Indicates the receive freqencies of frequency scanning. Unit:KHz"
        ::= { optixRtnOduPortFreqScanResultEntry 2 }

    -- 1.3.6.1.4.1.2011.2.25.4.40.4.10.72.1.3
    optixRtnOduPortScanResultRxRsl OBJECT-TYPE
        SYNTAX Integer32
        MAX-ACCESS read-only
        STATUS current
        DESCRIPTION
            "Indicates the receive power of frequency scanning(this node used only to 320 or 3202f). Unit:0.1 dBm"
        ::= { optixRtnOduPortFreqScanResultEntry 3 }

    -- 1.3.6.1.4.1.2011.2.25.4.40.4.10.80
    optixRtnScanFreqTrapCommon OBJECT IDENTIFIER ::= { optixODU 80 }

    -- 1.3.6.1.4.1.2011.2.25.4.40.4.10.80.5
    optixRptRtnFreqScanEndEvent OBJECT IDENTIFIER ::= { optixRtnScanFreqTrapCommon 5 }

    -- 1.3.6.1.4.1.2011.2.25.4.40.4.10.80.5.1
    optixRtnOduFreqScanEndIndexBid OBJECT-TYPE
        SYNTAX Unsigned32
        MAX-ACCESS accessible-for-notify
        STATUS current
        DESCRIPTION
            "Indicates the RF unit board ID."
        ::= { optixRptRtnFreqScanEndEvent 1 }

    -- 1.3.6.1.4.1.2011.2.25.4.40.4.10.80.5.2
    optixRtnOduFreqScanEndIndexSubID OBJECT-TYPE
        SYNTAX Unsigned32
        MAX-ACCESS accessible-for-notify
        STATUS current
        DESCRIPTION
            "Indicates the subboard ID."
        ::= { optixRptRtnFreqScanEndEvent 2 }

    -- 1.3.6.1.4.1.2011.2.25.4.40.4.10.80.5.3
    optixRptRtnFreqScanEndState OBJECT-TYPE
        SYNTAX OCTET STRING
        MAX-ACCESS accessible-for-notify
        STATUS current
        DESCRIPTION
            "Indicates the stop type of frequency scanning.
RTN900:
0-stopScanFreqStateNormal
1-stopScanFreqStateManual
2-stopScanFreqStateAbnormal
310/360/380/380H/380HN/380A/380AX:
0-stopScanFreqStateNormal
1-stopScanFreqStateManual
2-stopScanFreqStateExcept"
        ::= { optixRptRtnFreqScanEndEvent 3 }

    -- 1.3.6.1.4.1.2011.2.25.4.40.4.10.80.6
    optixRptRtnFreqScanEndExtEvent OBJECT IDENTIFIER ::= { optixRtnScanFreqTrapCommon 6 }

    -- 1.3.6.1.4.1.2011.2.25.4.40.4.10.80.6.1
    optixRtnOduFreqScanEndExtIndexBid OBJECT-TYPE
        SYNTAX Unsigned32
        MAX-ACCESS accessible-for-notify
        STATUS current
        DESCRIPTION
            "Indicates the RF unit board ID(this node used only to 320 or 3202f)."
        ::= { optixRptRtnFreqScanEndExtEvent 1 }

    -- 1.3.6.1.4.1.2011.2.25.4.40.4.10.80.6.2
    optixRtnOduFreqScanEndExtIndexSubID OBJECT-TYPE
        SYNTAX Unsigned32
        MAX-ACCESS accessible-for-notify
        STATUS current
        DESCRIPTION
            "Indicates the subboard ID(this node used only to 320 or 3202f)."
        ::= { optixRptRtnFreqScanEndExtEvent 2 }

    -- 1.3.6.1.4.1.2011.2.25.4.40.4.10.80.6.3
    optixRtnOduFreqScanEndExtIndexPid OBJECT-TYPE
        SYNTAX Unsigned32
        MAX-ACCESS accessible-for-notify
        STATUS current
        DESCRIPTION
            "Indicates the port ID(this node used only to 320 or 3202f)."
        ::= { optixRptRtnFreqScanEndExtEvent 3 }

    -- 1.3.6.1.4.1.2011.2.25.4.40.4.10.80.6.4
    optixRptRtnFreqScanEndExtState OBJECT-TYPE
        SYNTAX INTEGER
        {
            stopScanFreqStateNormal(0),
            stopScanFreqStateManual(1),
            stopScanFreqStateExcept(2)
        }
        MAX-ACCESS accessible-for-notify
        STATUS current
        DESCRIPTION
            "Indicates the stop type of frequency scanning(this node used only to 320 or 3202f)."
        ::= { optixRptRtnFreqScanEndExtEvent 4 }

    -- 1.3.6.1.4.1.2011.2.25.4.40.4.10.90
    optixRtnScanTrap OBJECT IDENTIFIER ::= { optixODU 90 }

    -- 1.3.6.1.4.1.2011.2.25.4.40.4.10.90.3
    optixRtnModuScanFreqFinishTrap NOTIFICATION-TYPE
        OBJECTS{ optixRtnModuBoardID,optixRtnModuSubCardID,optixRtnModuPortID,optixRtnModuCarrierID }
        STATUS current
        DESCRIPTION
            "Indicates the finish event of frequency scanning."
        ::= { optixRtnScanTrap 3 }

    -- 1.3.6.1.4.1.2011.2.25.4.40.4.10.90.4
    optixRtnFreqScanEndTrap NOTIFICATION-TYPE
        OBJECTS{ optixRtnOduFreqScanEndIndexBid,optixRtnOduFreqScanEndIndexSubID,optixRptRtnFreqScanEndState }
        STATUS current
        DESCRIPTION
            "Indicates the finish event of frequency scanning."
        ::= { optixRtnScanTrap 4 }

    -- 1.3.6.1.4.1.2011.2.25.4.40.4.10.90.5
    optixRtnFreqScanEndExtTrap NOTIFICATION-TYPE
        OBJECTS{ optixRtnOduFreqScanEndExtIndexBid,optixRtnOduFreqScanEndExtIndexSubID,optixRtnOduFreqScanEndExtIndexPid,optixRptRtnFreqScanEndExtState }
        STATUS current
        DESCRIPTION
            "Indicates the finish event of frequency scanning(this node used only to 320 or 3202f)."
        ::= { optixRtnScanTrap 5 }

    -- 1.3.6.1.4.1.2011.2.25.4.40.4.10.100
    optixRtnOduTemplateTable OBJECT-TYPE
        SYNTAX SEQUENCE OF OptixRtnOduTemplateEntry
        MAX-ACCESS not-accessible
        STATUS current
        DESCRIPTION
            "Describes parameters of the ODU template."
        ::= { optixODU 100 }

    -- 1.3.6.1.4.1.2011.2.25.4.40.4.10.100.1
    optixRtnOduTemplateEntry OBJECT-TYPE
        SYNTAX OptixRtnOduTemplateEntry
        MAX-ACCESS not-accessible
        STATUS current
        DESCRIPTION
            "Indicates the parameter entry for the ODU template"
        INDEX{ optixRtnOduIndex1,optixRtnOduIndex2,optixRtnOduIndex3 }
        ::= { optixRtnOduTemplateTable 1 }

    OptixRtnOduTemplateEntry ::=
        SEQUENCE {
            optixRtnOduTemplate
                INTEGER
        }

    -- 1.3.6.1.4.1.2011.2.25.4.40.4.10.100.1.1
    optixRtnOduTemplate OBJECT-TYPE
        SYNTAX INTEGER
        {
            relative(0),
            absolute(1)
        }
        MAX-ACCESS read-write
        STATUS current
        DESCRIPTION
            "Indicates the template of an RF port."
        DEFVAL{ relative }
        ::= { optixRtnOduTemplateEntry 1 }

    -- 1.3.6.1.4.1.2011.2.25.4.40.4.10.105
    optixRtnOduTypeInfoTable OBJECT-TYPE
    	SYNTAX SEQUENCE OF OptixRtnOduTypeInfoEntry
	MAX-ACCESS not-accessible
	STATUS current
	DESCRIPTION
	    "Indicates the type of ODU."
	::= { optixODU 105 }

    -- 1.3.6.1.4.1.2011.2.25.4.40.4.10.105.1
    optixRtnOduTypeInfoEntry OBJECT-TYPE
    	SYNTAX OptixRtnOduTypeInfoEntry
	MAX-ACCESS not-accessible
	STATUS current
	DESCRIPTION
	    "Indicates the type of ODU."
	INDEX{ optixRtnOduIndex1,optixRtnOduIndex2,optixRtnOduIndex3 }
	::= { optixRtnOduTypeInfoTable 1 }

    OptixRtnOduTypeInfoEntry ::=
    	SEQUENCE {
	    optixRtnLinkReportOduType
		OCTET STRING,
	    optixRtnEquipOduType
		OCTET STRING
		}

    -- 1.3.6.1.4.1.2011.2.25.4.40.4.10.105.1.1
    optixRtnLinkReportOduType OBJECT-TYPE
    	SYNTAX OCTET STRING
	MAX-ACCESS read-only
	STATUS current
	DESCRIPTION
	    "Indicates the type of LinkReportODU."
	::= { optixRtnOduTypeInfoEntry 1 }

    -- 1.3.6.1.4.1.2011.2.25.4.40.4.10.105.1.2
    optixRtnEquipOduType OBJECT-TYPE
    	SYNTAX OCTET STRING
	MAX-ACCESS read-only
	STATUS current
	DESCRIPTION
	    "Indicates the type of EquipODU."
	::= { optixRtnOduTypeInfoEntry 2 }

    -- 1.3.6.1.4.1.2011.2.25.4.40.4.10.110
    optixRtnCombineTable OBJECT-TYPE
        SYNTAX SEQUENCE OF OptixRtnCombineEntry
        MAX-ACCESS not-accessible
        STATUS current
        DESCRIPTION
            "Indicates the parameters of the RFU-SD combination mode."
        ::= { optixODU 110 }

    -- 1.3.6.1.4.1.2011.2.25.4.40.4.10.110.1
    optixRtnCombineEntry OBJECT-TYPE
        SYNTAX OptixRtnCombineEntry
        MAX-ACCESS not-accessible
        STATUS current
        DESCRIPTION
            "Indicates the parameter entry for the RFU-SD combine mode."
        INDEX{ optixRtnRFUBid,optixRtnRFUSubCardId }
        ::= { optixRtnCombineTable 1 }

    OptixRtnCombineEntry ::=
        SEQUENCE {
            optixRtnCombineMode
                OPTIXRtnCombineMode,
            optixRtnCombineActualMode
                OPTIXRtnCombineMode
        }

    -- 1.3.6.1.4.1.2011.2.25.4.40.4.10.110.1.1
    optixRtnCombineMode OBJECT-TYPE
        SYNTAX OPTIXRtnCombineMode
        MAX-ACCESS read-write
        STATUS current
        DESCRIPTION
            "Indicates the RFU-SD combination mode."
        DEFVAL{ 2 }
        ::= { optixRtnCombineEntry 1 }

    -- 1.3.6.1.4.1.2011.2.25.4.40.4.10.110.1.2
    optixRtnCombineActualMode OBJECT-TYPE
        SYNTAX OPTIXRtnCombineMode
        MAX-ACCESS read-only
        STATUS current
        DESCRIPTION
            "Indicates the RFU-SD actual combination mode."
        ::= { optixRtnCombineEntry 2 }

    -- 1.3.6.1.4.1.2011.2.25.4.40.4.10.120
    optixRtnSlavePowerTable OBJECT-TYPE
        SYNTAX SEQUENCE OF OptixRtnSlavePowerEntry
        MAX-ACCESS not-accessible
        STATUS current
        DESCRIPTION
            "Indicates the parameters related to the receive power of the RFU-SD slave port."
        ::= { optixODU 120 }

    -- 1.3.6.1.4.1.2011.2.25.4.40.4.10.120.1
    optixRtnSlavePowerEntry OBJECT-TYPE
        SYNTAX OptixRtnSlavePowerEntry
        MAX-ACCESS not-accessible
        STATUS current
        DESCRIPTION
            "Indicates the entry of the power parameters of the RFU-SD slave port."
        INDEX{ optixRtnRFUBid,optixRtnRFUSubCardId }
        ::= { optixRtnSlavePowerTable 1 }

    OptixRtnSlavePowerEntry ::=
        SEQUENCE {
            optixRtnSlaveCfgToBeRxPower
                Integer32,
            optixRtnSlaveRxPowerHighTh
                Integer32,
            optixRtnSlaveRxPowerLowTh
                Integer32,
            optixRtnSlaveActualRxPower
                Integer32,
            optixRtnMainActualRxPower
                Integer32,
	    optixRtnRealRxPower
                Integer32
        }

    -- 1.3.6.1.4.1.2011.2.25.4.40.4.10.120.1.1
    optixRtnSlaveCfgToBeRxPower OBJECT-TYPE
        SYNTAX Integer32
        MAX-ACCESS read-write
        STATUS current
        DESCRIPTION
            "Indicates the power expected to be received of the RFU-SD slave port. The unit is 0.1 dBm."
        ::= { optixRtnSlavePowerEntry 1 }

    -- 1.3.6.1.4.1.2011.2.25.4.40.4.10.120.1.2
    optixRtnSlaveRxPowerHighTh OBJECT-TYPE
        SYNTAX Integer32
        MAX-ACCESS read-write
        STATUS current
        DESCRIPTION
            "Indicates the upper threshold of the receive power of the RFU-SD slave port.The unit is 0.1 dBm (signed number)."
        ::= { optixRtnSlavePowerEntry 2 }

    -- 1.3.6.1.4.1.2011.2.25.4.40.4.10.120.1.3
    optixRtnSlaveRxPowerLowTh OBJECT-TYPE
        SYNTAX Integer32
        MAX-ACCESS read-write
        STATUS current
        DESCRIPTION
            "Indicates the lower threshold of the receive power of the RFU-SD slave port.The unit is 0.1 dBm (signed number)."
        ::= { optixRtnSlavePowerEntry 3 }

    -- 1.3.6.1.4.1.2011.2.25.4.40.4.10.120.1.4
    optixRtnSlaveActualRxPower OBJECT-TYPE
        SYNTAX Integer32
        MAX-ACCESS read-only
        STATUS current
        DESCRIPTION
            "Indicates the actual receive power of the RFU-SD slave port.The unit is 0.1 dBm (signed number)."
        ::= { optixRtnSlavePowerEntry 4 }
	
	
    -- 1.3.6.1.4.1.2011.2.25.4.40.4.10.120.1.5
    optixRtnMainActualRxPower OBJECT-TYPE
        SYNTAX Integer32
        MAX-ACCESS read-only
        STATUS current
        DESCRIPTION
            "Indicates the actual receive power of the RFU-SD main port.The unit is 0.1 dBm (signed number)."
        ::= { optixRtnSlavePowerEntry 5 }
	
    -- 1.3.6.1.4.1.2011.2.25.4.40.4.10.120.1.6
    optixRtnRealRxPower OBJECT-TYPE
        SYNTAX Integer32
        MAX-ACCESS read-only
        STATUS current
        DESCRIPTION
            "Indicates the real receive power of the RFU-SD slave port.The unit is 0.1 dBm (signed number)."
        ::= { optixRtnSlavePowerEntry 6 }

    -- 1.3.6.1.4.1.2011.2.25.4.40.4.10.130
    optixRtnFiberEqualTable OBJECT-TYPE
        SYNTAX SEQUENCE OF OptixRtnFiberEqualEntry
        MAX-ACCESS not-accessible
        STATUS current
        DESCRIPTION
            "Indicates the parameters of the RFU-SD delay compensation."
        ::= { optixODU 130 }

    -- 1.3.6.1.4.1.2011.2.25.4.40.4.10.130.1
    optixRtnFiberEqualEntry OBJECT-TYPE
        SYNTAX OptixRtnFiberEqualEntry
        MAX-ACCESS not-accessible
        STATUS current
        DESCRIPTION
            "Indicates the entry of the RFU-SD delay compensation parameter."
        INDEX{ optixRtnRFUBid,optixRtnRFUSubCardId }
        ::= { optixRtnFiberEqualTable 1 }

    OptixRtnFiberEqualEntry ::=
        SEQUENCE {
            optixRtnFiberEqualState
                OPTIXRtnFiberEqualState,
            optixRtnFiberEqualValue
                Integer32
        }

    -- 1.3.6.1.4.1.2011.2.25.4.40.4.10.130.1.1
    optixRtnFiberEqualState OBJECT-TYPE
        SYNTAX OPTIXRtnFiberEqualState
        MAX-ACCESS read-write
        STATUS current
        DESCRIPTION
            "Indicates the status of the RFU-SD delay compensation."
        DEFVAL{ start }
        ::= { optixRtnFiberEqualEntry 1 }

    -- 1.3.6.1.4.1.2011.2.25.4.40.4.10.130.1.2
    optixRtnFiberEqualValue OBJECT-TYPE
        SYNTAX Integer32
        MAX-ACCESS read-only
        STATUS current
        DESCRIPTION
            "Indicates the value of the RFU-SD delay compensation."
        ::= { optixRtnFiberEqualEntry 2 }

    -- 1.3.6.1.4.1.2011.2.25.4.40.4.10.140
    optixRtnRFUFrequencyTable OBJECT-TYPE
        SYNTAX SEQUENCE OF OptixRtnRFUFrequencyEntry
        MAX-ACCESS not-accessible
        STATUS current
        DESCRIPTION
            "Indicates the parameters related to the RFU receive frequency."
        ::= { optixODU 140 }

    -- 1.3.6.1.4.1.2011.2.25.4.40.4.10.140.1
    optixRtnRFUFrequencyEntry OBJECT-TYPE
        SYNTAX OptixRtnRFUFrequencyEntry
        MAX-ACCESS not-accessible
        STATUS current
        DESCRIPTION
            "Indicates the entry of the RFU receive frequency parameter."
        INDEX{ optixRtnRFUBid,optixRtnRFUSubCardId }
        ::= { optixRtnRFUFrequencyTable 1 }

    OptixRtnRFUFrequencyEntry ::=
        SEQUENCE {
            optixRtnRFURxFreq
                Unsigned32,
            optixRtnRFUMinRxFreq
                Unsigned32,
            optixRtnRFUMaxRxFreq
                Unsigned32
        }

    -- 1.3.6.1.4.1.2011.2.25.4.40.4.10.140.1.1
    optixRtnRFURxFreq OBJECT-TYPE
        SYNTAX Unsigned32
        MAX-ACCESS read-write
        STATUS current
        DESCRIPTION
            "Indicates the receive frequency of the RFU. The unit is KHz."
        ::= { optixRtnRFUFrequencyEntry 1 }

    -- 1.3.6.1.4.1.2011.2.25.4.40.4.10.140.1.2
    optixRtnRFUMinRxFreq OBJECT-TYPE
        SYNTAX Unsigned32
        MAX-ACCESS read-only
        STATUS current
        DESCRIPTION
            "Indicates the minimum value of the working range of the RFU receive frequencies. The unit is KHz."
        ::= { optixRtnRFUFrequencyEntry 2 }

    -- 1.3.6.1.4.1.2011.2.25.4.40.4.10.140.1.3
    optixRtnRFUMaxRxFreq OBJECT-TYPE
        SYNTAX Unsigned32
        MAX-ACCESS read-only
        STATUS current
        DESCRIPTION
            "Indicates the maximum value of the working range of the RFU receive frequencies. The unit is KHz."
        ::= { optixRtnRFUFrequencyEntry 3 }

    -- 1.3.6.1.4.1.2011.2.25.4.40.4.10.150
    optixRFUTrapCommon OBJECT IDENTIFIER ::= { optixODU 150 }

    -- 1.3.6.1.4.1.2011.2.25.4.40.4.10.150.1
    optixRFUTrapEvent OBJECT IDENTIFIER ::= { optixRFUTrapCommon 1 }

    -- 1.3.6.1.4.1.2011.2.25.4.40.4.10.150.1.1
    optixRptRtnRFUBid OBJECT-TYPE
        SYNTAX Unsigned32
        MAX-ACCESS accessible-for-notify
        STATUS current
        DESCRIPTION
            "Indicates the slot ID of the RFU board."
        ::= { optixRFUTrapEvent 1 }

    -- 1.3.6.1.4.1.2011.2.25.4.40.4.10.150.1.2
    optixRptRtnRFUSubCardId OBJECT-TYPE
        SYNTAX Unsigned32
        MAX-ACCESS accessible-for-notify
        STATUS current
        DESCRIPTION
            "Indicates the slot ID of the RFU subboard."
        ::= { optixRFUTrapEvent 2 }

    -- 1.3.6.1.4.1.2011.2.25.4.40.4.10.150.1.3
    optixRptRtnFiberEqualResult OBJECT-TYPE
        SYNTAX INTEGER
        {
            success(0),
            fail(1)
        }
        MAX-ACCESS accessible-for-notify
        STATUS current
        DESCRIPTION
            "Indicates the result of the delay compensation."
        ::= { optixRFUTrapEvent 3 }

    -- 1.3.6.1.4.1.2011.2.25.4.40.4.10.150.1.4
    optixRptRtnFiberEqualValue OBJECT-TYPE
        SYNTAX Integer32
        MAX-ACCESS accessible-for-notify
        STATUS current
        DESCRIPTION
            "Indicates the value of the delay compensation."
        ::= { optixRFUTrapEvent 4 }

    -- 1.3.6.1.4.1.2011.2.25.4.40.4.10.160
    optixRtnFiberEqualTrap OBJECT IDENTIFIER ::= { optixODU 160 }

    -- 1.3.6.1.4.1.2011.2.25.4.40.4.10.160.1
    optixRtnFiberEqualResultTrap NOTIFICATION-TYPE
        OBJECTS{ optixRptRtnRFUBid,optixRptRtnRFUSubCardId,optixRptRtnFiberEqualResult,optixRptRtnFiberEqualValue }
        STATUS current
        DESCRIPTION
            "Indicates the result of the delay compensation."
        ::= { optixRtnFiberEqualTrap 1 }

    -- 1.3.6.1.4.1.2011.2.25.4.40.4.10.170
    optixRtnRfuIndexTable OBJECT-TYPE
        SYNTAX SEQUENCE OF OptixRtnRfuIndexEntry
        MAX-ACCESS not-accessible
        STATUS current
        DESCRIPTION
            "Serves as the public index table for attribute tables related to an RFU."
        ::= { optixODU 170 }

    -- 1.3.6.1.4.1.2011.2.25.4.40.4.10.170.1
    optixRtnRfuIndexEntry OBJECT-TYPE
        SYNTAX OptixRtnRfuIndexEntry
        MAX-ACCESS not-accessible
        STATUS current
        DESCRIPTION
            "Indicates the index entry for an RFU."
        INDEX{ optixRtnRFUBid,optixRtnRFUSubCardId }
        ::= { optixRtnRfuIndexTable 1 }

    OptixRtnRfuIndexEntry ::=
        SEQUENCE {
            optixRtnRFUBid
                Unsigned32,
            optixRtnRFUSubCardId
                Unsigned32
        }

    -- 1.3.6.1.4.1.2011.2.25.4.40.4.10.170.1.1
    optixRtnRFUBid OBJECT-TYPE
        SYNTAX Unsigned32
        MAX-ACCESS not-accessible
        STATUS current
        DESCRIPTION
            "Indicates the RFU board ID."
        ::= { optixRtnRfuIndexEntry 1 }

    -- 1.3.6.1.4.1.2011.2.25.4.40.4.10.170.1.2
    optixRtnRFUSubCardId OBJECT-TYPE
        SYNTAX Unsigned32
        MAX-ACCESS not-accessible
        STATUS current
        DESCRIPTION
            "Indicates the subboard ID."
        ::= { optixRtnRfuIndexEntry 2 }

    -- 1.3.6.1.4.1.2011.2.25.4.40.4.10.190
    optixRtnFlapLinkDownTable OBJECT-TYPE
		SYNTAX SEQUENCE OF OptixRtnFlapLinkDownEntry
	MAX-ACCESS not-accessible
        STATUS current
        DESCRIPTION
            "Indicates the flapping-linkdown state."
        ::= { optixODU 190}
		
    -- 1.3.6.1.4.1.2011.2.25.4.40.4.10.190.1
    optixRtnFlapLinkDownEntry OBJECT-TYPE
        SYNTAX OptixRtnFlapLinkDownEntry
        MAX-ACCESS not-accessible
        STATUS current
        DESCRIPTION
            "Indicates the flapping-linkdown state."
        INDEX{ optixRtnOduIndex1,optixRtnOduIndex2,optixRtnOduIndex3 }
        ::= { optixRtnFlapLinkDownTable 1 }
		
    OptixRtnFlapLinkDownEntry ::=
    	SEQUENCE {
	    optixRtnOduFlapLinkDownStatus
	    	Unsigned32,
	    optixRtnOduFlapLinkDownChecktime
	    	Unsigned32,
	    optixRtnOduFlapLinkDownFrequency
	    	Unsigned32,
	    optixRtnOduFlapLinkRecoveryTime	
		Unsigned32
		}
		
    -- 1.3.6.1.4.1.2011.2.25.4.40.4.10.190.1.1
    optixRtnOduFlapLinkDownStatus OBJECT-TYPE
        SYNTAX Unsigned32
        {
            disable(0),
	    enable(1)
        }
        MAX-ACCESS read-write
        STATUS current
        DESCRIPTION
            "Indicates the flapping-linkdown status,it has two mode type:disable(0),enable(1)."
        ::= { optixRtnFlapLinkDownEntry 1 }
		
    -- 1.3.6.1.4.1.2011.2.25.4.40.4.10.190.1.2
    optixRtnOduFlapLinkDownChecktime OBJECT-TYPE
        SYNTAX Unsigned32
        MAX-ACCESS read-write
        STATUS current
        DESCRIPTION
            "Indicates the check time of flapping-linkdown,enable:30~180,disable:0.Unit:second."
        ::= { optixRtnFlapLinkDownEntry 2 }	
	
    -- 1.3.6.1.4.1.2011.2.25.4.40.4.10.190.1.3
    optixRtnOduFlapLinkDownFrequency OBJECT-TYPE
        SYNTAX Unsigned32
        MAX-ACCESS read-write
        STATUS current
        DESCRIPTION
            "Indicates the freqency of turnning off threshold, enable:3~30,disable:0."
        ::= { optixRtnFlapLinkDownEntry 3 }		

    -- 1.3.6.1.4.1.2011.2.25.4.40.4.10.190.1.4
    optixRtnOduFlapLinkRecoveryTime OBJECT-TYPE
        SYNTAX Unsigned32
        MAX-ACCESS read-write
        STATUS current
        DESCRIPTION
            "Indicates the recoveryTime of flapping-linkdown, enable:0~30,0 represents not automatically recovery,disable:0.Unit:minute."
        ::= { optixRtnFlapLinkDownEntry 4 }		

    -- 1.3.6.1.4.1.2011.2.25.4.40.4.10.108
    optixRtnOduInfoExtTable OBJECT-TYPE
        SYNTAX SEQUENCE OF OptixRtnOduInfoExtEntry
        MAX-ACCESS not-accessible
        STATUS current
        DESCRIPTION
            "Describes ODU information."
        ::= { optixODU 108}

    -- 1.3.6.1.4.1.2011.2.25.4.40.4.10.108.1
    optixRtnOduInfoExtEntry OBJECT-TYPE
        SYNTAX OptixRtnOduInfoExtEntry
        MAX-ACCESS not-accessible
        STATUS current
        DESCRIPTION
            "Indicates an ODU information entry."
        INDEX{ optixRtnOduIndex1,optixRtnOduIndex2 }
        ::= { optixRtnOduInfoExtTable 1 }

    OptixRtnOduInfoExtEntry ::=
        SEQUENCE {
            optixRtnOduFreqBandExt
                Unsigned32,
            optixRtnOduDeviceTypeExt
                OCTET STRING,
            optixRtnOduTRSpacingExt
                Unsigned32,
            optixRtnOduIFBandWidthExt
                Unsigned32,
            optixRtnOduIFBandWidthTypeExt
                INTEGER,
            optixRtnOduHighorLowStationExt
                INTEGER,
            optixRtnOduPowerTypeExt
                INTEGER,
            optixRtnOduFactoryCodeExt
                Unsigned32,
            optixRtnOduProducedYearExt
                Unsigned32,
            optixRtnOduProducedMonthExt
                Unsigned32,
            optixRtnOduSNCodeExt
                Unsigned32
        }

    -- 1.3.6.1.4.1.2011.2.25.4.40.4.10.108.1.1
    optixRtnOduFreqBandExt OBJECT-TYPE
        SYNTAX Unsigned32
        MAX-ACCESS read-only
        STATUS current
        DESCRIPTION
            "Indicates the frequency band, expressed in GHz."
        ::= { optixRtnOduInfoExtEntry 1 }

    -- 1.3.6.1.4.1.2011.2.25.4.40.4.10.108.1.2
    optixRtnOduDeviceTypeExt OBJECT-TYPE
        SYNTAX OCTET STRING
        MAX-ACCESS read-only
        STATUS current
        DESCRIPTION
            "Indicates the ODU device type:
sdh(Use only 360 or 380 or 380H or 380hn or 380a or 380ax)
highCapacity
pdh(Use only 360 or 380 or 380H or 380hn or 380a or 380ax)
lowCapacity
rfu
rfuSd
xmc3
xmc3w
xmc3h
xmc5d
xmc3e"
        ::= { optixRtnOduInfoExtEntry 2 }

    -- 1.3.6.1.4.1.2011.2.25.4.40.4.10.108.1.3
    optixRtnOduTRSpacingExt OBJECT-TYPE
        SYNTAX Unsigned32
        MAX-ACCESS read-only
        STATUS current
        DESCRIPTION
            "Indicates the T/R spacing, expressed in kHz."
        ::= { optixRtnOduInfoExtEntry 3 }

    -- 1.3.6.1.4.1.2011.2.25.4.40.4.10.108.1.4
    optixRtnOduIFBandWidthExt OBJECT-TYPE
        SYNTAX Unsigned32
	{
		bw7(7),
		bw14(14),
		bw28(28),
		bw40(40),
		bw56(56),
		bw112(112),           
		bw250(150),
		bw500(151),
		bw750(152),
		bw125(153),
		bw62p5(154),
		bw200(155),
		bw1000(156),
		bw1500(157),
		bw2000(158)
	}
        MAX-ACCESS read-only
        STATUS current
        DESCRIPTION
            "Indicates the supported IF bandwidth. 
If the value is between 0 and 149, it indicates the actual bandwidth in the unit of MHz.
If the value is between 150 and 255, it indicates a mapping index. You need calculate the actual bandwidth using the mapping index. For details about the mapping index, see the remarks."
        ::= { optixRtnOduInfoExtEntry 4 }

    -- 1.3.6.1.4.1.2011.2.25.4.40.4.10.108.1.5
    optixRtnOduIFBandWidthTypeExt OBJECT-TYPE
        SYNTAX INTEGER
        {
            fixed(0),
            max(1),
            zero(-1)
        }
        MAX-ACCESS read-only
        STATUS current
        DESCRIPTION
            "Indicates whether the supported IF bandwidth is variable. The values are as follows: 
0: fixed
1: variable"
        ::= { optixRtnOduInfoExtEntry 5 }

    -- 1.3.6.1.4.1.2011.2.25.4.40.4.10.108.1.6
    optixRtnOduHighorLowStationExt OBJECT-TYPE
        SYNTAX INTEGER
        {
            txLow(5),
            txHigh(10),
	    zero(0)
        }
        MAX-ACCESS read-only
        STATUS current
        DESCRIPTION
            "Indicates whether a station is high or low station.
5: Tx-Low (low station)
10: Tx-High (high station)
0: undifferentiated"
        ::= { optixRtnOduInfoExtEntry 6 }

    -- 1.3.6.1.4.1.2011.2.25.4.40.4.10.108.1.7
    optixRtnOduPowerTypeExt OBJECT-TYPE
        SYNTAX INTEGER
        {
            standard(5),
            high(10)
        }
        MAX-ACCESS read-only
        STATUS current
        DESCRIPTION
            "Indicates the transmit power type of an ODU.
5: standard output power
10: high output power"
        ::= { optixRtnOduInfoExtEntry 7 }

    -- 1.3.6.1.4.1.2011.2.25.4.40.4.10.108.1.8
    optixRtnOduFactoryCodeExt OBJECT-TYPE
        SYNTAX Unsigned32
        MAX-ACCESS read-only
        STATUS current
        DESCRIPTION
            "Indicates the vendor code."
        ::= { optixRtnOduInfoExtEntry 8 }

    -- 1.3.6.1.4.1.2011.2.25.4.40.4.10.108.1.9
    optixRtnOduProducedYearExt OBJECT-TYPE
        SYNTAX Unsigned32
        MAX-ACCESS read-only
        STATUS current
        DESCRIPTION
            "Indicates the manufacture year."
        ::= { optixRtnOduInfoExtEntry 9 }

    -- 1.3.6.1.4.1.2011.2.25.4.40.4.10.108.1.10
    optixRtnOduProducedMonthExt OBJECT-TYPE
        SYNTAX Unsigned32
        MAX-ACCESS read-only
        STATUS current
        DESCRIPTION
            "Indicates the manufacture month."
        ::= { optixRtnOduInfoExtEntry 10 }

    -- 1.3.6.1.4.1.2011.2.25.4.40.4.10.108.1.11
    optixRtnOduSNCodeExt OBJECT-TYPE
        SYNTAX Unsigned32
        MAX-ACCESS read-only
        STATUS current
        DESCRIPTION
            "Indicates the production sequence number."
        ::= { optixRtnOduInfoExtEntry 11 }

    -- 1.3.6.1.4.1.2011.2.25.4.40.4.10.109
    optixRtnOduPortInfoTable OBJECT-TYPE
        SYNTAX SEQUENCE OF OptixRtnOduPortInfoEntry
        MAX-ACCESS not-accessible
        STATUS current
        DESCRIPTION
            "Describes ODU information(this node used only to 320 or 3202f)."
        ::= { optixODU 109}

    -- 1.3.6.1.4.1.2011.2.25.4.40.4.10.109.1
    optixRtnOduPortInfoEntry OBJECT-TYPE
        SYNTAX OptixRtnOduPortInfoEntry
        MAX-ACCESS not-accessible
        STATUS current
        DESCRIPTION
            "Indicates an ODU information entry(this node used only to 320 or 3202f)."
        INDEX{ optixRtnOduIndex1,optixRtnOduIndex2,optixRtnOduIndex3 }
        ::= { optixRtnOduPortInfoTable 1 }

    OptixRtnOduPortInfoEntry ::=
        SEQUENCE {
            optixRtnOduPortFreqBand
                Unsigned32,
            optixRtnOduPortDeviceType
                OCTET STRING,
            optixRtnOduPortTRSpacing
                Unsigned32,
            optixRtnOduPortIFBandWidth
                Unsigned32,
            optixRtnOduPortIFBandWidthType
                INTEGER,
            optixRtnOduPortHighorLowStation
                INTEGER,
            optixRtnOduPortPowerType
                INTEGER,
            optixRtnOduPortFactoryCode
                Unsigned32,
            optixRtnOduPortProducedYear
                Unsigned32,
            optixRtnOduPortProducedMonth
                Unsigned32,
            optixRtnOduPortSNCode
                Unsigned32
        }

    -- 1.3.6.1.4.1.2011.2.25.4.40.4.10.109.1.1
    optixRtnOduPortFreqBand OBJECT-TYPE
        SYNTAX Unsigned32
        MAX-ACCESS read-only
        STATUS current
        DESCRIPTION
            "Indicates the frequency band, expressed in GHz(this node used only to 320 or 3202f)."
        ::= { optixRtnOduPortInfoEntry 1 }

    -- 1.3.6.1.4.1.2011.2.25.4.40.4.10.109.1.2
    optixRtnOduPortDeviceType OBJECT-TYPE
        SYNTAX OCTET STRING
        MAX-ACCESS read-only
        STATUS current
        DESCRIPTION
            "Indicates the ODU device type(this node used only to 320 or 3202f):
5-High Capacity
10-Low Capacity
13-XMC-3
14-XMC-3W
15-XMC-3H
16-XMC-5D
17-XMC-3E"
        ::= { optixRtnOduPortInfoEntry 2 }

    -- 1.3.6.1.4.1.2011.2.25.4.40.4.10.109.1.3
    optixRtnOduPortTRSpacing OBJECT-TYPE
        SYNTAX Unsigned32
        MAX-ACCESS read-only
        STATUS current
        DESCRIPTION
            "Indicates the T/R spacing, expressed in kHz(this node used only to 320 or 3202f)."
        ::= { optixRtnOduPortInfoEntry 3 }

    -- 1.3.6.1.4.1.2011.2.25.4.40.4.10.109.1.4
    optixRtnOduPortIFBandWidth OBJECT-TYPE
        SYNTAX Unsigned32
	{
		bw7(7),
		bw14(14),
		bw28(28),
		bw40(40),
		bw56(56),
		bw112(112),           
		bw250(150),
		bw500(151),
		bw750(152),
		bw125(153),
		bw62p5(154),
		bw200(155)
	}
        MAX-ACCESS read-only
        STATUS current
        DESCRIPTION
            "Indicates the supported IF bandwidth(this node used only to 320 or 3202f). 
If the value is between 0 and 149, it indicates the actual bandwidth in the unit of MHz.
If the value is between 150 and 255, it indicates a mapping index. You need calculate the actual bandwidth using the mapping index. For details about the mapping index, see the remarks."
        ::= { optixRtnOduPortInfoEntry 4 }

    -- 1.3.6.1.4.1.2011.2.25.4.40.4.10.109.1.5
    optixRtnOduPortIFBandWidthType OBJECT-TYPE
        SYNTAX INTEGER
        {
            fixed(0),
            max(1),
            zero(-1)
        }
        MAX-ACCESS read-only
        STATUS current
        DESCRIPTION
            "Indicates whether the supported IF bandwidth is variable(this node used only to 320 or 3202f). The values are as follows: 
0: fixed
1: variable"
        ::= { optixRtnOduPortInfoEntry 5 }

    -- 1.3.6.1.4.1.2011.2.25.4.40.4.10.109.1.6
    optixRtnOduPortHighorLowStation OBJECT-TYPE
        SYNTAX INTEGER
        {
            txLow(5),
            txHigh(10),
	    zero(0)
        }
        MAX-ACCESS read-only
        STATUS current
        DESCRIPTION
            "Indicates whether a station is high or low station(this node used only to 320 or 3202f).
5: Tx-Low (low station)
10: Tx-High (high station)
0: undifferentiated"
        ::= { optixRtnOduPortInfoEntry 6 }

    -- 1.3.6.1.4.1.2011.2.25.4.40.4.10.109.1.7
    optixRtnOduPortPowerType OBJECT-TYPE
        SYNTAX INTEGER
        {
            standard(5),
            high(10)
        }
        MAX-ACCESS read-only
        STATUS current
        DESCRIPTION
            "Indicates the transmit power type of an ODU(this node used only to 320 or 3202f).
5: standard output power
10: high output power"
        ::= { optixRtnOduPortInfoEntry 7 }

    -- 1.3.6.1.4.1.2011.2.25.4.40.4.10.109.1.8
    optixRtnOduPortFactoryCode OBJECT-TYPE
        SYNTAX Unsigned32
        MAX-ACCESS read-only
        STATUS current
        DESCRIPTION
            "Indicates the vendor code(this node used only to 320 or 3202f)."
        ::= { optixRtnOduPortInfoEntry 8 }

    -- 1.3.6.1.4.1.2011.2.25.4.40.4.10.109.1.9
    optixRtnOduPortProducedYear OBJECT-TYPE
        SYNTAX Unsigned32
        MAX-ACCESS read-only
        STATUS current
        DESCRIPTION
            "Indicates the manufacture year(this node used only to 320 or 3202f)."
        ::= { optixRtnOduPortInfoEntry 9 }

    -- 1.3.6.1.4.1.2011.2.25.4.40.4.10.109.1.10
    optixRtnOduPortProducedMonth OBJECT-TYPE
        SYNTAX Unsigned32
        MAX-ACCESS read-only
        STATUS current
        DESCRIPTION
            "Indicates the manufacture month(this node used only to 320 or 3202f)."
        ::= { optixRtnOduPortInfoEntry 10 }

    -- 1.3.6.1.4.1.2011.2.25.4.40.4.10.109.1.11
    optixRtnOduPortSNCode OBJECT-TYPE
        SYNTAX Unsigned32
        MAX-ACCESS read-only
        STATUS current
        DESCRIPTION
            "Indicates the production sequence number(this node used only to 320 or 3202f)."
        ::= { optixRtnOduPortInfoEntry 11 }


    -- 1.3.6.1.4.1.2011.2.25.4.40.4.10.102
    optixRtnIFModuTable OBJECT-TYPE
        SYNTAX SEQUENCE OF OptixRtnIFModuEntry
        MAX-ACCESS not-accessible
        STATUS current
        DESCRIPTION
            "Indicates the table of general attributes of an MODU."
        ::= { optixODU 102 }

    -- 1.3.6.1.4.1.2011.2.25.4.40.4.10.102.1
    optixRtnIFModuEntry OBJECT-TYPE
        SYNTAX OptixRtnIFModuEntry
        MAX-ACCESS not-accessible
        STATUS current
        DESCRIPTION
            "Indicates an entry of general attributes of an MODU."
        INDEX{ optixRtnOduIndex1,optixRtnOduIndex2,optixRtnOduIndex3 }
        ::= { optixRtnIFModuTable 1 }

    OptixRtnIFModuEntry ::=
        SEQUENCE {
            optixRtnModuLoop
                INTEGER,
            optixRtnModuFreqBand
                Unsigned32,
            optixRtnModuDeviceType
                INTEGER,
            optixRtnModuInfoTRSpacing
                Unsigned32,
            optixRtnModuBandWidth
                Unsigned32,
            optixRtnModuBandWidthType
                INTEGER,
            optixRtnModuHLStation
                INTEGER,
            optixRtnModuPowerType
                INTEGER,
            optixRtnModuFactoryCode
                Unsigned32,
            optixRtnModuProducedYear
                Unsigned32,
            optixRtnModuProducedMonth
                Unsigned32,
            optixRtnModuSNCode
                Unsigned32
        }

    -- 1.3.6.1.4.1.2011.2.25.4.40.4.10.102.1.4
    optixRtnModuLoop OBJECT-TYPE
        SYNTAX INTEGER
        {
            noloop(0),
            inloop(1)
        }
        MAX-ACCESS read-write
        STATUS current
        DESCRIPTION
            "Indicates the loop mode:
        0:no loop
        1:in loop"
        ::= { optixRtnIFModuEntry 4 }

    -- 1.3.6.1.4.1.2011.2.25.4.40.4.10.102.1.5
    optixRtnModuFreqBand OBJECT-TYPE
        SYNTAX Unsigned32
        MAX-ACCESS read-only
        STATUS current
        DESCRIPTION
        "Indicates the frequency band, expressed in GHz."
        ::= { optixRtnIFModuEntry 5 }

    -- 1.3.6.1.4.1.2011.2.25.4.40.4.10.102.1.6
    optixRtnModuDeviceType OBJECT-TYPE
        SYNTAX INTEGER
        {
            lowcapacity(10),
            highcapacity(5),
            rfu(11),
            rfu-sd(12), 
            xmc3(13),   
            xmc3w(14),  
            xmc3h(15),  
            xmc5d(16)
        }
        MAX-ACCESS read-only
        STATUS current
        DESCRIPTION
            "Indicates the MODU device type:
                10-Low Capacity
                5-High Capacity
                11-RFU
                12-RFU-SD
                13-XMC-3
                14-XMC-3W
                15-XMC-3H
                16-XMC-5D"
        ::= { optixRtnIFModuEntry 6 }	

    -- 1.3.6.1.4.1.2011.2.25.4.40.4.10.102.1.7
    optixRtnModuInfoTRSpacing OBJECT-TYPE
        SYNTAX Unsigned32
        MAX-ACCESS read-only
        STATUS current
        DESCRIPTION
        "Indicates the T/R spacing, expressed in kHz."
        ::= { optixRtnIFModuEntry 7 }

    -- 1.3.6.1.4.1.2011.2.25.4.40.4.10.102.1.8
    optixRtnModuBandWidth OBJECT-TYPE
    SYNTAX Unsigned32
    {
        bw7(7),
        bw14(14),
        bw28(28),
        bw40(40),
        bw56(56),
        bw112(112),
        bw250(150),
        bw500(151),
        bw750(152),
        bw125(153),
        bw62p5(154),
        bw200(155)
    }
        MAX-ACCESS read-only
        STATUS current
        DESCRIPTION
           "Indicates the supported IF bandwidth. 
If the value is between 0 and 149, it indicates the actual bandwidth in the unit of MHz.
If the value is between 150 and 255, it indicates a mapping index. You need calculate the actual bandwidth using the mapping index. For details about the mapping index, see the remarks."
        ::= { optixRtnIFModuEntry 8 }	

    -- 1.3.6.1.4.1.2011.2.25.4.40.4.10.102.1.9
    optixRtnModuBandWidthType OBJECT-TYPE
        SYNTAX INTEGER
        {
            max(1),
            fixed(0), 
            zero(-1)
        }
        MAX-ACCESS read-only
        STATUS current
        DESCRIPTION
        "Indicates whether the supported IF bandwidth is variable. The values are as follows: 
            0: fixed
            1: variable"
        ::= { optixRtnIFModuEntry 9 }	

    -- 1.3.6.1.4.1.2011.2.25.4.40.4.10.102.1.10
    optixRtnModuHLStation OBJECT-TYPE
        SYNTAX INTEGER
        {
            txLow(5),
            txHigh(10),
            zero(0)
        }
        MAX-ACCESS read-only
        STATUS current
        DESCRIPTION
        "Indicates whether a station is high or low station.
            5: Tx-Low (low station)
            10: Tx-High (high station)
            0: undifferentiated"
        ::= { optixRtnIFModuEntry 10 }

    -- 1.3.6.1.4.1.2011.2.25.4.40.4.10.102.1.11
    optixRtnModuPowerType OBJECT-TYPE
        SYNTAX INTEGER
        {
            standard(5),
            high(10)
        }
        MAX-ACCESS read-only
        STATUS current
        DESCRIPTION
            "Indicates the transmit power type of the MODU.
5: standard output power
10: high output power"
        ::= { optixRtnIFModuEntry 11 }	

    -- 1.3.6.1.4.1.2011.2.25.4.40.4.10.102.1.12
    optixRtnModuFactoryCode OBJECT-TYPE
        SYNTAX Unsigned32
        MAX-ACCESS read-only
        STATUS current
        DESCRIPTION
        "Indicates the vendor code."
        ::= { optixRtnIFModuEntry 12 }

    -- 1.3.6.1.4.1.2011.2.25.4.40.4.10.102.1.13
    optixRtnModuProducedYear OBJECT-TYPE
        SYNTAX Unsigned32
        MAX-ACCESS read-only
        STATUS current
        DESCRIPTION
            "Indicates the manufacture year."
        ::= { optixRtnIFModuEntry 13 }	

    -- 1.3.6.1.4.1.2011.2.25.4.40.4.10.102.1.14
    optixRtnModuProducedMonth OBJECT-TYPE
        SYNTAX Unsigned32
        MAX-ACCESS read-only
        STATUS current
        DESCRIPTION
            "Indicates the manufacture month."
        ::= { optixRtnIFModuEntry 14 }	

    -- 1.3.6.1.4.1.2011.2.25.4.40.4.10.102.1.15
    optixRtnModuSNCode OBJECT-TYPE
        SYNTAX Unsigned32
        MAX-ACCESS read-only
        STATUS current
        DESCRIPTION
            "Indicates the production sequence number."
        ::= { optixRtnIFModuEntry 15 }

    -- 1.3.6.1.4.1.2011.2.25.4.40.4.10.103
    optixRtnModuTable OBJECT-TYPE
        SYNTAX SEQUENCE OF OptixRtnModuEntry
        MAX-ACCESS not-accessible
        STATUS current
        DESCRIPTION
            "Describes parameters of the MODU."
        ::= { optixODU 103 }

    -- 1.3.6.1.4.1.2011.2.25.4.40.4.10.103.1
    optixRtnModuEntry OBJECT-TYPE
        SYNTAX OptixRtnModuEntry
        MAX-ACCESS not-accessible
        STATUS current
        DESCRIPTION
            "Indicates the parameter entry for the MODU."
        INDEX{ optixRtnOduIndex1,optixRtnOduIndex2,optixRtnOduIndex3,optixRtnOduIndex4 }
        ::= { optixRtnModuTable 1 }

    OptixRtnModuEntry ::=
        SEQUENCE {
            optixRtnModuSrPower
                INTEGER,
            optixRtnModuMaxPower
                INTEGER,
            optixRtnModuTxPower
                INTEGER,
            optixRtnModuWorkState
                INTEGER,
            optixRtnModuTRSpacing
                Unsigned32,
            optixRtnModuTxFreq
                Unsigned32,	
            optixRtnModuRxPowerHighTh
                Integer32,
            optixRtnModuRxPowerLowTH
                Integer32,
            optixRtnModuTxPowerHighTh
                Integer32,
            optixRtnModuTxPowerLowTH
                Integer32,
            optixRtnModuMinTxPower
                Integer32,
            optixRtnModuMaxTxPower
                Integer32,
            optixRtnModuMinTxFreq
                Unsigned32,
            optixRtnModuMaxTxFreq
                Unsigned32,	
            optixRtnModuMute
                INTEGER,
            optixRtnModuRealTxFreq
                Unsigned32,	
            optixRtnModuRealRxFreq
                Unsigned32,	
            optixRtnModuRealCfgPower
                INTEGER,
            optixRtnModuRealTxPower
                INTEGER,
            optixRtnModuRealRxPower
                INTEGER,
            optixRtnModuRealTRSpacing
                Unsigned32,
            optixRtnModuWorkWithFm
                INTEGER,
            optixRtnModuFmTxPower                
                INTEGER,
            optixRtnModuAMTslRange
                OCTET STRING,
            optixRtnModuFadeMargin
                INTEGER   
        }
    -- 1.3.6.1.4.1.2011.2.25.4.40.4.10.103.1.5
        optixRtnModuSrPower OBJECT-TYPE
        SYNTAX INTEGER
        MAX-ACCESS read-write
        STATUS current
        DESCRIPTION
            "Indicates the transmit power of an RF port. Signed type Value range: -100 to +350 Unit: 0.1 dBm"
        ::= { optixRtnModuEntry 5 }	

    -- 1.3.6.1.4.1.2011.2.25.4.40.4.10.103.1.6
    optixRtnModuMaxPower OBJECT-TYPE
        SYNTAX INTEGER
        MAX-ACCESS read-write
        STATUS current
        DESCRIPTION
            "Indicates the transmit power of an RF port. Signed type Value range: -100 to +350 Unit: 0.1 dBm"
        ::= { optixRtnModuEntry 6 }	

    -- 1.3.6.1.4.1.2011.2.25.4.40.4.10.103.1.7
    optixRtnModuTxPower OBJECT-TYPE
        SYNTAX INTEGER
        MAX-ACCESS read-write
        STATUS current
        DESCRIPTION
            "Indicates the transmit power of an RF port. Signed type Value range: -100 to +350 Unit: 0.1 dBm"
        ::= { optixRtnModuEntry 7 }	

    -- 1.3.6.1.4.1.2011.2.25.4.40.4.10.103.1.8
    optixRtnModuWorkState OBJECT-TYPE
        SYNTAX INTEGER
        {
            mute(0),
            unmute(1)
        }
        MAX-ACCESS read-write
        STATUS current
        DESCRIPTION
            "Indicates the transmission actual status of an RF transmitter. Values: 0: muted 1: unmuted"
        ::= { optixRtnModuEntry 8 }

    -- 1.3.6.1.4.1.2011.2.25.4.40.4.10.103.1.9
    optixRtnModuTRSpacing OBJECT-TYPE
        SYNTAX Unsigned32
        MAX-ACCESS read-write
        STATUS current
        DESCRIPTION
            "Indicates the TR spacing of an RF unit board to avoid interference. Unit: kHz"
        ::= { optixRtnModuEntry 9 }	

    -- 1.3.6.1.4.1.2011.2.25.4.40.4.10.103.1.10
    optixRtnModuTxFreq OBJECT-TYPE
        SYNTAX Unsigned32
        MAX-ACCESS read-write
        STATUS current
        DESCRIPTION
            "Indicates the actual transmit frequency of an RF unit. Unit: kHz"
        ::= { optixRtnModuEntry 10 }

    -- 1.3.6.1.4.1.2011.2.25.4.40.4.10.103.1.11
    optixRtnModuRxPowerHighTh OBJECT-TYPE
        SYNTAX Integer32
        MAX-ACCESS read-write
        STATUS current
        DESCRIPTION
            "Indicates the upper threshold of the receive power. Signed type The value range: -900 to -200 Unit: 0.1 dBm"
        ::= { optixRtnModuEntry 11 }

    -- 1.3.6.1.4.1.2011.2.25.4.40.4.10.103.1.12
    optixRtnModuRxPowerLowTH OBJECT-TYPE
        SYNTAX Integer32
        MAX-ACCESS read-write
        STATUS current
        DESCRIPTION
            "Indicates the lower threshold of the receive power. Signed type The value range: -900 to -200 Unit: 0.1 dBm"
        ::= { optixRtnModuEntry 12 }

    -- 1.3.6.1.4.1.2011.2.25.4.40.4.10.103.1.13
    optixRtnModuTxPowerHighTh OBJECT-TYPE
        SYNTAX Integer32
        MAX-ACCESS read-write
        STATUS current
        DESCRIPTION
            "Indicates the upper threshold of the transmit power. Signed type Unit: 0.1 dBm"
        ::= { optixRtnModuEntry 13 }

    -- 1.3.6.1.4.1.2011.2.25.4.40.4.10.103.1.14
    optixRtnModuTxPowerLowTH OBJECT-TYPE
        SYNTAX Integer32
        MAX-ACCESS read-write
        STATUS current
        DESCRIPTION
            "Indicates the upper threshold of the transmit power. Signed type Unit: 0.1 dBm"
        ::= { optixRtnModuEntry 14 }

    -- 1.3.6.1.4.1.2011.2.25.4.40.4.10.103.1.15
    optixRtnModuMinTxPower OBJECT-TYPE 
        SYNTAX Integer32
        MAX-ACCESS read-only
        STATUS current
        DESCRIPTION
            "Indicates the Lower threshold of the transmit power. Signed type The value range: -100 to +350 Unit: 0.1 dBm"
        ::= { optixRtnModuEntry 15 }

    -- 1.3.6.1.4.1.2011.2.25.4.40.4.10.103.1.16
    optixRtnModuMaxTxPower OBJECT-TYPE 
        SYNTAX Integer32
        MAX-ACCESS read-only
        STATUS current
        DESCRIPTION
            "Indicates the upper threshold of the transmit power. Signed type The value range: -100 to +350 Unit: 0.1 dBm"
        ::= { optixRtnModuEntry 16 }

    -- 1.3.6.1.4.1.2011.2.25.4.40.4.10.103.1.17
    optixRtnModuMinTxFreq OBJECT-TYPE
        SYNTAX Unsigned32
        MAX-ACCESS read-only
        STATUS current
        DESCRIPTION
            "Indicates the minimum transmit frequency of a RF unit. Unit: KHz"
        ::= { optixRtnModuEntry 17 }

    -- 1.3.6.1.4.1.2011.2.25.4.40.4.10.103.1.18
    optixRtnModuMaxTxFreq OBJECT-TYPE
        SYNTAX Unsigned32
        MAX-ACCESS read-only
        STATUS current
        DESCRIPTION
            "Indicates the maximum transmit frequency of a RF unit. Unit: KHz"
        ::= { optixRtnModuEntry 18 }

    -- 1.3.6.1.4.1.2011.2.25.4.40.4.10.103.1.19
    optixRtnModuMute OBJECT-TYPE
        SYNTAX INTEGER
        {
            mute(0),
            unmute(1)
        }
        MAX-ACCESS read-only
        STATUS current
        DESCRIPTION
            "Indicates the working status of RF unit. Values: 0: muted 1: unmuted"
        ::= { optixRtnModuEntry 19 }

    -- 1.3.6.1.4.1.2011.2.25.4.40.4.10.103.1.20
    optixRtnModuRealTxFreq OBJECT-TYPE
        SYNTAX Unsigned32
        MAX-ACCESS read-only
        STATUS current
        DESCRIPTION
           "Indicates the actual real transmit frequency of an RF unit. Unit: kHz"
        ::= { optixRtnModuEntry 20 }

    -- 1.3.6.1.4.1.2011.2.25.4.40.4.10.103.1.21
    optixRtnModuRealRxFreq OBJECT-TYPE
        SYNTAX Unsigned32
        MAX-ACCESS read-only
        STATUS current
        DESCRIPTION
           "Indicates the actual receive frequency of an RF unit. Unit: kHz"
        ::= { optixRtnModuEntry 21 }

    -- 1.3.6.1.4.1.2011.2.25.4.40.4.10.103.1.22
    optixRtnModuRealCfgPower OBJECT-TYPE
        SYNTAX INTEGER
        MAX-ACCESS read-only
        STATUS current
        DESCRIPTION
        "Indicates the real configure power of the RF unit.The unit is 0.1 dBm (signed number)."
        ::= { optixRtnModuEntry 22 }

    -- 1.3.6.1.4.1.2011.2.25.4.40.4.10.103.1.23
    optixRtnModuRealTxPower OBJECT-TYPE
        SYNTAX INTEGER
        MAX-ACCESS read-only
        STATUS current
        DESCRIPTION
        "Indicates the real transmit power of the RF unit.The unit is 0.1 dBm (signed number)."
        ::= { optixRtnModuEntry 23 }

    -- 1.3.6.1.4.1.2011.2.25.4.40.4.10.103.1.24
    optixRtnModuRealRxPower OBJECT-TYPE
        SYNTAX INTEGER
        MAX-ACCESS read-only
        STATUS current
        DESCRIPTION
        "Indicates the real receive power of the RF unit.The unit is 0.1 dBm (signed number)."
        ::= { optixRtnModuEntry 24 }

    -- 1.3.6.1.4.1.2011.2.25.4.40.4.10.103.1.25
    optixRtnModuRealTRSpacing OBJECT-TYPE
        SYNTAX Unsigned32
        MAX-ACCESS read-only
        STATUS current
        DESCRIPTION
            "Indicates the real TR spacing of an RF unit. Unit: kHz"
        ::= { optixRtnModuEntry 25 }

    -- 1.3.6.1.4.1.2011.2.25.4.40.4.10.103.1.26
    optixRtnModuFmTxPower OBJECT-TYPE
        SYNTAX INTEGER
        MAX-ACCESS read-write
        STATUS current
        DESCRIPTION
            "Indicates the transmit power of an FM.The unit is 0.1 dBm (signed number)."
        ::= { optixRtnModuEntry 26 }
        
    -- 1.3.6.1.4.1.2011.2.25.4.40.4.10.103.1.27
    optixRtnModuWorkWithFm OBJECT-TYPE
        SYNTAX INTEGER
        {
            mute(0),
            unmute(1)
        }
        MAX-ACCESS read-write
        STATUS current
        DESCRIPTION
            "Indicates the MODU work status."
        ::= { optixRtnModuEntry 27 }
        
    -- 1.3.6.1.4.1.2011.2.25.4.40.4.10.103.1.28
    optixRtnModuAMTslRange OBJECT-TYPE
        SYNTAX OCTET STRING
        MAX-ACCESS read-only
        STATUS current
        DESCRIPTION
            "Indicates the MODU AM transmit power range."
        ::= { optixRtnModuEntry 28 }

    -- 1.3.6.1.4.1.2011.2.25.4.40.4.10.103.1.29
        optixRtnModuFadeMargin OBJECT-TYPE
        SYNTAX INTEGER
        MAX-ACCESS read-write
        STATUS current
        DESCRIPTION
            "Indicates the MODU FadeMargin."
        ::= { optixRtnModuEntry 29 }
	
    -- 1.3.6.1.4.1.2011.2.25.4.40.4.10.107
    optixRtnOduResetTable OBJECT-TYPE
        SYNTAX SEQUENCE OF OptixRtnOduResetEntry
        MAX-ACCESS not-accessible
        STATUS current
        DESCRIPTION
            "Indicates the table for setting the ODU reset mode(this node used only to 320 or 3202f)."
        ::= { optixODU 107 }

    -- 1.3.6.1.4.1.2011.2.25.4.40.4.10.107.1
    optixRtnOduResetEntry OBJECT-TYPE
        SYNTAX OptixRtnOduResetEntry
        MAX-ACCESS not-accessible
        STATUS current
        DESCRIPTION
            "Indicates an entry for setting the ODU reset mode(this node used only to 320 or 3202f)."
        INDEX{ optixRtnOduIndex1,optixRtnOduIndex2,optixRtnOduIndex3 }
        ::= { optixRtnOduResetTable 1 }

    OptixRtnOduResetEntry ::=
        SEQUENCE {
            optixRtnOduResetType
                INTEGER
        }

    -- 1.3.6.1.4.1.2011.2.25.4.40.4.10.107.1.2
    optixRtnOduResetType OBJECT-TYPE
        SYNTAX INTEGER
        {
            hard(0),
            soft(1)
        }
        MAX-ACCESS read-write
        STATUS current
        DESCRIPTION
            "Indicates the ODU reset mode(this node used only to 320 or 3202f)."
        ::= { optixRtnOduResetEntry 2 }

    -- 1.3.6.1.4.1.2011.2.25.4.40.4.10.115
    optixRtnModuRFUFreqTable OBJECT-TYPE
        SYNTAX SEQUENCE OF OptixRtnModuRFUFreqEntry
        MAX-ACCESS not-accessible
        STATUS current
        DESCRIPTION
            "Indecates the parameters related to the RFU receive frequency of the MODU."
        ::= { optixODU 115 }

    -- 1.3.6.1.4.1.2011.2.25.4.40.4.10.115.1
    optixRtnModuRFUFreqEntry OBJECT-TYPE
        SYNTAX OptixRtnModuRFUFreqEntry
        MAX-ACCESS not-accessible
        STATUS current
        DESCRIPTION
            "Indicates the entry of the RFU receive frequency parameter of the MODU."
        INDEX{ optixRtnOduIndex1,optixRtnOduIndex2,optixRtnOduIndex3,optixRtnOduIndex4 }
        ::= { optixRtnModuRFUFreqTable 1 }
    
    OptixRtnModuRFUFreqEntry ::=
        SEQUENCE {
            optixRtnModuRFURxFreq
                Unsigned32,
            optixRtnModuRFUMinRxFreq
                Unsigned32,
            optixRtnModuRFUMaxRxFreq
                Unsigned32
        }
    
    -- 1.3.6.1.4.1.2011.2.25.4.40.4.10.115.1.5
    optixRtnModuRFURxFreq OBJECT-TYPE
        SYNTAX Unsigned32
        MAX-ACCESS read-write
        STATUS current
        DESCRIPTION
            "Indicates the RFU receive frequence of the MODU. The unit is kHz."
        ::= { optixRtnModuRFUFreqEntry 5 }
    
    -- 1.3.6.1.4.1.2011.2.25.4.40.4.10.115.1.6
    optixRtnModuRFUMinRxFreq OBJECT-TYPE
        SYNTAX Unsigned32
        MAX-ACCESS read-only
        STATUS current
        DESCRIPTION
            "Indicates the minimun value of the working range of the RFU receive freqencies. The unit is kHz."
        ::= { optixRtnModuRFUFreqEntry 6 }

    -- 1.3.6.1.4.1.2011.2.25.4.40.4.10.115.1.7
    optixRtnModuRFUMaxRxFreq OBJECT-TYPE
        SYNTAX Unsigned32
        MAX-ACCESS read-only
        STATUS current
        DESCRIPTION
            "Indicates the maximum value of the working range of the RFU receive freqencies. The unit is kHz."
        ::= { optixRtnModuRFUFreqEntry 7 }

    -- 1.3.6.1.4.1.2011.2.25.4.40.4.10.180
    optixRtnOduDuplexInfoTable OBJECT-TYPE
        SYNTAX SEQUENCE OF OptixRtnOduDuplexInfoEntry
        MAX-ACCESS not-accessible
        STATUS current
        DESCRIPTION
            "Indicates the information of an ODU's duplexer entry"
        ::= { optixODU 180 }

    -- 1.3.6.1.4.1.2011.2.25.4.40.4.10.180.1
    optixRtnOduDuplexInfoEntry OBJECT-TYPE
        SYNTAX OptixRtnOduDuplexInfoEntry
        MAX-ACCESS not-accessible
        STATUS current
        DESCRIPTION
            "Indicates the information of an ODU's duplexer entry"
        INDEX{ optixRtnOduIndex1,optixRtnOduIndex2,optixRtnOduIndex3 }
        ::= { optixRtnOduDuplexInfoTable 1 }

    OptixRtnOduDuplexInfoEntry ::=
        SEQUENCE {
            optixRtnOduDuplexSubFrequence
                INTEGER,
            optixRtnOduDuplexTRSpacing
                Unsigned32,
            optixRtnOduDuplexFreqMin
                Unsigned32,
            optixRtnOduDuplexFreqMax
                Unsigned32
        }

    -- 1.3.6.1.4.1.2011.2.25.4.40.4.10.180.1.1
    optixRtnOduDuplexSubFrequence OBJECT-TYPE
        SYNTAX INTEGER
        {
            a(1),
            b(2),
            c(3),
            d(4),
            e(5),
            f(6),
            g(7),
            h(8),
            i(9),
            j(10),
            k(11),
            l(12),
            m(13),
            n(14),
            o(15),
            p(16),
            q(17),
            r(18),
            s(19),
            t(20),
            u(21),
            v(22),
            w(23),
            x(24),
            y(25),
            z(26)
        }
        MAX-ACCESS read-only
        STATUS current
        DESCRIPTION
            "Indicates the frequency sub-band of an ODU's duplexer."
        ::= { optixRtnOduDuplexInfoEntry 1 }

    -- 1.3.6.1.4.1.2011.2.25.4.40.4.10.180.1.2
    optixRtnOduDuplexTRSpacing OBJECT-TYPE
        SYNTAX Unsigned32
        MAX-ACCESS read-only
        STATUS current
        DESCRIPTION
            "Indicates the T/R spacing of an ODU's duplexer, expressed in kHz."
        ::= { optixRtnOduDuplexInfoEntry 2 }

    -- 1.3.6.1.4.1.2011.2.25.4.40.4.10.180.1.3
    optixRtnOduDuplexFreqMin OBJECT-TYPE
        SYNTAX Unsigned32
        MAX-ACCESS read-only
        STATUS current
        DESCRIPTION
            "Indicates the minimum frequency of an ODU's duplexer, expressed in kHz."
        ::= { optixRtnOduDuplexInfoEntry 3 }

    -- 1.3.6.1.4.1.2011.2.25.4.40.4.10.180.1.4
    optixRtnOduDuplexFreqMax OBJECT-TYPE
        SYNTAX Unsigned32
        MAX-ACCESS read-only
        STATUS current
        DESCRIPTION
            "Indicates the maximum frequency of an ODU's duplexer, expressed in kHz."
        ::= { optixRtnOduDuplexInfoEntry 4 }

    -- 1.3.6.1.4.1.2011.2.25.4.40.4.10.111
    optixRtnModuFreqScanTable OBJECT-TYPE
        SYNTAX SEQUENCE OF OptixRtnModuFreqScanEntry
        MAX-ACCESS not-accessible
        STATUS current
        DESCRIPTION
            "Describes the information about RF unit start, frequency scanning stop, and obtaining of interfering frequency."
        ::= { optixODU 111 }

    -- 1.3.6.1.4.1.2011.2.25.4.40.4.10.111.1
    optixRtnModuFreqScanEntry OBJECT-TYPE
        SYNTAX OptixRtnModuFreqScanEntry
        MAX-ACCESS not-accessible
        STATUS current
        DESCRIPTION
            "Indicates the parameter entry for RF unit frequency scanning."
        INDEX{ optixRtnOduIndex1,optixRtnOduIndex2,optixRtnOduIndex3,optixRtnOduIndex4 }
        ::= { optixRtnModuFreqScanTable 1 }

    OptixRtnModuFreqScanEntry ::=
        SEQUENCE {
            optixRtnModuStartScanStartFreq
                Unsigned32,
            optixRtnModuStartScanEndFreq
                Unsigned32,
            optixRtnModuStartScanStep
                INTEGER,
            optixRtnModuStartScanBWid
                INTEGER,
            optixRtnModuStopFreqScan
                INTEGER,
            optixRtnModuInterferenceFreqBwid
                OCTET STRING,
            optixRtnModuInterferenceFreqLeftChannel
                INTEGER,
            optixRtnModuInterferenceFreqCfgChannel
                INTEGER,
            optixRtnModuInterferenceFreqRightChannel
                INTEGER
        }

    -- 1.3.6.1.4.1.2011.2.25.4.40.4.10.111.1.1
    optixRtnModuStartScanStartFreq OBJECT-TYPE
        SYNTAX Unsigned32
        MAX-ACCESS read-write
        STATUS current
        DESCRIPTION
            "Indicates the start frequency of frequency scanning. Unit:KHz"
        ::= { optixRtnModuFreqScanEntry 1 }

    -- 1.3.6.1.4.1.2011.2.25.4.40.4.10.111.1.2
    optixRtnModuStartScanEndFreq OBJECT-TYPE
        SYNTAX Unsigned32
        MAX-ACCESS read-write
        STATUS current
        DESCRIPTION
            "Indicates the end freqency of frequency scanning. Unit:KHz"
        ::= { optixRtnModuFreqScanEntry 2 }

    -- 1.3.6.1.4.1.2011.2.25.4.40.4.10.111.1.3
    optixRtnModuStartScanStep OBJECT-TYPE
        SYNTAX INTEGER
        {
            step1P5M(10),
            step1P75M(11),
            step3P5M(12),
            step7M(13),
            step14M(14)
        }
        MAX-ACCESS read-write
        STATUS current
        DESCRIPTION
            "Indicates the step of frequency scanning."
        ::= { optixRtnModuFreqScanEntry 3 }

    -- 1.3.6.1.4.1.2011.2.25.4.40.4.10.111.1.4
    optixRtnModuStartScanBWid OBJECT-TYPE
        SYNTAX INTEGER
        {
            bw3P5M(1),
            bw7M(2),
            bw14M(3),
            bw28M(4),
            bw40M(5),
            bw56M(6),
            bwFCC30M(7),
            bwFCC40M(8),
            bwFCC50M(9),
            bw112M(23),
            bwFCC10M(24),
            bwFCC20M(25),
            bwFCC60M(28),
            bw14MACCP(30),
            bw28MACCP(31),
            bw56MACCP(32),
            bw112MACCP(33),
			bw80M(34)
        }
        MAX-ACCESS read-write
        STATUS current
        DESCRIPTION
            "Indicates the bandwidth of frequency scanning,for calculating available frequencies."
        ::= { optixRtnModuFreqScanEntry 4 }

    -- 1.3.6.1.4.1.2011.2.25.4.40.4.10.111.1.5
    optixRtnModuStopFreqScan OBJECT-TYPE
        SYNTAX INTEGER
        {
            stop(0)
        }
        MAX-ACCESS read-write
        STATUS current
        DESCRIPTION
            "Indicates the stop of frequency scanning."
        DEFVAL{ 0 }
        ::= { optixRtnModuFreqScanEntry 5 }

    -- 1.3.6.1.4.1.2011.2.25.4.40.4.10.111.1.6
    optixRtnModuInterferenceFreqBwid OBJECT-TYPE
        SYNTAX OCTET STRING
        MAX-ACCESS read-only
        STATUS current
        DESCRIPTION
            "Indicates the configuration bandwidth."
        ::= { optixRtnModuFreqScanEntry 6 }

    -- 1.3.6.1.4.1.2011.2.25.4.40.4.10.111.1.7
    optixRtnModuInterferenceFreqLeftChannel OBJECT-TYPE
        SYNTAX INTEGER
        {
            stateUnknown(-1),
            stateNoInterference(0),
            stateInterference(1)
        }
        MAX-ACCESS read-only
        STATUS current
        DESCRIPTION
            "Indicates the left channel state of configuration frequency"
        ::= { optixRtnModuFreqScanEntry 7 }

    -- 1.3.6.1.4.1.2011.2.25.4.40.4.10.111.1.8
    optixRtnModuInterferenceFreqCfgChannel OBJECT-TYPE
        SYNTAX INTEGER
        {
            stateUnknown(-1),
            stateNoInterference(0),
            stateInterference(1)
        }
        MAX-ACCESS read-only
        STATUS current
        DESCRIPTION
            "Indicates the current channel state of configuration frequency."
        ::= { optixRtnModuFreqScanEntry 8 }

    -- 1.3.6.1.4.1.2011.2.25.4.40.4.10.111.1.9
    optixRtnModuInterferenceFreqRightChannel OBJECT-TYPE
        SYNTAX INTEGER
        {
            stateUnknown(-1),
            stateNoInterference(0),
            stateInterference(1)
        }
        MAX-ACCESS read-only
        STATUS current
        DESCRIPTION
            "Indicates the right channel state of configuration frequency."
        ::= { optixRtnModuFreqScanEntry 9 }
    -- 1.3.6.1.4.1.2011.2.25.4.40.4.10.112
    optixRtnModuFreqScanAvailFreqTable OBJECT-TYPE
        SYNTAX SEQUENCE OF OptixRtnModuFreqScanAvailFreqEntry
        MAX-ACCESS not-accessible
        STATUS current
        DESCRIPTION
            "Describes Available frequencies of the RF unit frequency scanning."
        ::= { optixODU 112 }

    -- 1.3.6.1.4.1.2011.2.25.4.40.4.10.112.1
    optixRtnModuFreqScanAvailFreqEntry OBJECT-TYPE
        SYNTAX OptixRtnModuFreqScanAvailFreqEntry
        MAX-ACCESS not-accessible
        STATUS current
        DESCRIPTION
            "Indicates the parameter entry for the RF unit frequency scanning."
        INDEX{ optixRtnOduIndex1,optixRtnOduIndex2,optixRtnOduIndex3,optixRtnOduIndex4,optixRtnIFPortlist }
        ::= { optixRtnModuFreqScanAvailFreqTable 1 }

    OptixRtnModuFreqScanAvailFreqEntry ::=
        SEQUENCE {
            optixRtnModuGetAvailableBwid
                OCTET STRING,
            optixRtnModuGetAvailableTxfreqs
                Unsigned32
        }

    -- 1.3.6.1.4.1.2011.2.25.4.40.4.10.112.1.2
    optixRtnModuGetAvailableBwid OBJECT-TYPE
        SYNTAX OCTET STRING
        MAX-ACCESS read-only
        STATUS current
        DESCRIPTION
            "Indicates the bandwidth that inputted when starting the frequency scanning."
        ::= { optixRtnModuFreqScanAvailFreqEntry 2 }

    -- 1.3.6.1.4.1.2011.2.25.4.40.4.10.112.1.3
    optixRtnModuGetAvailableTxfreqs OBJECT-TYPE
        SYNTAX Unsigned32
        MAX-ACCESS read-only
        STATUS current
        DESCRIPTION
            "Indicates the available freqencies of frequency scanning. Unit:KHz"
        ::= { optixRtnModuFreqScanAvailFreqEntry 3 }

    -- 1.3.6.1.4.1.2011.2.25.4.40.4.10.113
    optixRtnModuFreqScanResultTable OBJECT-TYPE
        SYNTAX SEQUENCE OF OptixRtnModuFreqScanResultEntry
        MAX-ACCESS not-accessible
        STATUS current
        DESCRIPTION
            "Describes result of the RF unit frequency scanning"
        ::= { optixODU 113 }

    -- 1.3.6.1.4.1.2011.2.25.4.40.4.10.113.1
    optixRtnModuFreqScanResultEntry OBJECT-TYPE
        SYNTAX OptixRtnModuFreqScanResultEntry
        MAX-ACCESS not-accessible
        STATUS current
        DESCRIPTION
            "Indicates the parameter entry for the RF unit frequency scanning."
        INDEX{ optixRtnOduIndex1,optixRtnOduIndex2,optixRtnOduIndex3,optixRtnOduIndex4,optixRtnIFPortlist }
        ::= { optixRtnModuFreqScanResultTable 1 }

    OptixRtnModuFreqScanResultEntry ::=
        SEQUENCE {
            optixRtnModuScanResultRxFreq
                Unsigned32,
            optixRtnModuScanResultRxRsl
                Integer32
        }

    -- 1.3.6.1.4.1.2011.2.25.4.40.4.10.113.1.2
    optixRtnModuScanResultRxFreq OBJECT-TYPE
        SYNTAX Unsigned32
        MAX-ACCESS read-only
        STATUS current
        DESCRIPTION
            "Indicates the receive freqencies of frequency scanning. Unit:KHz"
        ::= { optixRtnModuFreqScanResultEntry 2 }

    -- 1.3.6.1.4.1.2011.2.25.4.40.4.10.113.1.3
    optixRtnModuScanResultRxRsl OBJECT-TYPE
        SYNTAX Integer32
        MAX-ACCESS read-only
        STATUS current
        DESCRIPTION
            "Indicates the receive power of frequency scanning. Unit:0.1 dBm"
        ::= { optixRtnModuFreqScanResultEntry 3 }

     -- 1.3.6.1.4.1.2011.2.25.4.40.4.10.114
    optixRtnModuScanFreqTrapCommon OBJECT IDENTIFIER ::= { optixODU 114 }

    -- 1.3.6.1.4.1.2011.2.25.4.40.4.10.114.1
    optixRtnModuFreqScanFinishEvent OBJECT IDENTIFIER ::= { optixRtnModuScanFreqTrapCommon 1 }

    -- 1.3.6.1.4.1.2011.2.25.4.40.4.10.114.1.1
    optixRtnModuBoardID OBJECT-TYPE
        SYNTAX Unsigned32
        MAX-ACCESS accessible-for-notify
        STATUS current
        DESCRIPTION
            "Indicates the RF unit board ID."
        ::= { optixRtnModuFreqScanFinishEvent 1 }

    -- 1.3.6.1.4.1.2011.2.25.4.40.4.10.114.1.2
    optixRtnModuSubCardID OBJECT-TYPE
        SYNTAX Unsigned32
        MAX-ACCESS accessible-for-notify
        STATUS current
        DESCRIPTION
            "Indicates the subboard ID."
        ::= { optixRtnModuFreqScanFinishEvent 2 }

    -- 1.3.6.1.4.1.2011.2.25.4.40.4.10.114.1.3
    optixRtnModuPortID OBJECT-TYPE
        SYNTAX INTEGER
        MAX-ACCESS accessible-for-notify
        STATUS current
        DESCRIPTION
            "Indicates the port number of the main port."
        ::= { optixRtnModuFreqScanFinishEvent 3 }
        
    -- 1.3.6.1.4.1.2011.2.25.4.40.4.10.114.1.4
    optixRtnModuCarrierID OBJECT-TYPE
        SYNTAX INTEGER
        MAX-ACCESS accessible-for-notify
        STATUS current
        DESCRIPTION
            "Indicates the carrier ID."
        ::= { optixRtnModuFreqScanFinishEvent 4 }
        
    -- 1.3.6.1.4.1.2011.2.25.4.40.4.10.114.1.5
    optixRtnModuFreqScanStopState OBJECT-TYPE
        SYNTAX OCTET STRING
        MAX-ACCESS accessible-for-notify
        STATUS current
        DESCRIPTION
            "Indicates the stop type of frequency scanning."
        ::= { optixRtnModuFreqScanFinishEvent 5 } 

    -- 1.3.6.1.4.1.2011.2.25.4.40.4.10.260
    optixRtnModuRfModeTable OBJECT-TYPE
        SYNTAX SEQUENCE OF OptixRtnModuRfModeEntry
        MAX-ACCESS not-accessible
        STATUS current
        DESCRIPTION
            "Indicates the parameter table for the RF mode."
        ::= { optixODU 260 }

    -- 1.3.6.1.4.1.2011.2.25.4.40.4.10.260.1
    optixRtnModuRfModeEntry OBJECT-TYPE
        SYNTAX OptixRtnModuRfModeEntry
        MAX-ACCESS not-accessible
        STATUS current
        DESCRIPTION
            "Indicates the parameter entry for the RF mode."
        INDEX{ optixRtnOduIndex1,optixRtnOduIndex2,optixRtnOduIndex3 }
        ::= { optixRtnModuRfModeTable 1 }

    OptixRtnModuRfModeEntry ::=
        SEQUENCE {
            optixRtnModuRfMode
                INTEGER
        }

    -- 1.3.6.1.4.1.2011.2.25.4.40.4.10.260.1.1
    optixRtnModuRfMode OBJECT-TYPE
        SYNTAX INTEGER
        {
            singleport(0),
            multiport(1)
        }
        MAX-ACCESS read-write
        STATUS current
        DESCRIPTION
            "Indicates the mode of RF."
        ::= { optixRtnModuRfModeEntry 1 }        

    -- 1.3.6.1.4.1.2011.2.25.4.40.4.10.261
    optixRtnOduPortCrossTable OBJECT-TYPE
        SYNTAX SEQUENCE OF OptixRtnOduPortCrossEntry
        MAX-ACCESS not-accessible
        STATUS current
        DESCRIPTION
            "Describes the cross status of odu port."
        ::= { optixODU 261 }

    -- 1.3.6.1.4.1.2011.2.25.4.40.4.10.261.1
    optixRtnOduPortCrossEntry  OBJECT-TYPE
     	SYNTAX OptixRtnOduPortCrossEntry
        MAX-ACCESS not-accessible
        STATUS current
        DESCRIPTION
            "Describes the cross status of odu port."
        INDEX{ optixRtnOduIndex1, optixRtnOduIndex2 }
        ::= { optixRtnOduPortCrossTable 1 }

    OptixRtnOduPortCrossEntry ::=
    	SEQUENCE{
    	    optixRtnOduPortCrossStatus
    	    	INTEGER	
    	}

    -- 1.3.6.1.4.1.2011.2.25.4.40.4.10.261.1.1
  	optixRtnOduPortCrossStatus OBJECT-TYPE
  	    SYNTAX INTEGER {
  	          disable(0),
  	          enable(1)
   	    }
        MAX-ACCESS read-write
        STATUS current
        DESCRIPTION
            "Describes the cross status of odu port. Cross-state only for modu"
        ::= { optixRtnOduPortCrossEntry 1 }

    -- 1.3.6.1.4.1.2011.2.25.4.40.4.10.262
    optixRtnOduBoosterEnTable OBJECT-TYPE
        SYNTAX SEQUENCE OF OptixRtnOduBoosterEnEntry
        MAX-ACCESS not-accessible
        STATUS current
        DESCRIPTION
            "Describes the booster-type enable state of odu."
        ::= { optixODU 262 }

    -- 1.3.6.1.4.1.2011.2.25.4.40.4.10.262.1
    optixRtnOduBoosterEnEntry  OBJECT-TYPE
     	SYNTAX OptixRtnOduBoosterEnEntry
        MAX-ACCESS not-accessible
        STATUS current
        DESCRIPTION
            "Describes the booster-type enable state of odu."
        INDEX{ optixRtnOduBid, optixRtnOduSid, optixRtnOduBoosterType }
        ::= { optixRtnOduBoosterEnTable 1 }

    OptixRtnOduBoosterEnEntry ::=
    	SEQUENCE{
            optixRtnOduBid
                Unsigned32,
            optixRtnOduSid
                Unsigned32,
    	    optixRtnOduBoosterType
    	    	INTEGER,
            optixRtnOduEnableState
                INTEGER
    	}

    -- 1.3.6.1.4.1.2011.2.25.4.40.4.10.262.1.1
    optixRtnOduBid OBJECT-TYPE
        SYNTAX Unsigned32
        MAX-ACCESS not-accessible
        STATUS current
        DESCRIPTION
            "Indicates the board id of odu."
        ::= { optixRtnOduBoosterEnEntry 1 }

    -- 1.3.6.1.4.1.2011.2.25.4.40.4.10.262.1.2
    optixRtnOduSid OBJECT-TYPE
        SYNTAX Unsigned32
        MAX-ACCESS not-accessible
        STATUS current
        DESCRIPTION
            "Indicates the sub-board id of odu."
        ::= { optixRtnOduBoosterEnEntry 2 }

    -- 1.3.6.1.4.1.2011.2.25.4.40.4.10.262.1.3
  	optixRtnOduBoosterType OBJECT-TYPE
  	    SYNTAX INTEGER {
            baseTsl(0)
        }
        MAX-ACCESS not-accessible
        STATUS current
        DESCRIPTION
            "Indicates the booster-type of odu. 0:BASE-TSL."
        ::= { optixRtnOduBoosterEnEntry 3 }

    -- 1.3.6.1.4.1.2011.2.25.4.40.4.10.262.1.4
  	optixRtnOduEnableState OBJECT-TYPE
  	    SYNTAX INTEGER {
            disable(0),
            enable(1)
        }
        MAX-ACCESS read-write
        STATUS current
        DESCRIPTION
            "Indicates the enable state of booster-type of odu. Enable-state only for modu."
        ::= { optixRtnOduBoosterEnEntry 4 }
END
