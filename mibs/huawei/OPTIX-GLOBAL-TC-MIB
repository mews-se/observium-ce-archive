-- OPTIX-GLOBAL-TC-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-TC-MIB DEFINITIONS ::= BEGIN
    IMPORTS
        optixCommonGlobal
            FROM OPTIX-OID-MIB
        MODULE-IDENTITY
            FROM SNMPv2-SMI
        TEXTUAL-CONVENTION
            FROM SNMPv2-TC
        ;

    optixGlobalTCMIB MODULE-IDENTITY
        LAST-UPDATED "201204160000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module describes rules of Huawei transmit platform self-defined types."
        REVISION "201204160000Z"
        DESCRIPTION
            "The initial revision of this MIB module."
        ::={ optixCommonGlobal 99 }

    AlarmEventType ::= TEXTUAL-CONVENTION
        STATUS current
        DESCRIPTION
            "Alarm ID."
        SYNTAX INTEGER
        {
            almRLos(1),
            almTLos(2),
            almRLoc(3),
            almTLoc(4),
            almROof(5),
            almNoBdSoft(6),
            almRLof(8),
            almTF(9),
            almRsCrossTr(10),
            almB1Exc(12),
            almTrLoc(14),
            almHpCrossTr(16),
            almInPwrAbn(25),
            almOutPwrAbn(26),
            almTempOver(28),
            almTemHa(29),
            almTemLa(30),
            almInPwrHigh(31),
            almInPwrLow(32),
            almMsAis(33),
            almMsRdi(34),
            almB2Exc(35),
            almB2Sd(36),
            almMsRei(37),
            almMsCrossTr(38),
            almApsIndi(41),
            almApsFail(42),
            almLpRfi(48),
            almLpCrossTr(49),
            almLpSizeErr(51),
            almLsrWillDie(56),
            almLsrNoFited(57),
            almLSRBCMALM(58),
            almLsrCoolAlm(60),
            almOutPwrHigh(63),
            almOutPwrLow(64),
            almAuLop(66),
            almMsAdCrossTr(67),
            almB3Sd(70),
            almB3Exc(71),
            almAuAis(72),
            almHpUneq(75),
            almHpTim(76),
            almHpSlm(77),
            almHpRdi(78),
            almHpRei(79),
            almHpLom(81),
            almTuLop(82),
            almTuAis(83),
            almHpAdCrossTr(84),
            almJ0Mm(87),
            almLpRFifo(88),
            almLpTFifo(89),
            almLpUneq(90),
            almLpTim(91),
            almLpSlm(92),
            almLpRdi(93),
            almLpRei(94),
            almWRFail(99),
            almLTI(100),
            almSynBad(101),
            almTAlos(107),
            almSyncCLos(111),
            almFanFail(115),
            almE1Los(117),
            almUpE1Ais(118),
            almBdStatus(119),
            almWrgBdType(121),
            almPwrFail(125),
            almUpT1AIS(130),
            almALoc(139),
            almRSErr(141),
            almRFRst(159),
            almTFRst(160),
            almRpLoc(163),
            almTempAlarm(166),
            almB1SD(175),
            almK1K2M(180),
            almK2M(181),
            almBipSD(182),
            almBipExc(183),
            almExtSyncLos(184),
            almDbmsError(185),
            almTd(189),
            almS1SynChange(193),
            almNeStateInstall(197),
            almDbmsProtectMode(198),
            almCommunFail(199),
            almSecuAlm(200),
            almDownE1Ais(201),
            almOCD(214),
            almNeSfLost(215),
            almLCD(216),
            almUHCS(218),
            almCHCS(219),
            almVpAis(226),
            almVpRdi(227),
            almVcAis(228),
            almVcRdi(229),
            almEthLos(235),
            almHardBad(236),
            almLoopAlm(240),
            almLinkErr(261),
            almWOffline(262),
            almVoltLos(265),
            almE1Loc(266),
            almNoLsrParaFile(268),
            almALMALS(296),
            almClkNoTraceMode(333),
            almApsManualStop(336),
            almBdVerNmat(351),
            almLaserClosed(364),
            almBusErr(377),
            almPowerAlm(383),
            almLaserModErr(393),
            almPowerAbnormal(412),
            almSlaveBad(423),
            almModComFail(432),
            almBiosStatus(449),
            almNeSoftMM(571),
            almSwdlActivatedTimeOut(573),
            almSwdlNePkgCheck(574),
            almSwdlChgmngNoMatch(575),
            almBootRomBad(584),
            almLicenceErr(589),
            almSyncFail(591),
            almChipAbn(597),
            almV5Vcais(607),
            almLpsUniBiM(619),
            almPatchfileNotexist(620),
            almPatchErr(621),
            almPatchNotConfirm(622),
            almRtcFail(624),
            almBdNotInstalled(625),
            almMwLim(626),
            almMwLof(631),
            almRadioTslLow(635),
            almRadioTslHigh(636),
            almRadioRslHigh(637),
            almRadioRslLow(638),
            almRadioMute(639),
            almConfigNoSupport(640),
            almSwdlPkgNoBdSoft(2569),
            almSwdlRollbackFail(2570),
            almSwdlCommitFail(2571),
            almSwdlInProcess(2572),
            almSwdlPkgVerMM(2573),
            almSwdlAutoMatchInh(2574),
            almLagPortectFail(12288),
            almEthOamRmtLoop(12291),
            almEthOamRmtSd(12292),
            almEthOamRmtCritFault(12293),
            almEthOamDiscoverFail(12294),
            almDownT1AIS(12295),
            almExEthOamCCLos(12298),
            almExEthOamMpidCnflct(12299),
            almLptRfi(12300),
            almFlowOver(12301),
            almRelayAlarmCritical(12305),
            almRelayAlarmMajor(12306),
            almRelayAlarmMinor(12307),
            almRelayAlarmIgnore(12308),
            almRemoteFault(12544),
            almLocalFault(12545),
            almHardErr(12580),
            almNoElabel(12581),
            almLptActive(12582),
            almSysLogCommFail(12586),
            almMwRdi(12587),
            almMwFecUncor(12588),
            almIfInPwrAbn(12589),
            almWrgDevType(12593),
            almCFCardOffLine(12598),
            almCFCardFailed(12599),
            almCFCardWRDisabled(12600),
            almEthOamSelfLoop(12767),
            almEthOamVcgSelfLoop(12768),
            almLagPortFail(12769),
            almLagVcPortFail(12770),
            almTfCheckFail(12774),
            almPatchDeactTimeout(12775),
            almPatchActTimeout(12776),
            almCFCardFull(12777),
            almEthNoFlow(12786),
            almVctrunkNoFlow(12787),
            almPortModeMismatch(12788),
            almPatchPkgErr(12790),
            almSyncDisable(12792),
            almEthLinkDown(12793),
            almMacFcsExc(12794),
            almMacFcsSd(12795),
            almCesLospktExc(12796),
            almCesMisorderpktExc(12797),
            almCesStraypktExc(12798),
            almCesMalpktExc(12799),
            almCesJtrudrExc(12800),
            almCesJtrovrExc(12801),
            almCesRdi(12802),
            almMpDown(12803),
            almMpDelay(12804),
            almPppLcpFail(12805),
            almPppNcpFail(12806),
            almFdbSizeAlmElan(12807),
            almVpLoc(12808),
            almVcLoc(12809),
            almMplsTunnelLocv(12814),
            almMplsTunnelExcess(12815),
            almMplsTunnelMismatch(12816),
            almMplsTunnelMismerge(12817),
            almMplsTunnelUnknown(12818),
            almMplsTunnelBdi(12819),
            almMplsTunnelFdi(12820),
            almMplsTunnelSD(12821),
            almMplsTunnelSF(12822),
            almEthCfmMisMerge(12823),
            almEthCfmUnexPeri(12824),
            almEthCfmLoc(12825),
            almEthCfmRdi(12826),
            almEthEfmDf(12827),
            almEthEfmRemfault(12828),
            almEthEfmEvent(12829),
            almEthEfmLoopBack(12830),
            almEthApsTypeMismatch(12831),
            almEthApsPathMismatch(12832),
            almEthApsSwitchFail(12833),
            almEthApsLost(12834),
            almLagMemberDown(12836),
            almLagDown(12837),
            almImaGroupLeDown(12838),
            almImaGroupReDown(12839),
            almPwDown(12852),
            almPwDroppktExc(12853),
            almPwExcTraffic(12854),
            almLcsLimited(12860),
            almLicenseLost(12861),
            almXPICLos(12862),
            almIfCableOpen(12863),
            almIfModeUnSupported(12864),
            almNp1SWIndi(12865),
            almNp1SWFail(12866),
            almNp1ManualStop(12867),
            almModTypeMismatch(12868),
            almRpsIndi(12869),
            almMwBerEXC(12870),
            almMwBerSD(12871),
            almPatchChgsccNotmatch(12872),
            almStormCurQuenumOver(12884),
            almAcrLockFail(12910),
            almElpsCfgMismatch(12918),
            almEthPwrSupplyFail(12923),
            almImaE1Delay(12925),
            almLanLoc(12926),
            almEthAutoLinkDown(12928),
            almTimeNoTraceMode(12963),
            almTimeLos(12964),
            almExtTimeLoc(12972),
            almRadioFadingMarginInsuff(12989),
            almGspTnnlDown(12994),
            almGspIsisNbAuthErr(12996),
            almGspRsvpNbDown(12997),
            almGspRsvpNbAuthErr(12998),
            almArpMacMismatch(13008),
            almPassWordNeedChange(13047),
            almErpsInProtection(13048),
            almComExtEccFull(13049),
            almAMDownShift(13050),
            almMultiRplOwner(13064),
            almRadioRslBeyondTh(13069),
            almAtmpwLospktExc(13075),
            almAtmpwMisorderpktExc(13076),
            almAtmpwUnknowncellExc(13077),
            almCesPwRemoteLosPkt(13078),
            almCespwOppositeRai(13080),
            almCespwOppositeAcfault(13081),
            almMplsTunnelOamFail(13087),
            almCpuBusy(13090),
            almMplsPwLocv(13091),
            almMplsPwExcess(13092),
            almMplsPwMismatch(13093),
            almMplsPwMismerge(13094),
            almMplsPwUnknown(13095),
            almMplsPwBdi(13096),
            almMplsPwSD(13097),
            almMplsPwSF(13098),
            almPwapsTypeMismatch(13099),
            almPwapsPathMismatch(13100),
            almPwapsSwitchFail(13101),
            almPwapsLost(13102),
            almMcapsApsidMismatch(13103),
            almMcapsDnipwMismatch(13104),
            almImaTxclkMismatch(13105),
            almMcLmsCfgMisMatch(13106),
            almPwNoTraffic(13107),
            almLagBwMM(13108),
            almDcnSizeOver(13110),
            almDcnLinkOver(13111),
            almMemOver(13112),
            almMcspPathLocv(13113),
            almMclagCfgMismatch(13114),
            almLptCfgCloseport(13115),
            almLcsMisMatch(13122),
            almFanAging(13123),
            almCesCeBoundPktlos(13124),
            almNtpSyncFail(13125),
            almMplsPwOamfail(13135),
            almLcsFileNotExist(13144),
            almLcsExpired(13145),
            almLcsDaysOfGrace(13146),
            almCesK1K2M(13147),
            almCesK2M(13148),
            almCesApsIndi(13149),
            almCesApsFail(13150),
            almCesLpsUniBiM(13152),
            almOdcDoorOpen(13154),
            almOdcSurgeProtectionFail(13155),
            almOdcSmokeOver(13156),
            almOdcWaterAlm(13157),
            almOdcLoadPwrdown(13158),
            almOdcBatteryPwrDown(13159),
            almOdcBatteryCurrentAbn(13160),
            almOdcFanFailed(13161),
            almOdcTecAlm(13162),
            almOdcPowerFail(13163),
            almOdcHumiAbn(13164),
            almOdcMdlAbn(13165),
            almOdcTempAbn(13166),
            almSecRadiusFail(13169),
            almCesApsManualStop(13173),
            almIsisLspOver(13174),
            almDslTrunkLinkDown(13176),
            almMplsPwFdi(13182),
            almMwCfgMisMatch(13183),
            almLicenseDiff(13187),
            almPtpTimeStampAbn(13188),
            almPtpSourceSwitch(13194),
            almClkLockFail(13195),
            almTimeLockFail(13196),
            almCesAcrLockAbn(13277),
            almEthCfmFail(13281),
            almBgpPeerDown(13282),
            almLdpPeerDown(13283),
            almBdtempSensorFail(13284),
            almEnvtempSensorFail(13285),
            almOut1tempSensorFail(13286),
            almIntempSensorFail(13287),
            almOut2tempSensorFail(13288),
            almBat1tempSensorFail(13289),
            almEnvhumSensorFail(13290),
            almEnvtemp1SensorFail(13291),
            almEnvtemp2SensorFail(13292),
            almBat2tempSensorFail(13293),
            almMwE1Lost(13294),
            almMwContWave(13295),
            almIsisLspOverload(13303),
            almL3vpnTunnelDown(13307),
            almPortQueueDropOver(13374),
            almPortcarRedpktOver(13375),
            almTunnelApsDegraded(13377),
            almPgPrtDegraded(13382),
            almPgLinkFail(13383),
            almMwAmTest(13384),
            almMplsTunnelLck(13388),
            almMplsPwLck(13389),
            almMplsPwAis(13390),
            almMplsTunnelLock(13391),
            almMplsPwLock(13392),
            almMplsTunnelUnexpmeg(13393),
            almMplsTunnelUnexpmep(13394),
            almMplsTunnelUnexpper(13395),
            almMplsTunnelRdi(13396),
            almMplsTunnelAis(13397),
            almMplsPwUnexpmeg(13398),
            almMplsPwUnexpmep(13399),
            almMplsPwUnexpper(13400),
            almMPlsPwRdi(13401),
            almMplsPwCsf(13402),
            almMplsSectLocv(13403),
            almMplsSectOamFail(13404),
            almMplsSectUnexpmeg(13405),
            almMplsSectUnexpmep(13406),
            almMplsSectUnexpper(13407),
            almMplsSectRdi(13408),
            almMplsSectSd(13409),
            almMplsSectSf(13410),
            almMplsSectLock(13411),
            almSrvShutDownLd(13416),
            almPortExcTraffic(13417),
            almDropratioOver(13418),
            almPlaCfgMismatch(13422),
	    almDot1xRsNoresponse(13433),
	    almDot1xUsernumOver(13440),
	    almDot1xPrNoresponse(13550),
	    almDot1xPrUserOver(13551),
            almMacExtExc(13444),
            almMringOamLocvW(13445),
            almMringOamSdW(13451),
            almMringOamSfW(13452),
            almMringOamUnexpmegW(13453),
            almMringOamUnexpmepW(13454),
            almMringOamUnexpperW(13455),
            almMringOamRdiW(13456),
            almMringApsLostW(13457),
            almMringApsMismatchW(13458),
            almMringFarSwFailW(13460),
            almMringOamLocvE(13461),
            almMringOamSdE(13467),
            almMringOamSfE(13468),
            almMringOamUnexpmegE(13469),
            almMringOamUnexpmepE(13470),
            almMringOamUnexpperE(13471),
            almMringOamRdiE(13472),
            almMringApsLostE(13473),
            almMringApsMismatchE(13474),
            almMringFarSwFailE(13476),
            almEthCfmAis(13478),
            almUsbProcessFail(13484),
            almNbUnReachable(13485),
            almUniptpSrcNegoFail(13479),
            almUniptpSrcLoss(13480),
            almUniptpSrcSwitch(13481),
            almBwutilizationOver(13486),
            almDbmsDelete(13502),
            almLaserCheckErr(13506),
            almTunnelApsOutage(13507),
            almPwApsDegraded(13508),
            almPwApsOutage(13509),
            almNeIPConfusion(13513),
            almSslCertNoEnc(13514),
            almNbCfgMismatch(13533),
            almPlaMemberDown(13538),
            almPlaDown(13539),
            almSubnetRtConflict(13545),
            almElanSmacFlapping(13552),
            almPatchBdExclude(13557),
            almPatchBdMatchFail(13558),
            almISISADJACENCYCHANGE(13560),
            almBGPBACKTRANSITION(13561),
            almL3vTrapThreExceed(13562),
            almL3vTrapVrfDown(13563),
            almVersionNotsupport(13564),
            almRtTblLack(13619),
            almIpfpmLossRatioExce(13645),
            almIpfpmOneDelayExce(13646),
            almIpfpmTwoDelayExce(13647),
            almEthTrunkMemberDown(13655),
            almEthTrunkDown(13656),
            almOspfNbrStateChange(13663),
            almIpfpmInstTlpErr(13668),
            almPlaMemberDownExt(13669),
            almSwdlBdMatchFail(13673),			
            almArpFail(13689),
            almRfusdDelayUnequal(13692),
            almMplsLdpSessionDown(13700),
            almMplsLspTblLack(13701),
            almQueueResLack(13704),
            almCompressMismatch(13705),
            almLcsTrialPeriod(13719),
            almAesMacErr(13734),
            almReflectorIpCnflct(13736),
            almPwdEncryptRisk(13744),
            almUsbFileUnsec(13745),
            almProPktFlooding(13746),
            almSslCertDamaged(13759),
            almArpSpoof(13762),
            almProStatAbn(13774),
            almIgspEntriesExc(13775),
            almSslCertToExpire(13779),
            almPortBerSd(13810),
            almServOverFwdCapa(13891),
            almNvVportDown(13895),
            almFlowExcLcs(13907),
            almMwFecExc(13916),
            almPlaPktErr(13930),
            almBrdcastRatioOver(13933),
            almMimoLos(13937),
            almMimoLineMismatch(13938),
            almSoftwareUncommit(13948),
            almKmcKeySyncFail(13960),
            almLaserShut(63509),
            almHardNonSupport(63537),
            almVCATLOA(63538),
            almLFA(63554),
            almDdnLfa(63555),
            almLMFA(63558),
            almRMFA(63563),
            almFcsErr(63575),
            almB3ExcVc3(63577),
            almB3SdVc3(63579),
            almVcatlomVc12(63584),
            almVcatLomVc3(63585),
            almVCATSQMVC12(63587),
            almVcatSqmVc3(63588),
            almLpRdiVc12(63590),
            almLpRdiVc3(63591),
            almLpReiVc12(63592),
            almLpReiVc3(63593),
            almLpSlmVc12(63594),
            almLpSlmVc3(63595),
            almLpTimVc12(63596),
            almLpTimVc3(63597),
            almLpUneqVc12(63598),
            almLpUneqVc3(63599),
            almTuAisVc12(63600),
            almTuAisVc3(63601),
            almTuLopVc12(63602),
            almTuLopVc3(63603),
            almAlmImaLif(63614),
            almAlmImaLods(63615),
            almAlmImaRfi(63616),
            almAlmImaReTxUnusable(63617),
            almAlmImaReRxUnusable(63618),
            almAlmE1Rai(63622),
            almPortModuleOffline(63629),
            almThunderAlm(63635),
            almALMGFPdLFD(63638),
            almALMGFPdCSF(63639),
            almLaserModErrEx(63644),
            almLcasFop(63646),
            almLcasPlct(63647),
            almLcasTlct(63648),
            almLcasPlcr(63649),
            almLcasTlcr(63650),
            almLcasFopt(63651),
            almLcasFopr(63652),
            almNeDCNMode(65528),
            almLptIneffect(63656),
            almPs(120),
            almCfgVerify(147),
            almFpgaAbn(194),
            almB3ExcVc4(63578),
            almB3SdVc4(63580),
            almVcatLomVc4(63586),
            almVcatSqmVc4(63589),
            almAlmGfpdssf(63640),
            almAuCmm(260),
            almBeffecExc(335),
            almC2Vcais(366),
            almC2Pdi(368),
            almTestStatus(374),
            almSyncLockoff(390),
            almLaserModuleMismatch(606),
            almWsLos(644),
            almXcpIndi(12590),
            almPrbsLss(12643),
            almProtConnErr(12974),
            almE1Ais(13006),
            almE1Lof(13007),
            almBdLedtest(13419),
            almFldCfgCloseport(13949),
            almLaserTypeMismatch(13951),
            almStorageFail(13985),
            almIsisLspSeqExceed(14002),
            almIsisSeqReachMax(14003),
            almDeviceAuthFail(14007),
            almInsuffcntMemSpace(13983),
            almInsuffcntFlshSpace(13984),
            almErpsBlock(14035),
            almPwrAcFail(14051),
            almPwrAcAlarm(14052),
            almPwrDcAlarm(14053),
            almPwrSurgeAlarm(14054),
            almPwrSolarProt(14055),
            almPwrSloarFault(14056),
            almPwrTmpovrProt(14066),
            almPwrAcModProt(14067),
            almPwrCommFail(14068),
            almPwrUpgradeFalled(14057),
            almPwrOutputProt(14058),
            almPwrLlvdAlarm(14072),
            almPwrHardFault(14069),
            almBatHardFault(14059),
            almBatProtAlarm(14060),
            almBatAddrConflict(14070),
            almBatOverdischarge(14061),
            almBatOvercharge(14062),
            almBatTempAlarm(14063),
            almBatMissing(14064),
            almBatSohLow(14065),
            almBatSohWarning(14071),
            almDevDoorOpen(14075),
            almPatchOpTimeout(14041),
            almPatchInitFail(14042),
            almGpsmodLockFail(14077),
            almGpsmodInvalid(14078),
            almSepPortFault(14084),
            almErpsCfmFail(14085),
            almPatchMatchNoStart(14088),
            almDcnChannelBiterror(14102),
            almDcncfgNotCommit(14147),
            almLptAuthFail(14141),
            almPingLos(14150),
            almPingArpMismatch(14151),
            almErpsNotComplete(14164),
            almSrvLoopLd(14149),
            almDhcpFreeIpUseUp(14172),
            almApsStatusIndi(14174),
	    almAccessCtrlDisabled(14262),
            almPtpTimeAdjustOff(14284),
            almGpsLos(14285),
            almDbUnsave(14255),
            almEnergyCfgMismach(14319),
            almEnergyInprocess(14369),
	    almCaCfgMismatch(14382),
            almBdFileUnsecured(14407),
            almComboPortCfgMismatch(14408),
            almEthCfgMismatch(14459),
            almErpsHeartDetectFail(14400),
			almIpv4PrefixExceed(14581)
        }

    AlmDataNtfcnCdeType ::= TEXTUAL-CONVENTION
        STATUS current
        DESCRIPTION
            "The notification code of alarm."
        SYNTAX INTEGER
        {
            cr(1),
            mj(2),
            mn(3),
            ig(4),
            nr(5)
        }

    AlmDataSrvEffType ::= TEXTUAL-CONVENTION
        STATUS current
        DESCRIPTION
            "The effect on service caused by alarm."
        SYNTAX INTEGER
        {
            nsa(1),
            sa(2)
        }

    PerformanceEventType ::= TEXTUAL-CONVENTION
        STATUS current
        DESCRIPTION
            "Performance ID."
        SYNTAX INTEGER
        {
            pmRsBbe(1),
            pmRsEs(2),
            pmRsSes(3),
            pmRsOof(4),
            pmRsOfs(5),
            pmRsUas(6),
            pmRsCses(7),
            pmE1LcvSdh(12),
            pmE1LesSdh(13),
            pmE1LsesSdh(14),
            pmE1LLossSdh(15),
            pmMsBbe(16),
            pmMsEs(17),
            pmMsSes(18),
            pmMsFeBbe(19),
            pmMsFeEs(20),
            pmMsFeSes(21),
            pmMsUas(22),
            pmMsCses(23),
            pmMsFeCses(24),
            pmMsFeUas(33),
            pmAupjcHigh(42),
            pmAupjcLow(43),
            pmAupjcNew(44),
            pmHpBbe(48),
            pmHpEs(49),
            pmHpSes(50),
            pmHpFeBbe(51),
            pmHpFeEs(52),
            pmHpFeSes(53),
            pmHpUas(54),
            pmHpCses(55),
            pmHpFeCses(56),
            pmHpFeUas(76),
            pmTlbMax(96),
            pmTlbMin(97),
            pmTlbCur(98),
            pmTplMax(102),
            pmTplMin(103),
            pmTplCur(104),
            pmRplMax(105),
            pmRplMin(106),
            pmRplCur(107),
            pmOspiTmpMax(108),
            pmOspiTmpMin(109),
            pmOspiTmpCur(110),
            pmFecCorByteCnt(135),
            pmFecUncorBlockCnt(136),
            pmLpFeUas(142),
            pmLpBbe(144),
            pmLpEs(145),
            pmLpSes(146),
            pmLpFeBbe(147),
            pmLpFeEs(148),
            pmLpFeSes(149),
            pmLpUas(150),
            pmLpCses(151),
            pmLpFeCses(152),
            pmT1LcvSdh(164),
            pmT1LesSdh(165),
            pmT1LsesSdh(166),
            pmTupjcHigh(170),
            pmTupjcLow(171),
            pmTupjcNew(172),
            pmFecBefCorEr(252),
            pmRslMax(8606),
            pmRslMin(8607),
            pmRslCur(8608),
            pmTslMax(8609),
            pmTslMin(8610),
            pmTslCur(8611),
            pmCpuUsageMax(14919),
            pmCpuUsageMin(14920),
            pmCpuUsageCur(14921),
            pmMemUsageMax(14922),
            pmMemUsageMin(14923),
            pmMemUsageCur(14924),
            pmMplsTunnelLs(14933),
            pmMplsTunnelSls(14934),
            pmMplsTunnelCsls(14935),
            pmMplsTunnelUas(14936),
            pmEthCfmLs(14937),
            pmEthCfmSls(14938),
            pmEthCfmCsls(14939),
            pmEthCfmUas(14940),
            pmIfBbe(14941),
            pmIfEs(14942),
            pmIfSes(14943),
            pmIfUas(14944),
            pmIfCses(14945),
            pmBdTempMax(14991),
            pmBdTempMin(14992),
            pmBdTempCur(14993),
            pmQPSKWS(15033),
            pmQAMWS16(15034),
            pmQAMWS32(15035),
            pmQAMWS64(15036),
            pmQAMWS128(15037),
            pmQAMWS256(15038),
            pmCpuUsageAvg(15039),
            pmMemUsageAvg(15040),
            pmATPCPAdjust(15041),
            pmATPCNAdjust(15042),
            pmRslAvg(15043),
            pmTslAvg(15047),
            pmAMDownCnt(15048),
            pmAMUpCnt(15049),
            pmTLHTT(15050),
            pmTLLTT(15051),
            pmRLHTT(15052),
            pmRLLTT(15053),
            pmMPLSPWLS(15066),
            pmMPLSPWSLS(15067),
            pmMPLSPWCSLS(15068),
            pmMPLSPWUAS(15069),
            pmMAXFREQDEV(15088),
            pmMINFREQDEV(15089),
            pmAVGFREQDEV(15090),
            pmMAXPHASEOFFSET(15091),
            pmMINPHASEOFFSET(15092),
            pmAVGPHASEOFFSET(15093),
            pmMAXMEANPATHDELAY(15094),
            pmMINMEANPATHDELAY(15095),
            pmAVGMEANPATHDELAY(15096),
            pmMAXPOSITIVEDELAY(15103),
            pmMINPOSITIVEDELAY(15104),
            pmAVGPOSITIVEDELAY(15105),
            pmMAXNEGATIVEDELAY(15106),
            pmMINNEGATIVEDELAY(15107),
            pmAVGNEGATIVEDELAY(15108),
            pmCURNEGATIVEPDV(15418),
            pmOtu4Fesesr(15121),
            pmXpicXpdValue(15233),
            pmOduSsvTh(15234),
            pmXpdMax(15363),
            pmXpdMin(15364),
            pmE1Bbe(15365),
            pmE1Es(15366),
            pmE1Ses(15367),
            pmE1Cses(15368),
            pmE1Uas(15369),
            pmPgIfBbe(15370),
            pmPgIfEs(15371),
            pmPgIfSes(15372),
            pmPgIfCses(15373),
            pmPgIfUas(15374),
            pmIfSnrMax(15375),
            pmIfSnrMin(15376),
            pmIfSnrAvg(15377),
            pmQAMWS512(15411),
            pmQAMWS1024(15412),
            pmPaTempMax(15413),
            pmPaTempMin(15414),
            pmPaTempCur(15415),
            pmCURPOSITIVEPDV(15417),
            pmQpskSWS(15419),
            pmQamSWS16(15420),
            pmQamLWS512(15421),
            pmQamLWs1024(15422),
            pmIfBer(15479),
            pmQAMWS2048(15480),
            pmQpskS250MWS(15481),
            pmQpskS500MWS(15482),
            pmIfMseAvg(15507),
            pmIfMseMax(15508),
            pmIfMseMin(15509),
            pmIfMseCur(15510),
            pmMplsPwLsN(15607),
            pmMplsPwUasN(15608),
            pmMplsPwCslsN(15609),
            pmMplsPwSlsN(15610),
            pmMplsTunnelSlsN(15611),
            pmMplsTunnelLsN(15612),
            pmMplsTunnelCslsN(15613),
            pmMplsTunnelUasN(15614),
            pmEthCfmUasN(15619),
            pmEthCfmCslsN(15620),
            pmEthCfmSlsN(15621),
            pmEthCfmLsN(15622),
            pmQpskS62P5MWS(15615),
            pmQpskS125MWS(15616),
            pmQpskS750MWS(15617),
            pmPortBerCnt(15740),
            pmQamLWs2048(15855),
            pmBpsk250MWS(15856),
            pmBpsk500MWS(15857),
            pmBpsk750MWS(15858),
            pmBpsk1000MWS(15859),
            pmBpsk1500MWS(15860),
            pmBpsk2000MWS(15861),
            pmRsciMin(15976),
            pmRsciMax(15977),
            pmRsciCurr(15978),
            pmRsciAvg(15979),
            pmMcs0RxPkt(15926),
            pmMcs1RxPkt(15927),
            pmMcs2RxPkt(15928),
            pmMcs3RxPkt(15929),
            pmMcs4RxPkt(15930),
            pmMcs5RxPkt(15931),
            pmMcs6RxPkt(15932),
            pmMcs7RxPkt(15933),
            pmMcs8RxPkt(15934),
            pmChannelOccuptRate(15975),
            pmMcs0nss1RxPkt(15935),
            pmMcs1nss1RxPkt(15936),
            pmMcs2nss1RxPkt(15937),
            pmMcs3nss1RxPkt(15938),
            pmMcs4nss1RxPkt(15939),
            pmMcs5nss1RxPkt(15940),
            pmMcs6nss1RxPkt(15941),
            pmMcs7nss1RxPkt(15942),
            pmMcs8nss1RxPkt(15943),
            pmMcs9nss1RxPkt(15944),
            pmMcs0nss2RxPkt(15945),
            pmMcs1nss2RxPkt(15946),
            pmMcs2nss2RxPkt(15947),
            pmMcs3nss2RxPkt(15948),
            pmMcs4nss2RxPkt(15949),
            pmMcs5nss2RxPkt(15950),
            pmMcs6nss2RxPkt(15951),
            pmMcs7nss2RxPkt(15952),
            pmMcs8nss2RxPkt(15953),
            pmMcs9nss2RxPkt(15954),
            pmMcs0nss1TxPkt(15955),
            pmMcs1nss1TxPkt(15956),
            pmMcs2nss1TxPkt(15957),
            pmMcs3nss1TxPkt(15958),
            pmMcs4nss1TxPkt(15959),
            pmMcs5nss1TxPkt(15960),
            pmMcs6nss1TxPkt(15961),
            pmMcs7nss1TxPkt(15962),
            pmMcs8nss1TxPkt(15963),
            pmMcs9nss1TxPkt(15964),
            pmMcs0nss2TxPkt(15965),
            pmMcs1nss2TxPkt(15966),
            pmMcs2nss2TxPkt(15967),
            pmMcs3nss2TxPkt(15968),
            pmMcs4nss2TxPkt(15969),
            pmMcs5nss2TxPkt(15970),
            pmMcs6nss2TxPkt(15971),
            pmMcs7nss2TxPkt(15972),
            pmMcs8nss2TxPkt(15973),
            pmMcs9nss2TxPkt(15974),
            pmE3LcvSdh(37),
            pmE3LesSdh(38),
            pmE3LsesSdh(39),
            pmTcbbe(45),
            pmTcfebbe(46),
            pmTcobbe(47),
            pmEdfboxtmpmax(65),
            pmEdfboxtmpmin(66),
            pmEdfboxtmpcur(67),
            pmVc3bbe(80),
            pmVc3es(81),
            pmVc3ses(82),
            pmVc3febbe(83),
            pmVc3fees(84),
            pmVc3feses(85),
            pmVc3uas(86),
            pmVc3cses(87),
            pmVc3fecses(88),
            pmVc3feuas(89),
            pmOspiccvmax(99),
            pmOspiccvmin(100),
            pmOspiccvcur(101),
            pmWcvmax(112),
            pmWcvmin(113),
            pmWcvcur(114),
            pmCcvmax(115),
            pmCcvmin(116),
            pmCcvcur(117),
            pmBcvmax(118),
            pmBcvmin(119),
            pmEdrplmax(124),
            pmEdrplmin(125),
            pmEdrplcur(126),
            pmEdwcsmax(127),
            pmEdwcsmin(128),
            pmEdwcscur(129),
            pmEdtmpmax(130),
            pmEdtmpmin(131),
            pmEdtmpcur(132),
            pmFecCor0bitCnt(133),
            pmFecCor1bitCnt(134),
            pmEmuvolmax(138),
            pmEmuvolmin(139),
            pmEmuvolcur(141),
            pmT3LcvSdh(160),
            pmT3LesSdh(161),
            pmT3LsesSdh(162),
            pmT1LlossSdh(167),
            pmCrc4Err(185),
            pmDdnCrc4Err(186),
            pmXcstmpmax(188),
            pmXcstmpmin(189),
            pmXcstmpcur(190),
            pmSumiopmax(210),
            pmSumiopmin(211),
            pmSumiopcur(212),
            pmSumoopmax(213),
            pmSumoopmin(214),
            pmSumoopcur(215),
            pmEnvtmpmax(222),
            pmEnvtmpmin(223),
            pmEnvtmpcur(224),
            pmLsclcmax(225),
            pmLsclcmin(226),
            pmLsclccur(227),
            pmPclswlmax(228),
            pmPclswlmin(229),
            pmPclswlcur(230),
            pmPclswlomax(231),
            pmPclswlomin(232),
            pmPclswlocur(233),
            pmPclsopmax(234),
            pmPclsopmin(235),
            pmPclsopcur(236),
            pmPclssnmax(237),
            pmPclssnmin(238),
            pmPclssncur(239),
            pmCrc4bbe(240),
            pmCrc4es(241),
            pmCrc4ses(242),
            pmCrc4febbe(243),
            pmCrc4fees(244),
            pmCrc4feses(245),
            pmCrc4uas(246),
            pmCrc4cses(247),
            pmCrc4fecses(248),
            pmIctmpmax(249),
            pmIctmpmin(250),
            pmIctmpcur(251),
            pmCrc4feuas(254),
            pmOtu2smbip8(4170),
            pmOdu2pmbip8(4171),
            pmIcclcmax(4172),
            pmIcclcmin(4173),
            pmIcclccur(4174),
            pmCpTelDownCount(14915),
            pmCpTelDownTime(14916),
            pmCpCcDownCount(14917),
            pmCpCcDownTime(14918),
            pmQamws4096(15702),
            pmE3LlossSdh(40),
            pmLineOutPowermax(68),
            pmLineOutPowermin(69),
            pmLineOutPowercur(70),
            pmT3LlossSdh(163),
            pmLppsc(176),
            pmLppsd(177),
            pmDslCv(178),
            pmDslLosws(179),
            pmDslEs(180),
            pmDslSes(181),
            pmDslUas(182),
            pmDslLpa(183),
            pmDslSnr(184),
            pmPmutmpmax(192),
            pmPmutmpmin(193),
            pmPmutmpavg(194),
            pmLsOopMax(198),
            pmLsOopMin(199),
            pmLsOopCur(200),
            pmLsIopMax(201),
            pmLsIopMin(202),
            pmLsIopCur(203),
            pmLsTmpMax(204),
            pmLsTmpMin(205),
            pmLsTmpCur(206),
            pmLsBiasMax(207),
            pmLsBiasMin(208),
            pmLsBiasCur(209),
            pmPumptmpmax(216),
            pmPumptmpmin(217),
            pmPumptmpcur(218),
            pmPumpbisamax(219),
            pmPumpbisamin(220),
            pmPumpbisacur(221),
            pmLspOk(4128),
            pmLspFail(4129),
            pmPumpdrvcmax(4175),
            pmPumpdrvcmin(4176),
            pmPumpdrvccur(4177),
            pmPumpdrvvgmax(4178),
            pmPumpdrvvgmin(4179),
            pmPumpdrvvgcur(4180),
            pmTxBwutilExcs(15895),
            pmRxBwutilExcs(15896),
            pmBpskS62p5mWs(15897),
            pmBpskS125mWs(15898),
            pmPskWs8(15899),
            pmTolLdpwr(15903),
            pmBatvoltcur(15904),
            pmBatvoltmin(15905),
            pmBatvoltmax(15906),
            pmAcvoltcur(15907),
            pmAcvoltmin(15908),
            pmAcvlotmax(15909),
            pmTolAcpwr(15910),
            pmTolSolcurnt(15911),
            pmTolSoloutpwr(15912),
	    pmQamws8192(16079),
            pmTxBwutilExcsMin(16080),
            pmRxBwutilExcsMin(16081),
            pmTxBwutilExcsMid(16082),
            pmRxBwutilExcsMid(16083),
            pmTxBwutilExcsMax(16084),
            pmRxBwutilExcsMax(16085),
            pmQAMWS16384(16108),
            pmCrc6Err(8587),
            pmMAXCLKDA(16094),
            pmMINCLKDA(16095),
            pmAVGCLKDA(16096),
            pmRealPowerMax(16086),
            pmRealPowerMin(16087),
            pmRealPowerCur(16088),
            pmRealPowerAvg(16089),
            pmNomiPowerMax(16090),
            pmNomiPowerMin(16091),
            pmNomiPowerCur(16092),
            pmNomiPowerAvg(16093),
            pmMimoCapacityCur(16167),
            pmMimoCapacityMin(16168),
            pmMimoCapacityMax(16169),
            pmMimoCapacityAvg(16170),
            pmVDeflectMax(16208),
            pmVDeflectMin(16209),
            pmVDeflectCur(16210),
            pmShakeCount(16211),
	    pmHDeflectMax(16233),
            pmHDeflectMin(16234),
            pmHDeflectCur(16235),
	    pmVDeflectTs(16241),
	    pmIntternalAngleMax(16449),
	    pmIntternalAngleMin(16450),
	    pmIntternalAngleCur(16451)
        }
    ValidflagType ::= TEXTUAL-CONVENTION
        STATUS current
        DESCRIPTION
            "suspect interval flag of performance counter"
        SYNTAX INTEGER
        {
            invalid(0),
            valid(1)
        }

    ObjType ::= TEXTUAL-CONVENTION
        STATUS current
        DESCRIPTION
            "Objtype."
        SYNTAX INTEGER
        {
            ne(20),
            subcard(26),
            tunnel(40),
            pwIndex(41),
            pwofatm(42),
            pwofces(43),
            pwofl2vpn(44),
            atmConnection(45),
            l2vpnservice(46),
            vuniofces(47),
            vuniofl2vpn(48),
            mep(49),
            classifier(50),
            mlppp(51),
            apsGroup(52),
            tpsgroup(53),
            mstpportgroup(54),
            lag(55),
            synSource(56),
            sysClock(57),
            lpsgroup(58),
            mepperf(59),
            bfd(72),
            board(76),
            sccboard(77),
            fanbd(78),
            pwrBoard(79),
            laser(84),
            otu2path(89),
            odu2path(93),
            sdhPath(96),
            ethpath(98),
            port(101),
            ethPort(102),
            atmport(104),
            atmTrunk(105),
            och(106),
            newportpri(107),
            e1port(108),
            ifPort(110),
            oduPort(111),
            ifBoard(112),
            oduBoard(113),
            group1j1(114),
            odu2tcm1(126),
            odu2tcm2(127),
            odu2tcm3(128),
            odu2tcm4(129),
            odu2tcm5(130),
            odu2tcm6(131),
            lasergroup(119),
            sdhPort(144),
            vc12Path(146),
            vc34Path(147),
            ethvcgport(149),
            newsubcard(153),
            newsdhport(154),
            crossclockbd(152),
            virtualPort(155),
            vc4path(156),
            vc3path(158),
            ripnbr(159),
            ospfnbr(160),
            rsvpnbr(161),
            isisnbr(162),
            topsrv(163),
            l3vpnsrv(164),
            efi(167),
            l3vpnclassifier(171),
            wpidLaser(172),
            extClockIf(173),
            pwapsGroup(175),
            mcsp(177),
            lpt(178),
            cesacr(197),
            ldppeer(200),
            portflow(209),
            section(211),
            cvlanpriofds(212),
            svlanpriofds(213),
            ipdscpofds(214),
            vlanofvuni(215),
            vnniOfL2vpn(216),
            mplsring(218),
            mwport(220),
            vunigroup(221),
            vuniqueue(222),
            pwqueue(223),
            elps(224),
            pla(227),
            nmsport(228),
            testidperf(230),
            vrpisisadj(231),
            vrpbgp(232),
            vrpvrf(233),
            ipfpmInst(241),
            ethtrunk(242),
            vrpospfnbr(243),
            ipfpmInstance(244),
            wifi(247),
            cprilaser(250),
            cpriport(251),
            vrpldpssn(255),
            newmepperf(265),
            igsp(272),
            obsailaser(280),
            obsaiport(281),
            lptgroup(287),
            oducarrier(299),
            mimo(301)
        }

    DataPmEventType ::= TEXTUAL-CONVENTION
        STATUS current
        DESCRIPTION
            "Data Performance ID."
        SYNTAX INTEGER
        {
            pmRXPKT64(101),
            pmRXPKT65(102),
            pmRXPKT128(103),
            pmRXPKT256(104),
            pmRXPKT512(105),
            pmRXPKT1024(106),
            pmTXPKT64(107),
            pmTXPKT65(108),
            pmTXPKT128(109),
            pmTXPKT256(110),
            pmTXPKT512(111),
            pmTXPKT1024(112),
            pmRXUNICAST(113),
            pmRXMULCAST(114),
            pmRXBRDCAST(115),
            pmTXUNICAST(116),
            pmTXMULCAST(117),
            pmTXBRDCAST(118),
            pmRXPAUSE(119),
            pmTXPAUSE(120),
            pmETHDROP(121),
            pmETHUNDER(122),
            pmETHOVER(123),
            pmETHFRG(124),
            pmETHJAB(125),
            pmRXBGOOD(126),
            pmTXBGOOD(127),
            pmRXBBAD(128),
            pmTXBBAD(129),
            pmETHCOL(130),
            pmETHALI(131),
            pmETHFCS(132),
            pmETHUNICOL(133),
            pmETHMULCOL(134),
            pmETHLATECOL(135),
            pmETHEXCCOL(136),
            pmTXDEFFRM(137),
            pmETHCARERR(138),
            pmRXPKT1519(139),
            pmTXPKT1519(140),
            pmPKT64(141),
            pmPKT65(142),
            pmPKT128(143),
            pmPKT256(144),
            pmPKT512(145),
            pmPKT1024(146),
            pmPKT1519(147),
            pmRXGOODFULLFRAMESPEED(190),
            pmTXGOODFULLFRAMESPEED(191),
            pmRXFULLBGOOD(192),
            pmTXFULLBGOOD(193),
            pmRXCTLPKTS(194),
            pmTXCTLPKTS(195),
            pmTXETHDROP(196),
            pmTXETHOVER(197),
            pmTXPKTS(198),
            pmTXOCTETS(199),
            pmRXOCTETS(200),
            pmRXPKTS(201),
            pmETHCRCALI(202),
            pmETHUTILIZ(203),
            pmVCGRXOCTETS(350),
            pmVCGTXOCTETS(351),
            pmVCGRXPACKETS(352),
            pmVCGTXPACKETS(353),
            pmVCGRXGOODPACKETS(354),
            pmVCGTXGOODPACKETS(355),
            pmVCGRXSPEED(356),
            pmVCGTXSPEED(357),
            pmCESLOSPKTS(450),
            pmCESMISORDERPKTS(451),
            pmCESSTRAYPKTS(452),
            pmCESMALPKTS(453),
            pmCESJTRUDR(454),
            pmCESJTROVR(455),
            pmVUNIRCVPKTS(465),
            pmVUNIRCVBYTES(466),
            pmVUNISNDPKTS(467),
            pmVUNISNDBYTES(468),
            pmTUNNELRCVPKTS(469),
            pmTUNNELRCVBYTES(470),
            pmTUNNELSNDPKTS(471),
            pmTUNNELSNDBYTES(472),
            pmPWRCVPKTS(473),
            pmPWRCVBYTES(474),
            pmPWSNDPKTS(475),
            pmPWSNDBYTES(476),
            pmQOSSTRMMATCHPKTS(477),
            pmQOSSTRMMATCHBYTES(478),
            pmQOSCARGRNPKTS(479),
            pmQOSCARGRNBYTES(480),
            pmQOSCARYLWPKTS(481),
            pmQOSCARYLWBYTES(482),
            pmQOSCARREDPKTS(483),
            pmQOSCARREDBYTES(484),
            pmMPLSTUNNELFLR(485),
            pmMPLSTUNNELFL(486),
            pmMPLSTUNNELFD(487),
            pmMPLSTUNNELFDV(488),
            pmETHCFMFLR(489),
            pmETHCFMFL(490),
            pmETHCFMFD(491),
            pmETHCFMFDV(492),
            pmATMPWLOSPKTS(493),
            pmATMPWMISORDERPKTS(494),
            pmATMPWSNDCELLS(495),
            pmATMPWRCVCELLS(496),
            pmATMPWUNKNOWNCELLS(497),
            pmATMUNI1INCELLS(498),
            pmATMUNI1OUTCELLS(499),
            pmATMCORRECTEDHCSERR(500),
            pmATMUNCORRECTEDHCSERR(501),
            pmATMRCVCELLS(502),
            pmATMRCVIDLECELLS(503),
            pmATMSNDCELLS(504),
            pmPORTRXBYTESVAILABILITY(505),
            pmPWDROPPKTS(506),
            pmPWDROPBYTES(507),
            pmPWBANDWIDTHUTILISATION(508),
            pmPWAVAILABILITY(509),
            pmQOSPRIDROPPKTS(510),
            pmQOSPRIDROPBYTES(511),
            pmATMIFINRATEMAX(513),
            pmATMIFINRATEMIN(514),
            pmATMIFINRATEAVG(515),
            pmATMIFOUTRATEMAX(516),
            pmATMIFOUTRATEMIN(517),
            pmATMIFOUTRATEAVG(518),
            pmATMCELLAVAILABILITY(519),
            pmATMUNI1INRATEMAX(520),
            pmATMUNI1INRATEMIN(521),
            pmATMUNI1INRATEAVG(522),
            pmATMUNI1OUTRATEMAX(523),
            pmATMUNI1OUTRATEMIN(524),
            pmATMUNI1OUTRATEAVG(525),
            pmATMBOARDDROPCELLS(526),
            pmCESRXPKTS(532),
            pmPPPTXPKTS(534),
            pmPPPTXBYTES(535),
            pmPPPRXPKTS(536),
            pmPPPRXBYTES(537),
            pmPPPRXFCSPKTS(538),
            pmPPPTXLOSPKTS(547),
            pmPPPRXLOSPKTS(548),
            pmPPPRXBWUTILIZATION(549),
            pmPPPTXBWUTILIZATION(550),
            pmMPTXPKTS(551),
            pmMPTXBYTES(552),
            pmMPRXPKTS(553),
            pmMPRXBYTES(554),
            pmMPRXERRPKTS(555),
            pmMPTXTOTALPKTS(556),
            pmMPRXTOTALPKTS(557),
            pmMPRXBWUTILIZATION(558),
            pmMPTXBWUTILIZATION(559),
            pmPORTRXBWUTILIZATION(567),
            pmPORTTXBWUTILIZATION(568),
            pmTNLBWUTILISATION(577),
            pmATMUNI2INCELLS(578),
            pmATMUNI2OUTCELLS(579),
            pmATMUNI2INRATEMAX(580),
            pmATMUNI2INRATEMIN(581),
            pmATMUNI2INRATEAVG(582),
            pmATMUNI2OUTRATEMAX(583),
            pmATMUNI2OUTRATEMIN(584),
            pmATMUNI2OUTRATEAVG(585),
            pmTUNNELREVERSESNDPKTS(586),
            pmTUNNELREVERSESNDBYTES(587),
            pmTUNNELREVERSERCVPKTS(588),
            pmTUNNELREVERSERCVBYTES(589),
            pmMPLSPWFLR(590),
            pmMPLSPWFL(591),
            pmMPLSPWFD(592),
            pmMPLSPWFDV(593),
            pmTNLREVERSEBWUTILISATION(600),
            pmQOSPORTSTRMRCVMATCHPKTS(614),
            pmQOSPORTSTRMRCVMATCHBYTES(615),
            pmQOSPORTSTRMSNDMATCHPKTS(616),
            pmQOSPORTSTRMSNDMATCHBYTES(617),
            pmQOSPORTCARMarkedRedPKTS(618),
            pmQOSPORTCARMarkedYellowPKTS(620),
            pmQOSPORTCARMarkedGreenPKTS(622),
            pmMPLSTUNNEL1WFD(624),
            pmMPLSTUNNEL1WFDV(625),
            pmMPLSPW1WFD(626),
            pmMPLSPW1WFDV(627),
            pmDSCVLANPRIPKTS(638),
            pmDSCVLANPRIBYTES(639),
            pmDSSVLANPRIPKTS(640),
            pmDSSVLANPRIBYTES(641),
            pmDSDSCPPKTS(642),
            pmDSDSCPBYTES(643),
            pmVLANRCVPKTS(644),
            pmVLANRCVBYTES(645),
            pmVLANSNDPKTS(646),
            pmVLANSNDBYTES(647),
            pmPORTPRISNDPKTS(648),
            pmPORTPRISNDBYTES(649),
            pmPORTSTRMSHAPINGDROPPKTS(650),
            pmPORTSTRMSHAPINGDROPBYTES(651),
            pmPORTSTRMSHAPINGDROPRATIO(652),
            pmQOSPORTCARMarkedRedRATIO(653),
            pmQOSPORTQUEUEDROPRATIO(654),
            pmFLOWRXUTILIZATION(655),
            pmVUNITXUTILIZATION(657),
            pmVUNIGROUPSNDPKTS(658),
            pmVUNIGROUPSNDBYTES(659),
            pmVGROUPTXUTILIZATION(662),
            pmVUNIQUEUESNDDROPPKTS(663),
            pmVUNIQUEUESNDDROPBYTES(664),
            pmVUNIQUEUESNDDROPRATIO(665),
            pmVUNIGROUPSNDDROPPKTS(666),
            pmVUNIGROUPSNDDROPBYTES(667),
            pmVUNIGROUPSNDDROPRATIO(668),
            pmPWQUEUESNDDROPPKTS(669),
            pmPWQUEUESNDDROPBYTES(670),
            pmPWQUEUESNDDROPRATIO(671),
            pmTNLSNDDROPPKTS(672),
            pmTNLSNDDROPBYTES(673),
            pmTNLSNDDROPRATIO(674),
            pmQOSCARREDRATIO(675),
            pmTNLREVERSESNDDROPPKTS(676),
            pmTNLREVERSESNDDROPBYTES(677),
            pmTNLREVERSESNDDROPRATIO(678),
            pmRXBPS(679),
            pmTXBPS(680),
	    pmRXPPS(681),
            pmTXPPS(682),
            pmETHRXTHROUGHPUTMAX(683),
            pmETHRXTHROUGHPUTMIN(684),
            pmETHRXTHROUGHPUTAVG(685),
            pmETHTXTHROUGHPUTMAX(686),
            pmETHTXTHROUGHPUTMIN(687),
            pmETHTXTHROUGHPUTAVG(688),
            pmVUNISNDDROPPKTS(689),
            pmVUNISNDDROPBYTES(690),
            pmVUNISNDDROPRATIO(691),
            pmRXDROPRATIO(692),
            pmTXDROPRATIO(693),
            pmTUNNELREVERSERXBPS(698),
            pmTUNNELREVERSETXBPS(699),
            pmTUNNELREVERSERXPPS(700),
            pmTUNNELREVERSETXPPS(701),
            pmTUNNELRXBPS(702),
            pmTUNNELTXBPS(703),
            pmTUNNELRXPPS(704),
            pmTUNNELTXPPS(705),
            pmPWRXBPS(706),
            pmPWTXBPS(707),
            pmPWRXPPS(708),
            pmPWTXPPS(709),
            pmVUNIRXBPS(710),
            pmVUNITXBPS(711),
            pmVUNIRXPPS(712),
            pmVUNITXPPS(713),
            pmVLANRXBPS(714),
            pmVLANTXBPS(715),
            pmVLANRXPPS(716),
            pmVLANTXPPS(717),
            pmQOSPORTSTRMRXBPS(718),
            pmQOSPORTSTRMTXBPS(719),
            pmQOSPORTSTRMRXPPS(720),
            pmQOSPORTSTRMTXPPS(721),
            pmPORTPRITXBPS(722),
            pmPORTPRITXPPS(723),
            pmPWQUEUETXBPS(724),
            pmPWQUEUETXPPS(725),
            pmETHCFMFLRPRI0(726),
            pmETHCFMFLPRI0(727),
            pmETHCFMFDPRI0(728),
            pmETHCFMFDVPRI0(729),
            pmETHCFMFLRPRI1(730),
            pmETHCFMFLPRI1(731),
            pmETHCFMFDPRI1(732),
            pmETHCFMFDVPRI1(733),
            pmETHCFMFLRPRI2(734),
            pmETHCFMFLPRI2(735),
            pmETHCFMFDPRI2(736),
            pmETHCFMFDVPRI2(737),
            pmETHCFMFLRPRI3(738),
            pmETHCFMFLPRI3(739),
            pmETHCFMFDPRI3(740),
            pmETHCFMFDVPRI3(741),
            pmETHCFMFLRPRI4(742),
            pmETHCFMFLPRI4(743),
            pmETHCFMFDPRI4(744),
            pmETHCFMFDVPRI4(745),
            pmETHCFMFLRPRI5(746),
            pmETHCFMFLPRI5(747),
            pmETHCFMFDPRI5(748),
            pmETHCFMFDVPRI5(749),
            pmETHCFMFLRPRI6(750),
            pmETHCFMFLPRI6(751),
            pmETHCFMFDPRI6(752),
            pmETHCFMFDVPRI6(753),
            pmETHCFMFLRPRI7(754),
            pmETHCFMFLPRI7(755),
            pmETHCFMFDPRI7(756),
            pmETHCFMFDVPRI7(757),
            pmETHCFMLANFLTX(758),
            pmETHCFMLANFLRRX(759),
            pmETHCFMLANFLRX(760),
            pmETHCFMLANFD(761),
            pmETHCFMLANFDV(762),
            pmETHCFMLANFPSTX(765),
            pmETHCFMLANFBPSTX(766),
            pmETHCFMLANFPSRX(767),
            pmETHCFMLANFBPSRX(768),
            pmETHCFMFLRTXMAX(769),
            pmETHCFMFLRTXMIN(770),
            pmETHCFMFLRTXAVG(771),
            pmETHCFMFLRRXMAX(772),
            pmETHCFMFLRRXMIN(773),
            pmETHCFMFLRRXAVG(774),
            pmETHCFMLANFPSTXMAX(775),
            pmETHCFMLANFPSTXMIN(776),
            pmETHCFMLANFPSTXAVG(777),
            pmETHCFMLANFBPSTXMAX(778),
            pmETHCFMLANFBPSTXMIN(779),
            pmETHCFMLANFBPSTXAVG(780),
            pmETHCFMLANFPSRXMAX(781),
            pmETHCFMLANFPSRXMIN(782),
            pmETHCFMLANFPSRXAVG(783),
            pmETHCFMLANFBPSRXMAX(784),
            pmETHCFMLANFBPSRXMIN(785),
            pmETHCFMLANFBPSRXAVG(786),
            pmETHCFMLANFDMAX(787),
            pmETHCFMLANFDMIN(788),
            pmETHCFMLANFDAVG(789),
            pmETHCFMLANFDVMAX(790),
            pmETHCFMLANFDVMIN(791),
            pmETHCFMLANFDVAVG(792),
            pmETHCFMLANFLRTX(799),
            pmVUNIRXUTILIZATION(800),
            pmMPLSPWFLN(801),
            pmMPLSPWFLRN(802),
            pmMPLSTUNNELFLN(803),
            pmMPLSTUNNELFLRN(804),
            pmETHCFMFLRN(805),
            pmETHCFMFLN(806),
            pmPORTRXBWUTILIZATIONMIN(839),
            pmPORTRXBWUTILIZATIONAVG(840),
            pmPORTRXBWUTILIZATIONMAX(841),
            pmPORTTXBWUTILIZATIONMIN(842),
            pmPORTTXBWUTILIZATIONAVG(843),
            pmPORTTXBWUTILIZATIONMAX(844),
            pmTNLBWUTILISATIONMIN(859),
            pmTNLBWUTILISATIONAVG(860),
            pmTNLBWUTILISATIONMAX(861),
            pmTNLREVERSEBWUTILISATIONMIN(862),
            pmTNLREVERSEBWUTILISATIONAVG(863),
            pmTNLREVERSEBWUTILISATIONMAX(864),
            pmPWBANDWIDTHUTILISATIONMIN(865),
            pmPWBANDWIDTHUTILISATIONAVG(866),
            pmPWBANDWIDTHUTILISATIONMAX(867),
            pmTXDROPPKTS(868),
            pmRXDROPPKTS(869),
            pmTXBPSMIN(894),
            pmTXBPSAVG(895),
            pmTXBPSMAX(896),
            pmRXBPSMIN(897),
            pmRXBPSAVG(898),
            pmRXBPSMAX(899),
            pmECMPRSRATIO(941),
            pmTXHSTRAFFBWRATIO(956),
            pmRXBRDCASTRATIO(957),
            pmTXBRDCASTRATIO(958),
            pmQosPriBandwidthUtilisation(512),
            pmCesRxBytes(533),
            pmEthbadpkts(560),
            pmAtmpwBwUtilization(569),
            pmFlowTxUtilization(656),
            pmVunigroupRcvpkts(660),
            pmVunigroupRcvbytes(661),
            pmEthCfmFlrPri1N(807),
            pmEthCfmFlrPri0N(808),
            pmEthCfmFlrPri2N(809),
            pmEthCfmFlrPri3N(810),
            pmEthCfmFlrPri4N(811),
            pmEthCfmFlrPri5N(812),
            pmEthCfmFlrPri6N(813),
            pmEthCfmFlrPri7N(814),
            pmEthCfmFlPri0N(815),
            pmEthCfmFlPri1N(816),
            pmEthCfmFlPri2N(817),
            pmEthCfmFlPri3N(818),
            pmEthCfmFlPri4N(819),
            pmEthCfmFlPri5N(820),
            pmEthCfmFlPri6N(821),
            pmEthCfmFlPri7N(822),
            pmCesTxPkts(906),
            pmVlanRxUtilization(954),
            pmVlanTxUtilization(955),
            pmRxMaxBwUtilizationCapacity(966),
            pmTxMaxBwUtilizationCapacity(967)
        }

END
