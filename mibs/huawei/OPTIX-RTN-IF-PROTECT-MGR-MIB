-- OPTIX-RTN-IF-PROTECT-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-IF-PROTECT-MGR-MIB DEFINITIONS ::= BEGIN
    IMPORTS
        OBJECT-GROUP,MODULE-COMPLIANCE
            FROM SNMPv2-CONF
        Integer32,Unsigned32,OBJECT-TYPE,MODULE-IDENTITY,NOTIFICATION-TYPE
            FROM SNMPv2-SMI
        TEXTUAL-CONVENTION,RowStatus
            FROM SNMPv2-TC
        optixProvisionRtn
            FROM OPTIX-OID-MIB
        OPTIXRtnEnableStateType,optixRtnIndex1,optixRtnIndex2,optixRtnIndex3,optixRtnIndex4,optixRtngroupIndex,optixRtnboardIndex,optixRtnsubboardIndex,optixRtnportIndex
            FROM OPTIX-RTN-GENNERAL-MIB
        OPTIXRtnModulateModeType,OPTIXRtnBandWidthType,optixRtnBoardID,optixRtnSubCardID,optixRtnPortID
            FROM OPTIX-RTN-IFBOARD-ATTRIB-MIB
        OPTIXRtnOduWorkStateType
            FROM OPTIX-RTN-ODU-MGR-MIB
        ;

    optixRtnIFProtectMgr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query information about IF 1+1, IF N+1, XPIC, and PLA protection groups of RTN equipment, including the board position mapping, switching parameters, and the protection group status."
        REVISION "201204160935Z"
        DESCRIPTION
            "The initial revision of this MIB module1."
        ::={ optixProvisionRtn 5 }

    OPTIXRtn1j1PGSwCmdType ::= TEXTUAL-CONVENTION
        STATUS current
        DESCRIPTION
            "Indicates the switching type of an IF 1+1 protection group. The value can be Manual, Force, Lockout, Clear, or unknown."
        SYNTAX INTEGER
        {
            if1j1Manual(0),
            if1j1Force(1),
            if1j1Lockout(2),
            if1j1Clear(3),
            unknown(-1)
        }

    OPTIXRtn1j1PGSwDirType ::= TEXTUAL-CONVENTION
        STATUS current
        DESCRIPTION
            "Indicates the switching direction of an IF 1+1 protection group. The value can be WorkToProtect, ProtectToWork, or unknown."
        SYNTAX INTEGER
        {
            if1j1WorkToProtect(0),
            if1j1ProtectToWork(1),
            unknown(-1)
        }

    OPTIXRtnNj1PGSwCmdType ::= TEXTUAL-CONVENTION
        STATUS current
        DESCRIPTION
            "Indicates the switching type of an IF N+1 protection group. The value can be Lock, Unlock, Force, Forceclr, Man, Manclr, Exer, Exerclr, Clearall, Wtrclr, or unknown."
        SYNTAX Unsigned32
        {
            ifNj1Lock(15),
            ifNj1Unlock(31),
            ifNj1Force(14),
            ifNj1Forceclr(30),
            ifNj1Man(8),
            ifNj1Manclr(24),
            ifNj1Exer(4),
            ifNj1Exerclr(20),
            ifNj1Clearall(16),
            ifNj1Wtrclr(22),
            null(255)
        }

    OPTIXRtnCascading1j1PGProtectType ::= TEXTUAL-CONVENTION
        STATUS current
        DESCRIPTION
            "Indicates the service protection type of a cascading IF 1+1 protection group. Values: 0: noprot 1: lagprot 2: splitprot 255: invalid"
        SYNTAX Unsigned32
        {
            noprot(0),
            lagprot(1),
            splitprot(2),
            invalid(255)
        }

    OPTIXRtnCascadingPhyLagPGProtectTypeExt ::= TEXTUAL-CONVENTION
        STATUS current
        DESCRIPTION
            "Indicates the type of a cascading IF PLA protection group. Values:0: no protection 1: LAG protection 2: optical splitter protection 3:active active protection"
        SYNTAX INTEGER
        {
            noProtect(0),
            lagProtect(1),
            splitProtect(2),
            activeActive(3)
        }

    OPTIXRtnPgType ::= TEXTUAL-CONVENTION
        STATUS current
        DESCRIPTION
            "Indicates the protection group type."
        SYNTAX INTEGER
        {
            if1j1(1),
            vs1j1(2)
        }

    AlarmINHPG1J1EventType ::= TEXTUAL-CONVENTION
        STATUS current
        DESCRIPTION
            "Indicates the alarm ID for inhibition."
        SYNTAX INTEGER
        {
            almMwBerEXC(12870),
            almMwBerSD(12871),
            almMwRdi(12587),
            almRadioRslLow(638),
            almMacExtExc(13444),
            almMacFcsExc(12794),
	    all(0)
        }

    OPTIXRtnExtNj1Mode ::= TEXTUAL-CONVENTION
        STATUS current
        DESCRIPTION
            "Indicates the mode of the N+1 protection group."
        SYNTAX INTEGER
        {
            normal(0),
            enhanced(1)
        }

    OPTIXRtnNJ1ProtocolState ::= TEXTUAL-CONVENTION
        STATUS current
        DESCRIPTION
            "Indicates the status of the N+1 protection group."
        SYNTAX INTEGER
        {
            stop(0),
            start(1)
        }

    OPTIXRtn1j1DevWorkBoardProperty ::= TEXTUAL-CONVENTION
        STATUS current
        DESCRIPTION
            "Indicates the Property of 1j1 protect group"
        SYNTAX INTEGER
        {
            work(0),
            port(1),
            unknown(-1)
        }

    OPTIXRtnCascading1j1PGRoleType ::= TEXTUAL-CONVENTION
        STATUS current
        DESCRIPTION
            "Indicates the role of a cascading IF 1+1 protection group. Values: 0: working 1: protection"
        SYNTAX INTEGER
        {
            work(0),
            protect(1)
        }

    OPTIXRtnPhyLagPGStatus ::= TEXTUAL-CONVENTION
        STATUS current
        DESCRIPTION
            "Indicates the status of a PLA protection group. Values: 0: normal 1: abnormal -1: unknown"
        SYNTAX INTEGER
        {
            normal(0),
            abnormal(1),
            inhibited(2),
            uniNormal(3),
            unknown(-1)
        }

    OPTIXRtn1j1SwtichRequestType ::= TEXTUAL-CONVENTION
        STATUS current
        DESCRIPTION
            "Indicates the switching request of an IF 1+1 protection group. Value range: 0: normal 1: automatic 2: manual 3: forced 4: lockout 5: wait to restore 6: RDI"
        SYNTAX INTEGER
        {
            normal(0),
            automatic(1),
            manual(2),
            forced(3),
            lockout(4),
            waitRestore(5),
            rdi(6)
        }

    OPTIXRtn1j1LinkStateType ::= TEXTUAL-CONVENTION
        STATUS current
        DESCRIPTION
            "Indicates the IF 1+1 link status. Values: 0: normal 1: signal failure 2: signal deterioration -1: invalid"
        SYNTAX INTEGER
        {
            normal(0),
            signalFailure(1),
            signalDeterioration(2),
            invalid(-1)
        }

    OPTIXRtnPhyLagPGStateWorkStatus ::= TEXTUAL-CONVENTION
        STATUS current
        DESCRIPTION
            "Indicates the channel status of a PLA protection group. Values: 0: slave 1: master -1: unknown"
        SYNTAX INTEGER
        {
            slave(0),
            master(1),
            unknown(-1)
        }

    OPTIXRtnNj1PGSwitchRequestType ::= TEXTUAL-CONVENTION
        STATUS current
        DESCRIPTION
            "Indicates the switching request of an IF N+1 protection group. Values: 240: lockout 224: force 208: SF 176: SD 128: manual 96: wait to restore 64: exercise switching 32: reverse request 0: No request"
        SYNTAX INTEGER
        {
            lockout(240),
            force(224),
            sf(208),
            sd(176),
            manual(128),
            waitRestore(96),
            exerciseSwitching(64),
            reverseRequest(32),
            noRequest(0),
	    forceLow(192),
	    dnr(16)
        }

    OPTIXRtnNj1PGFarNearType ::= TEXTUAL-CONVENTION
        STATUS current
        DESCRIPTION
            "Indicates the switching far and near ends of an IF N+1 protection group. Values: 0: none 1: near end 2: far end"
        SYNTAX INTEGER
        {
            nornindi(0),
            near(1),
            remote(2)
        }

    OPTIXRtnPhyLagPGType ::= TEXTUAL-CONVENTION
        STATUS current
        DESCRIPTION
            "Indicates the type of an IF PLA protection group. Values: 0: pla, 1: epla, 2: nbpla, 3: nbepla,4: epla plus,5: sepla"
        SYNTAX INTEGER
        {
            pla(0),
            epla(1),
            nbpla(2),
            nbepla(3),
            eplaplus(4),
            sepla(5),
            seplaslave(6),
            seplasecondgeneration(7),
            seplaslavesecondgeneration(8)
        }

    OPTIXRtnCascadingPLAPGRoleType ::= TEXTUAL-CONVENTION
        STATUS current
        DESCRIPTION
            "Indicates the role of a cascading IF PLA protection group. Values: 0: slave NE 1: main NE -1:unknown"
        SYNTAX INTEGER
        {
            slave(0),
            master(1),
            unknown(-1)
        }

    OPTIXRtn1j1PGWorkModeType ::= TEXTUAL-CONVENTION
        STATUS current
        DESCRIPTION
            "Indicates the working mode of an IF 1+1 protection group. Values: 0: SD 1: FD 2: HSB"
        SYNTAX INTEGER
        {
            modeSD(0),
            modeFD(1),
            modeHSB(2)
        }

    OPTIXRtn1j1PGAlmReportModeType ::= TEXTUAL-CONVENTION
        STATUS current
        DESCRIPTION
            "Indicates the service alarm report mode. Values: 1: only board alarms 2: only protection group alarms 3: Protection group and board alarms"
        SYNTAX INTEGER
        {
            onlyBoardAlm(1),
            onlyProtectionGroupAlm(2),
            bothPgAndBoard(3)
        }

    OPTIXRtnRvtModeType ::= TEXTUAL-CONVENTION
        STATUS current
        DESCRIPTION
            "Indicates the revertive mode of an IF protection group. Values: 0: Norvt (non-revertive) 1: Rvt (revertive)"
        SYNTAX INTEGER
        {
            noRvt(0),
            rvt(1)
        }

    OPTIXRtnCascadingPhyLagPGProtectType ::= TEXTUAL-CONVENTION
        STATUS current
        DESCRIPTION
            "Indicates the type a cascading IF PLA protection group. Values:0: unprotected 1: protected -1: invalid"
        SYNTAX INTEGER
        {
            noProtect(0),
            protect(1),
            invalid(-1)
        }

    OPTIXRtn1j1PGBDStateType ::= TEXTUAL-CONVENTION
        STATUS current
        DESCRIPTION
            "Indicates the working status of an IF 1+1 board. Values: 0: normal 1: switching 2: RDI switching -1: unknown"
        SYNTAX INTEGER
        {
            normal(0),
            fail(1),
            rdiSwitching(2),
            unknown(-1)
        }

    OPTIXRtnNj1SwitchStateType ::= TEXTUAL-CONVENTION
        STATUS current
        DESCRIPTION
            "Indicates the switching status of an IF N+1 protection group. Values: 0: not started 1: idling 4: switching -1: protocol is starting"
        SYNTAX INTEGER
        {
            stop(0),
            idling(1),
            switching(4),
            starting(-1)
        }

    OPTIXRtnNj1PGSwitchReasonType ::= TEXTUAL-CONVENTION
        STATUS current
        DESCRIPTION
            "Cause type for IF 1+1 protection switching"
        SYNTAX INTEGER
        {
            local(1),
            extsw(2),
            kByte(3),
            timerOut(4)
        }

    OPTIXRtnStrategyType ::= TEXTUAL-CONVENTION
        STATUS current
        DESCRIPTION
            "Indicates the type of energysave"
        SYNTAX INTEGER
        {
            green(0)
        }

    -- 1.3.6.1.4.1.2011.2.25.4.40.5.10
    optixRtnIFProtect OBJECT IDENTIFIER ::= { optixRtnIFProtectMgr 10 }

    -- 1.3.6.1.4.1.2011.2.25.4.40.5.10.10
    optixRtn1j1PGParameterTable OBJECT-TYPE
        SYNTAX SEQUENCE OF OptixRtn1j1PGParameterEntry
        MAX-ACCESS not-accessible
        STATUS current
        DESCRIPTION
            "Describes configuration parameters for the working board and protection board in an IF 1+1 protection group."
        ::= { optixRtnIFProtect 10 }

    -- 1.3.6.1.4.1.2011.2.25.4.40.5.10.10.1
    optixRtn1j1PGParameterEntry OBJECT-TYPE
        SYNTAX OptixRtn1j1PGParameterEntry
        MAX-ACCESS not-accessible
        STATUS current
        DESCRIPTION
            "Indicates the parameter entry for an IF 1+1 protection group."
        INDEX{ optixRtn1j1PGID }
        ::= { optixRtn1j1PGParameterTable 1 }

    OptixRtn1j1PGParameterEntry ::=
        SEQUENCE {
            optixRtn1j1PGID
                Unsigned32,
            optixRtn1j1PGWorkBoardID
                Unsigned32,
            optixRtn1j1PGWorkSubCardID
                Unsigned32,
            optixRtn1j1PGWorkPortID
                Unsigned32,
            optixRtn1j1PGProtectBoardID
                Unsigned32,
            optixRtn1j1PGProtectSubCardID
                Unsigned32,
            optixRtn1j1PGProtectPortID
                Unsigned32,
            optixRtn1j1PGWorkMode
                OPTIXRtn1j1PGWorkModeType,
            optixRtn1j1PGRevertiveMode
                OPTIXRtnRvtModeType,
            optixRtn1j1PGWTRTime
                Unsigned32,
            optixRtn1j1PGRDISwEnableState
                OPTIXRtnEnableStateType,
            optixRtn1j1PGAlmReportMode
                OPTIXRtn1j1PGAlmReportModeType,
            optixRtn1j1PGAntiJitterTime
                Unsigned32,
            optixRtn1j1PGSwCmd
                OPTIXRtn1j1PGSwCmdType,
            optixRtn1j1PGSwDir
                OPTIXRtn1j1PGSwDirType,
            optixRtn1j1PGCfgRowStatus
                RowStatus
        }

    -- 1.3.6.1.4.1.2011.2.25.4.40.5.10.10.1.1
    optixRtn1j1PGID OBJECT-TYPE
        SYNTAX Unsigned32
        MAX-ACCESS not-accessible
        STATUS current
        DESCRIPTION
            "Indicates the IF 1+1 protection group ID."
        ::= { optixRtn1j1PGParameterEntry 1 }

    -- 1.3.6.1.4.1.2011.2.25.4.40.5.10.10.1.2
    optixRtn1j1PGWorkBoardID OBJECT-TYPE
        SYNTAX Unsigned32
        MAX-ACCESS read-create
        STATUS current
        DESCRIPTION
            "Indicates the working board ID of an IF 1+1 protection group."
        ::= { optixRtn1j1PGParameterEntry 2 }

    -- 1.3.6.1.4.1.2011.2.25.4.40.5.10.10.1.3
    optixRtn1j1PGWorkSubCardID OBJECT-TYPE
        SYNTAX Unsigned32
        MAX-ACCESS read-create
        STATUS current
        DESCRIPTION
            "Indicates the working subboard ID of an IF 1+1 protection group."
        DEFVAL{ 255 }
        ::= { optixRtn1j1PGParameterEntry 3 }

    -- 1.3.6.1.4.1.2011.2.25.4.40.5.10.10.1.4
    optixRtn1j1PGWorkPortID OBJECT-TYPE
        SYNTAX Unsigned32
        MAX-ACCESS read-create
        STATUS current
        DESCRIPTION
            "Indicates the working port ID of an IF 1+1 protection group."
        DEFVAL{ 1 }
        ::= { optixRtn1j1PGParameterEntry 4 }

    -- 1.3.6.1.4.1.2011.2.25.4.40.5.10.10.1.5
    optixRtn1j1PGProtectBoardID OBJECT-TYPE
        SYNTAX Unsigned32
        MAX-ACCESS read-create
        STATUS current
        DESCRIPTION
            "Indicates the protection board ID of an IF 1+1 protection group."
        ::= { optixRtn1j1PGParameterEntry 5 }

    -- 1.3.6.1.4.1.2011.2.25.4.40.5.10.10.1.6
    optixRtn1j1PGProtectSubCardID OBJECT-TYPE
        SYNTAX Unsigned32
        MAX-ACCESS read-create
        STATUS current
        DESCRIPTION
            "Indicates the protection subboard ID of an IF 1+1 protection group."
        DEFVAL{ 255 }
        ::= { optixRtn1j1PGParameterEntry 6 }

    -- 1.3.6.1.4.1.2011.2.25.4.40.5.10.10.1.7
    optixRtn1j1PGProtectPortID OBJECT-TYPE
        SYNTAX Unsigned32
        MAX-ACCESS read-create
        STATUS current
        DESCRIPTION
            "Indicates the protection port ID of an IF 1+1 protection group."
        DEFVAL{ 1 }
        ::= { optixRtn1j1PGParameterEntry 7 }

    -- 1.3.6.1.4.1.2011.2.25.4.40.5.10.10.1.8
    optixRtn1j1PGWorkMode OBJECT-TYPE
        SYNTAX OPTIXRtn1j1PGWorkModeType
        MAX-ACCESS read-create
        STATUS current
        DESCRIPTION
            "Indicates the working mode of an IF 1+1 protection group. Values: 0: SD 1: FD 2: HSB"
        DEFVAL{ 2 }
        ::= { optixRtn1j1PGParameterEntry 8 }

    -- 1.3.6.1.4.1.2011.2.25.4.40.5.10.10.1.9
    optixRtn1j1PGRevertiveMode OBJECT-TYPE
        SYNTAX OPTIXRtnRvtModeType
        MAX-ACCESS read-create
        STATUS current
        DESCRIPTION
            "Indicates the revertive mode of an IF 1+1 protection group. Values: 0: Norvt (non-revertive) 1: Rvt (revertive)"
        DEFVAL{ 1 }
        ::= { optixRtn1j1PGParameterEntry 9 }

    -- 1.3.6.1.4.1.2011.2.25.4.40.5.10.10.1.10
    optixRtn1j1PGWTRTime OBJECT-TYPE
        SYNTAX Unsigned32
        MAX-ACCESS read-create
        STATUS current
        DESCRIPTION
            "Indicates the WTR time of an IF 1+1 protection group. Value
        range: 300s to 720s"
        DEFVAL{ 600 }
        ::= { optixRtn1j1PGParameterEntry 10 }

    -- 1.3.6.1.4.1.2011.2.25.4.40.5.10.10.1.11
    optixRtn1j1PGRDISwEnableState OBJECT-TYPE
        SYNTAX OPTIXRtnEnableStateType
        MAX-ACCESS read-write
        STATUS current
        DESCRIPTION
            "Indicates the reverse switching status of an IF 1+1 protection
        group(this node is used only on RTN900 devices). Values: 0: disabled 1: enabled"
        DEFVAL{ 1 }
        ::= { optixRtn1j1PGParameterEntry 11 }

    -- 1.3.6.1.4.1.2011.2.25.4.40.5.10.10.1.12
    optixRtn1j1PGAlmReportMode OBJECT-TYPE
        SYNTAX OPTIXRtn1j1PGAlmReportModeType
        MAX-ACCESS read-write
        STATUS current
        DESCRIPTION
            "Indicates the service alarm report mode of an IF 1+1 protection group(this node is used only on RTN900 devices). Values: 1: only board alarms 2: only protection group alarms 3: PG group and board alarms"
        DEFVAL{ 1 }
        ::= { optixRtn1j1PGParameterEntry 12 }

    -- 1.3.6.1.4.1.2011.2.25.4.40.5.10.10.1.13
    optixRtn1j1PGAntiJitterTime OBJECT-TYPE
        SYNTAX Unsigned32
        MAX-ACCESS read-write
        STATUS current
        DESCRIPTION
            "Indicates the anti-jitter time of the switching alarm for an IF 1+1 protection group(this node is used only on RTN900 devices). Value range: 0s to 600s"
        DEFVAL{ 300 }
        ::= { optixRtn1j1PGParameterEntry 13 }

    -- 1.3.6.1.4.1.2011.2.25.4.40.5.10.10.1.14
    optixRtn1j1PGSwCmd OBJECT-TYPE
        SYNTAX OPTIXRtn1j1PGSwCmdType
        MAX-ACCESS read-write
        STATUS current
        DESCRIPTION
            "Indicates the switching mode of an IF 1+1 protection group(this node is used only on RTN900 devices)."
        ::= { optixRtn1j1PGParameterEntry 14 }

    -- 1.3.6.1.4.1.2011.2.25.4.40.5.10.10.1.15
    optixRtn1j1PGSwDir OBJECT-TYPE
        SYNTAX OPTIXRtn1j1PGSwDirType
        MAX-ACCESS read-write
        STATUS current
        DESCRIPTION
            "Indicates the switching direction of an IF 1+1 protection group(this node is used only on RTN900 devices)."
        ::= { optixRtn1j1PGParameterEntry 15 }

    -- 1.3.6.1.4.1.2011.2.25.4.40.5.10.10.1.50
    optixRtn1j1PGCfgRowStatus OBJECT-TYPE
        SYNTAX RowStatus
        MAX-ACCESS read-create
        STATUS current
        DESCRIPTION
            "Indicates the row status of an IF 1+1 protection group."
        DEFVAL{ active }
        ::= { optixRtn1j1PGParameterEntry 50 }

    -- 1.3.6.1.4.1.2011.2.25.4.40.5.10.20
    optixRtn1j1PGStateTable OBJECT-TYPE
        SYNTAX SEQUENCE OF OptixRtn1j1PGStateEntry
        MAX-ACCESS not-accessible
        STATUS current
        DESCRIPTION
            "Describes the current status of an IF 1+1 protection group, including the current working board and switching status of the protection group."
        ::= { optixRtnIFProtect 20 }

    -- 1.3.6.1.4.1.2011.2.25.4.40.5.10.20.1
    optixRtn1j1PGStateEntry OBJECT-TYPE
        SYNTAX OptixRtn1j1PGStateEntry
        MAX-ACCESS not-accessible
        STATUS current
        DESCRIPTION
            "Indicates the parameter entry for the current status of an IF 1+1 protection group."
        INDEX{ optixRtn1j1PGID }
        ::= { optixRtn1j1PGStateTable 1 }

    OptixRtn1j1PGStateEntry ::=
        SEQUENCE {
            optixRtn1j1PGStateDevWorkBoardID
                Unsigned32,
            optixRtn1j1PGStateDevWorkSubCardID
                Unsigned32,
            optixRtn1j1PGStateWorkPortID
                Unsigned32,
            optixRtn1j1PGDevWorkBoardState
                OPTIXRtn1j1PGBDStateType,
            optixRtn1j1PGDevProtectBoardState
                OPTIXRtn1j1PGBDStateType,
            optixRtn1j1PGDevSwtichRequest
                OPTIXRtn1j1SwtichRequestType,
            optixRtn1j1PGLinkWorkBoardID
                Unsigned32,
            optixRtn1j1PGLinkDevWorkSubCardID
                Unsigned32,
            optixRtn1j1PGLinkWorkPortID
                Unsigned32,
            optixRtn1j1PGWorkBoardLinkState
                OPTIXRtn1j1LinkStateType,
            optixRtn1j1PGProtBoardLinkState
                OPTIXRtn1j1LinkStateType,
            optixRtn1j1PGProtLinkSwitchRequest
                OPTIXRtn1j1SwtichRequestType
        }

    -- 1.3.6.1.4.1.2011.2.25.4.40.5.10.20.1.1
    optixRtn1j1PGStateDevWorkBoardID OBJECT-TYPE
        SYNTAX Unsigned32
        MAX-ACCESS read-only
        STATUS current
        DESCRIPTION
            "Indicates the current working board ID of an IF 1+1 protection group on the equipment side."
        ::= { optixRtn1j1PGStateEntry 1 }

    -- 1.3.6.1.4.1.2011.2.25.4.40.5.10.20.1.2
    optixRtn1j1PGStateDevWorkSubCardID OBJECT-TYPE
        SYNTAX Unsigned32
        MAX-ACCESS read-only
        STATUS current
        DESCRIPTION
            "Indicates the current working subboard ID of an IF 1+1 protection group on the equipment side."
        DEFVAL{ 255 }
        ::= { optixRtn1j1PGStateEntry 2 }

    -- 1.3.6.1.4.1.2011.2.25.4.40.5.10.20.1.3
    optixRtn1j1PGStateWorkPortID OBJECT-TYPE
        SYNTAX Unsigned32
        MAX-ACCESS read-only
        STATUS current
        DESCRIPTION
            "Indicates the current working port ID of an IF 1+1 protection group on the equipment side."
        ::= { optixRtn1j1PGStateEntry 3 }

    -- 1.3.6.1.4.1.2011.2.25.4.40.5.10.20.1.4
    optixRtn1j1PGDevWorkBoardState OBJECT-TYPE
        SYNTAX OPTIXRtn1j1PGBDStateType
        MAX-ACCESS read-only
        STATUS current
        DESCRIPTION
            "Indicates the working status of the main board on the equipment side. Values: 0: normal 1: switching 2: RDI switching -1: unknown"
        ::= { optixRtn1j1PGStateEntry 4 }

    -- 1.3.6.1.4.1.2011.2.25.4.40.5.10.20.1.5
    optixRtn1j1PGDevProtectBoardState OBJECT-TYPE
        SYNTAX OPTIXRtn1j1PGBDStateType
        MAX-ACCESS read-only
        STATUS current
        DESCRIPTION
            "Indicates the working status of the standby board on the equipment side. Values: 0: normal 1: switching 2: RDI switching -1: unknown"
        ::= { optixRtn1j1PGStateEntry 5 }

    -- 1.3.6.1.4.1.2011.2.25.4.40.5.10.20.1.6
    optixRtn1j1PGDevSwtichRequest OBJECT-TYPE
        SYNTAX OPTIXRtn1j1SwtichRequestType
        MAX-ACCESS read-only
        STATUS current
        DESCRIPTION
            "Indicates the switching request on the equipment side. Value range: 0: normal 1: automatic 2: manual 3: forced 4: lockout 5: wait to restore 6: RDI"
        ::= { optixRtn1j1PGStateEntry 6 }

    -- 1.3.6.1.4.1.2011.2.25.4.40.5.10.20.1.7
    optixRtn1j1PGLinkWorkBoardID OBJECT-TYPE
        SYNTAX Unsigned32
        MAX-ACCESS read-only
        STATUS current
        DESCRIPTION
            "Indicates the current working board ID on the link side."
        ::= { optixRtn1j1PGStateEntry 7 }

    -- 1.3.6.1.4.1.2011.2.25.4.40.5.10.20.1.8
    optixRtn1j1PGLinkDevWorkSubCardID OBJECT-TYPE
        SYNTAX Unsigned32
        MAX-ACCESS read-only
        STATUS current
        DESCRIPTION
            "Indicates the current working subboard ID on the link side."
        DEFVAL{ 255 }
        ::= { optixRtn1j1PGStateEntry 8 }

    -- 1.3.6.1.4.1.2011.2.25.4.40.5.10.20.1.9
    optixRtn1j1PGLinkWorkPortID OBJECT-TYPE
        SYNTAX Unsigned32
        MAX-ACCESS read-only
        STATUS current
        DESCRIPTION
            "Indicates the current working board port ID on the link side."
        ::= { optixRtn1j1PGStateEntry 9 }

    -- 1.3.6.1.4.1.2011.2.25.4.40.5.10.20.1.10
    optixRtn1j1PGWorkBoardLinkState OBJECT-TYPE
        SYNTAX OPTIXRtn1j1LinkStateType
        MAX-ACCESS read-only
        STATUS current
        DESCRIPTION
            "Indicates the signal status of the main board link. Values: 0: normal 1: signal failure 2: signal deterioration -1: invalid"
        ::= { optixRtn1j1PGStateEntry 10 }

    -- 1.3.6.1.4.1.2011.2.25.4.40.5.10.20.1.11
    optixRtn1j1PGProtBoardLinkState OBJECT-TYPE
        SYNTAX OPTIXRtn1j1LinkStateType
        MAX-ACCESS read-only
        STATUS current
        DESCRIPTION
            "Indicates the signal status of the standby board link. Values: 0: normal 1: signal failure 2: signal deterioration -1: invalid"
        ::= { optixRtn1j1PGStateEntry 11 }

    -- 1.3.6.1.4.1.2011.2.25.4.40.5.10.20.1.12
    optixRtn1j1PGProtLinkSwitchRequest OBJECT-TYPE
        SYNTAX OPTIXRtn1j1SwtichRequestType
        MAX-ACCESS read-only
        STATUS current
        DESCRIPTION
            "Indicates the switching request on the link side. Values: 0: normal 1: automatic 3: forced"
        ::= { optixRtn1j1PGStateEntry 12 }

    -- 1.3.6.1.4.1.2011.2.25.4.40.5.10.30
    optixRtnNj1PGParameterTable OBJECT-TYPE
        SYNTAX SEQUENCE OF OptixRtnNj1PGParameterEntry
        MAX-ACCESS not-accessible
        STATUS current
        DESCRIPTION
            "Describes configuration parameters for the working board and protection board in an IF N+1 protection group."
        ::= { optixRtnIFProtect 30 }

    -- 1.3.6.1.4.1.2011.2.25.4.40.5.10.30.1
    optixRtnNj1PGParameterEntry OBJECT-TYPE
        SYNTAX OptixRtnNj1PGParameterEntry
        MAX-ACCESS not-accessible
        STATUS current
        DESCRIPTION
            "Indicates the parameter entry for an IF N+1 protection group."
        INDEX{ optixRtnNj1PGID }
        ::= { optixRtnNj1PGParameterTable 1 }

    OptixRtnNj1PGParameterEntry ::=
        SEQUENCE {
            optixRtnNj1PGID
                Unsigned32,
            optixRtnNj1PGWTRTime
                Unsigned32,
            optixRtnNj1PGSDFlag
                OPTIXRtnEnableStateType,
            optixRtnNj1PGWorkChunnelNum
                Unsigned32,
            optixRtnNj1PGProtectBoardID
                Unsigned32,
            optixRtnNj1PGProtectSubCardID
                Unsigned32,
            optixRtnNj1PGProtectPortID
                Unsigned32,
            optixRtnNj1PGWorkBoardID1
                Unsigned32,
            optixRtnNj1PGWorkSubCardID1
                Unsigned32,
            optixRtnNj1PGWorkPortID1
                Unsigned32,
            optixRtnNj1PGWorkBoardID2
                Unsigned32,
            optixRtnNj1PGWorkSubCardID2
                Unsigned32,
            optixRtnNj1PGWorkPortID2
                Unsigned32,
            optixRtnNj1PGWorkBoardID3
                Unsigned32,
            optixRtnNj1PGWorkSubCardID3
                Unsigned32,
            optixRtnNj1PGWorkPortID3
                Unsigned32,
            optixRtnNj1PGWorkBoardID4
                Unsigned32,
            optixRtnNj1PGWorkSubCardID4
                Unsigned32,
            optixRtnNj1PGWorkPortID4
                Unsigned32,
            optixRtnNj1PGWorkBoardID5
                Unsigned32,
            optixRtnNj1PGWorkSubCardID5
                Unsigned32,
            optixRtnNj1PGWorkPortID5
                Unsigned32,
            optixRtnNj1PGWorkBoardID6
                Unsigned32,
            optixRtnNj1PGWorkSubCardID6
                Unsigned32,
            optixRtnNj1PGWorkPortID6
                Unsigned32,
            optixRtnNj1PGWorkBoardID7
                Unsigned32,
            optixRtnNj1PGWorkSubCardID7
                Unsigned32,
            optixRtnNj1PGWorkPortID7
                Unsigned32,
            optixRtnNj1PGStartProtocol
                Unsigned32,
            optixRtnNj1PGStopProtocol
                Unsigned32,
            optixRtnNj1PGSwChannel
                Unsigned32,
            optixRtnNj1PGSwCmd
                OPTIXRtnNj1PGSwCmdType,
            optixRtnNj1PGWorkChunnelsInfo
                OCTET STRING,
            optixRtnNj1PGCfgRowStatus
                RowStatus
        }

    -- 1.3.6.1.4.1.2011.2.25.4.40.5.10.30.1.1
    optixRtnNj1PGID OBJECT-TYPE
        SYNTAX Unsigned32
        MAX-ACCESS not-accessible
        STATUS current
        DESCRIPTION
            "Indicates the IF N+1 protection group ID."
        ::= { optixRtnNj1PGParameterEntry 1 }

    -- 1.3.6.1.4.1.2011.2.25.4.40.5.10.30.1.2
    optixRtnNj1PGWTRTime OBJECT-TYPE
        SYNTAX Unsigned32
        MAX-ACCESS read-write
        STATUS current
        DESCRIPTION
            "Indicates the WTR time of an IF N+1 protection group. Value range: 300s to 720s"
        DEFVAL{ 600 }
        ::= { optixRtnNj1PGParameterEntry 2 }

    -- 1.3.6.1.4.1.2011.2.25.4.40.5.10.30.1.3
    optixRtnNj1PGSDFlag OBJECT-TYPE
        SYNTAX OPTIXRtnEnableStateType
        MAX-ACCESS read-write
        STATUS current
        DESCRIPTION
            "Indicates the SD status of an IF N+1 protection group. Values: 0: disabled 1: enabled"
        DEFVAL{ 1 }
        ::= { optixRtnNj1PGParameterEntry 3 }

    -- 1.3.6.1.4.1.2011.2.25.4.40.5.10.30.1.4
    optixRtnNj1PGWorkChunnelNum OBJECT-TYPE
        SYNTAX Unsigned32
        MAX-ACCESS read-only
        STATUS current
        DESCRIPTION
            "Indicates the number of working channels in an IF N+1 protection group."
        ::= { optixRtnNj1PGParameterEntry 4 }

    -- 1.3.6.1.4.1.2011.2.25.4.40.5.10.30.1.5
    optixRtnNj1PGProtectBoardID OBJECT-TYPE
        SYNTAX Unsigned32
        MAX-ACCESS read-create
        STATUS current
        DESCRIPTION
            "Indicates the ID of the board on a protection channel in an IF N+1 protection group."
        ::= { optixRtnNj1PGParameterEntry 5 }

    -- 1.3.6.1.4.1.2011.2.25.4.40.5.10.30.1.6
    optixRtnNj1PGProtectSubCardID OBJECT-TYPE
        SYNTAX Unsigned32
        MAX-ACCESS read-create
        STATUS current
        DESCRIPTION
            "Indicates the ID of the subboard on a protection channel in an IF N+1 protection group."
        ::= { optixRtnNj1PGParameterEntry 6 }

    -- 1.3.6.1.4.1.2011.2.25.4.40.5.10.30.1.7
    optixRtnNj1PGProtectPortID OBJECT-TYPE
        SYNTAX Unsigned32
        MAX-ACCESS read-create
        STATUS current
        DESCRIPTION
            "Indicates the ID of the port on a protection channel in an IF N+1 protection group."
        ::= { optixRtnNj1PGParameterEntry 7 }

    -- 1.3.6.1.4.1.2011.2.25.4.40.5.10.30.1.8
    optixRtnNj1PGWorkBoardID1 OBJECT-TYPE
        SYNTAX Unsigned32
        MAX-ACCESS read-only
        STATUS current
        DESCRIPTION
            "Indicates the ID of the board on the first-priority working channel in an IF N+1 protection group."
        ::= { optixRtnNj1PGParameterEntry 8 }

    -- 1.3.6.1.4.1.2011.2.25.4.40.5.10.30.1.9
    optixRtnNj1PGWorkSubCardID1 OBJECT-TYPE
        SYNTAX Unsigned32
        MAX-ACCESS read-only
        STATUS current
        DESCRIPTION
            "Indicates the ID of the subboard on the first-priority working channel in an IF N+1 protection group."
        ::= { optixRtnNj1PGParameterEntry 9 }

    -- 1.3.6.1.4.1.2011.2.25.4.40.5.10.30.1.10
    optixRtnNj1PGWorkPortID1 OBJECT-TYPE
        SYNTAX Unsigned32
        MAX-ACCESS read-only
        STATUS current
        DESCRIPTION
            "Indicates the ID of the port on the first-priority working channel in an IF N+1 protection group."
        ::= { optixRtnNj1PGParameterEntry 10 }

    -- 1.3.6.1.4.1.2011.2.25.4.40.5.10.30.1.11
    optixRtnNj1PGWorkBoardID2 OBJECT-TYPE
        SYNTAX Unsigned32
        MAX-ACCESS read-only
        STATUS current
        DESCRIPTION
            "Indicates the ID of the board on the second-priority working channel in an IF N+1 protection group."
        ::= { optixRtnNj1PGParameterEntry 11 }

    -- 1.3.6.1.4.1.2011.2.25.4.40.5.10.30.1.12
    optixRtnNj1PGWorkSubCardID2 OBJECT-TYPE
        SYNTAX Unsigned32
        MAX-ACCESS read-only
        STATUS current
        DESCRIPTION
            "Indicates the ID of the subboard on the second-priority working channel in an IF N+1 protection group."
        DEFVAL{ 255 }
        ::= { optixRtnNj1PGParameterEntry 12 }

    -- 1.3.6.1.4.1.2011.2.25.4.40.5.10.30.1.13
    optixRtnNj1PGWorkPortID2 OBJECT-TYPE
        SYNTAX Unsigned32
        MAX-ACCESS read-only
        STATUS current
        DESCRIPTION
            "Indicates the ID of the port on the second-priority working channel in an IF N+1 protection group."
        DEFVAL{ 255 }
        ::= { optixRtnNj1PGParameterEntry 13 }

    -- 1.3.6.1.4.1.2011.2.25.4.40.5.10.30.1.14
    optixRtnNj1PGWorkBoardID3 OBJECT-TYPE
        SYNTAX Unsigned32
        MAX-ACCESS read-only
        STATUS current
        DESCRIPTION
            "Indicates the ID of the board on the third-priority working channel in an IF N+1 protection group."
        DEFVAL{ 255 }
        ::= { optixRtnNj1PGParameterEntry 14 }

    -- 1.3.6.1.4.1.2011.2.25.4.40.5.10.30.1.15
    optixRtnNj1PGWorkSubCardID3 OBJECT-TYPE
        SYNTAX Unsigned32
        MAX-ACCESS read-only
        STATUS current
        DESCRIPTION
            "Indicates the ID of the subboard on the third-priority working channel in an IF N+1 protection group."
        DEFVAL{ 255 }
        ::= { optixRtnNj1PGParameterEntry 15 }

    -- 1.3.6.1.4.1.2011.2.25.4.40.5.10.30.1.16
    optixRtnNj1PGWorkPortID3 OBJECT-TYPE
        SYNTAX Unsigned32
        MAX-ACCESS read-only
        STATUS current
        DESCRIPTION
            "Indicates the ID of the port on the third-priority working channel in an IF N+1 protection group."
        DEFVAL{ 255 }
        ::= { optixRtnNj1PGParameterEntry 16 }

    -- 1.3.6.1.4.1.2011.2.25.4.40.5.10.30.1.17
    optixRtnNj1PGWorkBoardID4 OBJECT-TYPE
        SYNTAX Unsigned32
        MAX-ACCESS read-only
        STATUS current
        DESCRIPTION
            "Indicates the ID of the board on the fourth-priority working channel in an IF N+1 protection group."
        DEFVAL{ 255 }
        ::= { optixRtnNj1PGParameterEntry 17 }

    -- 1.3.6.1.4.1.2011.2.25.4.40.5.10.30.1.18
    optixRtnNj1PGWorkSubCardID4 OBJECT-TYPE
        SYNTAX Unsigned32
        MAX-ACCESS read-only
        STATUS current
        DESCRIPTION
            "Indicates the ID of the subboard on the fourth-priority working channel in an IF N+1 protection group."
        DEFVAL{ 255 }
        ::= { optixRtnNj1PGParameterEntry 18 }

    -- 1.3.6.1.4.1.2011.2.25.4.40.5.10.30.1.19
    optixRtnNj1PGWorkPortID4 OBJECT-TYPE
        SYNTAX Unsigned32
        MAX-ACCESS read-only
        STATUS current
        DESCRIPTION
            "Indicates the ID of the port on the fourth-priority working channel in an IF N+1 protection group."
        DEFVAL{ 255 }
        ::= { optixRtnNj1PGParameterEntry 19 }

    -- 1.3.6.1.4.1.2011.2.25.4.40.5.10.30.1.20
    optixRtnNj1PGWorkBoardID5 OBJECT-TYPE
        SYNTAX Unsigned32
        MAX-ACCESS read-only
        STATUS current
        DESCRIPTION
            "Indicates the ID of the board on the fifth-priority working channel in an IF N+1 protection group."
        DEFVAL{ 255 }
        ::= { optixRtnNj1PGParameterEntry 20 }

    -- 1.3.6.1.4.1.2011.2.25.4.40.5.10.30.1.21
    optixRtnNj1PGWorkSubCardID5 OBJECT-TYPE
        SYNTAX Unsigned32
        MAX-ACCESS read-only
        STATUS current
        DESCRIPTION
            "Indicates the ID of the subboard on the fifth-priority working channel in an IF N+1 protection group."
        DEFVAL{ 255 }
        ::= { optixRtnNj1PGParameterEntry 21 }

    -- 1.3.6.1.4.1.2011.2.25.4.40.5.10.30.1.22
    optixRtnNj1PGWorkPortID5 OBJECT-TYPE
        SYNTAX Unsigned32
        MAX-ACCESS read-only
        STATUS current
        DESCRIPTION
            "Indicates the ID of the port on the fifth-priority working channel in an IF N+1 protection group."
        DEFVAL{ 255 }
        ::= { optixRtnNj1PGParameterEntry 22 }

    -- 1.3.6.1.4.1.2011.2.25.4.40.5.10.30.1.23
    optixRtnNj1PGWorkBoardID6 OBJECT-TYPE
        SYNTAX Unsigned32
        MAX-ACCESS read-only
        STATUS current
        DESCRIPTION
            "Indicates the ID of the board on the sixth-priority working channel in an IF N+1 protection group."
        DEFVAL{ 255 }
        ::= { optixRtnNj1PGParameterEntry 23 }

    -- 1.3.6.1.4.1.2011.2.25.4.40.5.10.30.1.24
    optixRtnNj1PGWorkSubCardID6 OBJECT-TYPE
        SYNTAX Unsigned32
        MAX-ACCESS read-only
        STATUS current
        DESCRIPTION
            "Indicates the ID of the subboard on the sixth-priority working channel in an IF N+1 protection group."
        DEFVAL{ 255 }
        ::= { optixRtnNj1PGParameterEntry 24 }

    -- 1.3.6.1.4.1.2011.2.25.4.40.5.10.30.1.25
    optixRtnNj1PGWorkPortID6 OBJECT-TYPE
        SYNTAX Unsigned32
        MAX-ACCESS read-only
        STATUS current
        DESCRIPTION
            "Indicates the ID of the port on the sixth-priority working channel in an IF N+1 protection group."
        DEFVAL{ 255 }
        ::= { optixRtnNj1PGParameterEntry 25 }

    -- 1.3.6.1.4.1.2011.2.25.4.40.5.10.30.1.26
    optixRtnNj1PGWorkBoardID7 OBJECT-TYPE
        SYNTAX Unsigned32
        MAX-ACCESS read-only
        STATUS current
        DESCRIPTION
            "Indicates the ID of the board on the seventh-priority working channel in an IF N+1 protection group."
        DEFVAL{ 255 }
        ::= { optixRtnNj1PGParameterEntry 26 }

    -- 1.3.6.1.4.1.2011.2.25.4.40.5.10.30.1.27
    optixRtnNj1PGWorkSubCardID7 OBJECT-TYPE
        SYNTAX Unsigned32
        MAX-ACCESS read-only
        STATUS current
        DESCRIPTION
            "Indicates the ID of the subboard on the seventh-priority working channel in an IF N+1 protection group."
        DEFVAL{ 255 }
        ::= { optixRtnNj1PGParameterEntry 27 }

    -- 1.3.6.1.4.1.2011.2.25.4.40.5.10.30.1.28
    optixRtnNj1PGWorkPortID7 OBJECT-TYPE
        SYNTAX Unsigned32
        MAX-ACCESS read-only
        STATUS current
        DESCRIPTION
            "Indicates the ID of the port on the seventh-priority working channel in an IF N+1 protection group."
        DEFVAL{ 255 }
        ::= { optixRtnNj1PGParameterEntry 28 }

    -- 1.3.6.1.4.1.2011.2.25.4.40.5.10.30.1.29
    optixRtnNj1PGStartProtocol OBJECT-TYPE
        SYNTAX Unsigned32
        MAX-ACCESS read-write
        STATUS current
        DESCRIPTION
            "To start the current IF N+1 protection group"
        ::= { optixRtnNj1PGParameterEntry 29 }

    -- 1.3.6.1.4.1.2011.2.25.4.40.5.10.30.1.30
    optixRtnNj1PGStopProtocol OBJECT-TYPE
        SYNTAX Unsigned32
        MAX-ACCESS read-write
        STATUS current
        DESCRIPTION
            "To stop the current IF N+1 protection group"
        ::= { optixRtnNj1PGParameterEntry 30 }

    -- 1.3.6.1.4.1.2011.2.25.4.40.5.10.30.1.31
    optixRtnNj1PGSwChannel OBJECT-TYPE
        SYNTAX Unsigned32
		{
		   null(255)
		}
        MAX-ACCESS read-write
        STATUS current
        DESCRIPTION
            "Indicates the switching channel of an IF N+1 protection group."
        ::= { optixRtnNj1PGParameterEntry 31 }

    -- 1.3.6.1.4.1.2011.2.25.4.40.5.10.30.1.32
    optixRtnNj1PGSwCmd OBJECT-TYPE
        SYNTAX OPTIXRtnNj1PGSwCmdType
        MAX-ACCESS read-write
        STATUS current
        DESCRIPTION
            "Indicates the switching type of an IF N+1 protection group."
        ::= { optixRtnNj1PGParameterEntry 32 }

    -- 1.3.6.1.4.1.2011.2.25.4.40.5.10.30.1.33
    optixRtnNj1PGWorkChunnelsInfo OBJECT-TYPE
        SYNTAX OCTET STRING (SIZE(0..16))
        MAX-ACCESS read-create
        STATUS current
        DESCRIPTION
            "Indicates the information about the working channel in an IF N+1 protection group."
        ::= { optixRtnNj1PGParameterEntry 33 }

    -- 1.3.6.1.4.1.2011.2.25.4.40.5.10.30.1.50
    optixRtnNj1PGCfgRowStatus OBJECT-TYPE
        SYNTAX RowStatus
        MAX-ACCESS read-create
        STATUS current
        DESCRIPTION
            "Indicates the row status of an IF N+1 protection group."
        DEFVAL{ active }
        ::= { optixRtnNj1PGParameterEntry 50 }

    -- 1.3.6.1.4.1.2011.2.25.4.40.5.10.40
    optixRtnNj1PGStateTable OBJECT-TYPE
        SYNTAX SEQUENCE OF OptixRtnNj1PGStateEntry
        MAX-ACCESS not-accessible
        STATUS current
        DESCRIPTION
            "Describes the corresponding channel status for an IF N+1 protection group, including the current working board and switching status of the protection group."
        ::= { optixRtnIFProtect 40 }

    -- 1.3.6.1.4.1.2011.2.25.4.40.5.10.40.1
    optixRtnNj1PGStateEntry OBJECT-TYPE
        SYNTAX OptixRtnNj1PGStateEntry
        MAX-ACCESS not-accessible
        STATUS current
        DESCRIPTION
            "Indicates the channel status entry for an IF N+1 protection group."
        INDEX{ optixRtnNj1PGID,optixRtnNj1PGPuID }
        ::= { optixRtnNj1PGStateTable 1 }

    OptixRtnNj1PGStateEntry ::=
        SEQUENCE {
            optixRtnNj1PGPuID
                Unsigned32,
            optixRtnNj1PGSwitchRequest
                OPTIXRtnNj1PGSwitchRequestType,
            optixRtnNj1PGSwitchState
                OPTIXRtnNj1SwitchStateType,
            optixRtnNj1PGProtectPath
                Unsigned32,
            optixRtnNj1PGFarNearIndicate
                OPTIXRtnNj1PGFarNearType
        }

    -- 1.3.6.1.4.1.2011.2.25.4.40.5.10.40.1.1
    optixRtnNj1PGPuID OBJECT-TYPE
        SYNTAX Unsigned32
        MAX-ACCESS not-accessible
        STATUS current
        DESCRIPTION
            "Indicates the protection unit ID. Value range: 1 to 7"
        ::= { optixRtnNj1PGStateEntry 1 }

    -- 1.3.6.1.4.1.2011.2.25.4.40.5.10.40.1.2
    optixRtnNj1PGSwitchRequest OBJECT-TYPE
        SYNTAX OPTIXRtnNj1PGSwitchRequestType
        MAX-ACCESS read-only
        STATUS current
        DESCRIPTION
            "Indicates the switching request. Values: 240: lockout 224: force 208: SF 176: SD 128: manual 96: wait to restore 64: exercise switching 32: reverse request 0: No request"
        ::= { optixRtnNj1PGStateEntry 2 }

    -- 1.3.6.1.4.1.2011.2.25.4.40.5.10.40.1.3
    optixRtnNj1PGSwitchState OBJECT-TYPE
        SYNTAX OPTIXRtnNj1SwitchStateType
        MAX-ACCESS read-only
        STATUS current
        DESCRIPTION
            "Indicates the switching status. Values: 0: not started 1: idling 4: switching -1: protocol is starting"
        ::= { optixRtnNj1PGStateEntry 3 }

    -- 1.3.6.1.4.1.2011.2.25.4.40.5.10.40.1.4
    optixRtnNj1PGProtectPath OBJECT-TYPE
        SYNTAX Unsigned32
        MAX-ACCESS read-only
        STATUS current
        DESCRIPTION
            "Indicates the protected working channel."
        ::= { optixRtnNj1PGStateEntry 4 }

    -- 1.3.6.1.4.1.2011.2.25.4.40.5.10.40.1.5
    optixRtnNj1PGFarNearIndicate OBJECT-TYPE
        SYNTAX OPTIXRtnNj1PGFarNearType
        MAX-ACCESS read-only
        STATUS current
        DESCRIPTION
            "Indicates far and near ends. Values: 0: none 1: near end 2: far end"
        ::= { optixRtnNj1PGStateEntry 5 }

    -- 1.3.6.1.4.1.2011.2.25.4.40.5.10.41
    optixRtnExtNJ1PgTable OBJECT-TYPE
        SYNTAX SEQUENCE OF OptixRtnExtNJ1PgEntry
        MAX-ACCESS not-accessible
        STATUS current
        DESCRIPTION
            "Indicates the table of the enhanced N+1 protection group."
        ::= { optixRtnIFProtect 41 }

    -- 1.3.6.1.4.1.2011.2.25.4.40.5.10.41.1
    optixRtnExtNJ1PgEntry OBJECT-TYPE
        SYNTAX OptixRtnExtNJ1PgEntry
        MAX-ACCESS not-accessible
        STATUS current
        DESCRIPTION
            "Indicates the entry of the enhanced N+1 protection group."
        INDEX{ optixRtnExtNJ1PGID }
        ::= { optixRtnExtNJ1PgTable 1 }

    OptixRtnExtNJ1PgEntry ::=
        SEQUENCE {
            optixRtnExtNJ1PGID
                Unsigned32,
            optixRtnExtNJ1Mode
                OPTIXRtnExtNj1Mode,
            optixRtnExtNJ1ProtectChunnel
                OCTET STRING,
            optixRtnExtNJ1WorkChunnel
                OCTET STRING,
            optixRtnExtNJ1RowStatus
                RowStatus
        }

    -- 1.3.6.1.4.1.2011.2.25.4.40.5.10.41.1.1
    optixRtnExtNJ1PGID OBJECT-TYPE
        SYNTAX Unsigned32 (1..7)
        MAX-ACCESS not-accessible
        STATUS current
        DESCRIPTION
            "Indicates the ID of the enhanced N+1 protection group."
        ::= { optixRtnExtNJ1PgEntry 1 }

    -- 1.3.6.1.4.1.2011.2.25.4.40.5.10.41.1.2
    optixRtnExtNJ1Mode OBJECT-TYPE
        SYNTAX OPTIXRtnExtNj1Mode
        MAX-ACCESS read-create
        STATUS current
        DESCRIPTION
            "Indicates the mode of the enhanced N+1 protection group."
        ::= { optixRtnExtNJ1PgEntry 2 }

    -- 1.3.6.1.4.1.2011.2.25.4.40.5.10.41.1.3
    optixRtnExtNJ1ProtectChunnel OBJECT-TYPE
        SYNTAX OCTET STRING (SIZE(0..16))
        MAX-ACCESS read-create
        STATUS current
        DESCRIPTION
            "Indicates information about the protection channel in an enhanced N+1 protection group"
        ::= { optixRtnExtNJ1PgEntry 3 }

    -- 1.3.6.1.4.1.2011.2.25.4.40.5.10.41.1.4
    optixRtnExtNJ1WorkChunnel OBJECT-TYPE
        SYNTAX OCTET STRING (SIZE(0..255))
        MAX-ACCESS read-create
        STATUS current
        DESCRIPTION
            "Indicates information about  working channels in an enhanced N+1 protection group."
        ::= { optixRtnExtNJ1PgEntry 4 }

    -- 1.3.6.1.4.1.2011.2.25.4.40.5.10.41.1.5
    optixRtnExtNJ1RowStatus OBJECT-TYPE
        SYNTAX RowStatus
        MAX-ACCESS read-create
        STATUS current
        DESCRIPTION
            "Indicates the running status of the enhanced N+1 protection group."
        ::= { optixRtnExtNJ1PgEntry 5 }

    -- 1.3.6.1.4.1.2011.2.25.4.40.5.10.42
    optixRtnNJ1ProtocolTable OBJECT-TYPE
        SYNTAX SEQUENCE OF OptixRtnNJ1ProtocolEntry
        MAX-ACCESS not-accessible
        STATUS current
        DESCRIPTION
            "Indicates the table of the N+1 protocol."
        ::= { optixRtnIFProtect 42 }

    -- 1.3.6.1.4.1.2011.2.25.4.40.5.10.42.1
    optixRtnNJ1ProtocolEntry OBJECT-TYPE
        SYNTAX OptixRtnNJ1ProtocolEntry
        MAX-ACCESS not-accessible
        STATUS current
        DESCRIPTION
            "Indicates the entry of the N+1 protocol."
        INDEX{ optixRtnNj1PGID }
        ::= { optixRtnNJ1ProtocolTable 1 }

    OptixRtnNJ1ProtocolEntry ::=
        SEQUENCE {
            optixRtnNj1ProtocolState
                OPTIXRtnNJ1ProtocolState,
            optixRtnNj1WTRTime
                Unsigned32,
            optixRtnNj1SDState
                OPTIXRtnEnableStateType
        }

    -- 1.3.6.1.4.1.2011.2.25.4.40.5.10.42.1.1
    optixRtnNj1ProtocolState OBJECT-TYPE
        SYNTAX OPTIXRtnNJ1ProtocolState
        MAX-ACCESS read-write
        STATUS current
        DESCRIPTION
            "Indicates the stop/start status of the N+1 protocol."
        ::= { optixRtnNJ1ProtocolEntry 1 }

    -- 1.3.6.1.4.1.2011.2.25.4.40.5.10.42.1.2
    optixRtnNj1WTRTime OBJECT-TYPE
        SYNTAX Unsigned32
        MAX-ACCESS read-write
        STATUS current
        DESCRIPTION
            "Indicates the WTR time of the N+1 protocol."
        ::= { optixRtnNJ1ProtocolEntry 2 }

    -- 1.3.6.1.4.1.2011.2.25.4.40.5.10.42.1.3
    optixRtnNj1SDState OBJECT-TYPE
        SYNTAX OPTIXRtnEnableStateType
        MAX-ACCESS read-write
        STATUS current
        DESCRIPTION
            "Indicates the SD enable status of the N+1 protocol."
        ::= { optixRtnNJ1ProtocolEntry 3 }

    -- 1.3.6.1.4.1.2011.2.25.4.40.5.10.43
    optixRtnNJ1SwitchTable OBJECT-TYPE
        SYNTAX SEQUENCE OF OptixRtnNJ1SwitchEntry
        MAX-ACCESS not-accessible
        STATUS current
        DESCRIPTION
            "Indicates the table of external command-triggered switching of the N+1 protection group."
        ::= { optixRtnIFProtect 43 }

    -- 1.3.6.1.4.1.2011.2.25.4.40.5.10.43.1
    optixRtnNJ1SwitchEntry OBJECT-TYPE
        SYNTAX OptixRtnNJ1SwitchEntry
        MAX-ACCESS not-accessible
        STATUS current
        DESCRIPTION
            "Indicates the entry of external command-triggered switching of the N+1 protection group."
        INDEX{ optixRtnNj1PGID, optixRtnNj1PGPuID }
        ::= { optixRtnNJ1SwitchTable 1 }

    OptixRtnNJ1SwitchEntry ::=
        SEQUENCE {
            optixRtnNj1SwitchChunnel
                OPTIXRtnNj1PGSwCmdType
        }

    -- 1.3.6.1.4.1.2011.2.25.4.40.5.10.43.1.1
    optixRtnNj1SwitchChunnel OBJECT-TYPE
        SYNTAX OPTIXRtnNj1PGSwCmdType
        MAX-ACCESS read-write
        STATUS current
        DESCRIPTION
            "Indicates the switching channel of the N+1 protection group."
        ::= { optixRtnNJ1SwitchEntry 1 }

    -- 1.3.6.1.4.1.2011.2.25.4.40.5.10.45
    optixRtnENJ1CCStatusTable OBJECT-TYPE
        SYNTAX SEQUENCE OF OptixRtnENJ1CCStatusEntry
        MAX-ACCESS not-accessible
        STATUS current
        DESCRIPTION
            "Indicates the table of external command-triggered status of the EN+1 protection group."
        ::= { optixRtnIFProtect 45 }

    -- 1.3.6.1.4.1.2011.2.25.4.40.5.10.45.1
    optixRtnENJ1CCStatusEntry OBJECT-TYPE
        SYNTAX OptixRtnENJ1CCStatusEntry
        MAX-ACCESS not-accessible
        STATUS current
        DESCRIPTION
            "Indicates the entry of external command-triggered status of the EN+1 protection group."
        INDEX{ optixRtnNj1PGID, optixRtnNj1PGPuID }
        ::= { optixRtnENJ1CCStatusTable 1 }

    OptixRtnENJ1CCStatusEntry ::=
        SEQUENCE {
            optixRtnENJ1CCStatus
                INTEGER
        }

    -- 1.3.6.1.4.1.2011.2.25.4.40.5.10.45.1.3
    optixRtnENJ1CCStatus OBJECT-TYPE
        SYNTAX INTEGER
        {
            disable(0),
            enable(1)
        }  
        MAX-ACCESS read-write
        STATUS current
        DESCRIPTION
            "Indicates the  status of the EN+1 protection group."
        ::= { optixRtnENJ1CCStatusEntry 3 }
        
    -- 1.3.6.1.4.1.2011.2.25.4.40.5.10.50
    optixRtnXPICPGParameterTable OBJECT-TYPE
        SYNTAX SEQUENCE OF OptixRtnXPICPGParameterEntry
        MAX-ACCESS not-accessible
        STATUS current
        DESCRIPTION
            "Describes configuration parameters for an IF XPIC protection group, including the boards in the horizon polarization direction and the vertical polarization direction."
        ::= { optixRtnIFProtect 50 }

    -- 1.3.6.1.4.1.2011.2.25.4.40.5.10.50.1
    optixRtnXPICPGParameterEntry OBJECT-TYPE
        SYNTAX OptixRtnXPICPGParameterEntry
        MAX-ACCESS not-accessible
        STATUS current
        DESCRIPTION
            "Indicates the parameter entry for an IF XPIC protection group."
        INDEX{ optixRtnXPICPGID }
        ::= { optixRtnXPICPGParameterTable 1 }

    OptixRtnXPICPGParameterEntry ::=
        SEQUENCE {
            optixRtnXPICPGID
                Unsigned32,
            optixRtnXPICPGHPolarBoardID
                Unsigned32,
            optixRtnXPICPGHPolarSubCardID
                Unsigned32,
            optixRtnXPICPGHPolarPortID
                Unsigned32,
            optixRtnXPICPGVPolarBoardID
                Unsigned32,
            optixRtnXPICPGVPolarSubCardID
                Unsigned32,
            optixRtnXPICPGVPolarPortID
                Unsigned32,
            optixRtnXPICPGOduFreq
                Unsigned32,
            optixRtnXPICPGCfgRowStatus
                RowStatus
        }

    -- 1.3.6.1.4.1.2011.2.25.4.40.5.10.50.1.1
    optixRtnXPICPGID OBJECT-TYPE
        SYNTAX Unsigned32
        MAX-ACCESS not-accessible
        STATUS current
        DESCRIPTION
            "Indicates the XPIC protection group ID."
        ::= { optixRtnXPICPGParameterEntry 1 }

    -- 1.3.6.1.4.1.2011.2.25.4.40.5.10.50.1.2
    optixRtnXPICPGHPolarBoardID OBJECT-TYPE
        SYNTAX Unsigned32
        MAX-ACCESS read-create
        STATUS current
        DESCRIPTION
            "Indicates the slot ID of an XPIC-enabled board in the horizon polarization direction."
        ::= { optixRtnXPICPGParameterEntry 2 }

    -- 1.3.6.1.4.1.2011.2.25.4.40.5.10.50.1.3
    optixRtnXPICPGHPolarSubCardID OBJECT-TYPE
        SYNTAX Unsigned32
        MAX-ACCESS read-create
        STATUS current
        DESCRIPTION
            "Indicates the subboard ID of an XPIC-enabled board in the horizon polarization direction."
        DEFVAL{ 255 }
        ::= { optixRtnXPICPGParameterEntry 3 }

    -- 1.3.6.1.4.1.2011.2.25.4.40.5.10.50.1.4
    optixRtnXPICPGHPolarPortID OBJECT-TYPE
        SYNTAX Unsigned32
        MAX-ACCESS read-create
        STATUS current
        DESCRIPTION
            "Indicates the port ID of an XPIC-enabled board in the horizon polarization direction."
        DEFVAL{ 1 }
        ::= { optixRtnXPICPGParameterEntry 4 }

    -- 1.3.6.1.4.1.2011.2.25.4.40.5.10.50.1.5
    optixRtnXPICPGVPolarBoardID OBJECT-TYPE
        SYNTAX Unsigned32
        MAX-ACCESS read-create
        STATUS current
        DESCRIPTION
            "Indicates the slot ID of an XPIC-enabled board in the vertical polarization direction."
        ::= { optixRtnXPICPGParameterEntry 5 }

    -- 1.3.6.1.4.1.2011.2.25.4.40.5.10.50.1.6
    optixRtnXPICPGVPolarSubCardID OBJECT-TYPE
        SYNTAX Unsigned32
        MAX-ACCESS read-create
        STATUS current
        DESCRIPTION
            "Indicates the subboard ID of an XPIC-enabled board in the vertical polarization direction."
        DEFVAL{ 255 }
        ::= { optixRtnXPICPGParameterEntry 6 }

    -- 1.3.6.1.4.1.2011.2.25.4.40.5.10.50.1.7
    optixRtnXPICPGVPolarPortID OBJECT-TYPE
        SYNTAX Unsigned32
        MAX-ACCESS read-create
        STATUS current
        DESCRIPTION
            "Indicates the port ID of an XPIC-enabled board in the vertical polarization direction."
        DEFVAL{ 1 }
        ::= { optixRtnXPICPGParameterEntry 7 }

    -- 1.3.6.1.4.1.2011.2.25.4.40.5.10.50.1.8
    optixRtnXPICPGOduFreq OBJECT-TYPE
        SYNTAX Unsigned32
        MAX-ACCESS read-create
        STATUS current
        DESCRIPTION
            "Indicates the transmission frequency of an ODU board in an XPIC protection group. When frequencies of the transmitter/receiver at both ends match, signals can be received and transmitted successfully. Unit: kHz"
        ::= { optixRtnXPICPGParameterEntry 8 }

    -- 1.3.6.1.4.1.2011.2.25.4.40.5.10.50.1.50
    optixRtnXPICPGCfgRowStatus OBJECT-TYPE
        SYNTAX RowStatus
        MAX-ACCESS read-create
        STATUS current
        DESCRIPTION
            "Indicates the row status of an XPIC protection group."
        DEFVAL{ active }
        ::= { optixRtnXPICPGParameterEntry 50 }

    -- 1.3.6.1.4.1.2011.2.25.4.40.5.10.60
    optixRtnXPICPGAMParameterTable OBJECT-TYPE
        SYNTAX SEQUENCE OF OptixRtnXPICPGAMParameterEntry
        MAX-ACCESS not-accessible
        STATUS current
        DESCRIPTION
            "Describes corresponding AM parameters of an XPIC protection group."
        ::= { optixRtnIFProtect 60 }

    -- 1.3.6.1.4.1.2011.2.25.4.40.5.10.60.1
    optixRtnXPICPGAMParameterEntry OBJECT-TYPE
        SYNTAX OptixRtnXPICPGAMParameterEntry
        MAX-ACCESS not-accessible
        STATUS current
        DESCRIPTION
            "Indicates the AM parameter entry for an XPIC protection group."
        INDEX{ optixRtnXPICPGID }
        ::= { optixRtnXPICPGAMParameterTable 1 }

    OptixRtnXPICPGAMParameterEntry ::=
        SEQUENCE {
            optixRtnXPICPGBandWidth
                OPTIXRtnBandWidthType,
            optixRtnXPICPGAMEnableStatus
                OPTIXRtnEnableStateType,
            optixRtnXPICPGAMBottomMode
                OPTIXRtnModulateModeType,
            optixRtnXPICPGAMPeakMode
                OPTIXRtnModulateModeType,
            optixRtnXPICPGAMManualMode
                OPTIXRtnModulateModeType
        }

    -- 1.3.6.1.4.1.2011.2.25.4.40.5.10.60.1.1
    optixRtnXPICPGBandWidth OBJECT-TYPE
        SYNTAX OPTIXRtnBandWidthType
        MAX-ACCESS read-write
        STATUS current
        DESCRIPTION
            "Indicates the channel bandwidth of an XPIC protection group. Values: 1: 3.5 Mbit/s 2: 7.0 Mbit/s 3: 14 Mbit/s 4: 28 Mbit/s 5: 40 Mbit/s 6: 56 Mbit/s"
        ::= { optixRtnXPICPGAMParameterEntry 1 }

    -- 1.3.6.1.4.1.2011.2.25.4.40.5.10.60.1.2
    optixRtnXPICPGAMEnableStatus OBJECT-TYPE
        SYNTAX OPTIXRtnEnableStateType
        MAX-ACCESS read-write
        STATUS current
        DESCRIPTION
            "Indicates the enable status of the AM function in an XPIC protection group. Values: 0: disabled 1: enabled"
        DEFVAL{ 0 }
        ::= { optixRtnXPICPGAMParameterEntry 2 }

    -- 1.3.6.1.4.1.2011.2.25.4.40.5.10.60.1.3
    optixRtnXPICPGAMBottomMode OBJECT-TYPE
        SYNTAX OPTIXRtnModulateModeType
        MAX-ACCESS read-write
        STATUS current
        DESCRIPTION
            "Indicates the lowest AM modulation scheme in an XPIC protection group."
        ::= { optixRtnXPICPGAMParameterEntry 3 }

    -- 1.3.6.1.4.1.2011.2.25.4.40.5.10.60.1.4
    optixRtnXPICPGAMPeakMode OBJECT-TYPE
        SYNTAX OPTIXRtnModulateModeType
        MAX-ACCESS read-write
        STATUS current
        DESCRIPTION
            "Indicates the highest AM modulation scheme in an XPIC protection group."
        ::= { optixRtnXPICPGAMParameterEntry 4 }

    -- 1.3.6.1.4.1.2011.2.25.4.40.5.10.60.1.5
    optixRtnXPICPGAMManualMode OBJECT-TYPE
        SYNTAX OPTIXRtnModulateModeType
        MAX-ACCESS read-write
        STATUS current
        DESCRIPTION
            "Indicates the manually specified modulation mode in an XPIC protection group."
        ::= { optixRtnXPICPGAMParameterEntry 5 }

    -- 1.3.6.1.4.1.2011.2.25.4.40.5.10.70
    optixRtnXPICPGATPCParameterTable OBJECT-TYPE
        SYNTAX SEQUENCE OF OptixRtnXPICPGATPCParameterEntry
        MAX-ACCESS not-accessible
        STATUS current
        DESCRIPTION
            "Describes corresponding ATPC parameters of an XPIC protection group."
        ::= { optixRtnIFProtect 70 }

    -- 1.3.6.1.4.1.2011.2.25.4.40.5.10.70.1
    optixRtnXPICPGATPCParameterEntry OBJECT-TYPE
        SYNTAX OptixRtnXPICPGATPCParameterEntry
        MAX-ACCESS not-accessible
        STATUS current
        DESCRIPTION
            "Indicates the ATPC parameter entry for an XPIC protection group."
        INDEX{ optixRtnXPICPGID }
        ::= { optixRtnXPICPGATPCParameterTable 1 }

    OptixRtnXPICPGATPCParameterEntry ::=
        SEQUENCE {
            optixRtnXPICPGATPCEnableState
                OPTIXRtnEnableStateType,
            optixRtnXPICPGATPCStep
                Unsigned32,
            optixRtnXPICPGATPCHighThreshold
                Integer32,
            optixRtnXPICPGATPCLowThreshold
                Integer32,
            optixRtnXPICPGATPCAutoThresholdState
                OPTIXRtnEnableStateType
        }

    -- 1.3.6.1.4.1.2011.2.25.4.40.5.10.70.1.1
    optixRtnXPICPGATPCEnableState OBJECT-TYPE
        SYNTAX OPTIXRtnEnableStateType
        MAX-ACCESS read-write
        STATUS current
        DESCRIPTION
            "Indicates the enable status of the ATPC function in an XPIC protection group. Values: 0: disabled 1: enabled"
        DEFVAL{ 0 }
        ::= { optixRtnXPICPGATPCParameterEntry 1 }

    -- 1.3.6.1.4.1.2011.2.25.4.40.5.10.70.1.2
    optixRtnXPICPGATPCStep OBJECT-TYPE
        SYNTAX Unsigned32
        MAX-ACCESS read-write
        STATUS current
        DESCRIPTION
            "Indicates the ATPC adjustment step in an XPIC protection group. The parameter refers to every increase or decrease in the ODU transmit power. Value range: 10 to 50"
        ::= { optixRtnXPICPGATPCParameterEntry 2 }

    -- 1.3.6.1.4.1.2011.2.25.4.40.5.10.70.1.3
    optixRtnXPICPGATPCHighThreshold OBJECT-TYPE
        SYNTAX Integer32
        MAX-ACCESS read-write
        STATUS current
        DESCRIPTION
            "Indicates the ATPC adjustment upper threshold in an XPIC protection group. When the receive signal level (RSL) is higher than the threshold, the transmitter automatically adjusts its transmit power. Signed type Value range: -850 to -200 Unit: 0.1 dBm"
        ::= { optixRtnXPICPGATPCParameterEntry 3 }

    -- 1.3.6.1.4.1.2011.2.25.4.40.5.10.70.1.4
    optixRtnXPICPGATPCLowThreshold OBJECT-TYPE
        SYNTAX Integer32
        MAX-ACCESS read-write
        STATUS current
        DESCRIPTION
            "Indicates the ATPC adjustment lower threshold in an XPIC protection group. When the receive signal level (RSL) is lower than the threshold, the transmitter automatically adjusts its transmit power. Signed type Value range: -900 to -250 Unit: 0.1 dBm"
        ::= { optixRtnXPICPGATPCParameterEntry 4 }

    -- 1.3.6.1.4.1.2011.2.25.4.40.5.10.70.1.5
    optixRtnXPICPGATPCAutoThresholdState OBJECT-TYPE
        SYNTAX OPTIXRtnEnableStateType
        MAX-ACCESS read-write
        STATUS current
        DESCRIPTION
            "Indicates the enable status of the ATPC automatic threshold configuration function in an XPIC protection group. The ATPC function enables the transmit power of a transmitter to automatically trace the change of the RSL at the receive end within the ATPC control range. The equipment automatically uses the preset ATPC upper and lower thresholds based on the working mode of the IF board. When the function is disabled, the manually set ATPC upper and lower thresholds are used. Values: 0: disabled 1: enabled"
        ::= { optixRtnXPICPGATPCParameterEntry 5 }

    -- 1.3.6.1.4.1.2011.2.25.4.40.5.10.80
    optixRtnXPICPGOduParameterTable OBJECT-TYPE
        SYNTAX SEQUENCE OF OptixRtnXPICPGOduParameterEntry
        MAX-ACCESS not-accessible
        STATUS current
        DESCRIPTION
            "Describes corresponding ODU parameters of an XPIC protection group."
        ::= { optixRtnIFProtect 80 }

    -- 1.3.6.1.4.1.2011.2.25.4.40.5.10.80.1
    optixRtnXPICPGOduParameterEntry OBJECT-TYPE
        SYNTAX OptixRtnXPICPGOduParameterEntry
        MAX-ACCESS not-accessible
        STATUS current
        DESCRIPTION
            "Indicates the ODU parameter entry for an XPIC protection group."
        INDEX{ optixRtnXPICPGID }
        ::= { optixRtnXPICPGOduParameterTable 1 }

    OptixRtnXPICPGOduParameterEntry ::=
        SEQUENCE {
            optixRtnXPICPGOduTxFreq
                Unsigned32,
            optixRtnXPICPGOduTxPower
                Integer32,
            optixRtnXPICPGOduMaxTxpower
                Integer32,
            optixRtnXPICPGOduTRSpacing
                Unsigned32,
            optixRtnXPICPGOduWorkState
                OPTIXRtnOduWorkStateType
        }

    -- 1.3.6.1.4.1.2011.2.25.4.40.5.10.80.1.1
    optixRtnXPICPGOduTxFreq OBJECT-TYPE
        SYNTAX Unsigned32
        MAX-ACCESS read-write
        STATUS current
        DESCRIPTION
            "Indicates the transmission frequency of an ODU board in an XPIC protection group. When frequencies of the transmitter/receiver at both ends match, signals can be received and transmitted successfully. Unit: kHz"
        ::= { optixRtnXPICPGOduParameterEntry 1 }

    -- 1.3.6.1.4.1.2011.2.25.4.40.5.10.80.1.2
    optixRtnXPICPGOduTxPower OBJECT-TYPE
        SYNTAX Integer32
        MAX-ACCESS read-write
        STATUS current
        DESCRIPTION
            "Indicates the transmit power of an ODU board in an XPIC protection group. Signed type Unit: 0.1 dBm Value range: 100 to 350"
        ::= { optixRtnXPICPGOduParameterEntry 2 }

    -- 1.3.6.1.4.1.2011.2.25.4.40.5.10.80.1.3
    optixRtnXPICPGOduMaxTxpower OBJECT-TYPE
        SYNTAX Integer32
        MAX-ACCESS read-write
        STATUS current
        DESCRIPTION
            "Indicates the maximum transmit power of an ODU board in an XPIC protection group. When the AM function is disabled, the maximum transmit power in the current mode is returned. When the AM function is enabled, the maximum transmit power in the guaranteed capability modulation mode is returned."
        ::= { optixRtnXPICPGOduParameterEntry 3 }

    -- 1.3.6.1.4.1.2011.2.25.4.40.5.10.80.1.4
    optixRtnXPICPGOduTRSpacing OBJECT-TYPE
        SYNTAX Unsigned32
        MAX-ACCESS read-write
        STATUS current
        DESCRIPTION
            "Indicates the T/R spacing of an ODU board in an XPIC protection group to avoid interference. Unit: kHz"
        ::= { optixRtnXPICPGOduParameterEntry 4 }

    -- 1.3.6.1.4.1.2011.2.25.4.40.5.10.80.1.5
    optixRtnXPICPGOduWorkState OBJECT-TYPE
        SYNTAX OPTIXRtnOduWorkStateType
        MAX-ACCESS read-write
        STATUS current
        DESCRIPTION
            "Indicates the transmission status of the corresponding RF transmitter for an XPIC protection group. Values: 0: muted 1: unmuted"
        DEFVAL{ 1 }
        ::= { optixRtnXPICPGOduParameterEntry 5 }

    -- 1.3.6.1.4.1.2011.2.25.4.40.5.10.81
    optixRtnXPICPGRFUFrequencyTable OBJECT-TYPE
        SYNTAX SEQUENCE OF OptixRtnXPICPGRFUFrequencyEntry
        MAX-ACCESS not-accessible
        STATUS current
        DESCRIPTION
            "Indicates the RFU frequency parameter of the XPIC workgroup."
        ::= { optixRtnIFProtect 81 }

    -- 1.3.6.1.4.1.2011.2.25.4.40.5.10.81.1
    optixRtnXPICPGRFUFrequencyEntry OBJECT-TYPE
        SYNTAX OptixRtnXPICPGRFUFrequencyEntry
        MAX-ACCESS not-accessible
        STATUS current
        DESCRIPTION
            "Indicates the entry of RFU frequency parameter of the XPIC workgroup."
        INDEX{ optixRtnXPICPGID }
        ::= { optixRtnXPICPGRFUFrequencyTable 1 }

    OptixRtnXPICPGRFUFrequencyEntry ::=
        SEQUENCE {
            optixRtnXPICPGRFURxFreq
                Unsigned32
        }

    -- 1.3.6.1.4.1.2011.2.25.4.40.5.10.81.1.1
    optixRtnXPICPGRFURxFreq OBJECT-TYPE
        SYNTAX Unsigned32
        MAX-ACCESS read-write
        STATUS current
        DESCRIPTION
            "Indicates the receive frequency of the XPIC workgroup."
        ::= { optixRtnXPICPGRFUFrequencyEntry 1 }

    -- 1.3.6.1.4.1.2011.2.25.4.40.5.10.87
    optixRtnXPICBdPolarMgr OBJECT IDENTIFIER ::= { optixRtnIFProtect 87 }

    -- 1.3.6.1.4.1.2011.2.25.4.40.5.10.87.1
    optixRtnBdPolarId OBJECT-TYPE
        SYNTAX Unsigned32
        MAX-ACCESS read-write
        STATUS current
        DESCRIPTION
            " xpic group id"
        DEFVAL{ 1 }
        ::= { optixRtnXPICBdPolarMgr 1 }

    -- 1.3.6.1.4.1.2011.2.25.4.40.5.10.87.2
    optixRtnBdPolarHBid OBJECT-TYPE
        SYNTAX Unsigned32
        MAX-ACCESS read-write
        STATUS current
        DESCRIPTION
            "H polar board id"
        DEFVAL{ 1 }
        ::= { optixRtnXPICBdPolarMgr 2 }

    -- 1.3.6.1.4.1.2011.2.25.4.40.5.10.87.3
    optixRtnBdPolarHSbid OBJECT-TYPE
        SYNTAX Unsigned32
        MAX-ACCESS read-write
        STATUS current
        DESCRIPTION
            " H polar subboard id"
        DEFVAL{ 255 }
        ::= { optixRtnXPICBdPolarMgr 3 }

    -- 1.3.6.1.4.1.2011.2.25.4.40.5.10.87.4
    optixRtnBdPolarHPid OBJECT-TYPE
        SYNTAX Unsigned32
        MAX-ACCESS read-write
        STATUS current
        DESCRIPTION
            " H polar port id"
        ::= { optixRtnXPICBdPolarMgr 4 }

    -- 1.3.6.1.4.1.2011.2.25.4.40.5.10.87.5
    optixRtnBdPolarVBid OBJECT-TYPE
        SYNTAX Unsigned32
        MAX-ACCESS read-write
        STATUS current
        DESCRIPTION
            "  V polar board id"
        DEFVAL{ 1 }
        ::= { optixRtnXPICBdPolarMgr 5 }

    -- 1.3.6.1.4.1.2011.2.25.4.40.5.10.87.6
    optixRtnBdPolarVSbid OBJECT-TYPE
        SYNTAX Unsigned32
        MAX-ACCESS read-write
        STATUS current
        DESCRIPTION
            " V polar subboard id"
        DEFVAL{ 255 }
        ::= { optixRtnXPICBdPolarMgr 6 }

    -- 1.3.6.1.4.1.2011.2.25.4.40.5.10.87.7
    optixRtnBdPolarVPid OBJECT-TYPE
        SYNTAX Unsigned32
        MAX-ACCESS read-write
        STATUS current
        DESCRIPTION
            " V polar port id"
        ::= { optixRtnXPICBdPolarMgr 7 }

    -- 1.3.6.1.4.1.2011.2.25.4.40.5.10.90
    optixRtnPhyLagPGParameterTable OBJECT-TYPE
        SYNTAX SEQUENCE OF OptixRtnPhyLagPGParameterEntry
        MAX-ACCESS not-accessible
        STATUS current
        DESCRIPTION
            "Describes configuration parameters for the working board and protection board in a PLA protection group."
        ::= { optixRtnIFProtect 90 }

    -- 1.3.6.1.4.1.2011.2.25.4.40.5.10.90.1
    optixRtnPhyLagPGParameterEntry OBJECT-TYPE
        SYNTAX OptixRtnPhyLagPGParameterEntry
        MAX-ACCESS not-accessible
        STATUS current
        DESCRIPTION
            "Indicates parameter entries for a PLA protection group."
        INDEX{ optixRtnPhyLagPGID }
        ::= { optixRtnPhyLagPGParameterTable 1 }

    OptixRtnPhyLagPGParameterEntry ::=
        SEQUENCE {
            optixRtnPhyLagPGID
                Unsigned32,
            optixRtnPhyLagPGType
                OPTIXRtnPhyLagPGType,
            optixRtnPhyLagPGMainBoardID
                Unsigned32,
            optixRtnPhyLagPGMainSubCardID
                Unsigned32,
            optixRtnPhyLagPGMainPortID
                Unsigned32,
            optixRtnPhyLagPGSlavePuNum
                Unsigned32,
            optixRtnPhyLagPGPu1BoardID
                Unsigned32,
            optixRtnPhyLagPGPu1SubCardID
                Unsigned32,
            optixRtnPhyLagPGPu1PortID
                Unsigned32,
            optixRtnPhyLagPGPu2BoardID
                Unsigned32,
            optixRtnPhyLagPGPu2SubCardID
                Unsigned32,
            optixRtnPhyLagPGPu2PortID
                Unsigned32,
            optixRtnPhyLagPGPu3BoardID
                Unsigned32,
            optixRtnPhyLagPGPu3SubCardID
                Unsigned32,
            optixRtnPhyLagPGPu3PortID
                Unsigned32,
            optixRtnPhyLagPGLinkThreshold
                Unsigned32,
            optixRtnPhyLagPGSlaveMemsInfo
                OCTET STRING,
            optixRtnPhyLagPGCfgRowStatus
                RowStatus
        }

    -- 1.3.6.1.4.1.2011.2.25.4.40.5.10.90.1.1
    optixRtnPhyLagPGID OBJECT-TYPE
        SYNTAX Unsigned32
        MAX-ACCESS not-accessible
        STATUS current
        DESCRIPTION
            "Indicates the protection group ID."
        ::= { optixRtnPhyLagPGParameterEntry 1 }

    -- 1.3.6.1.4.1.2011.2.25.4.40.5.10.90.1.2
    optixRtnPhyLagPGType OBJECT-TYPE
        SYNTAX OPTIXRtnPhyLagPGType
        MAX-ACCESS read-create
        STATUS current
        DESCRIPTION
            "Indicates the protection group type. Values: 0: pla, 1: epla, 2: nbpla, 3: nbepla,4: epla plus,5: sepla"
        DEFVAL{ 0 }
        ::= { optixRtnPhyLagPGParameterEntry 2 }

    -- 1.3.6.1.4.1.2011.2.25.4.40.5.10.90.1.3
    optixRtnPhyLagPGMainBoardID OBJECT-TYPE
        SYNTAX Unsigned32
        MAX-ACCESS read-create
        STATUS current
        DESCRIPTION
            "Indicates the main unit slot ID."
        ::= { optixRtnPhyLagPGParameterEntry 3 }

    -- 1.3.6.1.4.1.2011.2.25.4.40.5.10.90.1.4
    optixRtnPhyLagPGMainSubCardID OBJECT-TYPE
        SYNTAX Unsigned32
        MAX-ACCESS read-create
        STATUS current
        DESCRIPTION
            "Indicates the main subboard ID."
        ::= { optixRtnPhyLagPGParameterEntry 4 }

    -- 1.3.6.1.4.1.2011.2.25.4.40.5.10.90.1.5
    optixRtnPhyLagPGMainPortID OBJECT-TYPE
        SYNTAX Unsigned32
        MAX-ACCESS read-create
        STATUS current
        DESCRIPTION
            "Indicates the main unit port ID."
        ::= { optixRtnPhyLagPGParameterEntry 5 }

    -- 1.3.6.1.4.1.2011.2.25.4.40.5.10.90.1.6
    optixRtnPhyLagPGSlavePuNum OBJECT-TYPE
        SYNTAX Unsigned32
        MAX-ACCESS read-only
        STATUS current
        DESCRIPTION
            "Indicates the number of units. Value range: 1 to 15"
        DEFVAL{ 1 }
        ::= { optixRtnPhyLagPGParameterEntry 6 }

    -- 1.3.6.1.4.1.2011.2.25.4.40.5.10.90.1.7
    optixRtnPhyLagPGPu1BoardID OBJECT-TYPE
        SYNTAX Unsigned32
        MAX-ACCESS read-only
        STATUS current
        DESCRIPTION
            "Indicates the unit 1 slot ID."
        ::= { optixRtnPhyLagPGParameterEntry 7 }

    -- 1.3.6.1.4.1.2011.2.25.4.40.5.10.90.1.8
    optixRtnPhyLagPGPu1SubCardID OBJECT-TYPE
        SYNTAX Unsigned32
        MAX-ACCESS read-only
        STATUS current
        DESCRIPTION
            "Indicates the unit 1 subboard ID."
        ::= { optixRtnPhyLagPGParameterEntry 8 }

    -- 1.3.6.1.4.1.2011.2.25.4.40.5.10.90.1.9
    optixRtnPhyLagPGPu1PortID OBJECT-TYPE
        SYNTAX Unsigned32
        MAX-ACCESS read-only
        STATUS current
        DESCRIPTION
            "Indicates the unit 1 port ID."
        ::= { optixRtnPhyLagPGParameterEntry 9 }

    -- 1.3.6.1.4.1.2011.2.25.4.40.5.10.90.1.10
    optixRtnPhyLagPGPu2BoardID OBJECT-TYPE
        SYNTAX Unsigned32
        MAX-ACCESS read-only
        STATUS current
        DESCRIPTION
            "Indicates the unit 2 slot ID."
        DEFVAL{ 255 }
        ::= { optixRtnPhyLagPGParameterEntry 10 }

    -- 1.3.6.1.4.1.2011.2.25.4.40.5.10.90.1.11
    optixRtnPhyLagPGPu2SubCardID OBJECT-TYPE
        SYNTAX Unsigned32
        MAX-ACCESS read-only
        STATUS current
        DESCRIPTION
            "Indicates the unit 2 subboard ID."
        DEFVAL{ 255 }
        ::= { optixRtnPhyLagPGParameterEntry 11 }

    -- 1.3.6.1.4.1.2011.2.25.4.40.5.10.90.1.12
    optixRtnPhyLagPGPu2PortID OBJECT-TYPE
        SYNTAX Unsigned32
        MAX-ACCESS read-only
        STATUS current
        DESCRIPTION
            "Indicates the unit 2 port ID."
        DEFVAL{ 255 }
        ::= { optixRtnPhyLagPGParameterEntry 12 }

    -- 1.3.6.1.4.1.2011.2.25.4.40.5.10.90.1.13
    optixRtnPhyLagPGPu3BoardID OBJECT-TYPE
        SYNTAX Unsigned32
        MAX-ACCESS read-only
        STATUS current
        DESCRIPTION
            "Indicates the unit 3 slot ID."
        DEFVAL{ 255 }
        ::= { optixRtnPhyLagPGParameterEntry 13 }

    -- 1.3.6.1.4.1.2011.2.25.4.40.5.10.90.1.14
    optixRtnPhyLagPGPu3SubCardID OBJECT-TYPE
        SYNTAX Unsigned32
        MAX-ACCESS read-only
        STATUS current
        DESCRIPTION
            "Indicates the unit 3 subboard ID."
        DEFVAL{ 255 }
        ::= { optixRtnPhyLagPGParameterEntry 14 }

    -- 1.3.6.1.4.1.2011.2.25.4.40.5.10.90.1.15
    optixRtnPhyLagPGPu3PortID OBJECT-TYPE
        SYNTAX Unsigned32
        MAX-ACCESS read-only
        STATUS current
        DESCRIPTION
            "Indicates the unit 3 port ID."
        DEFVAL{ 255 }
        ::= { optixRtnPhyLagPGParameterEntry 15 }

    -- 1.3.6.1.4.1.2011.2.25.4.40.5.10.90.1.16
    optixRtnPhyLagPGLinkThreshold OBJECT-TYPE
        SYNTAX Unsigned32
        MAX-ACCESS read-write
        STATUS current
        DESCRIPTION
            "Indicates the minimum number of activated links in a physical LAG."
        ::= { optixRtnPhyLagPGParameterEntry 16 }

    -- 1.3.6.1.4.1.2011.2.25.4.40.5.10.90.1.17
    optixRtnPhyLagPGSlaveMemsInfo OBJECT-TYPE
        SYNTAX OCTET STRING (SIZE(0..64))
        MAX-ACCESS read-create
        STATUS current
        DESCRIPTION
            "Indicates the slave port information of a PLA protection group."
        ::= { optixRtnPhyLagPGParameterEntry 17 }

    -- 1.3.6.1.4.1.2011.2.25.4.40.5.10.90.1.50
    optixRtnPhyLagPGCfgRowStatus OBJECT-TYPE
        SYNTAX RowStatus
        MAX-ACCESS read-create
        STATUS current
        DESCRIPTION
            "Indicates the row status of a PLA protection group."
        DEFVAL{ active }
        ::= { optixRtnPhyLagPGParameterEntry 50 }

    -- 1.3.6.1.4.1.2011.2.25.4.40.5.10.91
    optixRtnPhyLagPGParameterExtTable OBJECT-TYPE
        SYNTAX SEQUENCE OF OptixRtnPhyLagPGParameterExtEntry
        MAX-ACCESS not-accessible
        STATUS current
        DESCRIPTION
            "Describes configuration parameters for the working board and protection board in the physical link aggregation group."
        ::= { optixRtnIFProtect 91 }

    -- 1.3.6.1.4.1.2011.2.25.4.40.5.10.91.1
    optixRtnPhyLagPGParameterExtEntry OBJECT-TYPE
        SYNTAX OptixRtnPhyLagPGParameterExtEntry
        MAX-ACCESS not-accessible
        STATUS current
        DESCRIPTION
            "Indicates parameter entries for the physical link aggregation group."
        INDEX{ optixRtnPhyLagPGIDExt }
        ::= { optixRtnPhyLagPGParameterExtTable 1 }

    OptixRtnPhyLagPGParameterExtEntry ::=
        SEQUENCE {
            optixRtnPhyLagPGIDExt
                Unsigned32,
            optixRtnPhyLagPGTypeExt
                OPTIXRtnPhyLagPGType,
            optixRtnPhyLagPGCfgCapacity
                Unsigned32,
            optixRtnPhyLagPGMainBoardIDExt
                Unsigned32,
            optixRtnPhyLagPGMainSubCardIDExt
                Unsigned32,
            optixRtnPhyLagPGMainPortIDExt
                Unsigned32,
            optixRtnPhyLagPGSlaveMemsExtInfo
                OCTET STRING,
            optixRtnPhyLagPGLinkThresholdExt
                Unsigned32,
            optixRtnPhyLagPGMaxCapacity
                Unsigned32,
            optixRtnPhyLagPGCfgRowStatusExt
                RowStatus
        }

    -- 1.3.6.1.4.1.2011.2.25.4.40.5.10.91.1.1
    optixRtnPhyLagPGIDExt OBJECT-TYPE
        SYNTAX Unsigned32
        MAX-ACCESS not-accessible
        STATUS current
        DESCRIPTION
            "Indicates the protection group ID of the physical link aggregation group."
        ::= { optixRtnPhyLagPGParameterExtEntry 1 }

    -- 1.3.6.1.4.1.2011.2.25.4.40.5.10.91.1.2
    optixRtnPhyLagPGTypeExt OBJECT-TYPE
        SYNTAX OPTIXRtnPhyLagPGType
        MAX-ACCESS read-create
        STATUS current
        DESCRIPTION
            "Indicates the type of the physical link aggregation group. Values: 0: pla, 1: epla, 2: nbpla, 3: nbepla,4: epla plus,5: sepla"
        ::= { optixRtnPhyLagPGParameterExtEntry 2 }

    -- 1.3.6.1.4.1.2011.2.25.4.40.5.10.91.1.3
    optixRtnPhyLagPGCfgCapacity OBJECT-TYPE
        SYNTAX Unsigned32
        MAX-ACCESS read-write
        STATUS current
        DESCRIPTION
            "Indicates the configuration capacity of the physical link aggregation group."
        DEFVAL{ 2500 }
        ::= { optixRtnPhyLagPGParameterExtEntry 3 }

    -- 1.3.6.1.4.1.2011.2.25.4.40.5.10.91.1.4
    optixRtnPhyLagPGMainBoardIDExt OBJECT-TYPE
        SYNTAX Unsigned32
        MAX-ACCESS read-create
        STATUS current
        DESCRIPTION
            "Indicates the main unit slot ID of the physical link aggregation group."
        ::= { optixRtnPhyLagPGParameterExtEntry 4 }

    -- 1.3.6.1.4.1.2011.2.25.4.40.5.10.91.1.5
    optixRtnPhyLagPGMainSubCardIDExt OBJECT-TYPE
        SYNTAX Unsigned32
        MAX-ACCESS read-create
        STATUS current
        DESCRIPTION
            "Indicates the main subboard ID of the physical link aggregation group."
        DEFVAL{ 255 }
        ::= { optixRtnPhyLagPGParameterExtEntry 5 }

    -- 1.3.6.1.4.1.2011.2.25.4.40.5.10.91.1.6
    optixRtnPhyLagPGMainPortIDExt OBJECT-TYPE
        SYNTAX Unsigned32
        MAX-ACCESS read-create
        STATUS current
        DESCRIPTION
            "Indicates the main unit port ID of the physical link aggregation group."
        ::= { optixRtnPhyLagPGParameterExtEntry 6 }

    -- 1.3.6.1.4.1.2011.2.25.4.40.5.10.91.1.7
    optixRtnPhyLagPGSlaveMemsExtInfo OBJECT-TYPE
        SYNTAX OCTET STRING (SIZE(0..64))
        MAX-ACCESS read-create
        STATUS current
        DESCRIPTION
            "Indicates the slave port information of the physical link aggregation group."
        ::= { optixRtnPhyLagPGParameterExtEntry 7 }

    -- 1.3.6.1.4.1.2011.2.25.4.40.5.10.91.1.8
    optixRtnPhyLagPGLinkThresholdExt OBJECT-TYPE
        SYNTAX Unsigned32
        MAX-ACCESS read-write
        STATUS current
        DESCRIPTION
            "Indicates the minimum number of activated links of the physical link aggregation group."
        DEFVAL{ 1 }
        ::= { optixRtnPhyLagPGParameterExtEntry 8 }

    -- 1.3.6.1.4.1.2011.2.25.4.40.5.10.91.1.9
    optixRtnPhyLagPGMaxCapacity OBJECT-TYPE
        SYNTAX Unsigned32
        MAX-ACCESS read-only
        STATUS current
        DESCRIPTION
            "Indicates the maximum capacity of the physical link aggregation group."
        ::= { optixRtnPhyLagPGParameterExtEntry 9 }

    -- 1.3.6.1.4.1.2011.2.25.4.40.5.10.91.1.50
    optixRtnPhyLagPGCfgRowStatusExt OBJECT-TYPE
        SYNTAX RowStatus
        MAX-ACCESS read-create
        STATUS current
        DESCRIPTION
            "Indicates the row status of the physical link aggregation group."
        DEFVAL{ active }
        ::= { optixRtnPhyLagPGParameterExtEntry 50 }

    -- 1.3.6.1.4.1.2011.2.25.4.40.5.10.92
    optixRtnPhyLagPGSwitchEnableTable OBJECT-TYPE
        SYNTAX SEQUENCE OF OptixRtnPhyLagPGSwitchEnableEntry
        MAX-ACCESS not-accessible
        STATUS current
        DESCRIPTION
            "Describes the state of the hitless switching enable parameter in an EPLA protection group of 980L."
        ::= { optixRtnIFProtect 92 }

    -- 1.3.6.1.4.1.2011.2.25.4.40.5.10.92.1
    optixRtnPhyLagPGSwitchEnableEntry OBJECT-TYPE
        SYNTAX OptixRtnPhyLagPGSwitchEnableEntry
        MAX-ACCESS not-accessible
        STATUS current
        DESCRIPTION
            "Indicates the entry for enabling hitless switching for an EPLA protection group."
        INDEX{ optixRtnPhyLagSwitchEnablePGID,optixRtnPhyLagSwitchEnablePGType }
        ::= { optixRtnPhyLagPGSwitchEnableTable 1 }

    OptixRtnPhyLagPGSwitchEnableEntry ::=
        SEQUENCE {
            optixRtnPhyLagSwitchEnablePGID
                Unsigned32,
            optixRtnPhyLagSwitchEnablePGType
                OPTIXRtnPhyLagPGType,
            optixRtnPhyLagPGSwitchEnable
                INTEGER,
            optixRtnAddEplaMemberInfo
                OCTET STRING,
            optixRtnDelEplaMemberInfo
                OCTET STRING
        }

    -- 1.3.6.1.4.1.2011.2.25.4.40.5.10.92.1.1
    optixRtnPhyLagSwitchEnablePGID OBJECT-TYPE
        SYNTAX Unsigned32 (1..12)
        MAX-ACCESS not-accessible
        STATUS current
        DESCRIPTION
            "Indicates the ID of an EPLA protection group."
        ::= { optixRtnPhyLagPGSwitchEnableEntry 1 }

    -- 1.3.6.1.4.1.2011.2.25.4.40.5.10.92.1.2
    optixRtnPhyLagSwitchEnablePGType OBJECT-TYPE
        SYNTAX OPTIXRtnPhyLagPGType
        MAX-ACCESS not-accessible
        STATUS current
        DESCRIPTION
            "Indicates the protection group type. Values: 0: pla 1: epla 2: nbpla 3: nbepla 4: eplaplus"
        ::= { optixRtnPhyLagPGSwitchEnableEntry 2 }

    -- 1.3.6.1.4.1.2011.2.25.4.40.5.10.92.1.3
    optixRtnPhyLagPGSwitchEnable OBJECT-TYPE
        SYNTAX INTEGER
        {
            disable(0),
            enable(1)
        }
        MAX-ACCESS read-write
        STATUS current
        DESCRIPTION
            "Indicates the state of the hitless switching enable parameter in an EPLA protection group."
        DEFVAL{ 0 }
        ::= { optixRtnPhyLagPGSwitchEnableEntry 3 }

    -- 1.3.6.1.4.1.2011.2.25.4.40.5.10.92.1.4
    optixRtnAddEplaMemberInfo OBJECT-TYPE
        SYNTAX OCTET STRING
        MAX-ACCESS read-write
        STATUS current
        DESCRIPTION
            "Indicates that members are added to a EPLA group in mode B."
        ::= { optixRtnPhyLagPGSwitchEnableEntry 4 }

    -- 1.3.6.1.4.1.2011.2.25.4.40.5.10.92.1.5
    optixRtnDelEplaMemberInfo OBJECT-TYPE
        SYNTAX OCTET STRING
        MAX-ACCESS read-write
        STATUS current
        DESCRIPTION
            "Indicates that members are deleted from a EPLA group in mode B."
        ::= { optixRtnPhyLagPGSwitchEnableEntry 5 }

    -- 1.3.6.1.4.1.2011.2.25.4.40.5.10.93
    optixRtnPhyLagServiceParaTable OBJECT-TYPE
        SYNTAX SEQUENCE OF OptixRtnPhyLagServiceParaEntry
        MAX-ACCESS not-accessible
        STATUS current
        DESCRIPTION
            "Indicates the priority threshold for high-priority services in a EPLA group."
        ::= { optixRtnIFProtect 93 }

    -- 1.3.6.1.4.1.2011.2.25.4.40.5.10.93.1
    optixRtnPhyLagServiceParaEntry OBJECT-TYPE
        SYNTAX OptixRtnPhyLagServiceParaEntry
        MAX-ACCESS not-accessible
        STATUS current
        DESCRIPTION
            "Indicates the priority threshold for high-priority services in a EPLA group."
        INDEX{ optixRtnPhyLagSerParaPGID,optixRtnPhyLagSerParaPGType }
        ::= { optixRtnPhyLagServiceParaTable 1 }

    OptixRtnPhyLagServiceParaEntry ::=
        SEQUENCE {
            optixRtnPhyLagSerParaPGID
                Unsigned32,
            optixRtnPhyLagSerParaPGType
                OPTIXRtnPhyLagPGType,
            optixRtnPhyLagServicePriorityThreshold
                Unsigned32,
            optixRtnConfigServScheduleMode
                INTEGER,
            optixRtnWorkingServScheduleMode
                INTEGER,
            optixRtnPhyMemberAttrInfo
                OCTET STRING
        }

    -- 1.3.6.1.4.1.2011.2.25.4.40.5.10.93.1.1
    optixRtnPhyLagSerParaPGID OBJECT-TYPE
        SYNTAX Unsigned32 (1..12)
        MAX-ACCESS not-accessible
        STATUS current
        DESCRIPTION
            "Indicates the protection group ID."
        ::= { optixRtnPhyLagServiceParaEntry 1 }

    -- 1.3.6.1.4.1.2011.2.25.4.40.5.10.93.1.2
    optixRtnPhyLagSerParaPGType OBJECT-TYPE
        SYNTAX OPTIXRtnPhyLagPGType
        MAX-ACCESS not-accessible
        STATUS current
        DESCRIPTION
            "Indicates the protection group type."
        ::= { optixRtnPhyLagServiceParaEntry 2 }

    -- 1.3.6.1.4.1.2011.2.25.4.40.5.10.93.1.3
    optixRtnPhyLagServicePriorityThreshold OBJECT-TYPE
        SYNTAX Unsigned32 (0..7)
        MAX-ACCESS read-write
        STATUS current
        DESCRIPTION
            "Indicates the priority threshold for services."
        DEFVAL{ 5 }
        ::= { optixRtnPhyLagServiceParaEntry 3 }

    -- 1.3.6.1.4.1.2011.2.25.4.40.5.10.93.1.4
    optixRtnConfigServScheduleMode OBJECT-TYPE
        SYNTAX INTEGER
        {
            modeA(0),
            modeB(1),
            modeAAccess(2)
        }
        MAX-ACCESS read-write
        STATUS current
        DESCRIPTION
            "Indicates the config prority of the slave unit.0: modeA; 1: modeB;2:modeAAccess"
        DEFVAL{ 1 }
        ::= { optixRtnPhyLagServiceParaEntry 4 }

    -- 1.3.6.1.4.1.2011.2.25.4.40.5.10.93.1.5
    optixRtnWorkingServScheduleMode OBJECT-TYPE
        SYNTAX INTEGER
        {
            modeA(0),
            modeB(1),
            modeAAccess(2),
            unknown(-1)
        }
        MAX-ACCESS read-write
        STATUS current
        DESCRIPTION
            "Indicates the scheduling mode for the working service. 0: modeA; 1: modeB;2:modeAAccess; 0xff: unknown"
        ::= { optixRtnPhyLagServiceParaEntry 5 }

    -- 1.3.6.1.4.1.2011.2.25.4.40.5.10.93.1.6
    optixRtnPhyMemberAttrInfo OBJECT-TYPE
        SYNTAX OCTET STRING
        MAX-ACCESS read-only
        STATUS current
        DESCRIPTION
            "Indicates tht arrtibute of the slave unit"
        ::= { optixRtnPhyLagServiceParaEntry 6 }

    -- 1.3.6.1.4.1.2011.2.25.4.40.5.10.94
    optixRtnPhyLagMemberPriTable OBJECT-TYPE
        SYNTAX SEQUENCE OF OptixRtnPhyLagMemberPriEntry
        MAX-ACCESS not-accessible
        STATUS current
        DESCRIPTION
            "Queries priorities of members in a EPLA group."
        ::= { optixRtnIFProtect 94 }

    -- 1.3.6.1.4.1.2011.2.25.4.40.5.10.94.1
    optixRtnPhyLagMemberPriEntry OBJECT-TYPE
        SYNTAX OptixRtnPhyLagMemberPriEntry
        MAX-ACCESS not-accessible
        STATUS current
        DESCRIPTION
            "Queries priorities of members in a EPLA group."
        INDEX{ optixRtnPhyLagMemPriPGID,optixRtnPhyLagMemPriPGType }
        ::= { optixRtnPhyLagMemberPriTable 1 }

    OptixRtnPhyLagMemberPriEntry ::=
        SEQUENCE {
            optixRtnPhyLagMemPriPGID
                Unsigned32,
            optixRtnPhyLagMemPriPGType
                OPTIXRtnPhyLagPGType,
            optixRtnPhyLagMemBoardId
                Unsigned32,
            optixRtnPhyLagMemSubCardId
                Unsigned32,
            optixRtnPhyLagMemPortId
                Unsigned32,
            optixRtnPhyLagMemChannelId
                Unsigned32,
            optixRtnPhyLagConfigPriority
                INTEGER,
            optixRtnPhyLagWorkingPriority
                INTEGER
        }

    -- 1.3.6.1.4.1.2011.2.25.4.40.5.10.94.1.1
    optixRtnPhyLagMemPriPGID OBJECT-TYPE
        SYNTAX Unsigned32 (1..12)
        MAX-ACCESS not-accessible
        STATUS current
        DESCRIPTION
            "Indicates the protection group ID."
        ::= { optixRtnPhyLagMemberPriEntry 1 }

    -- 1.3.6.1.4.1.2011.2.25.4.40.5.10.94.1.2
    optixRtnPhyLagMemPriPGType OBJECT-TYPE
        SYNTAX OPTIXRtnPhyLagPGType
        MAX-ACCESS not-accessible
        STATUS current
        DESCRIPTION
            "Indicates the protection group type."
        ::= { optixRtnPhyLagMemberPriEntry 2 }

    -- 1.3.6.1.4.1.2011.2.25.4.40.5.10.94.1.3
    optixRtnPhyLagMemBoardId OBJECT-TYPE
        SYNTAX Unsigned32
        MAX-ACCESS not-accessible
        STATUS current
        DESCRIPTION
            "Indicates the slot ID of the slave unit."
        ::= { optixRtnPhyLagMemberPriEntry 3 }

    -- 1.3.6.1.4.1.2011.2.25.4.40.5.10.94.1.4
    optixRtnPhyLagMemSubCardId OBJECT-TYPE
        SYNTAX Unsigned32
        MAX-ACCESS not-accessible
        STATUS current
        DESCRIPTION
            "Indicates the subboard ID of the slave unit."
        ::= { optixRtnPhyLagMemberPriEntry 4 }

    -- 1.3.6.1.4.1.2011.2.25.4.40.5.10.94.1.5
    optixRtnPhyLagMemPortId OBJECT-TYPE
        SYNTAX Unsigned32
        MAX-ACCESS not-accessible
        STATUS current
        DESCRIPTION
            "Indicates the port ID of the slave unit."
        ::= { optixRtnPhyLagMemberPriEntry 5 }

    -- 1.3.6.1.4.1.2011.2.25.4.40.5.10.94.1.6
    optixRtnPhyLagMemChannelId OBJECT-TYPE
        SYNTAX Unsigned32
        MAX-ACCESS not-accessible
        STATUS current
        DESCRIPTION
            "Indicates the channel ID of the salve unit."
        ::= { optixRtnPhyLagMemberPriEntry 6 }

    -- 1.3.6.1.4.1.2011.2.25.4.40.5.10.94.1.7
    optixRtnPhyLagConfigPriority OBJECT-TYPE
        SYNTAX INTEGER
        {
            auto(0),
            lowPri(1),
            highPri(2)
        }
        MAX-ACCESS read-write
        STATUS current
        DESCRIPTION
            "Indicates the config prority of the slave unit.0: auto; 1: lowPri; 2: highPri;"
        DEFVAL{ 0 }
        ::= { optixRtnPhyLagMemberPriEntry 7 }

    -- 1.3.6.1.4.1.2011.2.25.4.40.5.10.94.1.8
    optixRtnPhyLagWorkingPriority OBJECT-TYPE
        SYNTAX INTEGER
        {
            auto(0),
            lowPri(1),
            highPri(2),
            unknown(-1)
        }
        MAX-ACCESS read-write
        STATUS current
        DESCRIPTION
            "Indicates the scheduling mode of the slave unit. 0: auto; 1: lowPri; 2: highPri; 0xff: unknown;"
        ::= { optixRtnPhyLagMemberPriEntry 8 }

    -- 1.3.6.1.4.1.2011.2.25.4.40.5.10.96
    optixRtnPhyLagMemberStateTable OBJECT-TYPE
        SYNTAX SEQUENCE OF OptixRtnPhyLagMemberStateEntry
        MAX-ACCESS not-accessible
        STATUS current
        DESCRIPTION
            "Indicates status of members in a PLA group."
        ::= { optixRtnIFProtect 96 }

    -- 1.3.6.1.4.1.2011.2.25.4.40.5.10.96.1
    optixRtnPhyLagMemberStateEntry OBJECT-TYPE
        SYNTAX OptixRtnPhyLagMemberStateEntry
        MAX-ACCESS not-accessible
        STATUS current
        DESCRIPTION
            "Indicates status of members in a PLA group."
        INDEX{ optixRtnPhyLagMemStaPGId }
        ::= { optixRtnPhyLagMemberStateTable 1 }

    OptixRtnPhyLagMemberStateEntry ::=
        SEQUENCE {
            optixRtnPhyLagMemStaPGId
                Unsigned32,
            optixRtnPhyLagMemStateInfo
                OCTET STRING
        }

    -- 1.3.6.1.4.1.2011.2.25.4.40.5.10.96.1.1
    optixRtnPhyLagMemStaPGId OBJECT-TYPE
        SYNTAX Unsigned32 (1..12)
        MAX-ACCESS not-accessible
        STATUS current
        DESCRIPTION
            "Indicates the protection group ID."
        ::= { optixRtnPhyLagMemberStateEntry 1 }

    -- 1.3.6.1.4.1.2011.2.25.4.40.5.10.96.1.2
    optixRtnPhyLagMemStateInfo OBJECT-TYPE
        SYNTAX OCTET STRING
        MAX-ACCESS read-only
        STATUS current
        DESCRIPTION
            "Indicates the state information of the slave unit"
        ::= { optixRtnPhyLagMemberStateEntry 2 }

    -- 1.3.6.1.4.1.2011.2.25.4.40.5.10.97
    optixRtnPhyLagSdbPGParameterTable OBJECT-TYPE
        SYNTAX SEQUENCE OF OptixRtnPhyLagSdbPGParameterEntry
        MAX-ACCESS not-accessible
        STATUS current
        DESCRIPTION
            "Describes configuration parameters for the working board and protection board in the PLA group."
        ::= { optixRtnIFProtect 97 }

    -- 1.3.6.1.4.1.2011.2.25.4.40.5.10.97.1
    optixRtnPhyLagSdbPGParameterEntry OBJECT-TYPE
        SYNTAX OptixRtnPhyLagSdbPGParameterEntry
        MAX-ACCESS not-accessible
        STATUS current
        DESCRIPTION
            "Indicates parameter entries for a PLA group."
        INDEX{ optixRtnPhyLagSdbPGID }
        ::= { optixRtnPhyLagSdbPGParameterTable 1 }

    OptixRtnPhyLagSdbPGParameterEntry ::=
        SEQUENCE {
            optixRtnPhyLagSdbPGID
                Unsigned32,
            optixRtnPhyLagSdbPGType
                OPTIXRtnPhyLagPGType,
            optixRtnPhyLagSdbPGCfgCapacity
                Unsigned32,
            optixRtnPhyLagSdbPGMainBoardID
                Unsigned32,
            optixRtnPhyLagSdbPGMainSubCardID
                Unsigned32,
            optixRtnPhyLagSdbPGMainPortID
                Unsigned32,
            optixRtnPhyLagSdbPGSlaveMemsInfo
                OCTET STRING,
            optixRtnPhyLagSdbPGSlaveMemsAttrInfo
                OCTET STRING,
            optixRtnPhyLagSdbPGCfgRowStatus
                RowStatus
        }

    -- 1.3.6.1.4.1.2011.2.25.4.40.5.10.97.1.1
    optixRtnPhyLagSdbPGID OBJECT-TYPE
        SYNTAX Unsigned32 (1..12)
        MAX-ACCESS not-accessible
        STATUS current
        DESCRIPTION
            "Indicates the PLA group ID."
        ::= { optixRtnPhyLagSdbPGParameterEntry 1 }

    -- 1.3.6.1.4.1.2011.2.25.4.40.5.10.97.1.2
    optixRtnPhyLagSdbPGType OBJECT-TYPE
        SYNTAX OPTIXRtnPhyLagPGType
        MAX-ACCESS read-create
        STATUS current
        DESCRIPTION
            "Indicates the PLA group type."
        ::= { optixRtnPhyLagSdbPGParameterEntry 2 }

    -- 1.3.6.1.4.1.2011.2.25.4.40.5.10.97.1.3
    optixRtnPhyLagSdbPGCfgCapacity OBJECT-TYPE
        SYNTAX Unsigned32
        MAX-ACCESS read-write 
        STATUS current
        DESCRIPTION
            "Indicates the configuration capacity of a PLA group."
        DEFVAL{ 2500 }
        ::= { optixRtnPhyLagSdbPGParameterEntry 3 }

    -- 1.3.6.1.4.1.2011.2.25.4.40.5.10.97.1.4
    optixRtnPhyLagSdbPGMainBoardID OBJECT-TYPE
        SYNTAX Unsigned32
        MAX-ACCESS read-create
        STATUS current
        DESCRIPTION
            "Indicates the main unit slot ID of a PLA group."
        ::= { optixRtnPhyLagSdbPGParameterEntry 4 }

    -- 1.3.6.1.4.1.2011.2.25.4.40.5.10.97.1.5
    optixRtnPhyLagSdbPGMainSubCardID OBJECT-TYPE
        SYNTAX Unsigned32
        MAX-ACCESS read-create
        STATUS current
        DESCRIPTION
            "Indicates the main subboard ID of a PLA group."
        DEFVAL{ 255 }
        ::= { optixRtnPhyLagSdbPGParameterEntry 5 }

    -- 1.3.6.1.4.1.2011.2.25.4.40.5.10.97.1.6
    optixRtnPhyLagSdbPGMainPortID OBJECT-TYPE
        SYNTAX Unsigned32
        MAX-ACCESS read-create
        STATUS current
        DESCRIPTION
            "Indicates the main unit port ID of a PLA group."
        ::= { optixRtnPhyLagSdbPGParameterEntry 6 }

    -- 1.3.6.1.4.1.2011.2.25.4.40.5.10.97.1.7
    optixRtnPhyLagSdbPGSlaveMemsInfo OBJECT-TYPE
        SYNTAX OCTET STRING
        MAX-ACCESS read-create
        STATUS current
        DESCRIPTION
            "Indicates the slave port information of a PLA group."
        ::= { optixRtnPhyLagSdbPGParameterEntry 7 }

    -- 1.3.6.1.4.1.2011.2.25.4.40.5.10.97.1.8
    optixRtnPhyLagSdbPGSlaveMemsAttrInfo OBJECT-TYPE
        SYNTAX OCTET STRING
        MAX-ACCESS read-write
        STATUS current
        DESCRIPTION
            "Indicates information about ports and channels of slave members in a PLA group."
        ::= { optixRtnPhyLagSdbPGParameterEntry 8 }

    -- 1.3.6.1.4.1.2011.2.25.4.40.5.10.97.1.50
    optixRtnPhyLagSdbPGCfgRowStatus OBJECT-TYPE
        SYNTAX RowStatus
        MAX-ACCESS read-create
        STATUS current
        DESCRIPTION
            "Indicates the row status of a PLA group."
        DEFVAL{ active }
        ::= { optixRtnPhyLagSdbPGParameterEntry 50 }

    -- 1.3.6.1.4.1.2011.2.25.4.40.5.10.98
    optixRtnCascadingSDBPhyLagPGParameterTable OBJECT-TYPE
        SYNTAX SEQUENCE OF OptixRtnCascadingSDBPhyLagPGParameterEntry
        MAX-ACCESS not-accessible
        STATUS current
        DESCRIPTION
            "To create an EPLA protection group"
        ::= { optixRtnIFProtect 98 }

    -- 1.3.6.1.4.1.2011.2.25.4.40.5.10.98.1
    optixRtnCascadingSDBPhyLagPGParameterEntry OBJECT-TYPE
        SYNTAX OptixRtnCascadingSDBPhyLagPGParameterEntry
        MAX-ACCESS not-accessible
        STATUS current
        DESCRIPTION
            "To create an EPLA protection group"
        INDEX{ optixRtnCascadingSDBPhyLagPGId }
        ::= { optixRtnCascadingSDBPhyLagPGParameterTable 1 }

    OptixRtnCascadingSDBPhyLagPGParameterEntry ::=
        SEQUENCE {
            optixRtnCascadingSDBPhyLagPGId
                Unsigned32,
            optixRtnCascadingSDBPhyLagPGType
                INTEGER,
            optixRtnCascadingSDBPhyLagPGCapacity
                Unsigned32,
            optixRtnCascadingSDBPhyLagPGMasterBoardId
                Unsigned32,
            optixRtnCascadingSDBPhyLagPGMasterSubCardId
                Unsigned32,
            optixRtnCascadingSDBPhyLagPGMasterPortId
                Unsigned32,
            optixRtnCascadingSDBPhyLagPGInfo
                OCTET STRING,
            optixRtnCascadingSDBPhyLagPGSlaveType
                INTEGER,
            optixRtnCascadingSDBPhyLagPGSlaveMemMapInfo
                OCTET STRING,
            optixRtnCascadingSDBPhyLagPGRowStatus
                RowStatus
        }

    -- 1.3.6.1.4.1.2011.2.25.4.40.5.10.98.1.1
    optixRtnCascadingSDBPhyLagPGId OBJECT-TYPE
        SYNTAX Unsigned32
        MAX-ACCESS not-accessible
        STATUS current
        DESCRIPTION
            "Indicates the LAG ID"
        ::= { optixRtnCascadingSDBPhyLagPGParameterEntry 1 }

    -- 1.3.6.1.4.1.2011.2.25.4.40.5.10.98.1.2
    optixRtnCascadingSDBPhyLagPGType OBJECT-TYPE
        SYNTAX OPTIXRtnPhyLagPGType
        MAX-ACCESS read-create
        STATUS current
        DESCRIPTION
            "Indicates the LAG type"
        ::= { optixRtnCascadingSDBPhyLagPGParameterEntry 2 }

    -- 1.3.6.1.4.1.2011.2.25.4.40.5.10.98.1.3
    optixRtnCascadingSDBPhyLagPGCapacity OBJECT-TYPE
        SYNTAX Unsigned32
        MAX-ACCESS read-create
        STATUS current
        DESCRIPTION
            "Indicates the bandwidth capacity (unit: M).
	    Value range: 1000-7000
	    Step: 100
	    Default: 2500"
        DEFVAL{ 2500 }
        ::= { optixRtnCascadingSDBPhyLagPGParameterEntry 3 }

    -- 1.3.6.1.4.1.2011.2.25.4.40.5.10.98.1.4
    optixRtnCascadingSDBPhyLagPGMasterBoardId OBJECT-TYPE
        SYNTAX Unsigned32
        MAX-ACCESS read-create
        STATUS current
        DESCRIPTION
            "Indicates the slot ID of the primary port."
        ::= { optixRtnCascadingSDBPhyLagPGParameterEntry 4 }

    -- 1.3.6.1.4.1.2011.2.25.4.40.5.10.98.1.5
    optixRtnCascadingSDBPhyLagPGMasterSubCardId OBJECT-TYPE
        SYNTAX Unsigned32
        MAX-ACCESS read-create
        STATUS current
        DESCRIPTION
            "Indicates the subboard ID of the primary port."
        ::= { optixRtnCascadingSDBPhyLagPGParameterEntry 5 }

    -- 1.3.6.1.4.1.2011.2.25.4.40.5.10.98.1.6
    optixRtnCascadingSDBPhyLagPGMasterPortId OBJECT-TYPE
        SYNTAX Unsigned32
        MAX-ACCESS read-create
        STATUS current
        DESCRIPTION
            "Indicates the primary port ID."
        ::= { optixRtnCascadingSDBPhyLagPGParameterEntry 6 }

    -- 1.3.6.1.4.1.2011.2.25.4.40.5.10.98.1.7
    optixRtnCascadingSDBPhyLagPGInfo OBJECT-TYPE
        SYNTAX OCTET STRING
        MAX-ACCESS read-create
        STATUS current
        DESCRIPTION
            "Indicates the information of secondary ports."
        ::= { optixRtnCascadingSDBPhyLagPGParameterEntry 7 }

    -- 1.3.6.1.4.1.2011.2.25.4.40.5.10.98.1.8
    optixRtnCascadingSDBPhyLagPGSlaveType OBJECT-TYPE
        SYNTAX OPTIXRtnPhyLagPGType
        MAX-ACCESS read-create
        STATUS current
        DESCRIPTION
            "Indicates the LAG type"
        ::= { optixRtnCascadingSDBPhyLagPGParameterEntry 8 }

    -- 1.3.6.1.4.1.2011.2.25.4.40.5.10.98.1.9
    optixRtnCascadingSDBPhyLagPGSlaveMemMapInfo OBJECT-TYPE
        SYNTAX OCTET STRING
        MAX-ACCESS read-create
        STATUS current
        DESCRIPTION
            "Indicates the mapping between EPLA members and service ports"
        ::= { optixRtnCascadingSDBPhyLagPGParameterEntry 9 }

    -- 1.3.6.1.4.1.2011.2.25.4.40.5.10.98.1.50
    optixRtnCascadingSDBPhyLagPGRowStatus OBJECT-TYPE
        SYNTAX RowStatus
        MAX-ACCESS read-create
        STATUS current
        DESCRIPTION
            "Indicates the row status."
        DEFVAL{ active }
        ::= { optixRtnCascadingSDBPhyLagPGParameterEntry 50 }

    -- 1.3.6.1.4.1.2011.2.25.4.40.5.10.100
    optixRtnPhyLagPGStateTable OBJECT-TYPE
        SYNTAX SEQUENCE OF OptixRtnPhyLagPGStateEntry
        MAX-ACCESS not-accessible
        STATUS current
        DESCRIPTION
            "Describes parameters about a PLA protection group, including the current working board and the switching status of a protection group."
        ::= { optixRtnIFProtect 100 }

    -- 1.3.6.1.4.1.2011.2.25.4.40.5.10.100.1
    optixRtnPhyLagPGStateEntry OBJECT-TYPE
        SYNTAX OptixRtnPhyLagPGStateEntry
        MAX-ACCESS not-accessible
        STATUS current
        DESCRIPTION
            "Indicates status entry for a PLA protection group."
        INDEX{ optixRtnPhyLagPGID }
        ::= { optixRtnPhyLagPGStateTable 1 }

    OptixRtnPhyLagPGStateEntry ::=
        SEQUENCE {
            optixRtnPhyLagPGStateMainBoardID
                Unsigned32,
            optixRtnPhyLagPGStateMainSubCardID
                Unsigned32,
            optixRtnPhyLagPGStateMainPortID
                Unsigned32,
            optixRtnPhyLagPGMainHardStatus
                OPTIXRtnPhyLagPGStatus,
            optixRtnPhyLagPGMainLinkStatus
                OPTIXRtnPhyLagPGStatus,
            optixRtnPhyLagPGMainPuWorkStatus
                OPTIXRtnPhyLagPGStateWorkStatus,
            optixRtnPhyLagPGStateSlavePuNum
                Unsigned32,
            optixRtnPhyLagPGStatePu1BoardID
                Unsigned32,
            optixRtnPhyLagPGStatePu1SubCardID
                Unsigned32,
            optixRtnPhyLagPGStatePu1PortID
                Unsigned32,
            optixRtnPhyLagPGStatePu1HardStatus
                OPTIXRtnPhyLagPGStatus,
            optixRtnPhyLagPGStatePu1LinkStatus
                OPTIXRtnPhyLagPGStatus,
            optixRtnPhyLagPGStatePu1WorkStatus
                OPTIXRtnPhyLagPGStateWorkStatus,
            optixRtnPhyLagPGStatePu2BoardID
                Unsigned32,
            optixRtnPhyLagPGStatePu2SubCardID
                Unsigned32,
            optixRtnPhyLagPGStatePu2PortID
                Unsigned32,
            optixRtnPhyLagPGStatePu2HardStatus
                OPTIXRtnPhyLagPGStatus,
            optixRtnPhyLagPGStatePu2LinkStatus
                OPTIXRtnPhyLagPGStatus,
            optixRtnPhyLagPGStatePu2WorkStatus
                OPTIXRtnPhyLagPGStateWorkStatus,
            optixRtnPhyLagPGStatePu3BoardID
                Unsigned32,
            optixRtnPhyLagPGStatePu3SubCardID
                Unsigned32,
            optixRtnPhyLagPGStatePu3PortID
                Unsigned32,
            optixRtnPhyLagPGStatePu3HardStatus
                OPTIXRtnPhyLagPGStatus,
            optixRtnPhyLagPGStatePu3LinkStatus
                OPTIXRtnPhyLagPGStatus,
            optixRtnPhyLagPGStatePu3WorkStatus
                OPTIXRtnPhyLagPGStateWorkStatus,
            optixRtnPhyLagPGStatePu4BoardID
                Unsigned32,
            optixRtnPhyLagPGStatePu4SubCardID
                Unsigned32,
            optixRtnPhyLagPGStatePu4PortID
                Unsigned32,
            optixRtnPhyLagPGStatePu4HardStatus
                OPTIXRtnPhyLagPGStatus,
            optixRtnPhyLagPGStatePu4LinkStatus
                OPTIXRtnPhyLagPGStatus,
            optixRtnPhyLagPGStatePu4WorkStatus
                OPTIXRtnPhyLagPGStateWorkStatus,
            optixRtnPhyLagPGStatePu5BoardID
                Unsigned32,
            optixRtnPhyLagPGStatePu5SubCardID
                Unsigned32,
            optixRtnPhyLagPGStatePu5PortID
                Unsigned32,
            optixRtnPhyLagPGStatePu5HardStatus
                OPTIXRtnPhyLagPGStatus,
            optixRtnPhyLagPGStatePu5LinkStatus
                OPTIXRtnPhyLagPGStatus,
            optixRtnPhyLagPGStatePu5WorkStatus
                OPTIXRtnPhyLagPGStateWorkStatus,
            optixRtnPhyLagPGStatePu6BoardID
                Unsigned32,
            optixRtnPhyLagPGStatePu6SubCardID
                Unsigned32,
            optixRtnPhyLagPGStatePu6PortID
                Unsigned32,
            optixRtnPhyLagPGStatePu6HardStatus
                OPTIXRtnPhyLagPGStatus,
            optixRtnPhyLagPGStatePu6LinkStatus
                OPTIXRtnPhyLagPGStatus,
            optixRtnPhyLagPGStatePu6WorkStatus
                OPTIXRtnPhyLagPGStateWorkStatus,
            optixRtnPhyLagPGStatePu7BoardID
                Unsigned32,
            optixRtnPhyLagPGStatePu7SubCardID
                Unsigned32,
            optixRtnPhyLagPGStatePu7PortID
                Unsigned32,
            optixRtnPhyLagPGStatePu7HardStatus
                OPTIXRtnPhyLagPGStatus,
            optixRtnPhyLagPGStatePu7LinkStatus
                OPTIXRtnPhyLagPGStatus,
            optixRtnPhyLagPGStatePu7WorkStatus
                OPTIXRtnPhyLagPGStateWorkStatus,
            optixRtnPhyLagPGStatePu8BoardID
                Unsigned32,
            optixRtnPhyLagPGStatePu8SubCardID
                Unsigned32,
            optixRtnPhyLagPGStatePu8PortID
                Unsigned32,
            optixRtnPhyLagPGStatePu8HardStatus
                OPTIXRtnPhyLagPGStatus,
            optixRtnPhyLagPGStatePu8LinkStatus
                OPTIXRtnPhyLagPGStatus,
            optixRtnPhyLagPGStatePu8WorkStatus
                OPTIXRtnPhyLagPGStateWorkStatus,
            optixRtnPhyLagPGStatePu9BoardID
                Unsigned32,
            optixRtnPhyLagPGStatePu9SubCardID
                Unsigned32,
            optixRtnPhyLagPGStatePu9PortID
                Unsigned32,
            optixRtnPhyLagPGStatePu9HardStatus
                OPTIXRtnPhyLagPGStatus,
            optixRtnPhyLagPGStatePu9LinkStatus
                OPTIXRtnPhyLagPGStatus,
            optixRtnPhyLagPGStatePu9WorkStatus
                OPTIXRtnPhyLagPGStateWorkStatus,
            optixRtnPhyLagPGStatePu10BoardID
                Unsigned32,
            optixRtnPhyLagPGStatePu10SubCardID
                Unsigned32,
            optixRtnPhyLagPGStatePu10PortID
                Unsigned32,
            optixRtnPhyLagPGStatePu10HardStatus
                OPTIXRtnPhyLagPGStatus,
            optixRtnPhyLagPGStatePu10LinkStatus
                OPTIXRtnPhyLagPGStatus,
            optixRtnPhyLagPGStatePu10WorkStatus
                OPTIXRtnPhyLagPGStateWorkStatus,
            optixRtnPhyLagPGStatePu11BoardID
                Unsigned32,
            optixRtnPhyLagPGStatePu11SubCardID
                Unsigned32,
            optixRtnPhyLagPGStatePu11PortID
                Unsigned32,
            optixRtnPhyLagPGStatePu11HardStatus
                OPTIXRtnPhyLagPGStatus,
            optixRtnPhyLagPGStatePu11LinkStatus
                OPTIXRtnPhyLagPGStatus,
            optixRtnPhyLagPGStatePu11WorkStatus
                OPTIXRtnPhyLagPGStateWorkStatus
        }

    -- 1.3.6.1.4.1.2011.2.25.4.40.5.10.100.1.1
    optixRtnPhyLagPGStateMainBoardID OBJECT-TYPE
        SYNTAX Unsigned32
        MAX-ACCESS read-only
        STATUS current
        DESCRIPTION
            "Indicates the main unit slot ID."
        ::= { optixRtnPhyLagPGStateEntry 1 }

    -- 1.3.6.1.4.1.2011.2.25.4.40.5.10.100.1.2
    optixRtnPhyLagPGStateMainSubCardID OBJECT-TYPE
        SYNTAX Unsigned32
        MAX-ACCESS read-only
        STATUS current
        DESCRIPTION
            "Indicates the main unit subboard ID."
        ::= { optixRtnPhyLagPGStateEntry 2 }

    -- 1.3.6.1.4.1.2011.2.25.4.40.5.10.100.1.3
    optixRtnPhyLagPGStateMainPortID OBJECT-TYPE
        SYNTAX Unsigned32
        MAX-ACCESS read-only
        STATUS current
        DESCRIPTION
            "Indicates the main unit port ID."
        ::= { optixRtnPhyLagPGStateEntry 3 }

    -- 1.3.6.1.4.1.2011.2.25.4.40.5.10.100.1.4
    optixRtnPhyLagPGMainHardStatus OBJECT-TYPE
        SYNTAX OPTIXRtnPhyLagPGStatus
        MAX-ACCESS read-only
        STATUS current
        DESCRIPTION
            "Indicates the hardware status of the main unit. The values: 0: normal 1: abnormal -1: unknown"
        ::= { optixRtnPhyLagPGStateEntry 4 }

    -- 1.3.6.1.4.1.2011.2.25.4.40.5.10.100.1.5
    optixRtnPhyLagPGMainLinkStatus OBJECT-TYPE
        SYNTAX OPTIXRtnPhyLagPGStatus
        MAX-ACCESS read-only
        STATUS current
        DESCRIPTION
            "Indicates the link status of the main unit. Values: 0: normal 1: abnormal -1: unknown"
        ::= { optixRtnPhyLagPGStateEntry 5 }

    -- 1.3.6.1.4.1.2011.2.25.4.40.5.10.100.1.6
    optixRtnPhyLagPGMainPuWorkStatus OBJECT-TYPE
        SYNTAX OPTIXRtnPhyLagPGStateWorkStatus
        MAX-ACCESS read-only
        STATUS current
        DESCRIPTION
            "Indicates the working status of the main unit. Values: 0: slave port 1: main port"
        ::= { optixRtnPhyLagPGStateEntry 6 }

    -- 1.3.6.1.4.1.2011.2.25.4.40.5.10.100.1.7
    optixRtnPhyLagPGStateSlavePuNum OBJECT-TYPE
        SYNTAX Unsigned32
        MAX-ACCESS read-only
        STATUS current
        DESCRIPTION
            "Indicates the number of slave units. Value range: 1 to 15"
        ::= { optixRtnPhyLagPGStateEntry 7 }

    -- 1.3.6.1.4.1.2011.2.25.4.40.5.10.100.1.8
    optixRtnPhyLagPGStatePu1BoardID OBJECT-TYPE
        SYNTAX Unsigned32
        MAX-ACCESS read-only
        STATUS current
        DESCRIPTION
            "Indicates the slave unit 1 slot ID."
        ::= { optixRtnPhyLagPGStateEntry 8 }

    -- 1.3.6.1.4.1.2011.2.25.4.40.5.10.100.1.9
    optixRtnPhyLagPGStatePu1SubCardID OBJECT-TYPE
        SYNTAX Unsigned32
        MAX-ACCESS read-only
        STATUS current
        DESCRIPTION
            "Indicates the slave unit 1 subboard ID."
        ::= { optixRtnPhyLagPGStateEntry 9 }

    -- 1.3.6.1.4.1.2011.2.25.4.40.5.10.100.1.10
    optixRtnPhyLagPGStatePu1PortID OBJECT-TYPE
        SYNTAX Unsigned32
        MAX-ACCESS read-only
        STATUS current
        DESCRIPTION
            "Indicates the slave unit 1 port ID."
        ::= { optixRtnPhyLagPGStateEntry 10 }

    -- 1.3.6.1.4.1.2011.2.25.4.40.5.10.100.1.11
    optixRtnPhyLagPGStatePu1HardStatus OBJECT-TYPE
        SYNTAX OPTIXRtnPhyLagPGStatus
        MAX-ACCESS read-only
        STATUS current
        DESCRIPTION
            "Indicates the slave unit 1 hardware status. Values: 0: normal 1: abnormal -1: unknown"
        ::= { optixRtnPhyLagPGStateEntry 11 }

    -- 1.3.6.1.4.1.2011.2.25.4.40.5.10.100.1.12
    optixRtnPhyLagPGStatePu1LinkStatus OBJECT-TYPE
        SYNTAX OPTIXRtnPhyLagPGStatus
        MAX-ACCESS read-only
        STATUS current
        DESCRIPTION
            "Indicates the slave unit 1 link status. Values: 0: normal 1: abnormal -1: unknown"
        ::= { optixRtnPhyLagPGStateEntry 12 }

    -- 1.3.6.1.4.1.2011.2.25.4.40.5.10.100.1.13
    optixRtnPhyLagPGStatePu1WorkStatus OBJECT-TYPE
        SYNTAX OPTIXRtnPhyLagPGStateWorkStatus
        MAX-ACCESS read-only
        STATUS current
        DESCRIPTION
            "Indicates the slave unit 1 working status. Values: 0: slave port 1: main port"
        ::= { optixRtnPhyLagPGStateEntry 13 }

    -- 1.3.6.1.4.1.2011.2.25.4.40.5.10.100.1.14
    optixRtnPhyLagPGStatePu2BoardID OBJECT-TYPE
        SYNTAX Unsigned32
        MAX-ACCESS read-only
        STATUS current
        DESCRIPTION
            "Indicates the slave unit 2 slot ID."
        ::= { optixRtnPhyLagPGStateEntry 14 }

    -- 1.3.6.1.4.1.2011.2.25.4.40.5.10.100.1.15
    optixRtnPhyLagPGStatePu2SubCardID OBJECT-TYPE
        SYNTAX Unsigned32
        MAX-ACCESS read-only
        STATUS current
        DESCRIPTION
            "Indicates the slave unit 2 subboard ID."
        ::= { optixRtnPhyLagPGStateEntry 15 }

    -- 1.3.6.1.4.1.2011.2.25.4.40.5.10.100.1.16
    optixRtnPhyLagPGStatePu2PortID OBJECT-TYPE
        SYNTAX Unsigned32
        MAX-ACCESS read-only
        STATUS current
        DESCRIPTION
            "Indicates the slave unit 2 port ID."
        ::= { optixRtnPhyLagPGStateEntry 16 }

    -- 1.3.6.1.4.1.2011.2.25.4.40.5.10.100.1.17
    optixRtnPhyLagPGStatePu2HardStatus OBJECT-TYPE
        SYNTAX OPTIXRtnPhyLagPGStatus
        MAX-ACCESS read-only
        STATUS current
        DESCRIPTION
            "Indicates the slave unit 2 hardware status. Values: 0: normal 1: abnormal -1: unknown"
        ::= { optixRtnPhyLagPGStateEntry 17 }

    -- 1.3.6.1.4.1.2011.2.25.4.40.5.10.100.1.18
    optixRtnPhyLagPGStatePu2LinkStatus OBJECT-TYPE
        SYNTAX OPTIXRtnPhyLagPGStatus
        MAX-ACCESS read-only
        STATUS current
        DESCRIPTION
            "Indicates the slave unit 2 link status. Values: 0: normal 1: abnormal -1: unknown"
        ::= { optixRtnPhyLagPGStateEntry 18 }

    -- 1.3.6.1.4.1.2011.2.25.4.40.5.10.100.1.19
    optixRtnPhyLagPGStatePu2WorkStatus OBJECT-TYPE
        SYNTAX OPTIXRtnPhyLagPGStateWorkStatus
        MAX-ACCESS read-only
        STATUS current
        DESCRIPTION
            "Indicates the slave unit 2 working status. Values: 0: slave port 1: main port"
        ::= { optixRtnPhyLagPGStateEntry 19 }

    -- 1.3.6.1.4.1.2011.2.25.4.40.5.10.100.1.20
    optixRtnPhyLagPGStatePu3BoardID OBJECT-TYPE
        SYNTAX Unsigned32
        MAX-ACCESS read-only
        STATUS current
        DESCRIPTION
            "Indicates the slave unit 3 slot ID."
        ::= { optixRtnPhyLagPGStateEntry 20 }

    -- 1.3.6.1.4.1.2011.2.25.4.40.5.10.100.1.21
    optixRtnPhyLagPGStatePu3SubCardID OBJECT-TYPE
        SYNTAX Unsigned32
        MAX-ACCESS read-only
        STATUS current
        DESCRIPTION
            "Indicates the slave unit 3 subboard ID."
        ::= { optixRtnPhyLagPGStateEntry 21 }

    -- 1.3.6.1.4.1.2011.2.25.4.40.5.10.100.1.22
    optixRtnPhyLagPGStatePu3PortID OBJECT-TYPE
        SYNTAX Unsigned32
        MAX-ACCESS read-only
        STATUS current
        DESCRIPTION
            "Indicates the slave unit 3 port ID."
        ::= { optixRtnPhyLagPGStateEntry 22 }

    -- 1.3.6.1.4.1.2011.2.25.4.40.5.10.100.1.23
    optixRtnPhyLagPGStatePu3HardStatus OBJECT-TYPE
        SYNTAX OPTIXRtnPhyLagPGStatus
        MAX-ACCESS read-only
        STATUS current
        DESCRIPTION
            "Indicates the slave unit 3 hardware status. Values: 0: normal 1: abnormal -1: unknown"
        ::= { optixRtnPhyLagPGStateEntry 23 }

    -- 1.3.6.1.4.1.2011.2.25.4.40.5.10.100.1.24
    optixRtnPhyLagPGStatePu3LinkStatus OBJECT-TYPE
        SYNTAX OPTIXRtnPhyLagPGStatus
        MAX-ACCESS read-only
        STATUS current
        DESCRIPTION
            "Indicates the slave unit 3 link status. Values: 0: normal 1: abnormal -1: unknown"
        ::= { optixRtnPhyLagPGStateEntry 24 }

    -- 1.3.6.1.4.1.2011.2.25.4.40.5.10.100.1.25
    optixRtnPhyLagPGStatePu3WorkStatus OBJECT-TYPE
        SYNTAX OPTIXRtnPhyLagPGStateWorkStatus
        MAX-ACCESS read-only
        STATUS current
        DESCRIPTION
            "Indicates the slave unit 3 working status. Values: 0: slave port 1: main port"
        ::= { optixRtnPhyLagPGStateEntry 25 }

    -- 1.3.6.1.4.1.2011.2.25.4.40.5.10.100.1.26
    optixRtnPhyLagPGStatePu4BoardID OBJECT-TYPE
        SYNTAX Unsigned32
        MAX-ACCESS read-only
        STATUS current
        DESCRIPTION
            "Indicates the slave unit 4 slot ID."
        ::= { optixRtnPhyLagPGStateEntry 26 }

    -- 1.3.6.1.4.1.2011.2.25.4.40.5.10.100.1.27
    optixRtnPhyLagPGStatePu4SubCardID OBJECT-TYPE
        SYNTAX Unsigned32
        MAX-ACCESS read-only
        STATUS current
        DESCRIPTION
            "Indicates the slave unit 4 subboard ID."
        ::= { optixRtnPhyLagPGStateEntry 27 }

    -- 1.3.6.1.4.1.2011.2.25.4.40.5.10.100.1.28
    optixRtnPhyLagPGStatePu4PortID OBJECT-TYPE
        SYNTAX Unsigned32
        MAX-ACCESS read-only
        STATUS current
        DESCRIPTION
            "Indicates the slave unit 4 port ID."
        ::= { optixRtnPhyLagPGStateEntry 28 }

    -- 1.3.6.1.4.1.2011.2.25.4.40.5.10.100.1.29
    optixRtnPhyLagPGStatePu4HardStatus OBJECT-TYPE
        SYNTAX OPTIXRtnPhyLagPGStatus
        MAX-ACCESS read-only
        STATUS current
        DESCRIPTION
            "Indicates the slave unit 4 hardware status. Values: 0: normal 1: abnormal -1: unknown"
        ::= { optixRtnPhyLagPGStateEntry 29 }

    -- 1.3.6.1.4.1.2011.2.25.4.40.5.10.100.1.30
    optixRtnPhyLagPGStatePu4LinkStatus OBJECT-TYPE
        SYNTAX OPTIXRtnPhyLagPGStatus
        MAX-ACCESS read-only
        STATUS current
        DESCRIPTION
            "Indicates the slave unit 4 link status. Values: 0: normal 1: abnormal -1: unknown"
        ::= { optixRtnPhyLagPGStateEntry 30 }

    -- 1.3.6.1.4.1.2011.2.25.4.40.5.10.100.1.31
    optixRtnPhyLagPGStatePu4WorkStatus OBJECT-TYPE
        SYNTAX OPTIXRtnPhyLagPGStateWorkStatus
        MAX-ACCESS read-only
        STATUS current
        DESCRIPTION
            "Indicates the slave unit 4 working status. Values: 0: slave port 1: main port"
        ::= { optixRtnPhyLagPGStateEntry 31 }

    -- 1.3.6.1.4.1.2011.2.25.4.40.5.10.100.1.32
    optixRtnPhyLagPGStatePu5BoardID OBJECT-TYPE
        SYNTAX Unsigned32
        MAX-ACCESS read-only
        STATUS current
        DESCRIPTION
            "Indicates the slave unit 5 slot ID."
        ::= { optixRtnPhyLagPGStateEntry 32 }

    -- 1.3.6.1.4.1.2011.2.25.4.40.5.10.100.1.33
    optixRtnPhyLagPGStatePu5SubCardID OBJECT-TYPE
        SYNTAX Unsigned32
        MAX-ACCESS read-only
        STATUS current
        DESCRIPTION
            "Indicates the slave unit 5 subboard ID."
        ::= { optixRtnPhyLagPGStateEntry 33 }

    -- 1.3.6.1.4.1.2011.2.25.4.40.5.10.100.1.34
    optixRtnPhyLagPGStatePu5PortID OBJECT-TYPE
        SYNTAX Unsigned32
        MAX-ACCESS read-only
        STATUS current
        DESCRIPTION
            "Indicates the slave unit 5 port ID."
        ::= { optixRtnPhyLagPGStateEntry 34 }

    -- 1.3.6.1.4.1.2011.2.25.4.40.5.10.100.1.35
    optixRtnPhyLagPGStatePu5HardStatus OBJECT-TYPE
        SYNTAX OPTIXRtnPhyLagPGStatus
        MAX-ACCESS read-only
        STATUS current
        DESCRIPTION
            "Indicates the slave unit 5 hardware status. Values: 0: normal 1: abnormal -1: unknown"
        ::= { optixRtnPhyLagPGStateEntry 35 }

    -- 1.3.6.1.4.1.2011.2.25.4.40.5.10.100.1.36
    optixRtnPhyLagPGStatePu5LinkStatus OBJECT-TYPE
        SYNTAX OPTIXRtnPhyLagPGStatus
        MAX-ACCESS read-only
        STATUS current
        DESCRIPTION
            "Indicates the slave unit 5 link status. Values: 0: normal 1: abnormal -1: unknown"
        ::= { optixRtnPhyLagPGStateEntry 36 }

    -- 1.3.6.1.4.1.2011.2.25.4.40.5.10.100.1.37
    optixRtnPhyLagPGStatePu5WorkStatus OBJECT-TYPE
        SYNTAX OPTIXRtnPhyLagPGStateWorkStatus
        MAX-ACCESS read-only
        STATUS current
        DESCRIPTION
            "Indicates the slave unit 5 working status. Values: 0: slave port 1: main port"
        ::= { optixRtnPhyLagPGStateEntry 37 }

    -- 1.3.6.1.4.1.2011.2.25.4.40.5.10.100.1.38
    optixRtnPhyLagPGStatePu6BoardID OBJECT-TYPE
        SYNTAX Unsigned32
        MAX-ACCESS read-only
        STATUS current
        DESCRIPTION
            "Indicates the slave unit 6 slot ID."
        ::= { optixRtnPhyLagPGStateEntry 38 }

    -- 1.3.6.1.4.1.2011.2.25.4.40.5.10.100.1.39
    optixRtnPhyLagPGStatePu6SubCardID OBJECT-TYPE
        SYNTAX Unsigned32
        MAX-ACCESS read-only
        STATUS current
        DESCRIPTION
            "Indicates the slave unit 6 subboard ID."
        ::= { optixRtnPhyLagPGStateEntry 39 }

    -- 1.3.6.1.4.1.2011.2.25.4.40.5.10.100.1.40
    optixRtnPhyLagPGStatePu6PortID OBJECT-TYPE
        SYNTAX Unsigned32
        MAX-ACCESS read-only
        STATUS current
        DESCRIPTION
            "Indicates the slave unit 6 port ID."
        ::= { optixRtnPhyLagPGStateEntry 40 }

    -- 1.3.6.1.4.1.2011.2.25.4.40.5.10.100.1.41
    optixRtnPhyLagPGStatePu6HardStatus OBJECT-TYPE
        SYNTAX OPTIXRtnPhyLagPGStatus
        MAX-ACCESS read-only
        STATUS current
        DESCRIPTION
            "Indicates the slave unit 6 hardware status. Values: 0: normal 1: abnormal -1: unknown"
        ::= { optixRtnPhyLagPGStateEntry 41 }

    -- 1.3.6.1.4.1.2011.2.25.4.40.5.10.100.1.42
    optixRtnPhyLagPGStatePu6LinkStatus OBJECT-TYPE
        SYNTAX OPTIXRtnPhyLagPGStatus
        MAX-ACCESS read-only
        STATUS current
        DESCRIPTION
            "Indicates the slave unit 6 link status. Values: 0: normal 1: abnormal -1: unknown"
        ::= { optixRtnPhyLagPGStateEntry 42 }

    -- 1.3.6.1.4.1.2011.2.25.4.40.5.10.100.1.43
    optixRtnPhyLagPGStatePu6WorkStatus OBJECT-TYPE
        SYNTAX OPTIXRtnPhyLagPGStateWorkStatus
        MAX-ACCESS read-only
        STATUS current
        DESCRIPTION
            "Indicates the slave unit 6 working status. Values: 0: slave port 1: main port"
        ::= { optixRtnPhyLagPGStateEntry 43 }

    -- 1.3.6.1.4.1.2011.2.25.4.40.5.10.100.1.44
    optixRtnPhyLagPGStatePu7BoardID OBJECT-TYPE
        SYNTAX Unsigned32
        MAX-ACCESS read-only
        STATUS current
        DESCRIPTION
            "Indicates the slave unit 7 slot ID."
        ::= { optixRtnPhyLagPGStateEntry 44 }

    -- 1.3.6.1.4.1.2011.2.25.4.40.5.10.100.1.45
    optixRtnPhyLagPGStatePu7SubCardID OBJECT-TYPE
        SYNTAX Unsigned32
        MAX-ACCESS read-only
        STATUS current
        DESCRIPTION
            "Indicates the slave unit 7 subboard ID."
        ::= { optixRtnPhyLagPGStateEntry 45 }

    -- 1.3.6.1.4.1.2011.2.25.4.40.5.10.100.1.46
    optixRtnPhyLagPGStatePu7PortID OBJECT-TYPE
        SYNTAX Unsigned32
        MAX-ACCESS read-only
        STATUS current
        DESCRIPTION
            "Indicates the slave unit 7 port ID."
        ::= { optixRtnPhyLagPGStateEntry 46 }

    -- 1.3.6.1.4.1.2011.2.25.4.40.5.10.100.1.47
    optixRtnPhyLagPGStatePu7HardStatus OBJECT-TYPE
        SYNTAX OPTIXRtnPhyLagPGStatus
        MAX-ACCESS read-only
        STATUS current
        DESCRIPTION
            "Indicates the slave unit 7 hardware status. Values: 0: normal 1: abnormal -1: unknown"
        ::= { optixRtnPhyLagPGStateEntry 47 }

    -- 1.3.6.1.4.1.2011.2.25.4.40.5.10.100.1.48
    optixRtnPhyLagPGStatePu7LinkStatus OBJECT-TYPE
        SYNTAX OPTIXRtnPhyLagPGStatus
        MAX-ACCESS read-only
        STATUS current
        DESCRIPTION
            "Indicates the slave unit 7 link status. Values: 0: normal 1: abnormal -1: unknown"
        ::= { optixRtnPhyLagPGStateEntry 48 }

    -- 1.3.6.1.4.1.2011.2.25.4.40.5.10.100.1.49
    optixRtnPhyLagPGStatePu7WorkStatus OBJECT-TYPE
        SYNTAX OPTIXRtnPhyLagPGStateWorkStatus
        MAX-ACCESS read-only
        STATUS current
        DESCRIPTION
            "Indicates the slave unit 7 working status. Values: 0: slave port 1: main port"
        ::= { optixRtnPhyLagPGStateEntry 49 }

    -- 1.3.6.1.4.1.2011.2.25.4.40.5.10.100.1.50
    optixRtnPhyLagPGStatePu8BoardID OBJECT-TYPE
        SYNTAX Unsigned32
        MAX-ACCESS read-only
        STATUS current
        DESCRIPTION
            "Indicates the slave unit 8 slot ID."
        ::= { optixRtnPhyLagPGStateEntry 50 }

    -- 1.3.6.1.4.1.2011.2.25.4.40.5.10.100.1.51
    optixRtnPhyLagPGStatePu8SubCardID OBJECT-TYPE
        SYNTAX Unsigned32
        MAX-ACCESS read-only
        STATUS current
        DESCRIPTION
            "Indicates the slave unit 8 subboard ID."
        ::= { optixRtnPhyLagPGStateEntry 51 }

    -- 1.3.6.1.4.1.2011.2.25.4.40.5.10.100.1.52
    optixRtnPhyLagPGStatePu8PortID OBJECT-TYPE
        SYNTAX Unsigned32
        MAX-ACCESS read-only
        STATUS current
        DESCRIPTION
            "Indicates the slave unit 8 port ID."
        ::= { optixRtnPhyLagPGStateEntry 52 }

    -- 1.3.6.1.4.1.2011.2.25.4.40.5.10.100.1.53
    optixRtnPhyLagPGStatePu8HardStatus OBJECT-TYPE
        SYNTAX OPTIXRtnPhyLagPGStatus
        MAX-ACCESS read-only
        STATUS current
        DESCRIPTION
            "Indicates the slave unit 8 hardware status. Values: 0: normal 1: abnormal -1: unknown"
        ::= { optixRtnPhyLagPGStateEntry 53 }

    -- 1.3.6.1.4.1.2011.2.25.4.40.5.10.100.1.54
    optixRtnPhyLagPGStatePu8LinkStatus OBJECT-TYPE
        SYNTAX OPTIXRtnPhyLagPGStatus
        MAX-ACCESS read-only
        STATUS current
        DESCRIPTION
            "Indicates the slave unit 8 link status. Values: 0: normal 1: abnormal -1: unknown"
        ::= { optixRtnPhyLagPGStateEntry 54 }

    -- 1.3.6.1.4.1.2011.2.25.4.40.5.10.100.1.55
    optixRtnPhyLagPGStatePu8WorkStatus OBJECT-TYPE
        SYNTAX OPTIXRtnPhyLagPGStateWorkStatus
        MAX-ACCESS read-only
        STATUS current
        DESCRIPTION
            "Indicates the slave unit 8 working status. Values: 0: slave port 1: main port"
        ::= { optixRtnPhyLagPGStateEntry 55 }

    -- 1.3.6.1.4.1.2011.2.25.4.40.5.10.100.1.56
    optixRtnPhyLagPGStatePu9BoardID OBJECT-TYPE
        SYNTAX Unsigned32
        MAX-ACCESS read-only
        STATUS current
        DESCRIPTION
            "Indicates the slave unit 9 slot ID."
        ::= { optixRtnPhyLagPGStateEntry 56 }

    -- 1.3.6.1.4.1.2011.2.25.4.40.5.10.100.1.57
    optixRtnPhyLagPGStatePu9SubCardID OBJECT-TYPE
        SYNTAX Unsigned32
        MAX-ACCESS read-only
        STATUS current
        DESCRIPTION
            "Indicates the slave unit 9 subboard ID."
        ::= { optixRtnPhyLagPGStateEntry 57 }

    -- 1.3.6.1.4.1.2011.2.25.4.40.5.10.100.1.58
    optixRtnPhyLagPGStatePu9PortID OBJECT-TYPE
        SYNTAX Unsigned32
        MAX-ACCESS read-only
        STATUS current
        DESCRIPTION
            "Indicates the slave unit 9 port ID."
        ::= { optixRtnPhyLagPGStateEntry 58 }

    -- 1.3.6.1.4.1.2011.2.25.4.40.5.10.100.1.59
    optixRtnPhyLagPGStatePu9HardStatus OBJECT-TYPE
        SYNTAX OPTIXRtnPhyLagPGStatus
        MAX-ACCESS read-only
        STATUS current
        DESCRIPTION
            "Indicates the slave unit 9 hardware status. Values: 0: normal 1: abnormal -1: unknown"
        ::= { optixRtnPhyLagPGStateEntry 59 }

    -- 1.3.6.1.4.1.2011.2.25.4.40.5.10.100.1.60
    optixRtnPhyLagPGStatePu9LinkStatus OBJECT-TYPE
        SYNTAX OPTIXRtnPhyLagPGStatus
        MAX-ACCESS read-only
        STATUS current
        DESCRIPTION
            "Indicates the slave unit 9 link status. Values: 0: normal 1: abnormal -1: unknown"
        ::= { optixRtnPhyLagPGStateEntry 60 }

    -- 1.3.6.1.4.1.2011.2.25.4.40.5.10.100.1.61
    optixRtnPhyLagPGStatePu9WorkStatus OBJECT-TYPE
        SYNTAX OPTIXRtnPhyLagPGStateWorkStatus
        MAX-ACCESS read-only
        STATUS current
        DESCRIPTION
            "Indicates the slave unit 9 working status. Values: 0: slave port 1: main port"
        ::= { optixRtnPhyLagPGStateEntry 61 }

    -- 1.3.6.1.4.1.2011.2.25.4.40.5.10.100.1.62
    optixRtnPhyLagPGStatePu10BoardID OBJECT-TYPE
        SYNTAX Unsigned32
        MAX-ACCESS read-only
        STATUS current
        DESCRIPTION
            "Indicates the slave unit 10 slot ID."
        ::= { optixRtnPhyLagPGStateEntry 62 }

    -- 1.3.6.1.4.1.2011.2.25.4.40.5.10.100.1.63
    optixRtnPhyLagPGStatePu10SubCardID OBJECT-TYPE
        SYNTAX Unsigned32
        MAX-ACCESS read-only
        STATUS current
        DESCRIPTION
            "Indicates the slave unit 10 subboard ID."
        ::= { optixRtnPhyLagPGStateEntry 63 }

    -- 1.3.6.1.4.1.2011.2.25.4.40.5.10.100.1.64
    optixRtnPhyLagPGStatePu10PortID OBJECT-TYPE
        SYNTAX Unsigned32
        MAX-ACCESS read-only
        STATUS current
        DESCRIPTION
            "Indicates the slave unit 10 port ID."
        ::= { optixRtnPhyLagPGStateEntry 64 }

    -- 1.3.6.1.4.1.2011.2.25.4.40.5.10.100.1.65
    optixRtnPhyLagPGStatePu10HardStatus OBJECT-TYPE
        SYNTAX OPTIXRtnPhyLagPGStatus
        MAX-ACCESS read-only
        STATUS current
        DESCRIPTION
            "Indicates the slave unit 10 hardware status. Values: 0: normal 1: abnormal -1: unknown"
        ::= { optixRtnPhyLagPGStateEntry 65 }

    -- 1.3.6.1.4.1.2011.2.25.4.40.5.10.100.1.66
    optixRtnPhyLagPGStatePu10LinkStatus OBJECT-TYPE
        SYNTAX OPTIXRtnPhyLagPGStatus
        MAX-ACCESS read-only
        STATUS current
        DESCRIPTION
            "Indicates the slave unit 10 link status. Values: 0: normal 1: abnormal -1: unknown"
        ::= { optixRtnPhyLagPGStateEntry 66 }

    -- 1.3.6.1.4.1.2011.2.25.4.40.5.10.100.1.67
    optixRtnPhyLagPGStatePu10WorkStatus OBJECT-TYPE
        SYNTAX OPTIXRtnPhyLagPGStateWorkStatus
        MAX-ACCESS read-only
        STATUS current
        DESCRIPTION
            "Indicates the slave unit 10 working status. Values: 0: slave port 1: main port"
        ::= { optixRtnPhyLagPGStateEntry 67 }

    -- 1.3.6.1.4.1.2011.2.25.4.40.5.10.100.1.68
    optixRtnPhyLagPGStatePu11BoardID OBJECT-TYPE
        SYNTAX Unsigned32
        MAX-ACCESS read-only
        STATUS current
        DESCRIPTION
            "Indicates the slave unit 11 slot ID."
        ::= { optixRtnPhyLagPGStateEntry 68 }

    -- 1.3.6.1.4.1.2011.2.25.4.40.5.10.100.1.69
    optixRtnPhyLagPGStatePu11SubCardID OBJECT-TYPE
        SYNTAX Unsigned32
        MAX-ACCESS read-only
        STATUS current
        DESCRIPTION
            "Indicates the slave unit 11 subboard ID."
        ::= { optixRtnPhyLagPGStateEntry 69 }

    -- 1.3.6.1.4.1.2011.2.25.4.40.5.10.100.1.70
    optixRtnPhyLagPGStatePu11PortID OBJECT-TYPE
        SYNTAX Unsigned32
        MAX-ACCESS read-only
        STATUS current
        DESCRIPTION
            "Indicates the slave unit 11 port ID."
        ::= { optixRtnPhyLagPGStateEntry 70 }

    -- 1.3.6.1.4.1.2011.2.25.4.40.5.10.100.1.71
    optixRtnPhyLagPGStatePu11HardStatus OBJECT-TYPE
        SYNTAX OPTIXRtnPhyLagPGStatus
        MAX-ACCESS read-only
        STATUS current
        DESCRIPTION
            "Indicates the slave unit 11 hardware status. Values: 0: normal 1: abnormal -1: unknown"
        ::= { optixRtnPhyLagPGStateEntry 71 }

    -- 1.3.6.1.4.1.2011.2.25.4.40.5.10.100.1.72
    optixRtnPhyLagPGStatePu11LinkStatus OBJECT-TYPE
        SYNTAX OPTIXRtnPhyLagPGStatus
        MAX-ACCESS read-only
        STATUS current
        DESCRIPTION
            "Indicates the slave unit 11 link status. Values: 0: normal 1: abnormal -1: unknown"
        ::= { optixRtnPhyLagPGStateEntry 72 }

    -- 1.3.6.1.4.1.2011.2.25.4.40.5.10.100.1.73
    optixRtnPhyLagPGStatePu11WorkStatus OBJECT-TYPE
        SYNTAX OPTIXRtnPhyLagPGStateWorkStatus
        MAX-ACCESS read-only
        STATUS current
        DESCRIPTION
            "Indicates the slave unit 11 working status. Values: 0: slave port 1: main port"
        ::= { optixRtnPhyLagPGStateEntry 73 }

    -- 1.3.6.1.4.1.2011.2.25.4.40.5.10.110
    optixRtnCascading1j1PGParameterTable OBJECT-TYPE
        SYNTAX SEQUENCE OF OptixRtnCascading1j1PGParameterEntry
        MAX-ACCESS not-accessible
        STATUS current
        DESCRIPTION
            "Describes parameters about a cascading IF 1+1 protection group, including the IF board used in the protection group and the role of the IF board in the protection group."
        ::= { optixRtnIFProtect 110 }

    -- 1.3.6.1.4.1.2011.2.25.4.40.5.10.110.1
    optixRtnCascading1j1PGParameterEntry OBJECT-TYPE
        SYNTAX OptixRtnCascading1j1PGParameterEntry
        MAX-ACCESS not-accessible
        STATUS current
        DESCRIPTION
            "Indicates the parameter entry for a cascading IF 1+1 protection group."
        INDEX{ optixRtnCascading1j1PGID }
        ::= { optixRtnCascading1j1PGParameterTable 1 }

    OptixRtnCascading1j1PGParameterEntry ::=
        SEQUENCE {
            optixRtnCascading1j1PGID
                Unsigned32,
            optixRtnCascading1j1PGIFBoardID
                Unsigned32,
            optixRtnCascading1j1PGIFSubCardID
                Unsigned32,
            optixRtnCascading1j1PGIFPort
                Unsigned32,
            optixRtnCascading1j1PGRole
                OPTIXRtnCascading1j1PGRoleType,
            optixRtnCascading1j1PGWorkMode
                OPTIXRtn1j1PGWorkModeType,
            optixRtnCascading1j1PGRevertiveMode
                OPTIXRtnRvtModeType,
            optixRtnCascading1j1PGWTRTime
                Unsigned32,
            optixRtnCascading1j1PGRDISwEnableState
                OPTIXRtnEnableStateType,
            optixRtnCascading1j1PGProtectType
                OPTIXRtnCascading1j1PGProtectType,
            optixRtnCascading1j1PGSlaveMemsInfo
                OCTET STRING,
	    optixRtnCascading1j1PGSwCmd
	        OPTIXRtn1j1PGSwCmdType,
	    optixRtnCascading1j1PGSwDir
	    	OPTIXRtn1j1PGSwDirType,
            optixRtnCascadingPGCfgRowStatus
                RowStatus
        }

    -- 1.3.6.1.4.1.2011.2.25.4.40.5.10.110.1.1
    optixRtnCascading1j1PGID OBJECT-TYPE
        SYNTAX Unsigned32
        MAX-ACCESS not-accessible
        STATUS current
        DESCRIPTION
            "Indicates the protection group ID."
        ::= { optixRtnCascading1j1PGParameterEntry 1 }

    -- 1.3.6.1.4.1.2011.2.25.4.40.5.10.110.1.2
    optixRtnCascading1j1PGIFBoardID OBJECT-TYPE
        SYNTAX Unsigned32
        MAX-ACCESS read-create
        STATUS current
        DESCRIPTION
            "Indicates the IF board ID."
        ::= { optixRtnCascading1j1PGParameterEntry 2 }

    -- 1.3.6.1.4.1.2011.2.25.4.40.5.10.110.1.3
    optixRtnCascading1j1PGIFSubCardID OBJECT-TYPE
        SYNTAX Unsigned32
        MAX-ACCESS read-create
        STATUS current
        DESCRIPTION
            "Indicates the IF subboard ID."
        DEFVAL{ 255 }
        ::= { optixRtnCascading1j1PGParameterEntry 3 }

    -- 1.3.6.1.4.1.2011.2.25.4.40.5.10.110.1.4
    optixRtnCascading1j1PGIFPort OBJECT-TYPE
        SYNTAX Unsigned32
        MAX-ACCESS read-create
        STATUS current
        DESCRIPTION
            "Indicates the IF port ID."
        DEFVAL{ 1 }
        ::= { optixRtnCascading1j1PGParameterEntry 4 }

    -- 1.3.6.1.4.1.2011.2.25.4.40.5.10.110.1.5
    optixRtnCascading1j1PGRole OBJECT-TYPE
        SYNTAX OPTIXRtnCascading1j1PGRoleType
        MAX-ACCESS read-create
        STATUS current
        DESCRIPTION
            "Indicates the role of the IF board in the protection group. Values: 0: main board 1: standby board"
        DEFVAL{ 1 }
        ::= { optixRtnCascading1j1PGParameterEntry 5 }

    -- 1.3.6.1.4.1.2011.2.25.4.40.5.10.110.1.6
    optixRtnCascading1j1PGWorkMode OBJECT-TYPE
        SYNTAX OPTIXRtn1j1PGWorkModeType
        MAX-ACCESS read-create
        STATUS current
        DESCRIPTION
            "Indicates the work mode. Values: 0: SD 1: FD 2: HSB"
        DEFVAL{ 2 }
        ::= { optixRtnCascading1j1PGParameterEntry 6 }

    -- 1.3.6.1.4.1.2011.2.25.4.40.5.10.110.1.7
    optixRtnCascading1j1PGRevertiveMode OBJECT-TYPE
        SYNTAX OPTIXRtnRvtModeType
        MAX-ACCESS read-create
        STATUS current
        DESCRIPTION
            "Indicates the revertive mode. Values: 0: Norvt (non-revertive) 1: Rvt (revertive)"
        DEFVAL{ 1 }
        ::= { optixRtnCascading1j1PGParameterEntry 7 }

    -- 1.3.6.1.4.1.2011.2.25.4.40.5.10.110.1.8
    optixRtnCascading1j1PGWTRTime OBJECT-TYPE
        SYNTAX Unsigned32
        MAX-ACCESS read-create
        STATUS current
        DESCRIPTION
            "Indicates the WTR time. Value range: 300s to 720s"
        DEFVAL{ 600 }
        ::= { optixRtnCascading1j1PGParameterEntry 8 }

    -- 1.3.6.1.4.1.2011.2.25.4.40.5.10.110.1.9
    optixRtnCascading1j1PGRDISwEnableState OBJECT-TYPE
        SYNTAX OPTIXRtnEnableStateType
        MAX-ACCESS read-create
        STATUS current
        DESCRIPTION
            "Indicates the reverse switching status. Values: 0: disabled 1: enabled"
        DEFVAL{ 1 }
        ::= { optixRtnCascading1j1PGParameterEntry 9 }

    -- 1.3.6.1.4.1.2011.2.25.4.40.5.10.110.1.10
    optixRtnCascading1j1PGProtectType OBJECT-TYPE
        SYNTAX OPTIXRtnCascading1j1PGProtectType
        MAX-ACCESS read-create
        STATUS current
        DESCRIPTION
            "Indicates the service protection type. 0: noprot (no device-level protection scheme being used) 1: lagprot (LAG protection) 2: splitprot (optical splitter protection) -1: not supported. Has a fixed value of 255 for OptiX RTN 900"
        ::= { optixRtnCascading1j1PGParameterEntry 10 }

    -- 1.3.6.1.4.1.2011.2.25.4.40.5.10.110.1.11
    optixRtnCascading1j1PGSlaveMemsInfo OBJECT-TYPE
        SYNTAX OCTET STRING (SIZE(0..16))
        MAX-ACCESS read-create
        STATUS current
        DESCRIPTION
            "Indicates the information about the cascade members."
        ::= { optixRtnCascading1j1PGParameterEntry 11 }

	-- 1.3.6.1.4.1.2011.2.25.4.40.5.10.110.1.12
    optixRtnCascading1j1PGSwCmd OBJECT-TYPE
        SYNTAX OPTIXRtn1j1PGSwCmdType
        MAX-ACCESS read-create
        STATUS current
        DESCRIPTION
            "Indicates the switching mode of an IF 1+1 protection group."
        ::= { optixRtnCascading1j1PGParameterEntry 12 }

    -- 1.3.6.1.4.1.2011.2.25.4.40.5.10.110.1.13
    optixRtnCascading1j1PGSwDir OBJECT-TYPE
        SYNTAX OPTIXRtn1j1PGSwDirType
        MAX-ACCESS read-create
        STATUS current
        DESCRIPTION
            "Indicates the switching direction of an IF 1+1 protection group."
        ::= { optixRtnCascading1j1PGParameterEntry 13 }
		
    -- 1.3.6.1.4.1.2011.2.25.4.40.5.10.110.1.50
    optixRtnCascadingPGCfgRowStatus OBJECT-TYPE
        SYNTAX RowStatus
        MAX-ACCESS read-create
        STATUS current
        DESCRIPTION
            "Indicates the row status."
        DEFVAL{ active }
        ::= { optixRtnCascading1j1PGParameterEntry 50 }

    -- 1.3.6.1.4.1.2011.2.25.4.40.5.10.120
    optixRtnCascading1j1PGStateTable OBJECT-TYPE
        SYNTAX SEQUENCE OF OptixRtnCascading1j1PGStateEntry
        MAX-ACCESS not-accessible
        STATUS current
        DESCRIPTION
            "Describes parameters about the current status of an cascading IF 1+1 protection group, including the current working board and switching status of the protection group."
        ::= { optixRtnIFProtect 120 }

    -- 1.3.6.1.4.1.2011.2.25.4.40.5.10.120.1
    optixRtnCascading1j1PGStateEntry OBJECT-TYPE
        SYNTAX OptixRtnCascading1j1PGStateEntry
        MAX-ACCESS not-accessible
        STATUS current
        DESCRIPTION
            "Indicates the parameter entry for the current status of an cascading IF 1+1 protection group."
        INDEX{ optixRtnCascading1j1PGID }
        ::= { optixRtnCascading1j1PGStateTable 1 }

    OptixRtnCascading1j1PGStateEntry ::=
        SEQUENCE {
            optixRtnCascading1j1PGDevWorkNEID
                Unsigned32,
            optixRtnCascading1j1PGDevWorkBoardID
                Unsigned32,
            optixRtnCascading1j1PGWorkSubCardID
                Unsigned32,
            optixRtnCascading1j1PGWorkPortID
                Unsigned32,
            optixRtnCascading1j1PGDevWorkBoardState
                OPTIXRtn1j1PGBDStateType,
            optixRtnCascading1j1PGDevProtectBoardState
                OPTIXRtn1j1PGBDStateType,
            optixRtnCascading1j1PGDevSwtichRequest
                OPTIXRtn1j1SwtichRequestType,
            optixRtnCascading1j1PGLinkWorkNEID
                Unsigned32,
            optixRtnCascading1j1PGLinkWorkBoardID
                Unsigned32,
            optixRtnCascading1j1PGLinkWorkSubCardD
                Unsigned32,
            optixRtnCascading1j1PGLinkWorkPortID
                Unsigned32,
            optixRtnCascading1j1PGWorkBoardLinkState
                OPTIXRtn1j1LinkStateType,
            optixRtnCascading1j1PGProtectBoardLinkState
                OPTIXRtn1j1LinkStateType,
            optixRtnCascading1j1PGProtectLinkSwitchRequest
                OPTIXRtn1j1SwtichRequestType
        }

    -- 1.3.6.1.4.1.2011.2.25.4.40.5.10.120.1.1
    optixRtnCascading1j1PGDevWorkNEID OBJECT-TYPE
        SYNTAX Unsigned32
        MAX-ACCESS read-only
        STATUS current
        DESCRIPTION
            "Indicates the current working NE ID on the equipment side."
        ::= { optixRtnCascading1j1PGStateEntry 1 }

    -- 1.3.6.1.4.1.2011.2.25.4.40.5.10.120.1.2
    optixRtnCascading1j1PGDevWorkBoardID OBJECT-TYPE
        SYNTAX Unsigned32
        MAX-ACCESS read-only
        STATUS current
        DESCRIPTION
            "Indicates the current working board ID on the equipment side."
        ::= { optixRtnCascading1j1PGStateEntry 2 }

    -- 1.3.6.1.4.1.2011.2.25.4.40.5.10.120.1.3
    optixRtnCascading1j1PGWorkSubCardID OBJECT-TYPE
        SYNTAX Unsigned32
        MAX-ACCESS read-only
        STATUS current
        DESCRIPTION
            "Indicates the current working subboard ID on the equipment side."
        ::= { optixRtnCascading1j1PGStateEntry 3 }

    -- 1.3.6.1.4.1.2011.2.25.4.40.5.10.120.1.4
    optixRtnCascading1j1PGWorkPortID OBJECT-TYPE
        SYNTAX Unsigned32
        MAX-ACCESS read-only
        STATUS current
        DESCRIPTION
            "Indicates the current working port ID on the equipment side."
        ::= { optixRtnCascading1j1PGStateEntry 4 }

    -- 1.3.6.1.4.1.2011.2.25.4.40.5.10.120.1.5
    optixRtnCascading1j1PGDevWorkBoardState OBJECT-TYPE
        SYNTAX OPTIXRtn1j1PGBDStateType
        MAX-ACCESS read-only
        STATUS current
        DESCRIPTION
            "Indicates the working status of the main board on the equipment side. Values: 0: normal 1: switching 2: RDI switching -1: unknown"
        ::= { optixRtnCascading1j1PGStateEntry 5 }

    -- 1.3.6.1.4.1.2011.2.25.4.40.5.10.120.1.6
    optixRtnCascading1j1PGDevProtectBoardState OBJECT-TYPE
        SYNTAX OPTIXRtn1j1PGBDStateType
        MAX-ACCESS read-only
        STATUS current
        DESCRIPTION
            "Indicates the working status of the standby board on the equipment side. Values: 0: normal 1: switching 2: RDI switching -1: unknown"
        ::= { optixRtnCascading1j1PGStateEntry 6 }

    -- 1.3.6.1.4.1.2011.2.25.4.40.5.10.120.1.7
    optixRtnCascading1j1PGDevSwtichRequest OBJECT-TYPE
        SYNTAX OPTIXRtn1j1SwtichRequestType
        MAX-ACCESS read-only
        STATUS current
        DESCRIPTION
            "Indicates the switching request on the equipment side. Values: 0: normal 1: automatic 2: manual 3: forced 4: lockout 5: wait to restore 6: RDI"
        ::= { optixRtnCascading1j1PGStateEntry 7 }

    -- 1.3.6.1.4.1.2011.2.25.4.40.5.10.120.1.8
    optixRtnCascading1j1PGLinkWorkNEID OBJECT-TYPE
        SYNTAX Unsigned32
        MAX-ACCESS read-only
        STATUS current
        DESCRIPTION
            "Indicates the current working NE ID on the link side."
        ::= { optixRtnCascading1j1PGStateEntry 8 }

    -- 1.3.6.1.4.1.2011.2.25.4.40.5.10.120.1.9
    optixRtnCascading1j1PGLinkWorkBoardID OBJECT-TYPE
        SYNTAX Unsigned32
        MAX-ACCESS read-only
        STATUS current
        DESCRIPTION
            "Indicates the current working board ID on the link side."
        ::= { optixRtnCascading1j1PGStateEntry 9 }

    -- 1.3.6.1.4.1.2011.2.25.4.40.5.10.120.1.10
    optixRtnCascading1j1PGLinkWorkSubCardD OBJECT-TYPE
        SYNTAX Unsigned32
        MAX-ACCESS read-only
        STATUS current
        DESCRIPTION
            "Indicates the current working subboard ID on the link side."
        ::= { optixRtnCascading1j1PGStateEntry 10 }

    -- 1.3.6.1.4.1.2011.2.25.4.40.5.10.120.1.11
    optixRtnCascading1j1PGLinkWorkPortID OBJECT-TYPE
        SYNTAX Unsigned32
        MAX-ACCESS read-only
        STATUS current
        DESCRIPTION
            "Indicates the current working port ID on the link side."
        ::= { optixRtnCascading1j1PGStateEntry 11 }

    -- 1.3.6.1.4.1.2011.2.25.4.40.5.10.120.1.12
    optixRtnCascading1j1PGWorkBoardLinkState OBJECT-TYPE
        SYNTAX OPTIXRtn1j1LinkStateType
        MAX-ACCESS read-only
        STATUS current
        DESCRIPTION
            "Indicates the signal status of the main board link. Values: 0: normal 1: signal failure 2: signal deterioration -1: invalid"
        ::= { optixRtnCascading1j1PGStateEntry 12 }

    -- 1.3.6.1.4.1.2011.2.25.4.40.5.10.120.1.13
    optixRtnCascading1j1PGProtectBoardLinkState OBJECT-TYPE
        SYNTAX OPTIXRtn1j1LinkStateType
        MAX-ACCESS read-only
        STATUS current
        DESCRIPTION
            "Indicates the signal status of the stanby board link. Values: 0: normal 1: signal failure 2: signal deterioration -1: invalid"
        ::= { optixRtnCascading1j1PGStateEntry 13 }

    -- 1.3.6.1.4.1.2011.2.25.4.40.5.10.120.1.14
    optixRtnCascading1j1PGProtectLinkSwitchRequest OBJECT-TYPE
        SYNTAX OPTIXRtn1j1SwtichRequestType
        MAX-ACCESS read-only
        STATUS current
        DESCRIPTION
            "Indicates the switching request on the link side. Values: 0: normal 1: automatic 3: forced"
        ::= { optixRtnCascading1j1PGStateEntry 14 }

    -- 1.3.6.1.4.1.2011.2.25.4.40.5.10.130
    optixRtnCascadingPhyLagPGParameterTable OBJECT-TYPE
        SYNTAX SEQUENCE OF OptixRtnCascadingPhyLagPGParameterEntry
        MAX-ACCESS not-accessible
        STATUS current
        DESCRIPTION
            "Describes configuration parameters for the working board and protection board in a cascading PLA protection group."
        ::= { optixRtnIFProtect 130 }

    -- 1.3.6.1.4.1.2011.2.25.4.40.5.10.130.1
    optixRtnCascadingPhyLagPGParameterEntry OBJECT-TYPE
        SYNTAX OptixRtnCascadingPhyLagPGParameterEntry
        MAX-ACCESS not-accessible
        STATUS current
        DESCRIPTION
            "Indicates the parameter entry for a cascading PLA protection group."
        INDEX{ optixRtnCascadingPhyLagPGID }
        ::= { optixRtnCascadingPhyLagPGParameterTable 1 }

    OptixRtnCascadingPhyLagPGParameterEntry ::=
        SEQUENCE {
            optixRtnCascadingPhyLagPGID
                Unsigned32,
            optixRtnCascadingPhyLagPGMainBoardID
                Unsigned32,
            optixRtnCascadingPhyLagPGMainSubCardID
                Unsigned32,
            optixRtnCascadingPhyLagPGMainPortID
                Unsigned32,
            optixRtnCascadingPhyLagPGRole
                OPTIXRtnCascadingPLAPGRoleType,
            optixRtnCascadingPhyLagPGProtectType
                OPTIXRtnCascadingPhyLagPGProtectType,
            optixRtnCascadingPhyLagPGCascadingPuNum
                Unsigned32,
            optixRtnCascadingPhyLagPGPu1BoardID
                Unsigned32,
            optixRtnCascadingPhyLagPGPu1SubCardID
                Unsigned32,
            optixRtnCascadingPhyLagPGPu1PortID
                Unsigned32,
            optixRtnCascadingPhyLagPGPortNum
                Unsigned32,
            optixRtnCascadingPhyLagPGCascadingConMemsInfo
                OCTET STRING,
            optixRtnCascadingPhyLagPGCfgRowStatus
                RowStatus
        }

    -- 1.3.6.1.4.1.2011.2.25.4.40.5.10.130.1.1
    optixRtnCascadingPhyLagPGID OBJECT-TYPE
        SYNTAX Unsigned32
        MAX-ACCESS not-accessible
        STATUS current
        DESCRIPTION
            "Indicats the protection group ID."
        ::= { optixRtnCascadingPhyLagPGParameterEntry 1 }

    -- 1.3.6.1.4.1.2011.2.25.4.40.5.10.130.1.2
    optixRtnCascadingPhyLagPGMainBoardID OBJECT-TYPE
        SYNTAX Unsigned32
        MAX-ACCESS read-create
        STATUS current
        DESCRIPTION
            "Indicates the slot ID of the main unit."
        ::= { optixRtnCascadingPhyLagPGParameterEntry 2 }

    -- 1.3.6.1.4.1.2011.2.25.4.40.5.10.130.1.3
    optixRtnCascadingPhyLagPGMainSubCardID OBJECT-TYPE
        SYNTAX Unsigned32
        MAX-ACCESS read-create
        STATUS current
        DESCRIPTION
            "Indicates the subboard ID of the main unit."
        ::= { optixRtnCascadingPhyLagPGParameterEntry 3 }

    -- 1.3.6.1.4.1.2011.2.25.4.40.5.10.130.1.4
    optixRtnCascadingPhyLagPGMainPortID OBJECT-TYPE
        SYNTAX Unsigned32
        MAX-ACCESS read-create
        STATUS current
        DESCRIPTION
            "Indicates the port ID of the main unit."
        ::= { optixRtnCascadingPhyLagPGParameterEntry 4 }

    -- 1.3.6.1.4.1.2011.2.25.4.40.5.10.130.1.5
    optixRtnCascadingPhyLagPGRole OBJECT-TYPE
        SYNTAX OPTIXRtnCascadingPLAPGRoleType
        MAX-ACCESS read-create
        STATUS current
        DESCRIPTION
            "Indicates the role of the current NE in the PLA protection group. Values: 0: slave NE 1: main NE"
        ::= { optixRtnCascadingPhyLagPGParameterEntry 5 }

    -- 1.3.6.1.4.1.2011.2.25.4.40.5.10.130.1.6
    optixRtnCascadingPhyLagPGProtectType OBJECT-TYPE
        SYNTAX OPTIXRtnCascadingPhyLagPGProtectType
        MAX-ACCESS read-create
        STATUS current
        DESCRIPTION
            "Indicates the PLA protection group type. Values: 0: noprot (does not support equipment-level protection) 1: prot (support equipment-level protection) This parameter indicates whether the standby equipment is available when a fault occurs. The current equipment can only take the -1 value."
        ::= { optixRtnCascadingPhyLagPGParameterEntry 6 }

    -- 1.3.6.1.4.1.2011.2.25.4.40.5.10.130.1.7
    optixRtnCascadingPhyLagPGCascadingPuNum OBJECT-TYPE
        SYNTAX Unsigned32
        MAX-ACCESS read-create
        STATUS current
        DESCRIPTION
            "Indicates the number of cascading ports. Value range: 1 to 3"
        DEFVAL{ 1 }
        ::= { optixRtnCascadingPhyLagPGParameterEntry 7 }

    -- 1.3.6.1.4.1.2011.2.25.4.40.5.10.130.1.8
    optixRtnCascadingPhyLagPGPu1BoardID OBJECT-TYPE
        SYNTAX Unsigned32
        MAX-ACCESS read-only
        STATUS current
        DESCRIPTION
            "Indicates the board ID of the cascading unit 1."
        ::= { optixRtnCascadingPhyLagPGParameterEntry 8 }

    -- 1.3.6.1.4.1.2011.2.25.4.40.5.10.130.1.9
    optixRtnCascadingPhyLagPGPu1SubCardID OBJECT-TYPE
        SYNTAX Unsigned32
        MAX-ACCESS read-only
        STATUS current
        DESCRIPTION
            "Indicates the subboard ID of the cascading unit 1."
        ::= { optixRtnCascadingPhyLagPGParameterEntry 9 }

    -- 1.3.6.1.4.1.2011.2.25.4.40.5.10.130.1.10
    optixRtnCascadingPhyLagPGPu1PortID OBJECT-TYPE
        SYNTAX Unsigned32
        MAX-ACCESS read-only
        STATUS current
        DESCRIPTION
            "Indicates the port ID of the cascading unit 1."
        ::= { optixRtnCascadingPhyLagPGParameterEntry 10 }

    -- 1.3.6.1.4.1.2011.2.25.4.40.5.10.130.1.11
    optixRtnCascadingPhyLagPGPortNum OBJECT-TYPE
        SYNTAX Unsigned32
        MAX-ACCESS read-create
        STATUS current
        DESCRIPTION
            "Indicates the service port ID and has a fixed value of 0 for OptiX RTN 900."
        ::= { optixRtnCascadingPhyLagPGParameterEntry 11 }

    -- 1.3.6.1.4.1.2011.2.25.4.40.5.10.130.1.12
    optixRtnCascadingPhyLagPGCascadingConMemsInfo OBJECT-TYPE
        SYNTAX OCTET STRING
        MAX-ACCESS read-create
        STATUS current
        DESCRIPTION
            "Indicates cascading port information of a PLA group consisting of cascading NEs."
        ::= { optixRtnCascadingPhyLagPGParameterEntry 12 }

    -- 1.3.6.1.4.1.2011.2.25.4.40.5.10.130.1.50
    optixRtnCascadingPhyLagPGCfgRowStatus OBJECT-TYPE
        SYNTAX RowStatus
        MAX-ACCESS read-create
        STATUS current
        DESCRIPTION
            "Indicates the row status of a protection group"
        DEFVAL{ active }
        ::= { optixRtnCascadingPhyLagPGParameterEntry 50 }

    -- 1.3.6.1.4.1.2011.2.25.4.40.5.10.140
    optixRtnCascadingPhyLagPGStateTable OBJECT-TYPE
        SYNTAX SEQUENCE OF OptixRtnCascadingPhyLagPGStateEntry
        MAX-ACCESS not-accessible
        STATUS current
        DESCRIPTION
            "Describes parameters about the status of a cascading PLA protection group, including the current working board and the switching status of a protection group."
        ::= { optixRtnIFProtect 140 }

    -- 1.3.6.1.4.1.2011.2.25.4.40.5.10.140.1
    optixRtnCascadingPhyLagPGStateEntry OBJECT-TYPE
        SYNTAX OptixRtnCascadingPhyLagPGStateEntry
        MAX-ACCESS not-accessible
        STATUS current
        DESCRIPTION
            "Indicates the status parameter entry for a cascading PLA protection group."
        INDEX{ optixRtnCascadingPhyLagPGID }
        ::= { optixRtnCascadingPhyLagPGStateTable 1 }

    OptixRtnCascadingPhyLagPGStateEntry ::=
        SEQUENCE {
            optixRtnCascadingPhyLagPGStateMainNEID
                Unsigned32,
            optixRtnCascadingPhyLagPGStateMainBoardID
                Unsigned32,
            optixRtnCascadingPhyLagPGStateMainSubID
                Unsigned32,
            optixRtnCascadingPhyLagPGStateMainPortID
                Unsigned32,
            optixRtnCascadingPhyLagPGMainHardStatus
                OPTIXRtnPhyLagPGStatus,
            optixRtnCascadingPhyLagPGMainLinkStatus
                OPTIXRtnPhyLagPGStatus,
            optixRtnCascadingPhyLagPGMainMSStatus
                OPTIXRtnCascadingPLAPGRoleType,
            optixRtnCascadingPhyLagPGSlavePuNum
                Unsigned32,
            optixRtnCascadingPhyLagPGStatePu1NEID
                Unsigned32,
            optixRtnCascadingPhyLagPGStatePu1BoardID
                Unsigned32,
            optixRtnCascadingPhyLagPGStatePu1SubCardID
                Unsigned32,
            optixRtnCascadingPhyLagPGStatePu1PortID
                Unsigned32,
            optixRtnCascadingPhyLagPGStatePu1HardStatus
                OPTIXRtnPhyLagPGStatus,
            optixRtnCascadingPhyLagPGStatePu1LinkStatus
                OPTIXRtnPhyLagPGStatus,
            optixRtnCascadingPhyLagPGStatePu1MSStatus
                OPTIXRtnPhyLagPGStateWorkStatus
        }

    -- 1.3.6.1.4.1.2011.2.25.4.40.5.10.140.1.1
    optixRtnCascadingPhyLagPGStateMainNEID OBJECT-TYPE
        SYNTAX Unsigned32
        MAX-ACCESS read-only
        STATUS current
        DESCRIPTION
            "Indicates the main NE ID."
        ::= { optixRtnCascadingPhyLagPGStateEntry 1 }

    -- 1.3.6.1.4.1.2011.2.25.4.40.5.10.140.1.2
    optixRtnCascadingPhyLagPGStateMainBoardID OBJECT-TYPE
        SYNTAX Unsigned32
        MAX-ACCESS read-only
        STATUS current
        DESCRIPTION
            "Indicates the slot ID of the main unit."
        ::= { optixRtnCascadingPhyLagPGStateEntry 2 }

    -- 1.3.6.1.4.1.2011.2.25.4.40.5.10.140.1.3
    optixRtnCascadingPhyLagPGStateMainSubID OBJECT-TYPE
        SYNTAX Unsigned32
        MAX-ACCESS read-only
        STATUS current
        DESCRIPTION
            "Indicates the subboard ID of the main unit."
        ::= { optixRtnCascadingPhyLagPGStateEntry 3 }

    -- 1.3.6.1.4.1.2011.2.25.4.40.5.10.140.1.4
    optixRtnCascadingPhyLagPGStateMainPortID OBJECT-TYPE
        SYNTAX Unsigned32
        MAX-ACCESS read-only
        STATUS current
        DESCRIPTION
            "Indicates the port ID of the main unit."
        ::= { optixRtnCascadingPhyLagPGStateEntry 4 }

    -- 1.3.6.1.4.1.2011.2.25.4.40.5.10.140.1.5
    optixRtnCascadingPhyLagPGMainHardStatus OBJECT-TYPE
        SYNTAX OPTIXRtnPhyLagPGStatus
        MAX-ACCESS read-only
        STATUS current
        DESCRIPTION
            "Indicates the hardware status of the main unit. Values: 0: normal 1: abnormal -1: unknown"
        ::= { optixRtnCascadingPhyLagPGStateEntry 5 }

    -- 1.3.6.1.4.1.2011.2.25.4.40.5.10.140.1.6
    optixRtnCascadingPhyLagPGMainLinkStatus OBJECT-TYPE
        SYNTAX OPTIXRtnPhyLagPGStatus
        MAX-ACCESS read-only
        STATUS current
        DESCRIPTION
            "Indicates the link status of the main unit. Values: 0: normal 1: abnormal -1: unknown"
        ::= { optixRtnCascadingPhyLagPGStateEntry 6 }

    -- 1.3.6.1.4.1.2011.2.25.4.40.5.10.140.1.7
    optixRtnCascadingPhyLagPGMainMSStatus OBJECT-TYPE
        SYNTAX OPTIXRtnCascadingPLAPGRoleType
        MAX-ACCESS read-only
        STATUS current
        DESCRIPTION
            "Indicates the working status of the main unit. Values: 0: slave port 1: main port"
        ::= { optixRtnCascadingPhyLagPGStateEntry 7 }

    -- 1.3.6.1.4.1.2011.2.25.4.40.5.10.140.1.8
    optixRtnCascadingPhyLagPGSlavePuNum OBJECT-TYPE
        SYNTAX Unsigned32
        MAX-ACCESS read-only
        STATUS current
        DESCRIPTION
            "Indicates the number of cascading units. Value range: 1 to 3"
        ::= { optixRtnCascadingPhyLagPGStateEntry 8 }

    -- 1.3.6.1.4.1.2011.2.25.4.40.5.10.140.1.9
    optixRtnCascadingPhyLagPGStatePu1NEID OBJECT-TYPE
        SYNTAX Unsigned32
        MAX-ACCESS read-only
        STATUS current
        DESCRIPTION
            "Indicates the NE ID of the cascading unit 1."
        ::= { optixRtnCascadingPhyLagPGStateEntry 9 }

    -- 1.3.6.1.4.1.2011.2.25.4.40.5.10.140.1.10
    optixRtnCascadingPhyLagPGStatePu1BoardID OBJECT-TYPE
        SYNTAX Unsigned32
        MAX-ACCESS read-only
        STATUS current
        DESCRIPTION
            "Indicates the board ID of the cascading unit 1. An invalid value of 65535 is returned when the adjacency channel is faulty."
        ::= { optixRtnCascadingPhyLagPGStateEntry 10 }

    -- 1.3.6.1.4.1.2011.2.25.4.40.5.10.140.1.11
    optixRtnCascadingPhyLagPGStatePu1SubCardID OBJECT-TYPE
        SYNTAX Unsigned32
        MAX-ACCESS read-only
        STATUS current
        DESCRIPTION
            "Indicates the subboard ID of the cascading unit 1. An invalid value of 255 is returned when the adjacency channel is faulty."
        ::= { optixRtnCascadingPhyLagPGStateEntry 11 }

    -- 1.3.6.1.4.1.2011.2.25.4.40.5.10.140.1.12
    optixRtnCascadingPhyLagPGStatePu1PortID OBJECT-TYPE
        SYNTAX Unsigned32
        MAX-ACCESS read-only
        STATUS current
        DESCRIPTION
            "Indicates the port ID of the cascading unit 1. An invalid value of 255 is returned when the adjacency channel is faulty."
        ::= { optixRtnCascadingPhyLagPGStateEntry 12 }

    -- 1.3.6.1.4.1.2011.2.25.4.40.5.10.140.1.13
    optixRtnCascadingPhyLagPGStatePu1HardStatus OBJECT-TYPE
        SYNTAX OPTIXRtnPhyLagPGStatus
        MAX-ACCESS read-only
        STATUS current
        DESCRIPTION
            "Indicates the hardware status of the cascading unit 1. Values: 0: normal 1: abnormal -1: unknown"
        ::= { optixRtnCascadingPhyLagPGStateEntry 13 }

    -- 1.3.6.1.4.1.2011.2.25.4.40.5.10.140.1.14
    optixRtnCascadingPhyLagPGStatePu1LinkStatus OBJECT-TYPE
        SYNTAX OPTIXRtnPhyLagPGStatus
        MAX-ACCESS read-only
        STATUS current
        DESCRIPTION
            "Indicates the link status of the cascading unit 1. Values: 0: normal 1: abnormal -1: unknown"
        ::= { optixRtnCascadingPhyLagPGStateEntry 14 }

    -- 1.3.6.1.4.1.2011.2.25.4.40.5.10.140.1.15
    optixRtnCascadingPhyLagPGStatePu1MSStatus OBJECT-TYPE
        SYNTAX OPTIXRtnPhyLagPGStateWorkStatus
        MAX-ACCESS read-only
        STATUS current
        DESCRIPTION
            "Indicates the working status of the cascading unit 1. Values: 0: slave port 1: main port"
        ::= { optixRtnCascadingPhyLagPGStateEntry 15 }

    -- 1.3.6.1.4.1.2011.2.25.4.40.5.10.150
    optixRtnCascadingPhyLagPGParameterExtTable OBJECT-TYPE
        SYNTAX SEQUENCE OF OptixRtnCascadingPhyLagPGParameterExtEntry
        MAX-ACCESS not-accessible
        STATUS current
        DESCRIPTION
            "Describes configuration parameters for the working board and protection board in a cascading PLA/EPLA protection group."
        ::= { optixRtnIFProtect 150 }

    -- 1.3.6.1.4.1.2011.2.25.4.40.5.10.150.1
    optixRtnCascadingPhyLagPGParameterExtEntry OBJECT-TYPE
        SYNTAX OptixRtnCascadingPhyLagPGParameterExtEntry
        MAX-ACCESS not-accessible
        STATUS current
        DESCRIPTION
            "Indicates the parameter entry for a cascading PLA/EPLA protection group."
        INDEX{ optixRtnCascadingPhyLagPGID }
        ::= { optixRtnCascadingPhyLagPGParameterExtTable 1 }

    OptixRtnCascadingPhyLagPGParameterExtEntry ::=
        SEQUENCE {
            optixRtnCascadingPhyLagPGTypeExt
                OPTIXRtnPhyLagPGType,
            optixRtnCascadingPhyLagPGMainSlotIDExt
                Unsigned32,
            optixRtnCascadingPhyLagPGMainSubCardIDExt
                Unsigned32,
            optixRtnCascadingPhyLagPGMainPortIDExt
                Unsigned32,
            optixRtnPhyLagPGSlaveMemsInfoExt
                OCTET STRING,
            optixRtnCascadingPhyLagPGRoleExt
                OPTIXRtnCascadingPLAPGRoleType,
            optixRtnCascadingPhyLagPGProtectTypeExt
                OPTIXRtnCascadingPhyLagPGProtectTypeExt,
            optixRtnCascadingPhyLagLcConMemsInfo
                OCTET STRING,
            optixRtnCascadingPhyLagNbConMemsInfo
                OCTET STRING,
            optixRtnCascadingPhyLagPGLinkThresholdExt
                Unsigned32,
            optixRtnCascadingPhyLagPGServicePortInfo
                OCTET STRING,
            optixRtnCascadingPhyLagPGCfgRowStatusExt
                RowStatus
        }

    -- 1.3.6.1.4.1.2011.2.25.4.40.5.10.150.1.1
    optixRtnCascadingPhyLagPGTypeExt OBJECT-TYPE
        SYNTAX OPTIXRtnPhyLagPGType
        MAX-ACCESS read-create
        STATUS current
        DESCRIPTION
            "Indicates the protection group type. Values: 0: PLA 1: EPLA 2: cascading PLA 3:cascading EPLA"
        ::= { optixRtnCascadingPhyLagPGParameterExtEntry 1 }

    -- 1.3.6.1.4.1.2011.2.25.4.40.5.10.150.1.2
    optixRtnCascadingPhyLagPGMainSlotIDExt OBJECT-TYPE
        SYNTAX Unsigned32
        MAX-ACCESS read-create
        STATUS current
        DESCRIPTION
            "Indicates the slot ID of the main port."
        ::= { optixRtnCascadingPhyLagPGParameterExtEntry 2 }

    -- 1.3.6.1.4.1.2011.2.25.4.40.5.10.150.1.3
    optixRtnCascadingPhyLagPGMainSubCardIDExt OBJECT-TYPE
        SYNTAX Unsigned32
        MAX-ACCESS read-create
        STATUS current
        DESCRIPTION
            "Indicates the subboard ID of the main port."
        ::= { optixRtnCascadingPhyLagPGParameterExtEntry 3 }

    -- 1.3.6.1.4.1.2011.2.25.4.40.5.10.150.1.4
    optixRtnCascadingPhyLagPGMainPortIDExt OBJECT-TYPE
        SYNTAX Unsigned32
        MAX-ACCESS read-create
        STATUS current
        DESCRIPTION
            "Indicates the port number of the main port."
        ::= { optixRtnCascadingPhyLagPGParameterExtEntry 4 }

    -- 1.3.6.1.4.1.2011.2.25.4.40.5.10.150.1.5
    optixRtnPhyLagPGSlaveMemsInfoExt OBJECT-TYPE
        SYNTAX OCTET STRING
        MAX-ACCESS read-create
        STATUS current
        DESCRIPTION
            "Indicates the slave port information of the protection group."
        ::= { optixRtnCascadingPhyLagPGParameterExtEntry 5 }

    -- 1.3.6.1.4.1.2011.2.25.4.40.5.10.150.1.6
    optixRtnCascadingPhyLagPGRoleExt OBJECT-TYPE
        SYNTAX OPTIXRtnCascadingPLAPGRoleType
        MAX-ACCESS read-create
        STATUS current
        DESCRIPTION
            "Indicates the role of the current NE in the protection group. Values: 0: slave NE 1: master NE"
        ::= { optixRtnCascadingPhyLagPGParameterExtEntry 6 }

    -- 1.3.6.1.4.1.2011.2.25.4.40.5.10.150.1.7
    optixRtnCascadingPhyLagPGProtectTypeExt OBJECT-TYPE
        SYNTAX OPTIXRtnCascadingPhyLagPGProtectTypeExt
        MAX-ACCESS read-create
        STATUS current
        DESCRIPTION
            "Indicates the protection group type. Values: 0: no protection 1: LAG protection 2: optical splitter protection"
        ::= { optixRtnCascadingPhyLagPGParameterExtEntry 7 }

    -- 1.3.6.1.4.1.2011.2.25.4.40.5.10.150.1.8
    optixRtnCascadingPhyLagLcConMemsInfo OBJECT-TYPE
        SYNTAX OCTET STRING
        MAX-ACCESS read-create
        STATUS current
        DESCRIPTION
            "Indicates the local NE information of the protection group."
        ::= { optixRtnCascadingPhyLagPGParameterExtEntry 8 }

    -- 1.3.6.1.4.1.2011.2.25.4.40.5.10.150.1.9
    optixRtnCascadingPhyLagNbConMemsInfo OBJECT-TYPE
        SYNTAX OCTET STRING
        MAX-ACCESS read-create
        STATUS current
        DESCRIPTION
            "Indicates the neighbor NE information of the protection group."
        ::= { optixRtnCascadingPhyLagPGParameterExtEntry 9 }

    -- 1.3.6.1.4.1.2011.2.25.4.40.5.10.150.1.10
    optixRtnCascadingPhyLagPGLinkThresholdExt OBJECT-TYPE
        SYNTAX Unsigned32
        MAX-ACCESS read-create
        STATUS current
        DESCRIPTION
            "Indicates the minimum number of active links in the protection group."
        ::= { optixRtnCascadingPhyLagPGParameterExtEntry 10 }

    -- 1.3.6.1.4.1.2011.2.25.4.40.5.10.150.1.11
    optixRtnCascadingPhyLagPGServicePortInfo OBJECT-TYPE
        SYNTAX OCTET STRING
        MAX-ACCESS read-create
        STATUS deprecated
        DESCRIPTION
            "Indicates service port information of a PLA group consisting of cascading NEs."
        ::= { optixRtnCascadingPhyLagPGParameterExtEntry 11 }

    -- 1.3.6.1.4.1.2011.2.25.4.40.5.10.150.1.50
    optixRtnCascadingPhyLagPGCfgRowStatusExt OBJECT-TYPE
        SYNTAX RowStatus
        MAX-ACCESS read-create
        STATUS current
        DESCRIPTION
            "Indicates the row status of the protection group."
        DEFVAL{ active }
        ::= { optixRtnCascadingPhyLagPGParameterExtEntry 50 }

    -- 1.3.6.1.4.1.2011.2.25.4.40.5.10.160
    optixRtnCascadingPhyLagPGStateExtTable OBJECT-TYPE
        SYNTAX SEQUENCE OF OptixRtnCascadingPhyLagPGStateExtEntry
        MAX-ACCESS not-accessible
        STATUS current
        DESCRIPTION
            "Describes status parameters for the protection group."
        ::= { optixRtnIFProtect 160 }

    -- 1.3.6.1.4.1.2011.2.25.4.40.5.10.160.1
    optixRtnCascadingPhyLagPGStateExtEntry OBJECT-TYPE
        SYNTAX OptixRtnCascadingPhyLagPGStateExtEntry
        MAX-ACCESS not-accessible
        STATUS current
        DESCRIPTION
            "Indicates the status parameter entry for the protection group."
        INDEX{ optixRtnCascadingPhyLagPGID,optixRtnCascadingPhyLagPGStateMSNEID,optixRtnCascadingPhyLagPGStateMSSlotID,optixRtnCascadingPhyLagPGStateMSSubCardID,optixRtnCascadingPhyLagPGStateMSPortID }
        ::= { optixRtnCascadingPhyLagPGStateExtTable 1 }

    OptixRtnCascadingPhyLagPGStateExtEntry ::=
        SEQUENCE {
            optixRtnCascadingPhyLagPGStateMSNEID
                Unsigned32,
            optixRtnCascadingPhyLagPGStateMSSlotID
                Unsigned32,
            optixRtnCascadingPhyLagPGStateMSSubCardID
                Unsigned32,
            optixRtnCascadingPhyLagPGStateMSPortID
                Unsigned32,
            optixRtnCascadingPhyLagPGStateMSHardStatus
                OPTIXRtnPhyLagPGStatus,
            optixRtnCascadingPhyLagPGStateMSLinkStatus
                OPTIXRtnPhyLagPGStatus,
            optixRtnCascadingPhyLagPGStateMSStatusExt
                OPTIXRtnCascadingPLAPGRoleType
        }

    -- 1.3.6.1.4.1.2011.2.25.4.40.5.10.160.1.1
    optixRtnCascadingPhyLagPGStateMSNEID OBJECT-TYPE
        SYNTAX Unsigned32
        MAX-ACCESS not-accessible
        STATUS current
        DESCRIPTION
            "Indicates the NE ID of the protection group."
        ::= { optixRtnCascadingPhyLagPGStateExtEntry 1 }

    -- 1.3.6.1.4.1.2011.2.25.4.40.5.10.160.1.2
    optixRtnCascadingPhyLagPGStateMSSlotID OBJECT-TYPE
        SYNTAX Unsigned32
        MAX-ACCESS not-accessible
        STATUS current
        DESCRIPTION
            "Indicates the slot ID of the protection group."
        ::= { optixRtnCascadingPhyLagPGStateExtEntry 2 }

    -- 1.3.6.1.4.1.2011.2.25.4.40.5.10.160.1.3
    optixRtnCascadingPhyLagPGStateMSSubCardID OBJECT-TYPE
        SYNTAX Unsigned32
        MAX-ACCESS not-accessible
        STATUS current
        DESCRIPTION
            "Indicates the subboard ID of the protection group."
        ::= { optixRtnCascadingPhyLagPGStateExtEntry 3 }

    -- 1.3.6.1.4.1.2011.2.25.4.40.5.10.160.1.4
    optixRtnCascadingPhyLagPGStateMSPortID OBJECT-TYPE
        SYNTAX Unsigned32
        MAX-ACCESS not-accessible
        STATUS current
        DESCRIPTION
            "Indicates the port number of the protection group."
        ::= { optixRtnCascadingPhyLagPGStateExtEntry 4 }

    -- 1.3.6.1.4.1.2011.2.25.4.40.5.10.160.1.5
    optixRtnCascadingPhyLagPGStateMSHardStatus OBJECT-TYPE
        SYNTAX OPTIXRtnPhyLagPGStatus
        MAX-ACCESS read-only
        STATUS current
        DESCRIPTION
            "Indicates the hardware status of the member port in the protection group. Values: 0: normal 1: abnormal -1: unknown"
        ::= { optixRtnCascadingPhyLagPGStateExtEntry 5 }

    -- 1.3.6.1.4.1.2011.2.25.4.40.5.10.160.1.6
    optixRtnCascadingPhyLagPGStateMSLinkStatus OBJECT-TYPE
        SYNTAX OPTIXRtnPhyLagPGStatus
        MAX-ACCESS read-only
        STATUS current
        DESCRIPTION
            "Indicates the link status of the member port in the protection group. Values: 0: normal 1: abnormal -1: unknown"
        ::= { optixRtnCascadingPhyLagPGStateExtEntry 6 }

    -- 1.3.6.1.4.1.2011.2.25.4.40.5.10.160.1.7
    optixRtnCascadingPhyLagPGStateMSStatusExt OBJECT-TYPE
        SYNTAX OPTIXRtnCascadingPLAPGRoleType
        MAX-ACCESS read-only
        STATUS current
        DESCRIPTION
            "Indicates the working status of the member port in the protection group. Values: 0: slave port 1: main port"
        ::= { optixRtnCascadingPhyLagPGStateExtEntry 7 }

    -- 1.3.6.1.4.1.2011.2.25.4.40.5.10.180
    optixRtnFO1j1PGStateTable OBJECT-TYPE
        SYNTAX SEQUENCE OF OptixRtnFO1j1PGStateEntry
        MAX-ACCESS not-accessible
        STATUS current
        DESCRIPTION
            "Describes parameters about the current status of an FO IF 1+1 protection group, including the current working board and switching status of the protection group."
        ::= { optixRtnIFProtect 180 }

    -- 1.3.6.1.4.1.2011.2.25.4.40.5.10.180.1
    optixRtnFO1j1PGStateEntry OBJECT-TYPE
        SYNTAX OptixRtnFO1j1PGStateEntry
        MAX-ACCESS not-accessible
        STATUS current
        DESCRIPTION
            "Indicates the parameter entry for the current status of an FO IF 1+1 protection group."
        INDEX{ optixRtnCascading1j1PGrID }
        ::= { optixRtnFO1j1PGStateTable 1 }

    OptixRtnFO1j1PGStateEntry ::=
        SEQUENCE {
            optixRtnFO1j1PGDevWorkNEID
                Unsigned32,
            optixRtnFO1j1PGDevWorkBoardID
                Unsigned32,
            optixRtnFO1j1PGWorkSubCardID
                Unsigned32,
            optixRtnFO1j1PGWorkPortID
                Unsigned32,
            optixRtnFO1j1PGDevWorkBoardState
                OPTIXRtn1j1PGBDStateType,
            optixRtnFO1j1PGDevProtectBoardState
                OPTIXRtn1j1PGBDStateType,
            optixRtnFO1j1PGDevSwtichRequest
                OPTIXRtn1j1SwtichRequestType,
            optixRtnFO1j1PGLinkWorkNEID
                Unsigned32,
            optixRtnFO1j1PGLinkWorkBoardID
                Unsigned32,
            optixRtnFO1j1PGLinkWorkSubCardID
                Unsigned32,
            optixRtnFO1j1PGLinkWorkPortID
                Unsigned32,
            optixRtnFO1j1PGWorkBoardLinkState
                OPTIXRtn1j1LinkStateType,
            optixRtnFO1j1PGProtectBoardLinkState
                OPTIXRtn1j1LinkStateType,
            optixRtnFO1j1PGProtectLinkSwitchRequest
                OPTIXRtn1j1SwtichRequestType
        }

    -- 1.3.6.1.4.1.2011.2.25.4.40.5.10.180.1.1
    optixRtnFO1j1PGDevWorkNEID OBJECT-TYPE
        SYNTAX Unsigned32
        MAX-ACCESS read-only
        STATUS current
        DESCRIPTION
            "Indicates the current working NE ID on the equipment side."
        ::= { optixRtnFO1j1PGStateEntry 1 }

    -- 1.3.6.1.4.1.2011.2.25.4.40.5.10.180.1.2
    optixRtnFO1j1PGDevWorkBoardID OBJECT-TYPE
        SYNTAX Unsigned32
        MAX-ACCESS read-only
        STATUS current
        DESCRIPTION
            "Indicates the current working board ID on the equipment side."
        ::= { optixRtnFO1j1PGStateEntry 2 }

    -- 1.3.6.1.4.1.2011.2.25.4.40.5.10.180.1.3
    optixRtnFO1j1PGWorkSubCardID OBJECT-TYPE
        SYNTAX Unsigned32
        MAX-ACCESS read-only
        STATUS current
        DESCRIPTION
            "Indicates the current working subboard ID on the equipment side."
        ::= { optixRtnFO1j1PGStateEntry 3 }

    -- 1.3.6.1.4.1.2011.2.25.4.40.5.10.180.1.4
    optixRtnFO1j1PGWorkPortID OBJECT-TYPE
        SYNTAX Unsigned32
        MAX-ACCESS read-only
        STATUS current
        DESCRIPTION
            "Indicates the current working port ID on the equipment side."
        ::= { optixRtnFO1j1PGStateEntry 4 }

    -- 1.3.6.1.4.1.2011.2.25.4.40.5.10.180.1.5
    optixRtnFO1j1PGDevWorkBoardState OBJECT-TYPE
        SYNTAX OPTIXRtn1j1PGBDStateType
        MAX-ACCESS read-only
        STATUS current
        DESCRIPTION
            "Indicates the working status of the main board on the equipment side. Values: 0: normal 1: switching 2: RDI switching 255: unknown"
        ::= { optixRtnFO1j1PGStateEntry 5 }

    -- 1.3.6.1.4.1.2011.2.25.4.40.5.10.180.1.6
    optixRtnFO1j1PGDevProtectBoardState OBJECT-TYPE
        SYNTAX OPTIXRtn1j1PGBDStateType
        MAX-ACCESS read-only
        STATUS current
        DESCRIPTION
            "Indicates the working status of the standby board on the equipment side. Values: 0: normal 1: switching 2: RDI switching 255: unknown"
        ::= { optixRtnFO1j1PGStateEntry 6 }

    -- 1.3.6.1.4.1.2011.2.25.4.40.5.10.180.1.7
    optixRtnFO1j1PGDevSwtichRequest OBJECT-TYPE
        SYNTAX OPTIXRtn1j1SwtichRequestType
        MAX-ACCESS read-only
        STATUS current
        DESCRIPTION
            "Indicates the switching request on the equipment side. Values: 0: normal 1: automatic 2: manual 3: forced 4: lockout 5: wait to restore 6: RDI"
        ::= { optixRtnFO1j1PGStateEntry 7 }

    -- 1.3.6.1.4.1.2011.2.25.4.40.5.10.180.1.8
    optixRtnFO1j1PGLinkWorkNEID OBJECT-TYPE
        SYNTAX Unsigned32
        MAX-ACCESS read-only
        STATUS current
        DESCRIPTION
            "Indicates the current working NE ID on the link side."
        ::= { optixRtnFO1j1PGStateEntry 8 }

    -- 1.3.6.1.4.1.2011.2.25.4.40.5.10.180.1.9
    optixRtnFO1j1PGLinkWorkBoardID OBJECT-TYPE
        SYNTAX Unsigned32
        MAX-ACCESS read-only
        STATUS current
        DESCRIPTION
            "Indicates the current working board ID on the link side."
        ::= { optixRtnFO1j1PGStateEntry 9 }

    -- 1.3.6.1.4.1.2011.2.25.4.40.5.10.180.1.10
    optixRtnFO1j1PGLinkWorkSubCardID OBJECT-TYPE
        SYNTAX Unsigned32
        MAX-ACCESS read-only
        STATUS current
        DESCRIPTION
            "Indicates the current working subboard ID on the link side."
        ::= { optixRtnFO1j1PGStateEntry 10 }

    -- 1.3.6.1.4.1.2011.2.25.4.40.5.10.180.1.11
    optixRtnFO1j1PGLinkWorkPortID OBJECT-TYPE
        SYNTAX Unsigned32
        MAX-ACCESS read-only
        STATUS current
        DESCRIPTION
            "Indicates the current working port ID on the link side."
        ::= { optixRtnFO1j1PGStateEntry 11 }

    -- 1.3.6.1.4.1.2011.2.25.4.40.5.10.180.1.12
    optixRtnFO1j1PGWorkBoardLinkState OBJECT-TYPE
        SYNTAX OPTIXRtn1j1LinkStateType
        MAX-ACCESS read-only
        STATUS current
        DESCRIPTION
            "Indicates the signal status of the main board link. Values: 0: normal 1: signal failure 2: signal deterioration 255: invalid"
        ::= { optixRtnFO1j1PGStateEntry 12 }

    -- 1.3.6.1.4.1.2011.2.25.4.40.5.10.180.1.13
    optixRtnFO1j1PGProtectBoardLinkState OBJECT-TYPE
        SYNTAX OPTIXRtn1j1LinkStateType
        MAX-ACCESS read-only
        STATUS current
        DESCRIPTION
            "Indicates the signal status of the stanby board link. Values: 0: normal 1: signal failure 2: signal deterioration 255: invalid"
        ::= { optixRtnFO1j1PGStateEntry 13 }

    -- 1.3.6.1.4.1.2011.2.25.4.40.5.10.180.1.14
    optixRtnFO1j1PGProtectLinkSwitchRequest OBJECT-TYPE
        SYNTAX OPTIXRtn1j1SwtichRequestType
        MAX-ACCESS read-only
        STATUS current
        DESCRIPTION
            "Indicates the switching request on the link side. Values: 0: normal 1: automatic 3: forced"
        ::= { optixRtnFO1j1PGStateEntry 14 }

	-- 1.3.6.1.4.1.2011.2.25.4.40.5.10.190
    optixRtnCascading1j1PGParameterExTable OBJECT-TYPE
        SYNTAX SEQUENCE OF OptixRtnCascading1j1PGParameterExEntry
        MAX-ACCESS not-accessible
        STATUS current
        DESCRIPTION
            "Describes parameters about an FO IF 1+1 protection group, including the IF board used in the protection group and the role of the IF board in the protection group."
        ::= { optixRtnIFProtect 190 }

    -- 1.3.6.1.4.1.2011.2.25.4.40.5.10.190.1
    optixRtnCascading1j1PGParameterExEntry OBJECT-TYPE
        SYNTAX OptixRtnCascading1j1PGParameterExEntry
        MAX-ACCESS not-accessible
        STATUS current
        DESCRIPTION
            "Indicates the parameter entry for an FO IF 1+1 protection group."
        INDEX{ optixRtnCascading1j1PGrID }
        ::= { optixRtnCascading1j1PGParameterExTable 1 }

    OptixRtnCascading1j1PGParameterExEntry ::=
        SEQUENCE {
            optixRtnCascading1j1PGrID
                Unsigned32,
            optixRtnCascading1j1PGrRevertiveMode
                OPTIXRtnRvtModeType,
            optixRtnCascading1j1PGrWTRTime
                Unsigned32,
            optixRtnCascading1j1PGrBID
                Unsigned32,
            optixRtnCascading1j1PGrCasPortID
                Unsigned32
        }

    -- 1.3.6.1.4.1.2011.2.25.4.40.5.10.190.1.1
    optixRtnCascading1j1PGrID OBJECT-TYPE
        SYNTAX Unsigned32
        MAX-ACCESS not-accessible
        STATUS current
        DESCRIPTION
            "Indicates the protection group ID."
        ::= { optixRtnCascading1j1PGParameterExEntry 1 }

    -- 1.3.6.1.4.1.2011.2.25.4.40.5.10.190.1.2
    optixRtnCascading1j1PGrRevertiveMode OBJECT-TYPE
        SYNTAX OPTIXRtnRvtModeType
        MAX-ACCESS read-write
        STATUS current
        DESCRIPTION
            "Indicates the reversion mode. Values: 0: norvt (non-revertive) 1: rvt (revertive)"
        ::= { optixRtnCascading1j1PGParameterExEntry 2 }

    -- 1.3.6.1.4.1.2011.2.25.4.40.5.10.190.1.3
    optixRtnCascading1j1PGrWTRTime OBJECT-TYPE
        SYNTAX Unsigned32
        MAX-ACCESS read-write
        STATUS current
        DESCRIPTION
            "Indicates the WTR time. Value range: 300s to 720s"
        DEFVAL{ 600 }
        ::= { optixRtnCascading1j1PGParameterExEntry 3 }

    -- 1.3.6.1.4.1.2011.2.25.4.40.5.10.190.1.4
    optixRtnCascading1j1PGrBID OBJECT-TYPE
        SYNTAX Unsigned32
        MAX-ACCESS read-write
        STATUS current
        DESCRIPTION
            "Indicates the board ID(this node is used only on RTN300 devices)."
        ::= { optixRtnCascading1j1PGParameterExEntry 4 }

    -- 1.3.6.1.4.1.2011.2.25.4.40.5.10.190.1.5
    optixRtnCascading1j1PGrCasPortID OBJECT-TYPE
        SYNTAX Unsigned32
        MAX-ACCESS read-write
        STATUS current
        DESCRIPTION
            "Indicates the cascade port ID(this node is used only on RTN300 devices). Value range: 2 to 5"
        DEFVAL{ 3 }
        ::= { optixRtnCascading1j1PGParameterExEntry 5 }

    -- 1.3.6.1.4.1.2011.2.25.4.40.5.10.200
    optixRtnINHPGAlmTable OBJECT-TYPE
        SYNTAX SEQUENCE OF OptixRtnINHPGAlmEntry
        MAX-ACCESS not-accessible
        STATUS current
        DESCRIPTION
            "Indicates the configuration parameters related to the alarm inhibition of the protection group."
        ::= { optixRtnIFProtect 200 }

    -- 1.3.6.1.4.1.2011.2.25.4.40.5.10.200.1
    optixRtnINHPGAlmEntry OBJECT-TYPE
        SYNTAX OptixRtnINHPGAlmEntry
        MAX-ACCESS not-accessible
        STATUS current
        DESCRIPTION
            "Indicates the configuration parameter entry related to the alarm inhibition of the protection group."
        INDEX{ optixRtnINHPgType,optixRtnINHPgID,optixRtnINHPgAlmEvent }
        ::= { optixRtnINHPGAlmTable 1 }

    OptixRtnINHPGAlmEntry ::=
        SEQUENCE {
            optixRtnINHPgType
                OPTIXRtnPgType,
            optixRtnINHPgID
                Unsigned32,
            optixRtnINHPgAlmEvent
                AlarmINHPG1J1EventType,
            optixRtnINHPgAlmStatus
                OPTIXRtnEnableStateType
        }

    -- 1.3.6.1.4.1.2011.2.25.4.40.5.10.200.1.1
    optixRtnINHPgType OBJECT-TYPE
        SYNTAX OPTIXRtnPgType
        MAX-ACCESS not-accessible
        STATUS current
        DESCRIPTION
            "Indicates the type of the protection group. Value range: 1 indicates IF 1+1 protection. 2 indicates cascading 1+1 protection."
        ::= { optixRtnINHPGAlmEntry 1 }

    -- 1.3.6.1.4.1.2011.2.25.4.40.5.10.200.1.2
    optixRtnINHPgID OBJECT-TYPE
        SYNTAX Unsigned32
        MAX-ACCESS not-accessible
        STATUS current
        DESCRIPTION
            "Indicates the ID of the protection group."
        ::= { optixRtnINHPGAlmEntry 2 }

    -- 1.3.6.1.4.1.2011.2.25.4.40.5.10.200.1.3
    optixRtnINHPgAlmEvent OBJECT-TYPE
        SYNTAX AlarmINHPG1J1EventType
        MAX-ACCESS not-accessible
        STATUS current
        DESCRIPTION
            "Indicates the ID of the inhibited alarm."
        ::= { optixRtnINHPGAlmEntry 3 }

    -- 1.3.6.1.4.1.2011.2.25.4.40.5.10.200.1.4
    optixRtnINHPgAlmStatus OBJECT-TYPE
        SYNTAX OPTIXRtnEnableStateType
        MAX-ACCESS read-write
        STATUS current
        DESCRIPTION
            "Indicates the enable status of the alarm inhibition. Value range: 0 indicates disabled and 1 indicates enabled."
        ::= { optixRtnINHPGAlmEntry 4 }

    -- 1.3.6.1.4.1.2011.2.25.4.40.5.10.210
    optixRtnNbplaStateTable OBJECT-TYPE
        SYNTAX SEQUENCE OF OptixRtnNbplaStateEntry
        MAX-ACCESS not-accessible
        STATUS current
        DESCRIPTION
            "It is applicable to the cascade PLA/EPLA management table."
        ::= { optixRtnIFProtect 210 }

    -- 1.3.6.1.4.1.2011.2.25.4.40.5.10.210.1
    optixRtnNbplaStateEntry OBJECT-TYPE
        SYNTAX OptixRtnNbplaStateEntry
        MAX-ACCESS not-accessible
        STATUS current
        DESCRIPTION
            "It is applicable to the cascade PLA management table and the cascade EPLA management table (containing only two members)."
        INDEX{ optixRtnCascadingPhyLagPGID }
        ::= { optixRtnNbplaStateTable 1 }

    OptixRtnNbplaStateEntry ::=
        SEQUENCE {
            optixRtnPLANEId
                Unsigned32,
            optixRtnPLAMSBID
                Unsigned32,
            optixRtnPLAMSSUBID
                Unsigned32,
            optixRtnPLAMSPID
                INTEGER,
            optixRtnPLAHardState
                INTEGER,
            optixRtnPLALinkState
                INTEGER,
            optixRtnPLAMSState
                INTEGER
        }

    -- 1.3.6.1.4.1.2011.2.25.4.40.5.10.210.1.1
    optixRtnPLANEId OBJECT-TYPE
        SYNTAX Unsigned32
        MAX-ACCESS read-only
        STATUS current
        DESCRIPTION
            "Indicates the ID of the working NE."
        ::= { optixRtnNbplaStateEntry 1 }

    -- 1.3.6.1.4.1.2011.2.25.4.40.5.10.210.1.2
    optixRtnPLAMSBID OBJECT-TYPE
        SYNTAX Unsigned32
        MAX-ACCESS read-only
        STATUS current
        DESCRIPTION
            "Indicates the ID of the active port on the working NE."
        ::= { optixRtnNbplaStateEntry 2 }

    -- 1.3.6.1.4.1.2011.2.25.4.40.5.10.210.1.3
    optixRtnPLAMSSUBID OBJECT-TYPE
        SYNTAX Unsigned32
        MAX-ACCESS read-only
        STATUS current
        DESCRIPTION
            "Indicates the subboard ID of the active port on the working NE."
        ::= { optixRtnNbplaStateEntry 3 }

    -- 1.3.6.1.4.1.2011.2.25.4.40.5.10.210.1.4
    optixRtnPLAMSPID OBJECT-TYPE
        SYNTAX INTEGER
        MAX-ACCESS read-only
        STATUS current
        DESCRIPTION
            "Indicates the active port number of the working NE."
        ::= { optixRtnNbplaStateEntry 4 }

    -- 1.3.6.1.4.1.2011.2.25.4.40.5.10.210.1.5
    optixRtnPLAHardState OBJECT-TYPE
        SYNTAX INTEGER
        {
            normal(0),
            abnormal(1),
            unknown(255),
            unknownState(-1)
        }
        MAX-ACCESS read-only
        STATUS current
        DESCRIPTION
            "Indicates the hardware status of the active port on the working NE."
        ::= { optixRtnNbplaStateEntry 5 }

    -- 1.3.6.1.4.1.2011.2.25.4.40.5.10.210.1.6
    optixRtnPLALinkState OBJECT-TYPE
        SYNTAX INTEGER
        {
            normal(0),
            abnormal(1),
            unknown(255),
            unknownState(-1)
        }
        MAX-ACCESS read-only
        STATUS current
        DESCRIPTION
            "Indicates the link status of the active port on the working NE."
        ::= { optixRtnNbplaStateEntry 6 }

    -- 1.3.6.1.4.1.2011.2.25.4.40.5.10.210.1.7
    optixRtnPLAMSState OBJECT-TYPE
        SYNTAX INTEGER
        {
            slave(0),
            master(1),
            unknown(255)
        }
        MAX-ACCESS read-only
        STATUS current
        DESCRIPTION
            "Indicates the current status (active/standby) of the active port on the working NE."
        ::= { optixRtnNbplaStateEntry 7 }

    -- 1.3.6.1.4.1.2011.2.25.4.40.5.10.221
    optixRtnCascading1j1PGAlmNewTable OBJECT-TYPE
        SYNTAX SEQUENCE OF OptixRtnCascading1j1PGAlmNewEntry
        MAX-ACCESS not-accessible
        STATUS current
        DESCRIPTION
            "Describes parameters about a cascading IF 1+1 protection group, including the IF board used in the protection group and the role of the IF board in the protection group."
        ::= { optixRtnIFProtect 221 }

    -- 1.3.6.1.4.1.2011.2.25.4.40.5.10.221.1
    optixRtnCascading1j1PGAlmNewEntry OBJECT-TYPE
        SYNTAX OptixRtnCascading1j1PGAlmNewEntry
        MAX-ACCESS not-accessible
        STATUS current
        DESCRIPTION
            "Indicates the parameter entry for a cascading IF 1+1 protection group."
        INDEX{ optixRtnCascading1j1PGID }
        ::= { optixRtnCascading1j1PGAlmNewTable 1 }

    OptixRtnCascading1j1PGAlmNewEntry ::=
        SEQUENCE {
            optixRtnCascading1j1PGsrvalmNew
                Unsigned32,
            optixRtnCascading1j1PGalmmomNew
                Unsigned32
        }
    -- 1.3.6.1.4.1.2011.2.25.4.40.5.10.221.1.1
    optixRtnCascading1j1PGsrvalmNew OBJECT-TYPE
        SYNTAX Unsigned32
        MAX-ACCESS read-write
        STATUS current
        DESCRIPTION
            "Indicates the protection group srvalm."
        ::= { optixRtnCascading1j1PGAlmNewEntry 1 }

    -- 1.3.6.1.4.1.2011.2.25.4.40.5.10.221.1.2
    optixRtnCascading1j1PGalmmomNew OBJECT-TYPE
        SYNTAX Unsigned32
	{
             reportIfBdAlm(1),
             report1J1PgAlm(2),
             reportIfBdAnd1J1PgAlm(3)
	}
        MAX-ACCESS read-write
        STATUS current
        DESCRIPTION
            "Indicates the IF board almmom."
        ::= { optixRtnCascading1j1PGAlmNewEntry 2 }

    -- 1.3.6.1.4.1.2011.2.25.4.40.5.10.230
    optixRtnNonCascade1j1StateParameterTable OBJECT-TYPE
        SYNTAX SEQUENCE OF OptixRtnNonCascade1j1StateParameterEntry
        MAX-ACCESS not-accessible
        STATUS current
        DESCRIPTION
            "Describes parameters about an FO IF 1+1 protection group, including the IF board used in the protection group and the role of the IF board in the protection group."
        ::= { optixRtnIFProtect 230 }

    -- 1.3.6.1.4.1.2011.2.25.4.40.5.10.230.1
    optixRtnNonCascade1j1StateParameterEntry OBJECT-TYPE
        SYNTAX OptixRtnNonCascade1j1StateParameterEntry
        MAX-ACCESS not-accessible
        STATUS current
        DESCRIPTION
            "Indicates the parameter entry for an FO IF 1+1 protection group."
        INDEX{ optixRtnCascading1j1PGrID }
        ::= { optixRtnNonCascade1j1StateParameterTable 1 }

    OptixRtnNonCascade1j1StateParameterEntry ::=
        SEQUENCE {
            optixRtnNonCascade1j1DevWorkBoardID
                Unsigned32,
            optixRtnNonCascade1j1DevWorkSubCardID
                Unsigned32,
            optixRtnNonCascade1j1DevWorkPortID
                Unsigned32,
            optixRtnNonCascade1j1DevWorkBoardState
                OPTIXRtn1j1PGBDStateType,
            optixRtnNonCascade1j1DevProtectBoardState
                OPTIXRtn1j1PGBDStateType,
            optixRtnNonCascade1j1DevSwtichRequest
                OPTIXRtn1j1SwtichRequestType,
            optixRtnNonCascade1j1LinkWorkBoardID
                Unsigned32,
            optixRtnNonCascade1j1LinkWorkSubCardID
                Unsigned32,
            optixRtnNonCascade1j1LinkWorkPortID
                Unsigned32,
            optixRtnNonCascade1j1WorkBoardLinkState
                OPTIXRtn1j1LinkStateType,
            optixRtnNonCascade1j1ProtectBoardLinkState
                OPTIXRtn1j1LinkStateType,
            optixRtnNonCascade1j1ProtectLinkSwitchRequest
                OPTIXRtn1j1SwtichRequestType,
            optixRtnNonCascade1j1RDIEnState
                INTEGER,
            optixRtnNonCascade1j1PGSwCmd
                INTEGER,
            optixRtnNonCascade1j1PGSwDir
                INTEGER
        }

    -- 1.3.6.1.4.1.2011.2.25.4.40.5.10.230.1.1
    optixRtnNonCascade1j1DevWorkBoardID OBJECT-TYPE
        SYNTAX Unsigned32
        MAX-ACCESS read-only
        STATUS current
        DESCRIPTION
            "Indicates the current working board ID on the equipment side."
        ::= { optixRtnNonCascade1j1StateParameterEntry 1 }

    -- 1.3.6.1.4.1.2011.2.25.4.40.5.10.230.1.2
    optixRtnNonCascade1j1DevWorkSubCardID OBJECT-TYPE
        SYNTAX Unsigned32
        MAX-ACCESS read-only
        STATUS current
        DESCRIPTION
            "Indicates the current working subboard ID on the equipment side."
        ::= { optixRtnNonCascade1j1StateParameterEntry 2 }

    -- 1.3.6.1.4.1.2011.2.25.4.40.5.10.230.1.3
    optixRtnNonCascade1j1DevWorkPortID OBJECT-TYPE
        SYNTAX Unsigned32
        MAX-ACCESS read-only
        STATUS current
        DESCRIPTION
            "Indicates the current working port ID on the equipment side."
        ::= { optixRtnNonCascade1j1StateParameterEntry 3 }

    -- 1.3.6.1.4.1.2011.2.25.4.40.5.10.230.1.4
    optixRtnNonCascade1j1DevWorkBoardState OBJECT-TYPE
        SYNTAX OPTIXRtn1j1PGBDStateType
        MAX-ACCESS read-only
        STATUS current
        DESCRIPTION
            "Indicates the working status of the main board on the equipment side. Values: 0: normal 1: switching 2: RDI switching 255: unknown"
        ::= { optixRtnNonCascade1j1StateParameterEntry 4 }

    -- 1.3.6.1.4.1.2011.2.25.4.40.5.10.230.1.5
    optixRtnNonCascade1j1DevProtectBoardState OBJECT-TYPE
        SYNTAX OPTIXRtn1j1PGBDStateType
        MAX-ACCESS read-only
        STATUS current
        DESCRIPTION
            "Indicates the working status of the standby board on the equipment side. Values: 0: normal 1: switching 2: RDI switching 255: unknown"
        ::= { optixRtnNonCascade1j1StateParameterEntry 5 }

    -- 1.3.6.1.4.1.2011.2.25.4.40.5.10.230.1.6
    optixRtnNonCascade1j1DevSwtichRequest OBJECT-TYPE
        SYNTAX OPTIXRtn1j1SwtichRequestType
        MAX-ACCESS read-only
        STATUS current
        DESCRIPTION
            "Indicates the switching request on the equipment side. Values: 0: normal 1: automatic 2: manual 3: forced 4: lockout 5: wait to restore 6: RDI"
        ::= { optixRtnNonCascade1j1StateParameterEntry 6 }

    -- 1.3.6.1.4.1.2011.2.25.4.40.5.10.230.1.7
    optixRtnNonCascade1j1LinkWorkBoardID OBJECT-TYPE
        SYNTAX Unsigned32
        MAX-ACCESS read-only
        STATUS current
        DESCRIPTION
            "Indicates the current working board ID on the link side."
        ::= { optixRtnNonCascade1j1StateParameterEntry 7 }

    -- 1.3.6.1.4.1.2011.2.25.4.40.5.10.230.1.8
    optixRtnNonCascade1j1LinkWorkSubCardID OBJECT-TYPE
        SYNTAX Unsigned32
        MAX-ACCESS read-only
        STATUS current
        DESCRIPTION
            "Indicates the current working subboard ID on the link side."
        ::= { optixRtnNonCascade1j1StateParameterEntry 8 }

    -- 1.3.6.1.4.1.2011.2.25.4.40.5.10.230.1.9
    optixRtnNonCascade1j1LinkWorkPortID OBJECT-TYPE
        SYNTAX Unsigned32
        MAX-ACCESS read-only
        STATUS current
        DESCRIPTION
            "Indicates the current working port ID on the link side."
        ::= { optixRtnNonCascade1j1StateParameterEntry 9 }

    -- 1.3.6.1.4.1.2011.2.25.4.40.5.10.230.1.10
    optixRtnNonCascade1j1WorkBoardLinkState OBJECT-TYPE
        SYNTAX OPTIXRtn1j1LinkStateType
        MAX-ACCESS read-only
        STATUS current
        DESCRIPTION
            "Indicates the signal status of the main board link. Values: 0: normal 1: signal failure 2: signal deterioration 255: invalid"
        ::= { optixRtnNonCascade1j1StateParameterEntry 10 }

    -- 1.3.6.1.4.1.2011.2.25.4.40.5.10.230.1.11
    optixRtnNonCascade1j1ProtectBoardLinkState OBJECT-TYPE
        SYNTAX OPTIXRtn1j1LinkStateType
        MAX-ACCESS read-only
        STATUS current
        DESCRIPTION
            "Indicates the signal status of the stanby board link. Values: 0: normal 1: signal failure 2: signal deterioration 255: invalid"
        ::= { optixRtnNonCascade1j1StateParameterEntry 11 }

    -- 1.3.6.1.4.1.2011.2.25.4.40.5.10.230.1.12
    optixRtnNonCascade1j1ProtectLinkSwitchRequest OBJECT-TYPE
        SYNTAX OPTIXRtn1j1SwtichRequestType
        MAX-ACCESS read-only
        STATUS current
        DESCRIPTION
            "Indicates the switching request on the link side. Values: 0: normal 1: automatic 3: forced"
        ::= { optixRtnNonCascade1j1StateParameterEntry 12 }

    -- 1.3.6.1.4.1.2011.2.25.4.40.5.10.230.1.13
    optixRtnNonCascade1j1RDIEnState OBJECT-TYPE
        SYNTAX INTEGER
        {
            disable(0),
            enbale(1)
        }
        MAX-ACCESS read-write
        STATUS current
        DESCRIPTION
            "Indicates the state of RDI"
        DEFVAL{ 1 }
        ::= { optixRtnNonCascade1j1StateParameterEntry 13 }

    -- 1.3.6.1.4.1.2011.2.25.4.40.5.10.230.1.14
    optixRtnNonCascade1j1PGSwCmd OBJECT-TYPE
        SYNTAX INTEGER
        {
            manual(0),
            force(1),
            lockout(2),
            clear(3)
        }
        MAX-ACCESS read-write
        STATUS current
        DESCRIPTION
            "Indicates the switch mode"
        DEFVAL{ 255 }
        ::= { optixRtnNonCascade1j1StateParameterEntry 14 }

    -- 1.3.6.1.4.1.2011.2.25.4.40.5.10.230.1.15
    optixRtnNonCascade1j1PGSwDir OBJECT-TYPE
        SYNTAX INTEGER
        {
            w2p(0),
            p2w(1)
        }
        MAX-ACCESS read-write
        STATUS current
        DESCRIPTION
            "Indicates the switch direction"
        DEFVAL{ 1 }
        ::= { optixRtnNonCascade1j1StateParameterEntry 15 }

    -- 1.3.6.1.4.1.2011.2.25.4.40.5.10.237 
    optixRtnCfgEplaThroughAttrTable OBJECT-TYPE
        SYNTAX SEQUENCE OF OptixRtnCfgEplaThroughAttrEntry
        MAX-ACCESS not-accessible
        STATUS current
        DESCRIPTION
            ""
        ::= { optixRtnIFProtect 237 }

    -- 1.3.6.1.4.1.2011.2.25.4.40.5.10.237.1
    optixRtnCfgEplaThroughAttrEntry OBJECT-TYPE
        SYNTAX OptixRtnCfgEplaThroughAttrEntry
        MAX-ACCESS not-accessible
        STATUS current
        DESCRIPTION
            ""
        INDEX{ optixRtngroupIndex,optixRtnboardIndex,optixRtnsubboardIndex,optixRtnportIndex}
        ::= { optixRtnCfgEplaThroughAttrTable 1 }

    OptixRtnCfgEplaThroughAttrEntry ::=
        SEQUENCE {
            optixRtnCfgEplaThroughAttrDeviceType 
            	Unsigned32,
            optixRtnCfgEplaThroughAttrBandWidth 
            	Unsigned32,
            optixRtnCfgEplaThroughAttrVlanId 
            	Unsigned32,
            optixRtnCfgEplaThroughAttrMainboardID 
            	Unsigned32,
            optixRtnCfgEplaThroughAttrMianSubboardID 
            	Unsigned32,
            optixRtnCfgEplaThroughAttrMianPortID 
            	Unsigned32				
        }
  
    -- 1.3.6.1.4.1.2011.2.25.4.40.5.10.237.1.5
    optixRtnCfgEplaThroughAttrDeviceType OBJECT-TYPE
        SYNTAX   Unsigned32        
	{
		huawei(0),
		third-Party(1)
	}
        MAX-ACCESS read-write
        STATUS current
        DESCRIPTION
            "device type"
        ::= { optixRtnCfgEplaThroughAttrEntry 5 }
		
    -- 1.3.6.1.4.1.2011.2.25.4.40.5.10.237.1.6
    optixRtnCfgEplaThroughAttrBandWidth OBJECT-TYPE
        SYNTAX   Unsigned32 		
        MAX-ACCESS read-write
        STATUS current
        DESCRIPTION
            "band width"
        ::= { optixRtnCfgEplaThroughAttrEntry 6 }
		
    -- 1.3.6.1.4.1.2011.2.25.4.40.5.10.237.1.7
    optixRtnCfgEplaThroughAttrVlanId OBJECT-TYPE
        SYNTAX   Unsigned32        
        MAX-ACCESS read-write
        STATUS current
        DESCRIPTION
            "vlanid"
        ::= { optixRtnCfgEplaThroughAttrEntry 7 }

    -- 1.3.6.1.4.1.2011.2.25.4.40.5.10.237.1.8
    optixRtnCfgEplaThroughAttrMainboardID OBJECT-TYPE
        SYNTAX   Unsigned32        
        MAX-ACCESS read-write
        STATUS current
        DESCRIPTION
            "epla mian boardid"
        ::= { optixRtnCfgEplaThroughAttrEntry 8 }

    -- 1.3.6.1.4.1.2011.2.25.4.40.5.10.237.1.9
    optixRtnCfgEplaThroughAttrMianSubboardID OBJECT-TYPE
        SYNTAX   Unsigned32        
        MAX-ACCESS read-write
        STATUS current
        DESCRIPTION
            "epla mian subboardid"
        ::= { optixRtnCfgEplaThroughAttrEntry 9 }		

    -- 1.3.6.1.4.1.2011.2.25.4.40.5.10.237.1.10
    optixRtnCfgEplaThroughAttrMianPortID OBJECT-TYPE
        SYNTAX   Unsigned32        
        MAX-ACCESS read-write
        STATUS current
        DESCRIPTION
            "epla mian portid"
        ::= { optixRtnCfgEplaThroughAttrEntry 10 }
		
 -- 1.3.6.1.4.1.2011.2.25.4.40.5.10.238
    optixRtnCCEnableTable OBJECT-TYPE
        SYNTAX SEQUENCE OF OptixRtnCCEnableEntry
        MAX-ACCESS not-accessible
        STATUS current
        DESCRIPTION
            "Describes the state of the CC enable parameter in an EPLA protection group ."
        ::= { optixRtnIFProtect 238 }

    -- 1.3.6.1.4.1.2011.2.25.4.40.5.10.238.1
    optixRtnCCEnableEntry OBJECT-TYPE
        SYNTAX OptixRtnCCEnableEntry
        MAX-ACCESS not-accessible
        STATUS current
        DESCRIPTION
            "Indicates the entry for enabling CC for an EPLA protection group."
        INDEX{ optixRtnCCEnablePGID,optixRtnCCEnablePGType }
        ::= { optixRtnCCEnableTable 1 }

    OptixRtnCCEnableEntry ::=
        SEQUENCE {
            optixRtnCCEnablePGID
                Unsigned32,
            optixRtnCCEnablePGType
                OPTIXRtnPhyLagPGType,
            optixRtnCCEnable
                INTEGER
        }

    -- 1.3.6.1.4.1.2011.2.25.4.40.5.10.238.1.1
    optixRtnCCEnablePGID OBJECT-TYPE
        SYNTAX Unsigned32 (1..12)
        MAX-ACCESS not-accessible
        STATUS current
        DESCRIPTION
            "Indicates the ID of an EPLA protection group."
        ::= { optixRtnCCEnableEntry 1 }

    -- 1.3.6.1.4.1.2011.2.25.4.40.5.10.238.1.2
    optixRtnCCEnablePGType OBJECT-TYPE
        SYNTAX OPTIXRtnPhyLagPGType
        MAX-ACCESS not-accessible
        STATUS current
        DESCRIPTION
            "Indicates the protection group type. Values: 0: pla 1: epla 2: nbpla 3: nbepla 4: eplaplus"
        ::= { optixRtnCCEnableEntry 2 }

    -- 1.3.6.1.4.1.2011.2.25.4.40.5.10.238.1.3
    optixRtnCCEnable OBJECT-TYPE
        SYNTAX INTEGER
        {
            disable(0),
            enable(1)
        }
        MAX-ACCESS read-write
        STATUS current
        DESCRIPTION
            "Indicates the state of the  CC enable parameter in an EPLA protection group."
        DEFVAL{ 0 }
        ::= { optixRtnCCEnableEntry 3 }	

    -- 1.3.6.1.4.1.2011.2.25.4.40.5.10.240
    optixRtnNonCascadePLAParameterTable OBJECT-TYPE
        SYNTAX SEQUENCE OF OptixRtnNonCascadePLAParameterEntry
        MAX-ACCESS not-accessible
        STATUS current
        DESCRIPTION
            "Describes configuration parameters for the working board and protection board in a cascading PLA/EPLA protection group."
        ::= { optixRtnIFProtect 240 }

    -- 1.3.6.1.4.1.2011.2.25.4.40.5.10.240.1
    optixRtnNonCascadePLAParameterEntry OBJECT-TYPE
        SYNTAX OptixRtnNonCascadePLAParameterEntry
        MAX-ACCESS not-accessible
        STATUS current
        DESCRIPTION
            "Indicates the parameter entry for a cascading PLA/EPLA protection group."
        INDEX{ optixRtnPhyLagPGID }
        ::= { optixRtnNonCascadePLAParameterTable 1 }

    OptixRtnNonCascadePLAParameterEntry ::=
        SEQUENCE {
            optixRtnNonCascadePLAPGType
                OPTIXRtnPhyLagPGType,
            optixRtnNonCascadePLAPGMainSlotID
                Unsigned32,
            optixRtnNonCascadePLAPGMainSubCardID
                Unsigned32,
            optixRtnNonCascadePLAPGMainPortID
                Unsigned32,
            optixRtnNonCascadePLAPGSlaveMemsInfo
                OCTET STRING,
            optixRtnNonCascadePLAPGLinkThreshold
                Unsigned32,
            optixRtnNonCascadePLAPGRowStatus
                RowStatus
        }

    -- 1.3.6.1.4.1.2011.2.25.4.40.5.10.240.1.1
    optixRtnNonCascadePLAPGType OBJECT-TYPE
        SYNTAX OPTIXRtnPhyLagPGType
        MAX-ACCESS read-create
        STATUS current
        DESCRIPTION
            "Indicates the protection group type. Values: 0: PLA 1: EPLA 2: cascading PLA 3:cascading EPLA"
        ::= { optixRtnNonCascadePLAParameterEntry 1 }

    -- 1.3.6.1.4.1.2011.2.25.4.40.5.10.240.1.2
    optixRtnNonCascadePLAPGMainSlotID OBJECT-TYPE
        SYNTAX Unsigned32
        MAX-ACCESS read-create
        STATUS current
        DESCRIPTION
            "Indicates the slot ID of the main port."
        ::= { optixRtnNonCascadePLAParameterEntry 2 }

    -- 1.3.6.1.4.1.2011.2.25.4.40.5.10.240.1.3
    optixRtnNonCascadePLAPGMainSubCardID OBJECT-TYPE
        SYNTAX Unsigned32
        MAX-ACCESS read-create
        STATUS current
        DESCRIPTION
            "Indicates the subboard ID of the main port."
        ::= { optixRtnNonCascadePLAParameterEntry 3 }

    -- 1.3.6.1.4.1.2011.2.25.4.40.5.10.240.1.4
    optixRtnNonCascadePLAPGMainPortID OBJECT-TYPE
        SYNTAX Unsigned32
        MAX-ACCESS read-create
        STATUS current
        DESCRIPTION
            "Indicates the port number of the main port."
        ::= { optixRtnNonCascadePLAParameterEntry 4 }

    -- 1.3.6.1.4.1.2011.2.25.4.40.5.10.240.1.5
    optixRtnNonCascadePLAPGSlaveMemsInfo OBJECT-TYPE
        SYNTAX OCTET STRING
        MAX-ACCESS read-create
        STATUS current
        DESCRIPTION
            "Indicates the slave port information of the protection group."
        ::= { optixRtnNonCascadePLAParameterEntry 5 }

    -- 1.3.6.1.4.1.2011.2.25.4.40.5.10.240.1.6
    optixRtnNonCascadePLAPGLinkThreshold OBJECT-TYPE
        SYNTAX Unsigned32
        MAX-ACCESS read-create
        STATUS current
        DESCRIPTION
            "Indicates the minimum number of active links in the protection group."
        ::= { optixRtnNonCascadePLAParameterEntry 6 }

    -- 1.3.6.1.4.1.2011.2.25.4.40.5.10.240.1.50
    optixRtnNonCascadePLAPGRowStatus OBJECT-TYPE
        SYNTAX RowStatus
        MAX-ACCESS read-create
        STATUS current
        DESCRIPTION
            "Indicates the row status of the protection group."
        DEFVAL{ active }
        ::= { optixRtnNonCascadePLAParameterEntry 50 }

    -- 1.3.6.1.4.1.2011.2.25.4.40.5.10.250
    optixRtnNonCascadePLAPGStateTable OBJECT-TYPE
        SYNTAX SEQUENCE OF OptixRtnNonCascadePLAPGStateEntry
        MAX-ACCESS not-accessible
        STATUS current
        DESCRIPTION
            "Describes parameters about a PLA protection group, including the current working board and the switching status of a protection group."
        ::= { optixRtnIFProtect 250 }

    -- 1.3.6.1.4.1.2011.2.25.4.40.5.10.250.1
    optixRtnNonCascadePLAPGStateEntry OBJECT-TYPE
        SYNTAX OptixRtnNonCascadePLAPGStateEntry
        MAX-ACCESS not-accessible
        STATUS current
        DESCRIPTION
            "Indicates status entry for a PLA protection group."
        INDEX{ optixRtnPhyLagPGID }
        ::= { optixRtnNonCascadePLAPGStateTable 1 }

    OptixRtnNonCascadePLAPGStateEntry ::=
        SEQUENCE {
            optixRtnNonCascadePLAMainBoardID
                Unsigned32,
            optixRtnNonCascadePLAMainSubCardID
                Unsigned32,
            optixRtnNonCascadePLAMainPortID
                Unsigned32,
            optixRtnNonCascadePLAMainHardStatus
                OPTIXRtnPhyLagPGStatus,
            optixRtnNonCascadePLAMainLinkStatus
                OPTIXRtnPhyLagPGStatus,
            optixRtnNonCascadePLAMainPuWorkStatus
                OPTIXRtnPhyLagPGStateWorkStatus,
            optixRtnNonCascadePLASlavePuNum
                Unsigned32,
            optixRtnNonCascadePLAPu1BoardID
                Unsigned32,
            optixRtnNonCascadePLAPu1SubCardID
                Unsigned32,
            optixRtnNonCascadePLAPu1PortID
                Unsigned32,
            optixRtnNonCascadePLAPu1HardStatus
                OPTIXRtnPhyLagPGStatus,
            optixRtnNonCascadePLAPu1LinkStatus
                OPTIXRtnPhyLagPGStatus,
            optixRtnNonCascadePLAPu1WorkStatus
                OPTIXRtnPhyLagPGStateWorkStatus
        }

    -- 1.3.6.1.4.1.2011.2.25.4.40.5.10.250.1.1
    optixRtnNonCascadePLAMainBoardID OBJECT-TYPE
        SYNTAX Unsigned32
        MAX-ACCESS read-only
        STATUS current
        DESCRIPTION
            "Indicates the main unit slot ID."
        ::= { optixRtnNonCascadePLAPGStateEntry 1 }

    -- 1.3.6.1.4.1.2011.2.25.4.40.5.10.250.1.2
    optixRtnNonCascadePLAMainSubCardID OBJECT-TYPE
        SYNTAX Unsigned32
        MAX-ACCESS read-only
        STATUS current
        DESCRIPTION
            "Indicates the main unit subboard ID."
        ::= { optixRtnNonCascadePLAPGStateEntry 2 }

    -- 1.3.6.1.4.1.2011.2.25.4.40.5.10.250.1.3
    optixRtnNonCascadePLAMainPortID OBJECT-TYPE
        SYNTAX Unsigned32
        MAX-ACCESS read-only
        STATUS current
        DESCRIPTION
            "Indicates the main unit port ID."
        ::= { optixRtnNonCascadePLAPGStateEntry 3 }

    -- 1.3.6.1.4.1.2011.2.25.4.40.5.10.250.1.4
    optixRtnNonCascadePLAMainHardStatus OBJECT-TYPE
        SYNTAX OPTIXRtnPhyLagPGStatus
        MAX-ACCESS read-only
        STATUS current
        DESCRIPTION
            "Indicates the hardware status of the main unit. The values: 0: normal 1: abnormal -1: unknown"
        ::= { optixRtnNonCascadePLAPGStateEntry 4 }

    -- 1.3.6.1.4.1.2011.2.25.4.40.5.10.250.1.5
    optixRtnNonCascadePLAMainLinkStatus OBJECT-TYPE
        SYNTAX OPTIXRtnPhyLagPGStatus
        MAX-ACCESS read-only
        STATUS current
        DESCRIPTION
            "Indicates the link status of the main unit. Values: 0: normal 1: abnormal -1: unknown"
        ::= { optixRtnNonCascadePLAPGStateEntry 5 }

    -- 1.3.6.1.4.1.2011.2.25.4.40.5.10.250.1.6
    optixRtnNonCascadePLAMainPuWorkStatus OBJECT-TYPE
        SYNTAX OPTIXRtnPhyLagPGStateWorkStatus
        MAX-ACCESS read-only
        STATUS current
        DESCRIPTION
            "Indicates the working status of the main unit. Values: 0: slave port 1: main port"
        ::= { optixRtnNonCascadePLAPGStateEntry 6 }

    -- 1.3.6.1.4.1.2011.2.25.4.40.5.10.250.1.7
    optixRtnNonCascadePLASlavePuNum OBJECT-TYPE
        SYNTAX Unsigned32
        MAX-ACCESS read-only
        STATUS current
        DESCRIPTION
            "Indicates the number of slave units. Value range: 1 to 3"
        ::= { optixRtnNonCascadePLAPGStateEntry 7 }

    -- 1.3.6.1.4.1.2011.2.25.4.40.5.10.250.1.8
    optixRtnNonCascadePLAPu1BoardID OBJECT-TYPE
        SYNTAX Unsigned32
        MAX-ACCESS read-only
        STATUS current
        DESCRIPTION
            "Indicates the slave unit 1 slot ID."
        ::= { optixRtnNonCascadePLAPGStateEntry 8 }

    -- 1.3.6.1.4.1.2011.2.25.4.40.5.10.250.1.9
    optixRtnNonCascadePLAPu1SubCardID OBJECT-TYPE
        SYNTAX Unsigned32
        MAX-ACCESS read-only
        STATUS current
        DESCRIPTION
            "Indicates the slave unit 1 subboard ID."
        ::= { optixRtnNonCascadePLAPGStateEntry 9 }

    -- 1.3.6.1.4.1.2011.2.25.4.40.5.10.250.1.10
    optixRtnNonCascadePLAPu1PortID OBJECT-TYPE
        SYNTAX Unsigned32
        MAX-ACCESS read-only
        STATUS current
        DESCRIPTION
            "Indicates the slave unit 1 port ID."
        ::= { optixRtnNonCascadePLAPGStateEntry 10 }

    -- 1.3.6.1.4.1.2011.2.25.4.40.5.10.250.1.11
    optixRtnNonCascadePLAPu1HardStatus OBJECT-TYPE
        SYNTAX OPTIXRtnPhyLagPGStatus
        MAX-ACCESS read-only
        STATUS current
        DESCRIPTION
            "Indicates the slave unit 1 hardware status. Values: 0: normal 1: abnormal -1: unknown"
        ::= { optixRtnNonCascadePLAPGStateEntry 11 }

    -- 1.3.6.1.4.1.2011.2.25.4.40.5.10.250.1.12
    optixRtnNonCascadePLAPu1LinkStatus OBJECT-TYPE
        SYNTAX OPTIXRtnPhyLagPGStatus
        MAX-ACCESS read-only
        STATUS current
        DESCRIPTION
            "Indicates the slave unit 1 link status. Values: 0: normal 1: abnormal -1: unknown"
        ::= { optixRtnNonCascadePLAPGStateEntry 12 }

    -- 1.3.6.1.4.1.2011.2.25.4.40.5.10.250.1.13
    optixRtnNonCascadePLAPu1WorkStatus OBJECT-TYPE
        SYNTAX OPTIXRtnPhyLagPGStateWorkStatus
        MAX-ACCESS read-only
        STATUS current
        DESCRIPTION
            "Indicates the slave unit 1 working status. Values: 0: slave port 1: main port"
        ::= { optixRtnNonCascadePLAPGStateEntry 13 }

    -- 1.3.6.1.4.1.2011.2.25.4.40.5.10.260
    optixRtnPlaMinuplkthExtTable OBJECT-TYPE
       	SYNTAX SEQUENCE OF OptixRtnPlaMinuplkthExtEntry
        MAX-ACCESS not-accessible
        STATUS current
        DESCRIPTION
          "Pla Minuplkth Table ."
        ::= { optixRtnIFProtect 260 } 
        
    -- 1.3.6.1.4.1.2011.2.25.4.40.5.10.260.1
    optixRtnPlaMinuplkthExtEntry OBJECT-TYPE
        SYNTAX OptixRtnPlaMinuplkthExtEntry
        MAX-ACCESS not-accessible
        STATUS current
        DESCRIPTION
            "Pla Minuplkth Entry"
        INDEX{ optixRtnIndex1 }
        ::= { optixRtnPlaMinuplkthExtTable 1 } 
            
    OptixRtnPlaMinuplkthExtEntry ::=
    	SEQUENCE {
            optixRtnIPGMinuplink
            	Unsigned32        
    	} 
   
    -- 1.3.6.1.4.1.2011.2.25.4.40.5.10.260.1.1
    optixRtnIPGMinuplink OBJECT-TYPE
        SYNTAX Unsigned32
        MAX-ACCESS read-write
        STATUS current
        DESCRIPTION
            "Indicats the protection Pla Minuplkth."
        ::= { optixRtnPlaMinuplkthExtEntry 1 }

    -- 1.3.6.1.4.1.2011.2.25.4.40.5.10.280
    optixRtnPlaWtrTimeTable OBJECT-TYPE
       	SYNTAX SEQUENCE OF OptixRtnPlaWtrTimeEntry
        MAX-ACCESS not-accessible
        STATUS current
        DESCRIPTION
          "Pla wtr-time Table ."
        ::= { optixRtnIFProtect 280 } 
        
    -- 1.3.6.1.4.1.2011.2.25.4.40.5.10.280.1
    optixRtnPlaWtrTimeEntry OBJECT-TYPE
        SYNTAX OptixRtnPlaWtrTimeEntry
        MAX-ACCESS not-accessible
        STATUS current
        DESCRIPTION
            "Pla wtr-time Entry"
        INDEX{ optixRtnIndex1 }
        ::= { optixRtnPlaWtrTimeTable 1 } 
            
    OptixRtnPlaWtrTimeEntry ::=
    	SEQUENCE {
            optixRtnEplaWtrState
            	INTEGER,
            optixRtnEplaWtrTime
            	Unsigned32                
    	} 
   
    -- 1.3.6.1.4.1.2011.2.25.4.40.5.10.280.1.2
    optixRtnEplaWtrState OBJECT-TYPE
        SYNTAX INTEGER
        {
            disable(0),
            enable(1)
        }        
        MAX-ACCESS read-write
        STATUS current
        DESCRIPTION
            "Indicats the protection Pla wtr-state."
        ::= { optixRtnPlaWtrTimeEntry 2 }
        
    -- 1.3.6.1.4.1.2011.2.25.4.40.5.10.280.1.3
    optixRtnEplaWtrTime OBJECT-TYPE
        SYNTAX Unsigned32
        MAX-ACCESS read-write
        STATUS current
        DESCRIPTION
            "Indicats the protection Pla wtr-time."
        ::= { optixRtnPlaWtrTimeEntry 3 }  

    -- 1.3.6.1.4.1.2011.2.25.4.40.5.10.281
    optixRtnPlaForceSwitchTable OBJECT-TYPE
       	SYNTAX SEQUENCE OF OptixRtnPlaForceSwitchEntry
        MAX-ACCESS not-accessible
        STATUS current
        DESCRIPTION
          "Pla Force Switch Table."
        ::= { optixRtnIFProtect 281 } 

    -- 1.3.6.1.4.1.2011.2.25.4.40.5.10.281.1
    optixRtnPlaForceSwitchEntry OBJECT-TYPE
        SYNTAX OptixRtnPlaForceSwitchEntry
        MAX-ACCESS not-accessible
        STATUS current
        DESCRIPTION
            "Pla Force Switch Entry"
        INDEX{ optixRtnPlaGroupIndex, optixRtnPlaBoardIndex, optixRtnPlaSubboardIndex, optixRtnPlaPortIndex, optixPlaChannelIdIndex}
        ::= { optixRtnPlaForceSwitchTable 1 } 
            
    OptixRtnPlaForceSwitchEntry ::=
    	SEQUENCE {
            optixRtnPlaGroupIndex
                Unsigned32,
            optixRtnPlaBoardIndex
                Unsigned32,
            optixRtnPlaSubboardIndex
                Unsigned32,
            optixRtnPlaPortIndex
                Unsigned32,
            optixPlaChannelIdIndex
                Unsigned32,
            optixRtnPlaForceSwitchLocalStatus
                INTEGER,
            optixRtnPlaForceSwitchRemoteStatus
                INTEGER
    }

    -- 1.3.6.1.4.1.2011.2.25.4.40.5.10.281.1.1
    optixRtnPlaGroupIndex OBJECT-TYPE
        SYNTAX Unsigned32
        MAX-ACCESS not-accessible
        STATUS current
        DESCRIPTION
            "Indicates the Pla groupIndex."
        ::= { optixRtnPlaForceSwitchEntry 1 }

    -- 1.3.6.1.4.1.2011.2.25.4.40.5.10.281.1.2
    optixRtnPlaBoardIndex OBJECT-TYPE
        SYNTAX Unsigned32
        MAX-ACCESS not-accessible
        STATUS current
        DESCRIPTION
            "Indicates the Pla boardIndex."
        ::= { optixRtnPlaForceSwitchEntry 2 }

    -- 1.3.6.1.4.1.2011.2.25.4.40.5.10.281.1.3
    optixRtnPlaSubboardIndex OBJECT-TYPE
        SYNTAX Unsigned32
        MAX-ACCESS not-accessible
        STATUS current
        DESCRIPTION
            "Indicates the Pla subboardIndex."
        ::= { optixRtnPlaForceSwitchEntry 3 }

    -- 1.3.6.1.4.1.2011.2.25.4.40.5.10.281.1.4
    optixRtnPlaPortIndex OBJECT-TYPE
        SYNTAX Unsigned32
        MAX-ACCESS not-accessible
        STATUS current
        DESCRIPTION
            "Indicates the Pla portIndex."
        ::= { optixRtnPlaForceSwitchEntry 4 }

    -- 1.3.6.1.4.1.2011.2.25.4.40.5.10.281.1.5
    optixPlaChannelIdIndex OBJECT-TYPE
        SYNTAX Unsigned32
        MAX-ACCESS not-accessible
        STATUS current
        DESCRIPTION
            "Indicates the Pla ChannelIdIndex."
        ::= { optixRtnPlaForceSwitchEntry 5 }

    -- 1.3.6.1.4.1.2011.2.25.4.40.5.10.281.1.6
    optixRtnPlaForceSwitchLocalStatus OBJECT-TYPE
        SYNTAX INTEGER
        {
            disable(0),
            enable(1)
        }
        MAX-ACCESS read-write
        STATUS current
        DESCRIPTION
            "Indicats the protection Pla Force Switch Local Status."
        ::= { optixRtnPlaForceSwitchEntry 6 }

    -- 1.3.6.1.4.1.2011.2.25.4.40.5.10.281.1.7
    optixRtnPlaForceSwitchRemoteStatus OBJECT-TYPE
        SYNTAX INTEGER
        {
            disable(0),
            enable(1)
        }
        MAX-ACCESS read-only
        STATUS current
        DESCRIPTION
            "Indicats the protection Pla Force Switch Remote Status."
        ::= { optixRtnPlaForceSwitchEntry 7 }

    -- 1.3.6.1.4.1.2011.2.25.4.40.5.10.290
    optixRtnComboStatTable OBJECT-TYPE
       	SYNTAX SEQUENCE OF OptixRtnComboStatEntry
        MAX-ACCESS not-accessible
        STATUS current
        DESCRIPTION
          "combo port Table ."
        ::= { optixRtnIFProtect 290 } 
        
   -- 1.3.6.1.4.1.2011.2.25.4.40.5.10.290.1
   optixRtnComboStatEntry OBJECT-TYPE
        SYNTAX OptixRtnComboStatEntry
        MAX-ACCESS not-accessible
        STATUS current
        DESCRIPTION
            "combo port Entry"
        INDEX{ optixRtnIndex1,optixRtnIndex2,optixRtnIndex3 }
        ::= { optixRtnComboStatTable 1 } 
            
    OptixRtnComboStatEntry ::=
    	SEQUENCE {
            optixRtnComboState
            	INTEGER               
    	} 
   
    -- 1.3.6.1.4.1.2011.2.25.4.40.5.10.290.1.4
    optixRtnComboState OBJECT-TYPE
        SYNTAX INTEGER
        {
            disable(0),
            xpic(1),
            ca(2)
        }        
        MAX-ACCESS read-write
        STATUS current
        DESCRIPTION
            "Indicats the combo port state."
        ::= { optixRtnComboStatEntry 4 }
        
    -- 1.3.6.1.4.1.2011.2.25.4.40.5.10.300
    optixRtnPLAGroupTable OBJECT-TYPE
        SYNTAX SEQUENCE OF OptixRtnPLAGroupEntry
        MAX-ACCESS not-accessible
        STATUS current
        DESCRIPTION
            "Describes configuration parameters for the working board and protection board in a Test PLA protection group."
        ::= { optixRtnIFProtect 300 }

    -- 1.3.6.1.4.1.2011.2.25.4.40.5.10.300.1
    optixRtnPLAGroupEntry OBJECT-TYPE
        SYNTAX OptixRtnPLAGroupEntry
        MAX-ACCESS not-accessible
        STATUS current
        DESCRIPTION
            "Indicates the parameter entry for a Test PLA protection group."
        INDEX{ optixRtnIndex1 }
        ::= { optixRtnPLAGroupTable 1 }

    OptixRtnPLAGroupEntry ::=
        SEQUENCE {
            optixRtnPLAGroupID
                Unsigned32,
            optixRtnPLAGroupMainBoardID
                Unsigned32,
            optixRtnPLAGroupMainSubCardID
                Unsigned32,
            optixRtnPLAGroupMainPortID
                Unsigned32,
            optixRtnPLAGroupCascadingPuNum
                Unsigned32,
            optixRtnPLAGroupPu1BoardID
                Unsigned32,
            optixRtnPLAGroupPu1SubCardID
                Unsigned32,
            optixRtnPLAGroupPu1PortID
                Unsigned32,
            optixRtnPLAGroupCfgRowStatus
                RowStatus
        }

    -- 1.3.6.1.4.1.2011.2.25.4.40.5.10.300.1.1
    optixRtnPLAGroupID OBJECT-TYPE
        SYNTAX Unsigned32
        MAX-ACCESS not-accessible
        STATUS current
        DESCRIPTION
            "Indicats the protection group ID."
        ::= { optixRtnPLAGroupEntry 1 }

    -- 1.3.6.1.4.1.2011.2.25.4.40.5.10.300.1.2
    optixRtnPLAGroupMainBoardID OBJECT-TYPE
        SYNTAX Unsigned32
        MAX-ACCESS read-create
        STATUS current
        DESCRIPTION
            "Indicates the slot ID of the main unit."
        ::= { optixRtnPLAGroupEntry 2 }

    -- 1.3.6.1.4.1.2011.2.25.4.40.5.10.300.1.3
    optixRtnPLAGroupMainSubCardID OBJECT-TYPE
        SYNTAX Unsigned32
        MAX-ACCESS read-create
        STATUS current
        DESCRIPTION
            "Indicates the subboard ID of the main unit."
        ::= { optixRtnPLAGroupEntry 3 }

    -- 1.3.6.1.4.1.2011.2.25.4.40.5.10.300.1.4
    optixRtnPLAGroupMainPortID OBJECT-TYPE
        SYNTAX Unsigned32
        MAX-ACCESS read-create
        STATUS current
        DESCRIPTION
            "Indicates the port ID of the main unit."
        ::= { optixRtnPLAGroupEntry 4 }

    -- 1.3.6.1.4.1.2011.2.25.4.40.5.10.300.1.5
    optixRtnPLAGroupCascadingPuNum OBJECT-TYPE
        SYNTAX Unsigned32
        MAX-ACCESS read-create
        STATUS current
        DESCRIPTION
            "Indicates the number of Test ports. Value range: 1 to 3"
        DEFVAL{ 1 }
        ::= { optixRtnPLAGroupEntry 5 }

    -- 1.3.6.1.4.1.2011.2.25.4.40.5.10.300.1.6
    optixRtnPLAGroupPu1BoardID OBJECT-TYPE
        SYNTAX Unsigned32
        MAX-ACCESS read-only
        STATUS current
        DESCRIPTION
            "Indicates the board ID of the Test unit 1."
        ::= { optixRtnPLAGroupEntry 6 }

    -- 1.3.6.1.4.1.2011.2.25.4.40.5.10.300.1.7
    optixRtnPLAGroupPu1SubCardID OBJECT-TYPE
        SYNTAX Unsigned32
        MAX-ACCESS read-only
        STATUS current
        DESCRIPTION
            "Indicates the subboard ID of the Test unit 1."
        ::= { optixRtnPLAGroupEntry 7 }

    -- 1.3.6.1.4.1.2011.2.25.4.40.5.10.300.1.8
    optixRtnPLAGroupPu1PortID OBJECT-TYPE
        SYNTAX Unsigned32
        MAX-ACCESS read-only
        STATUS current
        DESCRIPTION
            "Indicates the port ID of the Test unit 1."
        ::= { optixRtnPLAGroupEntry 8 }

    -- 1.3.6.1.4.1.2011.2.25.4.40.5.10.300.1.50
    optixRtnPLAGroupCfgRowStatus OBJECT-TYPE
        SYNTAX RowStatus
        MAX-ACCESS read-create
        STATUS current
        DESCRIPTION
            "Indicates the row status of a protection group"
        DEFVAL{ active }
        ::= { optixRtnPLAGroupEntry 50 }

    -- 1.3.6.1.4.1.2011.2.25.4.40.5.10.340
    optixRtnEnergySaveStrategyTable OBJECT-TYPE
        SYNTAX SEQUENCE OF OptixRtnEnergySaveStrategyEntry
        MAX-ACCESS not-accessible
        STATUS current
        DESCRIPTION 
            "Indicate the table of energysave strategy"
        ::= { optixRtnIFProtect 340 }
    
    -- 1.3.6.1.4.1.2011.2.25.4.40.5.10.340.1
    optixRtnEnergySaveStrategyEntry OBJECT-TYPE
        SYNTAX OptixRtnEnergySaveStrategyEntry
        MAX-ACCESS not-accessible
        STATUS current
        DESCRIPTION
            "Indicates the entries of energysave strategy"
        INDEX {optixRtnStrategyGroupID}
        ::= { optixRtnEnergySaveStrategyTable 1 }

    OptixRtnEnergySaveStrategyEntry ::=
        SEQUENCE {
            optixRtnStrategyGroupID
                Unsigned32,
            optixRtnStrategyState
                INTEGER,
            optixRtnStrategyType
                OPTIXRtnStrategyType,
            optixRtnStrategyHighThresHold
                Unsigned32,
            optixRtnStrategyLowThresHold
                Unsigned32,
            optixRtnStrategyStartHoldTime
                Unsigned32,
            optixRtnStrategyEndHoldTime
                Unsigned32,
            optixRtnStrategyStartTime
                Unsigned32,
            optixRtnStrategyEndTime
                Unsigned32,
            optixRtnStrategyCfgRowStatus
                RowStatus
        }

    -- 1.3.6.1.4.1.2011.2.25.4.40.5.10.340.1.1
    optixRtnStrategyGroupID OBJECT-TYPE
        SYNTAX Unsigned32
        MAX-ACCESS not-accessible
        STATUS current
        DESCRIPTION
            "Indicates the energysave group ID"
        ::= { optixRtnEnergySaveStrategyEntry 1 }
    
    -- 1.3.6.1.4.1.2011.2.25.4.40.5.10.340.1.2
    optixRtnStrategyState OBJECT-TYPE
        SYNTAX INTEGER
        {
            disable(0),
            enable(1)
        }
        MAX-ACCESS read-create
        STATUS current
        DESCRIPTION
            "Indicates the state of the energysave group"
        DEFVAL{0}
        ::= { optixRtnEnergySaveStrategyEntry 2 }
    
    -- 1.3.6.1.4.1.2011.2.25.4.40.5.10.340.1.3
    optixRtnStrategyType OBJECT-TYPE
        SYNTAX OPTIXRtnStrategyType
        MAX-ACCESS read-create
        STATUS current
        DESCRIPTION
            "Indicates the type of energy save group. 0: green"
        DEFVAL{0}
        ::= { optixRtnEnergySaveStrategyEntry 3 }
    
    -- 1.3.6.1.4.1.2011.2.25.4.40.5.10.340.1.4
    optixRtnStrategyHighThresHold OBJECT-TYPE
        SYNTAX Unsigned32
        MAX-ACCESS read-create
        STATUS current
        DESCRIPTION
            "Indicates the high threshold of energysave group. Range:(0 ~ 100), low < high"
        ::= { optixRtnEnergySaveStrategyEntry 4 }
    
    -- 1.3.6.1.4.1.2011.2.25.4.40.5.10.340.1.5
    optixRtnStrategyLowThresHold OBJECT-TYPE
        SYNTAX Unsigned32
        MAX-ACCESS read-create
        STATUS current
        DESCRIPTION
            "Indicates the low threshold of energysave group. Range:(0 ~ 100]), low < high"
        ::= { optixRtnEnergySaveStrategyEntry 5 }

    -- 1.3.6.1.4.1.2011.2.25.4.40.5.10.340.1.6
    optixRtnStrategyStartHoldTime OBJECT-TYPE
        SYNTAX Unsigned32
        MAX-ACCESS read-create
        STATUS current
        DESCRIPTION
            "Inidcates the start filt time of energysave. Unit: second, range:[0,3600]."
        ::= { optixRtnEnergySaveStrategyEntry 6 }

    -- 1.3.6.1.4.1.2011.2.25.4.40.5.10.340.1.7
    optixRtnStrategyEndHoldTime OBJECT-TYPE
        SYNTAX Unsigned32
        MAX-ACCESS read-create
        STATUS current
        DESCRIPTION
            "Inidcates the end filt time of energysave. Unit: second, range:[0,3600]."
        ::= { optixRtnEnergySaveStrategyEntry 7 }

    -- 1.3.6.1.4.1.2011.2.25.4.40.5.10.340.1.8
    optixRtnStrategyStartTime OBJECT-TYPE
        SYNTAX Unsigned32
        MAX-ACCESS read-create
        STATUS current
        DESCRIPTION
            "Inidcates the start time of energysave. Unit: minute, range:[0,1439]."
        ::= { optixRtnEnergySaveStrategyEntry 8 }

    -- 1.3.6.1.4.1.2011.2.25.4.40.5.10.340.1.9
    optixRtnStrategyEndTime OBJECT-TYPE
        SYNTAX Unsigned32
        MAX-ACCESS read-create
        STATUS current
        DESCRIPTION
            "Inidcates the end time of energysave. Unit: minute, range:[0,1439]."
        ::= { optixRtnEnergySaveStrategyEntry 9 }

    -- 1.3.6.1.4.1.2011.2.25.4.40.5.10.340.1.50
    optixRtnStrategyCfgRowStatus OBJECT-TYPE
        SYNTAX RowStatus
        MAX-ACCESS read-create
        STATUS current
        DESCRIPTION
            "Indicates the row status of a energysave group."
        DEFVAL{ active }
        ::= { optixRtnEnergySaveStrategyEntry 50 }

    -- 1.3.6.1.4.1.2011.2.25.4.40.5.10.341
    optixRtnEnergySaveMemberTable OBJECT-TYPE
        SYNTAX SEQUENCE OF OptixRtnEnergySaveMemberEntry
        MAX-ACCESS not-accessible
        STATUS current
        DESCRIPTION
            "Describes the members of energysave strategy group."
        ::= { optixRtnIFProtect 341 }
    
    -- 1.3.6.1.4.1.2011.2.25.4.40.5.10.341.1
    optixRtnEnergySaveMemberEntry OBJECT-TYPE
        SYNTAX OptixRtnEnergySaveMemberEntry
        MAX-ACCESS not-accessible
        STATUS current
        DESCRIPTION
            "Indicates the member entry of energysave strategy group."
        INDEX{ optixRtnStrategyGroupMemberID }
        ::= { optixRtnEnergySaveMemberTable 1 }

    OptixRtnEnergySaveMemberEntry ::=
        SEQUENCE {
            optixRtnStrategyGroupMemberID
                Unsigned32,
            optixRtnMemberInfo
                OCTET STRING,
            optixRtnMemberInfoDel
                OCTET STRING
        }

    -- 1.3.6.1.4.1.2011.2.25.4.40.5.10.341.1.1
    optixRtnStrategyGroupMemberID OBJECT-TYPE
        SYNTAX Unsigned32
        MAX-ACCESS not-accessible
        STATUS current
        DESCRIPTION
            "Indicates the member ID  of energysave strategy group."
        ::= { optixRtnEnergySaveMemberEntry 1 }

    -- 1.3.6.1.4.1.2011.2.25.4.40.5.10.341.1.2
    optixRtnMemberInfo OBJECT-TYPE
        SYNTAX OCTET STRING
        MAX-ACCESS read-create
        STATUS current
        DESCRIPTION
            "Indicates or adds the member info of energysave strategy group. Params:memberNum,boardId1,subboardId1,portId1,carrierId1,boardId2,subboardId2,portId2,carrierId2,..."
        ::= { optixRtnEnergySaveMemberEntry 2 }

    -- 1.3.6.1.4.1.2011.2.25.4.40.5.10.341.1.3
    optixRtnMemberInfoDel OBJECT-TYPE
        SYNTAX OCTET STRING
        MAX-ACCESS read-create
        STATUS current
        DESCRIPTION
            "Deletes the member info of energysave strategy group. Params:memberNum,boardId1,subboardId1,portId1,carrierId1,boardId2,subboardId2,portId2,carrierId2,..."
        ::= { optixRtnEnergySaveMemberEntry 3 }

    -- 1.3.6.1.4.1.2011.2.25.4.40.5.20
    optixRtnProtectTrapCommon OBJECT IDENTIFIER ::= { optixRtnIFProtectMgr 20 }

    -- 1.3.6.1.4.1.2011.2.25.4.40.5.20.1
    optixRptRtn1j1PGEvent OBJECT IDENTIFIER ::= { optixRtnProtectTrapCommon 1 }

    -- 1.3.6.1.4.1.2011.2.25.4.40.5.20.1.1
    optixRptRtn1j1PGID OBJECT-TYPE
        SYNTAX Unsigned32
        MAX-ACCESS accessible-for-notify
        STATUS current
        DESCRIPTION
            "Indicates the IF 1+1 protection group ID."
        ::= { optixRptRtn1j1PGEvent 1 }

    -- 1.3.6.1.4.1.2011.2.25.4.40.5.20.1.2
    optixRptRtn1j1PGCurrWorkBoardID OBJECT-TYPE
        SYNTAX Unsigned32
        MAX-ACCESS accessible-for-notify
        STATUS current
        DESCRIPTION
            "Indicates the current working slot ID of an IF 1+1 protection group."
        ::= { optixRptRtn1j1PGEvent 2 }

    -- 1.3.6.1.4.1.2011.2.25.4.40.5.20.1.3
    optixRptRtn1j1PGCurrWorkSubCardID OBJECT-TYPE
        SYNTAX Unsigned32
        MAX-ACCESS accessible-for-notify
        STATUS current
        DESCRIPTION
            "Indicates the current working subboard ID of an IF 1+1 protection group."
        ::= { optixRptRtn1j1PGEvent 3 }

    -- 1.3.6.1.4.1.2011.2.25.4.40.5.20.1.4
    optixRptRtn1j1PGCurrWorkPortID OBJECT-TYPE
        SYNTAX Unsigned32
        MAX-ACCESS accessible-for-notify
        STATUS current
        DESCRIPTION
            "Indicates the current working port ID of an IF 1+1 protection group."
        ::= { optixRptRtn1j1PGEvent 4 }

    -- 1.3.6.1.4.1.2011.2.25.4.40.5.20.1.5
    optixRptRtn1j1PGCurrWorkChannel OBJECT-TYPE
        SYNTAX OPTIXRtnCascading1j1PGRoleType
        MAX-ACCESS accessible-for-notify
        STATUS current
        DESCRIPTION
            "Indicates the current working channel identifier of an IF 1+1 protection group."
        ::= { optixRptRtn1j1PGEvent 5 }

    -- 1.3.6.1.4.1.2011.2.25.4.40.5.20.1.6
    optixRptRtn1j1PGMainBoardState OBJECT-TYPE
        SYNTAX OPTIXRtn1j1PGBDStateType
        MAX-ACCESS accessible-for-notify
        STATUS current
        DESCRIPTION
            "Indicates the working status of the main board in an IF 1+1 protection group."
        ::= { optixRptRtn1j1PGEvent 6 }

    -- 1.3.6.1.4.1.2011.2.25.4.40.5.20.1.7
    optixRptRtn1j1PGBackupBoardState OBJECT-TYPE
        SYNTAX OPTIXRtn1j1PGBDStateType
        MAX-ACCESS accessible-for-notify
        STATUS current
        DESCRIPTION
            "Indicates the working status of the standby board in an IF 1+1 protection group."
        ::= { optixRptRtn1j1PGEvent 7 }

    -- 1.3.6.1.4.1.2011.2.25.4.40.5.20.1.8
    optixRptRtn1j1PGSwitchRequest OBJECT-TYPE
        SYNTAX OPTIXRtn1j1SwtichRequestType
        MAX-ACCESS accessible-for-notify
        STATUS current
        DESCRIPTION
            "Indicates the switching request of an IF 1+1 protection group."
        ::= { optixRptRtn1j1PGEvent 8 }

    -- 1.3.6.1.4.1.2011.2.25.4.40.5.20.10
    optixRptRtnNj1PGEvent OBJECT IDENTIFIER ::= { optixRtnProtectTrapCommon 10 }

    -- 1.3.6.1.4.1.2011.2.25.4.40.5.20.10.1
    optixRptRtnNj1PGID OBJECT-TYPE
        SYNTAX Unsigned32
        MAX-ACCESS accessible-for-notify
        STATUS current
        DESCRIPTION
            "Indicates the IF N+1 protection group ID."
        ::= { optixRptRtnNj1PGEvent 1 }

    -- 1.3.6.1.4.1.2011.2.25.4.40.5.20.10.2
    optixRptRtnNj1Channel OBJECT-TYPE
        SYNTAX Unsigned32
        MAX-ACCESS accessible-for-notify
        STATUS current
        DESCRIPTION
            "Indicates the channel ID of an IF N+1 protection group."
        ::= { optixRptRtnNj1PGEvent 2 }

    -- 1.3.6.1.4.1.2011.2.25.4.40.5.20.10.3
    optixRptRtnNj1PGSwitchRequest OBJECT-TYPE
        SYNTAX OPTIXRtnNj1PGSwitchRequestType
        MAX-ACCESS accessible-for-notify
        STATUS current
        DESCRIPTION
            "Indicates the switching request of an IF N+1 protection group."
        ::= { optixRptRtnNj1PGEvent 3 }

    -- 1.3.6.1.4.1.2011.2.25.4.40.5.20.10.4
    optixRptRtnNj1PGSwitchState OBJECT-TYPE
        SYNTAX OPTIXRtnNj1SwitchStateType
        MAX-ACCESS accessible-for-notify
        STATUS current
        DESCRIPTION
            "Indicates the switching status of an IF N+1 protection group."
        ::= { optixRptRtnNj1PGEvent 4 }

    -- 1.3.6.1.4.1.2011.2.25.4.40.5.20.10.5
    optixRptRtnNj1PGProtectedPath OBJECT-TYPE
        SYNTAX Unsigned32
        MAX-ACCESS accessible-for-notify
        STATUS current
        DESCRIPTION
            "Indicates the protected unit of an IF N+1 protection group."
        ::= { optixRptRtnNj1PGEvent 5 }

    -- 1.3.6.1.4.1.2011.2.25.4.40.5.20.10.6
    optixRptRtnNj1PGFarNearIndicate OBJECT-TYPE
        SYNTAX OPTIXRtnNj1PGFarNearType
        MAX-ACCESS accessible-for-notify
        STATUS current
        DESCRIPTION
            "Indicates the switching far and near ends of an IF N+1 protection group."
        ::= { optixRptRtnNj1PGEvent 6 }

    -- 1.3.6.1.4.1.2011.2.25.4.40.5.20.10.7
    optixRptRtnNj1PGSwitchReason OBJECT-TYPE
        SYNTAX OPTIXRtnNj1PGSwitchReasonType
        MAX-ACCESS accessible-for-notify
        STATUS current
        DESCRIPTION
            "Indicates the switching causes for an IF N+1 protection group."
        ::= { optixRptRtnNj1PGEvent 7 }

    -- 1.3.6.1.4.1.2011.2.25.4.40.5.20.20
    optixRptRtnPLAPGEvent OBJECT IDENTIFIER ::= { optixRtnProtectTrapCommon 20 }

    -- 1.3.6.1.4.1.2011.2.25.4.40.5.20.20.1
    optixRptRtnPLAPGID OBJECT-TYPE
        SYNTAX Unsigned32
        MAX-ACCESS accessible-for-notify
        STATUS current
        DESCRIPTION
            "Indicates the ID of a PLA protection group."
        ::= { optixRptRtnPLAPGEvent 1 }

    -- 1.3.6.1.4.1.2011.2.25.4.40.5.20.20.2
    optixRptRtnPLAPGMainBoardID OBJECT-TYPE
        SYNTAX Unsigned32
        MAX-ACCESS accessible-for-notify
        STATUS current
        DESCRIPTION
            "Indicates the main unit slot ID of a PLA protection group."
        ::= { optixRptRtnPLAPGEvent 2 }

    -- 1.3.6.1.4.1.2011.2.25.4.40.5.20.20.3
    optixRptRtnPLAPGMainSubCardID OBJECT-TYPE
        SYNTAX Unsigned32
        MAX-ACCESS accessible-for-notify
        STATUS current
        DESCRIPTION
            "Indicates the main unit slot ID of a PLA protection group."
        ::= { optixRptRtnPLAPGEvent 3 }

    -- 1.3.6.1.4.1.2011.2.25.4.40.5.20.20.4
    optixRptRtnPLAPGMainPortID OBJECT-TYPE
        SYNTAX Unsigned32
        MAX-ACCESS accessible-for-notify
        STATUS current
        DESCRIPTION
            "Indicates the main unit port ID of a PLA protection group."
        ::= { optixRptRtnPLAPGEvent 4 }

    -- 1.3.6.1.4.1.2011.2.25.4.40.5.20.20.5
    optixRptRtnPLAPGMainHardStatus OBJECT-TYPE
        SYNTAX OPTIXRtnPhyLagPGStatus
        MAX-ACCESS accessible-for-notify
        STATUS current
        DESCRIPTION
            "Indicates the main unit hardware status of a PLA protection group."
        ::= { optixRptRtnPLAPGEvent 5 }

    -- 1.3.6.1.4.1.2011.2.25.4.40.5.20.20.6
    optixRptRtnPLAPGMainLinkStatus OBJECT-TYPE
        SYNTAX OPTIXRtnPhyLagPGStatus
        MAX-ACCESS accessible-for-notify
        STATUS current
        DESCRIPTION
            "Indicates the main unit link status of a PLA protection group."
        ::= { optixRptRtnPLAPGEvent 6 }

    -- 1.3.6.1.4.1.2011.2.25.4.40.5.20.20.7
    optixRptRtnPLAPGMainWorkStatus OBJECT-TYPE
        SYNTAX OPTIXRtnPhyLagPGStateWorkStatus
        MAX-ACCESS accessible-for-notify
        STATUS current
        DESCRIPTION
            "Indicates the main unit switching status of a PLA protection group."
        ::= { optixRptRtnPLAPGEvent 7 }

    -- 1.3.6.1.4.1.2011.2.25.4.40.5.20.20.8
    optixRptRtnPLAPGSlavePortNum OBJECT-TYPE
        SYNTAX Unsigned32
        MAX-ACCESS accessible-for-notify
        STATUS current
        DESCRIPTION
            "Indicates the number of slave units in a PLA protection group."
        ::= { optixRptRtnPLAPGEvent 8 }

    -- 1.3.6.1.4.1.2011.2.25.4.40.5.20.20.9
    optixRptRtnPLAPGSlaveStatus OBJECT-TYPE
        SYNTAX OCTET STRING
        MAX-ACCESS accessible-for-notify
        STATUS current
        DESCRIPTION
            "Indicates the slave units switching status of a PLA protection group."
        ::= { optixRptRtnPLAPGEvent 9 }
		
    -- 1.3.6.1.4.1.2011.2.25.4.40.5.20.240
    optixRptRtnPLAPGScheduleModeChangeEvent OBJECT IDENTIFIER ::= { optixRtnProtectTrapCommon 240 }

    -- 1.3.6.1.4.1.2011.2.25.4.40.5.20.240.1
    optixRptRtnPLAPGId OBJECT-TYPE
        SYNTAX Unsigned32
        MAX-ACCESS accessible-for-notify
        STATUS current
        DESCRIPTION
            "Indicates the ID of a PLA protection group."
        ::= { optixRptRtnPLAPGScheduleModeChangeEvent 1 }

    -- 1.3.6.1.4.1.2011.2.25.4.40.5.20.240.2
    optixRptRtnPLAPGType OBJECT-TYPE
        SYNTAX Unsigned32
        MAX-ACCESS accessible-for-notify
        STATUS current
        DESCRIPTION
            "Indicates the Type of a PLA protection group."
        ::= { optixRptRtnPLAPGScheduleModeChangeEvent 2 }

    -- 1.3.6.1.4.1.2011.2.25.4.40.5.20.240.3
    optixRptRtnPLAPGCfgMode OBJECT-TYPE
        SYNTAX Unsigned32
        {
            modeA(0),
            modeB(1),
            modeAAccess(2),
            unknown(255)
        }		
        MAX-ACCESS accessible-for-notify
        STATUS current
        DESCRIPTION
            "Indicates the CfgMode of a PLA protection group."
        ::= { optixRptRtnPLAPGScheduleModeChangeEvent 3 }

    -- 1.3.6.1.4.1.2011.2.25.4.40.5.20.240.4
    optixRptRtnPLAPGWorkMode OBJECT-TYPE
        SYNTAX Unsigned32
        {
            modeA(0),
            modeB(1),
            modeAAccess(2),
            unknown(255)
        }	
        MAX-ACCESS accessible-for-notify
        STATUS current
        DESCRIPTION
            "Indicates the WorkMode of a PLA protection group."
        ::= { optixRptRtnPLAPGScheduleModeChangeEvent 4 }
		
    -- 1.3.6.1.4.1.2011.2.25.4.40.5.20.30
    optixRptRtnCascading1j1PGEvent OBJECT IDENTIFIER ::= { optixRtnProtectTrapCommon 30 }

    -- 1.3.6.1.4.1.2011.2.25.4.40.5.20.30.1
    optixRptRtnC1j1PGID OBJECT-TYPE
        SYNTAX Unsigned32
        MAX-ACCESS accessible-for-notify
        STATUS current
        DESCRIPTION
            "Indicates the cascading IF 1+1 protection group ID."
        ::= { optixRptRtnCascading1j1PGEvent 1 }

    -- 1.3.6.1.4.1.2011.2.25.4.40.5.20.30.2
    optixRptRtnC1j1PGWorkNEID OBJECT-TYPE
        SYNTAX Unsigned32
        MAX-ACCESS accessible-for-notify
        STATUS current
        DESCRIPTION
            "Indicates the current working NE ID of a cascading IF 1+1 protection group on the equipment side."
        ::= { optixRptRtnCascading1j1PGEvent 2 }

    -- 1.3.6.1.4.1.2011.2.25.4.40.5.20.30.3
    optixRptRtnC1j1PGWorkBoardID OBJECT-TYPE
        SYNTAX Unsigned32
        MAX-ACCESS accessible-for-notify
        STATUS current
        DESCRIPTION
            "Indicates the current working board ID of a cascading IF 1+1 protection group on the equipment side."
        ::= { optixRptRtnCascading1j1PGEvent 3 }

    -- 1.3.6.1.4.1.2011.2.25.4.40.5.20.30.4
    optixRptRtnC1j1PGWorkSubCardID OBJECT-TYPE
        SYNTAX Unsigned32
        MAX-ACCESS accessible-for-notify
        STATUS current
        DESCRIPTION
            "Indicates the current working subboard ID of a cascading IF 1+1 protection group on the equipment side."
        ::= { optixRptRtnCascading1j1PGEvent 4 }

    -- 1.3.6.1.4.1.2011.2.25.4.40.5.20.30.5
    optixRptRtnC1j1PGWorkPortID OBJECT-TYPE
        SYNTAX Unsigned32
        MAX-ACCESS accessible-for-notify
        STATUS current
        DESCRIPTION
            "Indicates the current working port ID of a cascading IF 1+1 protection group on the equipment side."
        ::= { optixRptRtnCascading1j1PGEvent 5 }

    -- 1.3.6.1.4.1.2011.2.25.4.40.5.20.30.6
    optixRptRtnC1j1PGCurrWorkChannel OBJECT-TYPE
        SYNTAX OPTIXRtnCascading1j1PGRoleType
        MAX-ACCESS accessible-for-notify
        STATUS current
        DESCRIPTION
            "Indicates the current working channel identifier of an cascading IF 1+1 protection group."
        ::= { optixRptRtnCascading1j1PGEvent 6 }

    -- 1.3.6.1.4.1.2011.2.25.4.40.5.20.30.7
    optixRptRtnC1j1PGWorkBoardState OBJECT-TYPE
        SYNTAX OPTIXRtn1j1PGBDStateType
        MAX-ACCESS accessible-for-notify
        STATUS current
        DESCRIPTION
            "Indicates the working status of the main board on the equipment side. Values: 0: normal 1: switching 2: RDI switching -1: unknown"
        ::= { optixRptRtnCascading1j1PGEvent 7 }

    -- 1.3.6.1.4.1.2011.2.25.4.40.5.20.30.8
    optixRptRtnC1j1PGProtectBoardState OBJECT-TYPE
        SYNTAX OPTIXRtn1j1PGBDStateType
        MAX-ACCESS accessible-for-notify
        STATUS current
        DESCRIPTION
            "Indicates the working status of the standby board on the equipment side. Values: 0: normal 1: switching 2: RDI switching -1: unknown"
        ::= { optixRptRtnCascading1j1PGEvent 8 }

    -- 1.3.6.1.4.1.2011.2.25.4.40.5.20.30.9
    optixRptRtnC1j1PGSwtichRequest OBJECT-TYPE
        SYNTAX OPTIXRtn1j1SwtichRequestType
        MAX-ACCESS accessible-for-notify
        STATUS current
        DESCRIPTION
            "Indicates the switching request on the equipment side. Value range: 0: normal 1: automatic 2: manual 3: forced 4: lockout 5: wait to restore 6: RDI"
        ::= { optixRptRtnCascading1j1PGEvent 9 }

    -- 1.3.6.1.4.1.2011.2.25.4.40.5.20.40
    optixRptRtnCascadingPLAPGEvent OBJECT IDENTIFIER ::= { optixRtnProtectTrapCommon 40 }

    -- 1.3.6.1.4.1.2011.2.25.4.40.5.20.40.1
    optixRptRtnCPLAPGID OBJECT-TYPE
        SYNTAX Unsigned32
        MAX-ACCESS accessible-for-notify
        STATUS current
        DESCRIPTION
            "Indicates the cascading PLA protection group ID."
        ::= { optixRptRtnCascadingPLAPGEvent 1 }

    -- 1.3.6.1.4.1.2011.2.25.4.40.5.20.40.2
    optixRptRtnCPLAPGMainNEID OBJECT-TYPE
        SYNTAX Unsigned32
        MAX-ACCESS accessible-for-notify
        STATUS current
        DESCRIPTION
            "Indicates the main NE ID."
        ::= { optixRptRtnCascadingPLAPGEvent 2 }

    -- 1.3.6.1.4.1.2011.2.25.4.40.5.20.40.3
    optixRptRtnCPLAPGMainBoardID OBJECT-TYPE
        SYNTAX Unsigned32
        MAX-ACCESS accessible-for-notify
        STATUS current
        DESCRIPTION
            "Indicates the slot ID of the main unit."
        ::= { optixRptRtnCascadingPLAPGEvent 3 }

    -- 1.3.6.1.4.1.2011.2.25.4.40.5.20.40.4
    optixRptRtnCPLAPGMainSubID OBJECT-TYPE
        SYNTAX Unsigned32
        MAX-ACCESS accessible-for-notify
        STATUS current
        DESCRIPTION
            "Indicates the subboard ID of the main unit."
        ::= { optixRptRtnCascadingPLAPGEvent 4 }

    -- 1.3.6.1.4.1.2011.2.25.4.40.5.20.40.5
    optixRptRtnCPLAPGMainPortID OBJECT-TYPE
        SYNTAX Unsigned32
        MAX-ACCESS accessible-for-notify
        STATUS current
        DESCRIPTION
            "Indicates the port ID of the main unit."
        ::= { optixRptRtnCascadingPLAPGEvent 5 }

    -- 1.3.6.1.4.1.2011.2.25.4.40.5.20.40.6
    optixRptRtnCPLAPGMainHardStatus OBJECT-TYPE
        SYNTAX OPTIXRtnPhyLagPGStatus
        MAX-ACCESS accessible-for-notify
        STATUS current
        DESCRIPTION
            "Indicates the hardware status of the main unit. The values: 0: normal 1: abnormal -1: unknown"
        ::= { optixRptRtnCascadingPLAPGEvent 6 }

    -- 1.3.6.1.4.1.2011.2.25.4.40.5.20.40.7
    optixRptRtnCPLAPGMainLinkStatus OBJECT-TYPE
        SYNTAX OPTIXRtnPhyLagPGStatus
        MAX-ACCESS accessible-for-notify
        STATUS current
        DESCRIPTION
            "Indicates the link status of the main unit. The values: 0: normal 1: abnormal -1: unknown"
        ::= { optixRptRtnCascadingPLAPGEvent 7 }

    -- 1.3.6.1.4.1.2011.2.25.4.40.5.20.40.8
    optixRptRtnCPLAPGMainMSStatus OBJECT-TYPE
        SYNTAX OPTIXRtnPhyLagPGStateWorkStatus
        MAX-ACCESS accessible-for-notify
        STATUS current
        DESCRIPTION
            "Indicates the working status of the main unit. Values: 0: slave port 1: main port"
        ::= { optixRptRtnCascadingPLAPGEvent 8 }

    -- 1.3.6.1.4.1.2011.2.25.4.40.5.20.40.9
    optixRptRtnCPLAPGSlavePuNum OBJECT-TYPE
        SYNTAX Unsigned32
        MAX-ACCESS accessible-for-notify
        STATUS current
        DESCRIPTION
            "Indicates the number of cascading units. Value range: 1 to 3"
        ::= { optixRptRtnCascadingPLAPGEvent 9 }

    -- 1.3.6.1.4.1.2011.2.25.4.40.5.20.40.10
    optixRptRtnCPLAPGPu1NEID OBJECT-TYPE
        SYNTAX Unsigned32
        MAX-ACCESS accessible-for-notify
        STATUS current
        DESCRIPTION
            "Indicates the NE ID of the cascading unit 1."
        ::= { optixRptRtnCascadingPLAPGEvent 10 }

    -- 1.3.6.1.4.1.2011.2.25.4.40.5.20.40.11
    optixRptRtnCPLAPGPu1BoardID OBJECT-TYPE
        SYNTAX Unsigned32
        MAX-ACCESS accessible-for-notify
        STATUS current
        DESCRIPTION
            "Indicates the board ID of the cascading unit 1. An invalid value of 65535 is returned when the adjacency channel is faulty."
        ::= { optixRptRtnCascadingPLAPGEvent 11 }

    -- 1.3.6.1.4.1.2011.2.25.4.40.5.20.40.12
    optixRptRtnCPLAPGPu1SubCardID OBJECT-TYPE
        SYNTAX Unsigned32
        MAX-ACCESS accessible-for-notify
        STATUS current
        DESCRIPTION
            "Indicates the subboard ID of the cascading unit 1. An invalid value of 255 is returned when the adjacency channel is faulty."
        ::= { optixRptRtnCascadingPLAPGEvent 12 }

    -- 1.3.6.1.4.1.2011.2.25.4.40.5.20.40.13
    optixRptRtnCPLAPGPu1PortID OBJECT-TYPE
        SYNTAX Unsigned32
        MAX-ACCESS accessible-for-notify
        STATUS current
        DESCRIPTION
            "Indicates the port ID of the cascading unit 1. An invalid value of 255 is returned when the adjacency channel is faulty."
        ::= { optixRptRtnCascadingPLAPGEvent 13 }

    -- 1.3.6.1.4.1.2011.2.25.4.40.5.20.40.14
    optixRptRtnCPLAPGPu1HardStatus OBJECT-TYPE
        SYNTAX OPTIXRtnPhyLagPGStatus
        MAX-ACCESS accessible-for-notify
        STATUS current
        DESCRIPTION
            "Indicates the hardware status of the cascading unit 1. Values: 0: normal 1: abnormal -1: unknown"
        ::= { optixRptRtnCascadingPLAPGEvent 14 }

    -- 1.3.6.1.4.1.2011.2.25.4.40.5.20.40.15
    optixRptRtnCPLAPGPu1LinkStatus OBJECT-TYPE
        SYNTAX OPTIXRtnPhyLagPGStatus
        MAX-ACCESS accessible-for-notify
        STATUS current
        DESCRIPTION
            "Indicates the link status of the cascading unit 1. Values: 0: normal 1: abnormal -1: unknown"
        ::= { optixRptRtnCascadingPLAPGEvent 15 }

    -- 1.3.6.1.4.1.2011.2.25.4.40.5.20.40.16
    optixRptRtnCPLAPGPu1MSStatus OBJECT-TYPE
        SYNTAX OPTIXRtnPhyLagPGStateWorkStatus
        MAX-ACCESS accessible-for-notify
        STATUS current
        DESCRIPTION
            "Indicates the working status of the cascading unit 1. Values: 0: slave port 1: main port"
        ::= { optixRptRtnCascadingPLAPGEvent 16 }

    -- 1.3.6.1.4.1.2011.2.25.4.40.5.20.41
    optixRtnNonCascade1J1SwitchEvent OBJECT IDENTIFIER ::= { optixRtnProtectTrapCommon 41 }

    -- 1.3.6.1.4.1.2011.2.25.4.40.5.20.41.1
    optixRtnNonCascade1J1GPID OBJECT-TYPE
        SYNTAX Unsigned32
        MAX-ACCESS accessible-for-notify
        STATUS current
        DESCRIPTION
            "Indicates the protection group ID."
        ::= { optixRtnNonCascade1J1SwitchEvent 1 }

    -- 1.3.6.1.4.1.2011.2.25.4.40.5.20.41.2
    optixRtnNonCascade1J1BoardID OBJECT-TYPE
        SYNTAX Unsigned32
        MAX-ACCESS accessible-for-notify
        STATUS current
        DESCRIPTION
            "Indicates the slot ID of the current working board on the equipment side."
        ::= { optixRtnNonCascade1J1SwitchEvent 2 }

    -- 1.3.6.1.4.1.2011.2.25.4.40.5.20.41.3
    optixRtnNonCascade1J1SubCardID OBJECT-TYPE
        SYNTAX Unsigned32
        MAX-ACCESS accessible-for-notify
        STATUS current
        DESCRIPTION
            "Indicates the subcard ID of the current working board on the equipment side."
        ::= { optixRtnNonCascade1J1SwitchEvent 3 }

    -- 1.3.6.1.4.1.2011.2.25.4.40.5.20.41.4
    optixRtnNonCascade1J1PortID OBJECT-TYPE
        SYNTAX Unsigned32
        MAX-ACCESS accessible-for-notify
        STATUS current
        DESCRIPTION
            "Indicates the port ID of the current working board on the equipment side."
        ::= { optixRtnNonCascade1J1SwitchEvent 4 }

    -- 1.3.6.1.4.1.2011.2.25.4.40.5.20.41.5
    optixRtnNonCascade1J1DevWorkBoardProperty OBJECT-TYPE
        SYNTAX OPTIXRtn1j1DevWorkBoardProperty
        MAX-ACCESS accessible-for-notify
        STATUS current
        DESCRIPTION
            "Indicates whether the current working board on the equipment board is a working or protection board. The values are as follows:
0-working
1-protection"
        ::= { optixRtnNonCascade1J1SwitchEvent 5 }

    -- 1.3.6.1.4.1.2011.2.25.4.40.5.20.41.6
    optixRtnNonCascade1J1WorkBoardDevState OBJECT-TYPE
        SYNTAX OPTIXRtn1j1PGBDStateType
        MAX-ACCESS accessible-for-notify
        STATUS current
        DESCRIPTION
            "Indicates the status of the current working board on the equipment side. The values are as follows: 
0-normal
1-fail
2-rdi
255-unknown"
        ::= { optixRtnNonCascade1J1SwitchEvent 6 }

    -- 1.3.6.1.4.1.2011.2.25.4.40.5.20.41.7
    optixRtnNonCascade1J1ProtBoardDevState OBJECT-TYPE
        SYNTAX OPTIXRtn1j1PGBDStateType
        MAX-ACCESS accessible-for-notify
        STATUS current
        DESCRIPTION
            "Indicates the status of the current protection board on the equipment side. The values are as follows: 
0-normal
1-fail
2-rdi
255-unknown"
        ::= { optixRtnNonCascade1J1SwitchEvent 7 }

    -- 1.3.6.1.4.1.2011.2.25.4.40.5.20.41.8
    optixRtnNonCascade1J1DevSwtichRequest OBJECT-TYPE
        SYNTAX OPTIXRtn1j1SwtichRequestType
        MAX-ACCESS accessible-for-notify
        STATUS current
        DESCRIPTION
            "Indicates the equipment-side switching request:
0-state-normal
1-state-auto
2-state-manual
3-state-force
4-state-lockout
5-state-wtr
6-state-rdi"
        ::= { optixRtnNonCascade1J1SwitchEvent 8 }

    -- 1.3.6.1.4.1.2011.2.25.4.40.5.20.43
    optixRtnIFBitErrorCodeTestEvent OBJECT IDENTIFIER ::= { optixRtnProtectTrapCommon 43 }

    -- 1.3.6.1.4.1.2011.2.25.4.40.5.20.43.1
    optixRtnIFBECTBoardId OBJECT-TYPE
        SYNTAX Unsigned32
        MAX-ACCESS accessible-for-notify
        STATUS current
        DESCRIPTION
            "Indicates the slot ID of the IF board."
        ::= { optixRtnIFBitErrorCodeTestEvent 1 }

    -- 1.3.6.1.4.1.2011.2.25.4.40.5.20.43.2
    optixRtnIFBECTSubCardId OBJECT-TYPE
        SYNTAX Unsigned32
        MAX-ACCESS accessible-for-notify
        STATUS current
        DESCRIPTION
            "Indicates the subcard ID."
        ::= { optixRtnIFBitErrorCodeTestEvent 2 }

    -- 1.3.6.1.4.1.2011.2.25.4.40.5.20.43.3
    optixRtnIFBECTPortId OBJECT-TYPE
        SYNTAX Unsigned32
        MAX-ACCESS accessible-for-notify
        STATUS current
        DESCRIPTION
            "Indicates the port ID."
        ::= { optixRtnIFBitErrorCodeTestEvent 3 }

    -- 1.3.6.1.4.1.2011.2.25.4.40.5.20.43.4
    optixRtnIFBECTType OBJECT-TYPE
        SYNTAX INTEGER
        {
            e1(1),
            if(2),
            cpri(3)
        }
        MAX-ACCESS accessible-for-notify
        STATUS current
        DESCRIPTION
            "Indicates the test type: 
1-E1
2-IF
3-CPRI"
        ::= { optixRtnIFBitErrorCodeTestEvent 4 }

    -- 1.3.6.1.4.1.2011.2.25.4.40.5.20.43.5
    optixRtnIFBECTPathId OBJECT-TYPE
        SYNTAX Unsigned32
        MAX-ACCESS accessible-for-notify
        STATUS current
        DESCRIPTION
            "Indicates the path ID.
Set the parameter to 0 if this field is not in use."
        ::= { optixRtnIFBitErrorCodeTestEvent 5 }

    -- 1.3.6.1.4.1.2011.2.25.4.40.5.20.43.6
    optixRtnIFBECTDirection OBJECT-TYPE
        SYNTAX INTEGER
        {
            ingressDir(1),
            egressDir(2)
        }
        MAX-ACCESS accessible-for-notify
        STATUS current
        DESCRIPTION
            "Indicates the test direction:
1-Ingress
2-Egress"
        ::= { optixRtnIFBitErrorCodeTestEvent 6 }

    -- 1.3.6.1.4.1.2011.2.25.4.40.5.20.43.7
    optixRtnIFBECTMode OBJECT-TYPE
        SYNTAX INTEGER
        {
            shortTerm(1),
            longTerm(2),
            longlongTerm(3)
        }
        MAX-ACCESS accessible-for-notify
        STATUS current
        DESCRIPTION
            "Indicates the test type. 
1: short-term test
2: long-term test
3: super long-term test"
        ::= { optixRtnIFBitErrorCodeTestEvent 7 }

    -- 1.3.6.1.4.1.2011.2.25.4.40.5.20.43.8
    optixRtnIFBECTTimeStamp OBJECT-TYPE
        SYNTAX Unsigned32
        MAX-ACCESS accessible-for-notify
        STATUS current
        DESCRIPTION
            "The value starts from 0x0001. The test duration is measured in seconds in short-term tests and minutes in long-term tests and super-long-term tests."
        ::= { optixRtnIFBitErrorCodeTestEvent 8 }

    -- 1.3.6.1.4.1.2011.2.25.4.40.5.20.43.9
    optixRtnIFBECTStartTime OBJECT-TYPE
        SYNTAX OCTET STRING
        MAX-ACCESS accessible-for-notify
        STATUS current
        DESCRIPTION
            "Indicates the start time of a test in the format of YYYYMMDDHHMMSS and the time starts from the year 1990."
        ::= { optixRtnIFBitErrorCodeTestEvent 9 }

    -- 1.3.6.1.4.1.2011.2.25.4.40.5.20.43.10
    optixRtnIFBECTCurTime OBJECT-TYPE
        SYNTAX OCTET STRING
        MAX-ACCESS accessible-for-notify
        STATUS current
        DESCRIPTION
            "Indicates the current time of a test in the format of YYYYMMDDHHMMSS and the time starts from the year 1990."
        ::= { optixRtnIFBitErrorCodeTestEvent 10 }

    -- 1.3.6.1.4.1.2011.2.25.4.40.5.20.43.11
    optixRtnIFBECTProgress OBJECT-TYPE
        SYNTAX Unsigned32
        MAX-ACCESS accessible-for-notify
        STATUS current
        DESCRIPTION
            "Indicates the test progress. Value range: 1-100"
        ::= { optixRtnIFBitErrorCodeTestEvent 11 }

    -- 1.3.6.1.4.1.2011.2.25.4.40.5.20.43.12
    optixRtnIFBECTDataTypeNum OBJECT-TYPE
        SYNTAX Unsigned32
        MAX-ACCESS accessible-for-notify
        STATUS current
        DESCRIPTION
            "Indicates the number of parameter types N (N >= 1 and currently N = 2). The data types are described as follows:"
        ::= { optixRtnIFBitErrorCodeTestEvent 12 }

    -- 1.3.6.1.4.1.2011.2.25.4.40.5.20.43.13
    optixRtnIFBECTType1 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeTestEvent 13 }

    -- 1.3.6.1.4.1.2011.2.25.4.40.5.20.43.14
    optixRtnIFBECTTestResult1 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeTestEvent 14 }

    -- 1.3.6.1.4.1.2011.2.25.4.40.5.20.43.15
    optixRtnIFBECTType2 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeTestEvent 15 }

    -- 1.3.6.1.4.1.2011.2.25.4.40.5.20.43.16
    optixRtnIFBECTTestResult2 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeTestEvent 16 }

    -- 1.3.6.1.4.1.2011.2.25.4.40.5.20.43.17
    optixRtnIFBECTType3 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeTestEvent 17 }

    -- 1.3.6.1.4.1.2011.2.25.4.40.5.20.43.18
    optixRtnIFBECTTestResult3 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeTestEvent 18 }

    -- 1.3.6.1.4.1.2011.2.25.4.40.5.20.43.19
    optixRtnIFBECTType4 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeTestEvent 19 }

    -- 1.3.6.1.4.1.2011.2.25.4.40.5.20.43.20
    optixRtnIFBECTTestResult4 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeTestEvent 20 }

    -- 1.3.6.1.4.1.2011.2.25.4.40.5.20.43.21
    optixRtnIFBECTType5 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeTestEvent 21 }

    -- 1.3.6.1.4.1.2011.2.25.4.40.5.20.43.22
    optixRtnIFBECTTestResult5 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeTestEvent 22 }

    -- 1.3.6.1.4.1.2011.2.25.4.40.5.20.43.23
    optixRtnIFBECTType6 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeTestEvent 23 }

    -- 1.3.6.1.4.1.2011.2.25.4.40.5.20.43.24
    optixRtnIFBECTTestResult6 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeTestEvent 24 }
	
    -- 1.3.6.1.4.1.2011.2.25.4.40.5.20.46
    optixRtnIFBitOldTestEvent OBJECT IDENTIFIER ::= { optixRtnProtectTrapCommon 46 }

    -- 1.3.6.1.4.1.2011.2.25.4.40.5.20.46.1
    optixRtnBECTBoardId OBJECT-TYPE
        SYNTAX Unsigned32
        MAX-ACCESS accessible-for-notify
        STATUS current
        DESCRIPTION
            "Indicates the slot ID of the IF board."
        ::= { optixRtnIFBitOldTestEvent 1 }

    -- 1.3.6.1.4.1.2011.2.25.4.40.5.20.46.2
    optixRtnBECTSubCardId OBJECT-TYPE
        SYNTAX Unsigned32
        MAX-ACCESS accessible-for-notify
        STATUS current
        DESCRIPTION
            "Indicates the subcard ID."
        ::= { optixRtnIFBitOldTestEvent 2 }
    -- 1.3.6.1.4.1.2011.2.25.4.40.5.20.46.3
    optixRtnBECTPortId OBJECT-TYPE
        SYNTAX Unsigned32
        MAX-ACCESS accessible-for-notify
        STATUS current
        DESCRIPTION
            "Indicates the port ID."
        ::= { optixRtnIFBitOldTestEvent 3 }
		
    -- 1.3.6.1.4.1.2011.2.25.4.40.5.20.46.4
    optixRtnBECTTimeStamp OBJECT-TYPE
        SYNTAX Unsigned32
        MAX-ACCESS accessible-for-notify
        STATUS current
        DESCRIPTION
            "The value starts from 0x0001. The test duration is measured in seconds in short-term tests and minutes in long-term tests and super-long-term tests."
        ::= { optixRtnIFBitOldTestEvent 4 }
		
    -- 1.3.6.1.4.1.2011.2.25.4.40.5.20.46.5
    optixRtnBECTErrorNum OBJECT-TYPE
        SYNTAX Unsigned32
        MAX-ACCESS accessible-for-notify
        STATUS current
        DESCRIPTION
            "Indicates the number of error ."
        ::= { optixRtnIFBitOldTestEvent 5 }
		
    -- 1.3.6.1.4.1.2011.2.25.4.40.5.20.47
    optixRtnIFBitTestEvent OBJECT IDENTIFIER ::= { optixRtnProtectTrapCommon 47 }

    -- 1.3.6.1.4.1.2011.2.25.4.40.5.20.47.1
    optixRtnIFBITTESTBoardId OBJECT-TYPE
        SYNTAX Unsigned32
        MAX-ACCESS accessible-for-notify
        STATUS current
        DESCRIPTION
            "Indicates the slot ID of the IF board."
        ::= { optixRtnIFBitTestEvent 1 }
		
    -- 1.3.6.1.4.1.2011.2.25.4.40.5.20.47.2
    optixRtnIFBITTESTSubCardId OBJECT-TYPE
        SYNTAX Unsigned32
        MAX-ACCESS accessible-for-notify
        STATUS current
        DESCRIPTION
            "Indicates the subcard ID."
        ::= { optixRtnIFBitTestEvent 2 }
		
    -- 1.3.6.1.4.1.2011.2.25.4.40.5.20.47.3
    optixRtnIFBITTESTPortId OBJECT-TYPE
        SYNTAX Unsigned32
        MAX-ACCESS accessible-for-notify
        STATUS current
        DESCRIPTION
            "Indicates the port ID."
        ::= { optixRtnIFBitTestEvent 3 }
		
    -- 1.3.6.1.4.1.2011.2.25.4.40.5.20.47.4
    optixRtnIFBITTESTMode OBJECT-TYPE
        SYNTAX INTEGER
        {
            shortTerm(1),
            longTerm(2),
            longlongTerm(3)
        }
        MAX-ACCESS accessible-for-notify
        STATUS current
        DESCRIPTION
            "Indicates the test type. 
1: short-term test
2: long-term test
3: super long-term test"
        ::= { optixRtnIFBitTestEvent 4 }
		
    -- 1.3.6.1.4.1.2011.2.25.4.40.5.20.47.5
    optixRtnIFBITTESTTimeStamp OBJECT-TYPE
        SYNTAX Unsigned32
        MAX-ACCESS accessible-for-notify
        STATUS current
        DESCRIPTION
            "The value starts from 0x0001. The test duration is measured in seconds in short-term tests and minutes in long-term tests and hours in super-long-term tests."
        ::= { optixRtnIFBitTestEvent 5 }
		
    -- 1.3.6.1.4.1.2011.2.25.4.40.5.20.47.6
    optixRtnIFBITTESTStartTime OBJECT-TYPE
        SYNTAX OCTET STRING
        MAX-ACCESS accessible-for-notify
        STATUS current
        DESCRIPTION
            "Indicates the start time of a test in the format of YYYYMMDDHHMMSS and the time starts from the year 1990."
        ::= { optixRtnIFBitTestEvent 6 }
		
    -- 1.3.6.1.4.1.2011.2.25.4.40.5.20.47.7
    optixRtnIFBITTESTCurTime OBJECT-TYPE
        SYNTAX OCTET STRING
        MAX-ACCESS accessible-for-notify
        STATUS current
        DESCRIPTION
            "Indicates the current time of a test in the format of YYYYMMDDHHMMSS and the time starts from the year 1990."
        ::= { optixRtnIFBitTestEvent 7 }
		
    -- 1.3.6.1.4.1.2011.2.25.4.40.5.20.47.8	
    optixRtnIFBITTESTProgress OBJECT-TYPE
       SYNTAX Unsigned32
        MAX-ACCESS accessible-for-notify
        STATUS current
        DESCRIPTION
            "Indicates the test progress. Value range: 1-100"
        ::= { optixRtnIFBitTestEvent 8 }
		
    -- 1.3.6.1.4.1.2011.2.25.4.40.5.20.47.9
    optixRtnIFBITTESTDataTypeNum OBJECT-TYPE
        SYNTAX Unsigned32
        MAX-ACCESS accessible-for-notify
        STATUS current
        DESCRIPTION
            "Indicates the number of parameter types N (N >= 1 and currently N = 2). The data types are described as follows:"
        ::= { optixRtnIFBitTestEvent 9 }
		
    -- 1.3.6.1.4.1.2011.2.25.4.40.5.20.47.10
    optixRtnIFBITTESTType1 OBJECT-TYPE
        SYNTAX Unsigned32
        MAX-ACCESS accessible-for-notify
        STATUS current
        DESCRIPTION
             "The data types are as follows:
1: number of bit errors
2: BER (calculated based on the number of bit errors)
3: errored second
4: severely errored second
5: unavailable second
6: background block error"
        ::= { optixRtnIFBitTestEvent 10 }
		
    -- 1.3.6.1.4.1.2011.2.25.4.40.5.20.47.11		
    optixRtnIFBITTESTTestResult1 OBJECT-TYPE
        SYNTAX Unsigned32
        MAX-ACCESS accessible-for-notify
        STATUS current
        DESCRIPTION
    "Indicates the statistics. 
Each 5-byte string represents the accumulative value for a certain type of statistics data. The first byte indicates the data type and the other four bytes indicate the accumulative value."
        ::= { optixRtnIFBitTestEvent 11 }
		
    -- 1.3.6.1.4.1.2011.2.25.4.40.5.20.47.12
    optixRtnIFBITTESTType2 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitTestEvent 12 }
		
    -- 1.3.6.1.4.1.2011.2.25.4.40.5.20.47.13
    optixRtnIFBITTESTTestResult2 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitTestEvent 13 }
		
     -- 1.3.6.1.4.1.2011.2.25.4.40.5.20.47.14
     optixRtnIFBITTESTType3 OBJECT-TYPE
         SYNTAX Unsigned32
         MAX-ACCESS accessible-for-notify
         STATUS current
         DESCRIPTION
            "The data types are as follows:
1: number of bit errors
2: BER (calculated based on the number of bit errors)
3: errored second
4: severely errored second
5: unavailable second
6: background block error"
        ::= { optixRtnIFBitTestEvent 14 }
		
    -- 1.3.6.1.4.1.2011.2.25.4.40.5.20.47.15		
    optixRtnIFBITTESTTestResult3 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitTestEvent 15 }
		
     -- 1.3.6.1.4.1.2011.2.25.4.40.5.20.47.16
     optixRtnIFBITTESTType4 OBJECT-TYPE
         SYNTAX Unsigned32
         MAX-ACCESS accessible-for-notify
         STATUS current
         DESCRIPTION
            "The data types are as follows:
1: number of bit errors
2: BER (calculated based on the number of bit errors)
3: errored second
4: severely errored second
5: unavailable second
6: background block error"
        ::= { optixRtnIFBitTestEvent 16 }
		
     -- 1.3.6.1.4.1.2011.2.25.4.40.5.20.47.17
     optixRtnIFBITTESTTestResult4 OBJECT-TYPE
         SYNTAX Unsigned32
         MAX-ACCESS accessible-for-notify
         STATUS current
         DESCRIPTION
            "Indicates the statistics. 
Each 5-byte string represents the accumulative value for a certain type of statistics data. The first byte indicates the data type and the other four bytes indicate the accumulative value."
        ::= { optixRtnIFBitTestEvent 17 }
		
     -- 1.3.6.1.4.1.2011.2.25.4.40.5.20.47.18		
     optixRtnIFBITTESTType5 OBJECT-TYPE
         SYNTAX Unsigned32
         MAX-ACCESS accessible-for-notify
         STATUS current
         DESCRIPTION
            "The data types are as follows:
1: number of bit errors
2: BER (calculated based on the number of bit errors)
3: errored second
4: severely errored second
5: unavailable second
6: background block error"
        ::= { optixRtnIFBitTestEvent 18 }
		
     -- 1.3.6.1.4.1.2011.2.25.4.40.5.20.47.19
     optixRtnIFBITTESTTestResult5 OBJECT-TYPE
         SYNTAX Unsigned32
         MAX-ACCESS accessible-for-notify
         STATUS current
         DESCRIPTION
            "Indicates the statistics. 
Each 5-byte string represents the accumulative value for a certain type of statistics data. The first byte indicates the data type and the other four bytes indicate the accumulative value."
        ::= { optixRtnIFBitTestEvent 19 }
		
     -- 1.3.6.1.4.1.2011.2.25.4.40.5.20.47.20
     optixRtnIFBITTESTType6 OBJECT-TYPE
         SYNTAX Unsigned32
         MAX-ACCESS accessible-for-notify
         STATUS current
         DESCRIPTION
            "The data types are as follows:
1: number of bit errors
2: BER (calculated based on the number of bit errors)
3: errored second
4: severely errored second
5: unavailable second
6: background block error"
        ::= { optixRtnIFBitTestEvent 20 }
		
     -- 1.3.6.1.4.1.2011.2.25.4.40.5.20.47.21
     optixRtnIFBITTESTTestResult6 OBJECT-TYPE
         SYNTAX Unsigned32
         MAX-ACCESS accessible-for-notify
         STATUS current
         DESCRIPTION
            "Indicates the statistics. 
Each 5-byte string represents the accumulative value for a certain type of statistics data. The first byte indicates the data type and the other four bytes indicate the accumulative value."
        ::= { optixRtnIFBitTestEvent 21 }

    -- 1.3.6.1.4.1.2011.2.25.4.40.5.20.48
    optixRtnIFBitErrorCodeExTestEvent OBJECT IDENTIFIER ::= { optixRtnProtectTrapCommon 48 }

    -- 1.3.6.1.4.1.2011.2.25.4.40.5.20.48.1
    optixRtnIFBitEXTestBoardId OBJECT-TYPE
        SYNTAX Unsigned32
        MAX-ACCESS accessible-for-notify
        STATUS current
        DESCRIPTION
            "Indicates the slot ID of the IF board."
        ::= { optixRtnIFBitErrorCodeExTestEvent 1 }

    -- 1.3.6.1.4.1.2011.2.25.4.40.5.20.48.2
    optixRtnIFBitEXTestSubCardId OBJECT-TYPE
        SYNTAX Unsigned32
        MAX-ACCESS accessible-for-notify
        STATUS current
        DESCRIPTION
            "Indicates the subcard ID."
        ::= { optixRtnIFBitErrorCodeExTestEvent 2 }

    -- 1.3.6.1.4.1.2011.2.25.4.40.5.20.48.3
    optixRtnIFBitEXTestPortId OBJECT-TYPE
        SYNTAX Unsigned32
        MAX-ACCESS accessible-for-notify
        STATUS current
        DESCRIPTION
            "Indicates the port ID."
        ::= { optixRtnIFBitErrorCodeExTestEvent 3 }

    -- 1.3.6.1.4.1.2011.2.25.4.40.5.20.48.4
    optixRtnIFBitEXTestMode OBJECT-TYPE
        SYNTAX INTEGER
        {
            shortTerm(1),
            longTerm(2),
            longlongTerm(3)
        }
        MAX-ACCESS accessible-for-notify
        STATUS current
        DESCRIPTION
            "Indicates the test type. 
1: short-term test
2: long-term test
3: super long-term test"
        ::= { optixRtnIFBitErrorCodeExTestEvent 4 }

    -- 1.3.6.1.4.1.2011.2.25.4.40.5.20.48.5
    optixRtnIFBitEXTestTimeStamp OBJECT-TYPE
        SYNTAX Unsigned32
        MAX-ACCESS accessible-for-notify
        STATUS current
        DESCRIPTION
            "The value starts from 0x0001. The test duration is measured in seconds in short-term tests and minutes in long-term tests and super-long-term tests."
        ::= { optixRtnIFBitErrorCodeExTestEvent 5 }

    -- 1.3.6.1.4.1.2011.2.25.4.40.5.20.48.6
    optixRtnIFBitEXTestStartTime OBJECT-TYPE
        SYNTAX OCTET STRING
        MAX-ACCESS accessible-for-notify
        STATUS current
        DESCRIPTION
            "Indicates the start time of a test in the format of YYYYMMDDHHMMSS and the time starts from the year 1990."
        ::= { optixRtnIFBitErrorCodeExTestEvent 6 }

    -- 1.3.6.1.4.1.2011.2.25.4.40.5.20.48.7
    optixRtnIFBitEXTestCurTime OBJECT-TYPE
        SYNTAX OCTET STRING
        MAX-ACCESS accessible-for-notify
        STATUS current
        DESCRIPTION
            "Indicates the current time of a test in the format of YYYYMMDDHHMMSS and the time starts from the year 1990."
        ::= { optixRtnIFBitErrorCodeExTestEvent 7 }

    -- 1.3.6.1.4.1.2011.2.25.4.40.5.20.48.8
    optixRtnIFBitEXTestProgress OBJECT-TYPE
        SYNTAX Unsigned32
        MAX-ACCESS accessible-for-notify
        STATUS current
        DESCRIPTION
            "Indicates the test progress. Value range: 1-100"
        ::= { optixRtnIFBitErrorCodeExTestEvent 8 }

    -- 1.3.6.1.4.1.2011.2.25.4.40.5.20.48.9
    optixRtnIFBitEXTestDataTypeNum OBJECT-TYPE
        SYNTAX Unsigned32
        MAX-ACCESS accessible-for-notify
        STATUS current
        DESCRIPTION
            "Indicates the number of parameter types N (N >= 1 and currently N = 2). The data types are described as follows:"
        ::= { optixRtnIFBitErrorCodeExTestEvent 9 }

    -- 1.3.6.1.4.1.2011.2.25.4.40.5.20.48.10
    optixRtnIFBitEXTestType1 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeExTestEvent 10 }

    -- 1.3.6.1.4.1.2011.2.25.4.40.5.20.48.11
    optixRtnIFBitEXTestTestResult1 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeExTestEvent 11 }

    -- 1.3.6.1.4.1.2011.2.25.4.40.5.20.48.12
    optixRtnIFBitEXTestType2 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnIFBitErrorCodeExTestEvent 12 }

    -- 1.3.6.1.4.1.2011.2.25.4.40.5.20.48.13
    optixRtnIFBitEXTestTestResult2 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnIFBitErrorCodeExTestEvent 13 }

    -- 1.3.6.1.4.1.2011.2.25.4.40.5.20.49
    optixRtnE1PRBSTestEvent OBJECT IDENTIFIER ::= { optixRtnProtectTrapCommon 49 }

    -- 1.3.6.1.4.1.2011.2.25.4.40.5.20.49.1
    optixRtnE1PRBSBoardId OBJECT-TYPE
        SYNTAX Unsigned32
        MAX-ACCESS accessible-for-notify
        STATUS current
        DESCRIPTION
            "Indicates the slot ID of the IF board."
        ::= { optixRtnE1PRBSTestEvent 1 }

    -- 1.3.6.1.4.1.2011.2.25.4.40.5.20.49.2
    optixRtnE1PRBSSubCardId OBJECT-TYPE
        SYNTAX Unsigned32
        MAX-ACCESS accessible-for-notify
        STATUS current
        DESCRIPTION
            "Indicates the subcard ID."
        ::= { optixRtnE1PRBSTestEvent 2 }

    -- 1.3.6.1.4.1.2011.2.25.4.40.5.20.49.3
    optixRtnE1PRBSPortId OBJECT-TYPE
        SYNTAX Unsigned32
        MAX-ACCESS accessible-for-notify
        STATUS current
        DESCRIPTION
            "Indicates the port ID."
        ::= { optixRtnE1PRBSTestEvent 3 }

    -- 1.3.6.1.4.1.2011.2.25.4.40.5.20.49.4
    optixRtnE1PRBSPathId OBJECT-TYPE
        SYNTAX Unsigned32
        MAX-ACCESS accessible-for-notify
        STATUS current
        DESCRIPTION
            "Indicates the path ID.
Set the parameter to 0 if this field is not in use."
        ::= { optixRtnE1PRBSTestEvent 4 }

    -- 1.3.6.1.4.1.2011.2.25.4.40.5.20.49.5
    optixRtnE1PRBSDirection OBJECT-TYPE
        SYNTAX INTEGER
        {
            ingressDir(1),
            egressDir(2)
        }
        MAX-ACCESS accessible-for-notify
        STATUS current
        DESCRIPTION
            "Indicates the test direction:
1-Ingress
2-Egress"
        ::= { optixRtnE1PRBSTestEvent 5 }

    -- 1.3.6.1.4.1.2011.2.25.4.40.5.20.49.6
    optixRtnE1PRBSMode OBJECT-TYPE
        SYNTAX INTEGER
        {
            shortTerm(1),
            longTerm(2),
            longlongTerm(3)
        }
        MAX-ACCESS accessible-for-notify
        STATUS current
        DESCRIPTION
            "Indicates the test type. 
1: short-term test
2: long-term test
3: super long-term test"
        ::= { optixRtnE1PRBSTestEvent 6 }

    -- 1.3.6.1.4.1.2011.2.25.4.40.5.20.49.7
    optixRtnE1PRBSTimeStamp OBJECT-TYPE
        SYNTAX Unsigned32
        MAX-ACCESS accessible-for-notify
        STATUS current
        DESCRIPTION
            "The value starts from 0x0001. The test duration is measured in seconds in short-term tests and minutes in long-term tests and super-long-term tests."
        ::= { optixRtnE1PRBSTestEvent 7 }

    -- 1.3.6.1.4.1.2011.2.25.4.40.5.20.49.8
    optixRtnE1PRBSStartTime OBJECT-TYPE
        SYNTAX OCTET STRING
        MAX-ACCESS accessible-for-notify
        STATUS current
        DESCRIPTION
            "Indicates the start time of a test in the format of YYYYMMDDHHMMSS and the time starts from the year 1990."
        ::= { optixRtnE1PRBSTestEvent 8 }

    -- 1.3.6.1.4.1.2011.2.25.4.40.5.20.49.9
    optixRtnE1PRBSCurTime OBJECT-TYPE
        SYNTAX OCTET STRING
        MAX-ACCESS accessible-for-notify
        STATUS current
        DESCRIPTION
            "Indicates the current time of a test in the format of YYYYMMDDHHMMSS and the time starts from the year 1990."
        ::= { optixRtnE1PRBSTestEvent 9 }

    -- 1.3.6.1.4.1.2011.2.25.4.40.5.20.49.10
    optixRtnE1PRBSProgress OBJECT-TYPE
        SYNTAX Unsigned32
        MAX-ACCESS accessible-for-notify
        STATUS current
        DESCRIPTION
            "Indicates the test progress. Value range: 1-100"
        ::= { optixRtnE1PRBSTestEvent 10 }

    -- 1.3.6.1.4.1.2011.2.25.4.40.5.20.49.11
    optixRtnE1PRBSDataTypeNum OBJECT-TYPE
        SYNTAX Unsigned32
        MAX-ACCESS accessible-for-notify
        STATUS current
        DESCRIPTION
            "Indicates the number of parameter types N (N >= 1 and currently N = 2). The data types are described as follows:"
        ::= { optixRtnE1PRBSTestEvent 11 }

    -- 1.3.6.1.4.1.2011.2.25.4.40.5.20.49.12
    optixRtnE1PRBSType1 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnE1PRBSTestEvent 12 }

    -- 1.3.6.1.4.1.2011.2.25.4.40.5.20.49.13
    optixRtnE1PRBSTestResult1 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnE1PRBSTestEvent 13 }

    -- 1.3.6.1.4.1.2011.2.25.4.40.5.20.49.14
    optixRtnE1PRBSType2 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnE1PRBSTestEvent 14 }

    -- 1.3.6.1.4.1.2011.2.25.4.40.5.20.49.15
    optixRtnE1PRBSTestResult2 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnE1PRBSTestEvent 15 }

    -- 1.3.6.1.4.1.2011.2.25.4.40.5.20.49.16
    optixRtnE1PRBSType3 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnE1PRBSTestEvent 16 }

    -- 1.3.6.1.4.1.2011.2.25.4.40.5.20.49.17
    optixRtnE1PRBSTestResult3 OBJECT-TYPE
        SYNTAX Unsigned32
        MAX-ACCESS accessible-for-notify
        STATUS current
        DESCRIPTION
            "Indicates the statistics. 
                Each 5-byte string represents the accumulative value for a certain type of statistics data. The first byte indicates the data type and the other four bytes indicate the accumulative value."
        ::= { optixRtnE1PRBSTestEvent 17 }

    -- 1.3.6.1.4.1.2011.2.25.4.40.5.20.49.19
    optixRtnE1PRBSType4 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnE1PRBSTestEvent 19 }

    -- 1.3.6.1.4.1.2011.2.25.4.40.5.20.49.20
    optixRtnE1PRBSTestResult4 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnE1PRBSTestEvent 20 }

    -- 1.3.6.1.4.1.2011.2.25.4.40.5.20.49.21
    optixRtnE1PRBSType5 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnE1PRBSTestEvent 21 }

    -- 1.3.6.1.4.1.2011.2.25.4.40.5.20.49.22
    optixRtnE1PRBSTestResult5 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnE1PRBSTestEvent 22 }

    -- 1.3.6.1.4.1.2011.2.25.4.40.5.20.49.23
    optixRtnE1PRBSType6 OBJECT-TYPE
        SYNTAX Unsigned32
        MAX-ACCESS accessible-for-notify
        STATUS current
        DESCRIPTION
            "The data types are as follows:
1: number of bit errors
2: BER (calculated based on the number of bit errors)
3: errored second
4: severely errored second
5: unavailable second
6: background block error"
        ::= { optixRtnE1PRBSTestEvent 23 }

    -- 1.3.6.1.4.1.2011.2.25.4.40.5.20.49.24
    optixRtnE1PRBSTestResult6 OBJECT-TYPE
        SYNTAX Unsigned32
        MAX-ACCESS accessible-for-notify
        STATUS current
        DESCRIPTION
            "Indicates the statistics. 
Each 5-byte string represents the accumulative value for a certain type of statistics data. The first byte indicates the data type and the other four bytes indicate the accumulative value."
        ::= { optixRtnE1PRBSTestEvent 24 }

    -- 1.3.6.1.4.1.2011.2.25.4.40.5.20.90
    optixRptRtnAggergationMemberStateEvent OBJECT IDENTIFIER ::= { optixRtnProtectTrapCommon 90 }

    -- 1.3.6.1.4.1.2011.2.25.4.40.5.20.90.1
    optixRptRtnMSGroupID OBJECT-TYPE
        SYNTAX Unsigned32
        MAX-ACCESS accessible-for-notify
        STATUS current
        DESCRIPTION
            "Indicates the cascading PLA protection group ID."
        ::= { optixRptRtnAggergationMemberStateEvent 1 }

    -- 1.3.6.1.4.1.2011.2.25.4.40.5.20.90.2
    optixRptRtnMSGroupType OBJECT-TYPE
        SYNTAX OPTIXRtnPhyLagPGType
        MAX-ACCESS accessible-for-notify
        STATUS current
        DESCRIPTION
            "Indicates the main NE ID."
        ::= { optixRptRtnAggergationMemberStateEvent 2 }

    -- 1.3.6.1.4.1.2011.2.25.4.40.5.20.90.3
    optixRptRtnMSBoardID OBJECT-TYPE
        SYNTAX Unsigned32
        MAX-ACCESS accessible-for-notify
        STATUS current
        DESCRIPTION
            "Indicates the slot ID of the slave unit."
        ::= { optixRptRtnAggergationMemberStateEvent 3 }

    -- 1.3.6.1.4.1.2011.2.25.4.40.5.20.90.4
    optixRptRtnMSSubBoardID OBJECT-TYPE
        SYNTAX Unsigned32
        MAX-ACCESS accessible-for-notify
        STATUS current
        DESCRIPTION
            "Indicates the subboard ID of the slave unit."
        ::= { optixRptRtnAggergationMemberStateEvent 4 }

    -- 1.3.6.1.4.1.2011.2.25.4.40.5.20.90.5
    optixRptRtnMSPortID OBJECT-TYPE
        SYNTAX Unsigned32
        MAX-ACCESS accessible-for-notify
        STATUS current
        DESCRIPTION
            "Indicates the port ID of the slave unit."
        ::= { optixRptRtnAggergationMemberStateEvent 5 }

    -- 1.3.6.1.4.1.2011.2.25.4.40.5.20.90.6
    optixRptRtnMSChannelID OBJECT-TYPE
        SYNTAX Unsigned32
        MAX-ACCESS accessible-for-notify
        STATUS current
        DESCRIPTION
            "Indicates the channel ID of the salve unit."
        ::= { optixRptRtnAggergationMemberStateEvent 6 }

    -- 1.3.6.1.4.1.2011.2.25.4.40.5.20.90.7
    optixRptRtnMSHardState OBJECT-TYPE
        SYNTAX INTEGER
        {
            normal(0),
            abnormal(1),
            unknown(-1)
        }
        MAX-ACCESS accessible-for-notify
        STATUS current
        DESCRIPTION
            "Indicates the hardware status of the salve unit. The values: 0: normal 1: abnormal"
        ::= { optixRptRtnAggergationMemberStateEvent 7 }

    -- 1.3.6.1.4.1.2011.2.25.4.40.5.20.90.8
    optixRptRtnMSLinkState OBJECT-TYPE
        SYNTAX INTEGER
        {
            normal(0),
            abnormal(1),
            unknown(-1)
        }
        MAX-ACCESS accessible-for-notify
        STATUS current
        DESCRIPTION
            "Indicates the link status of the slave unit. The values: 0: normal 1: abnormal"
        ::= { optixRptRtnAggergationMemberStateEvent 8 }

    -- 1.3.6.1.4.1.2011.2.25.4.40.5.20.90.9
    optixRptRtnMSMasterSlaveState OBJECT-TYPE
        SYNTAX INTEGER
        {
            slave(0),
            master(1),
            unknown(255)
        }
        MAX-ACCESS accessible-for-notify
        STATUS current
        DESCRIPTION
            "Indicates the working status of the main unit. Values: 0: slave port 1: main port"
        ::= { optixRptRtnAggergationMemberStateEvent 9 }

    -- 1.3.6.1.4.1.2011.2.25.4.40.5.20.100
    optixRptRtnAggergationMemberPriEvent OBJECT IDENTIFIER ::= { optixRtnProtectTrapCommon 100 }

    -- 1.3.6.1.4.1.2011.2.25.4.40.5.20.100.1
    optixRptRtnEPLAGroupID OBJECT-TYPE
        SYNTAX Unsigned32
        MAX-ACCESS accessible-for-notify
        STATUS current
        DESCRIPTION
            "Indicates the cascading PLA protection group ID."
        ::= { optixRptRtnAggergationMemberPriEvent 1 }

    -- 1.3.6.1.4.1.2011.2.25.4.40.5.20.100.2
    optixRptRtnEPLAGroupType OBJECT-TYPE
        SYNTAX OPTIXRtnPhyLagPGType
        MAX-ACCESS accessible-for-notify
        STATUS current
        DESCRIPTION
            "Indicates the main NE ID."
        ::= { optixRptRtnAggergationMemberPriEvent 2 }

    -- 1.3.6.1.4.1.2011.2.25.4.40.5.20.100.3
    optixRptRtnEPLABoardID OBJECT-TYPE
        SYNTAX Unsigned32
        MAX-ACCESS accessible-for-notify
        STATUS current
        DESCRIPTION
            "Indicates the slot ID of the slave unit."
        ::= { optixRptRtnAggergationMemberPriEvent 3 }

    -- 1.3.6.1.4.1.2011.2.25.4.40.5.20.100.4
    optixRptRtnEPLASubBoardID OBJECT-TYPE
        SYNTAX Unsigned32
        MAX-ACCESS accessible-for-notify
        STATUS current
        DESCRIPTION
            "Indicates the subboard ID of the slave unit."
        ::= { optixRptRtnAggergationMemberPriEvent 4 }

    -- 1.3.6.1.4.1.2011.2.25.4.40.5.20.100.5
    optixRptRtnEPLAPortID OBJECT-TYPE
        SYNTAX Unsigned32
        MAX-ACCESS accessible-for-notify
        STATUS current
        DESCRIPTION
            "Indicates the port ID of the slave unit."
        ::= { optixRptRtnAggergationMemberPriEvent 5 }

    -- 1.3.6.1.4.1.2011.2.25.4.40.5.20.100.6
    optixRptRtnEPLAChannelID OBJECT-TYPE
        SYNTAX Unsigned32
        MAX-ACCESS accessible-for-notify
        STATUS current
        DESCRIPTION
            "Indicates the channel ID of the salve unit."
        ::= { optixRptRtnAggergationMemberPriEvent 6 }

    -- 1.3.6.1.4.1.2011.2.25.4.40.5.20.100.7
    optixRptRtnEPLACfgPri OBJECT-TYPE
        SYNTAX INTEGER
        {
            auto(0),
            lowpri(1),
            highpri(2),
            unknown(255)
        }
        MAX-ACCESS accessible-for-notify
        STATUS current
        DESCRIPTION
            "Indicates the config prority of the slave unit.0: auto; 1: lowPri; 2: highPri 0xff: unknown"
        ::= { optixRptRtnAggergationMemberPriEvent 7 }

    -- 1.3.6.1.4.1.2011.2.25.4.40.5.20.100.8
    optixRptRtnEPLAWorkPri OBJECT-TYPE
        SYNTAX INTEGER
        {
            auto(0),
            lowpri(1),
            highpri(2),
            unknown(-1)
        }
        MAX-ACCESS accessible-for-notify
        STATUS current
        DESCRIPTION
            "Indicates the scheduling mode of the slave unit. 0: auto; 1: lowPri; 2: highPri 0xff: unknown"
        ::= { optixRptRtnAggergationMemberPriEvent 8 }

    -- 1.3.6.1.4.1.2011.2.25.4.40.5.30
    optixRtnTrap OBJECT IDENTIFIER ::= { optixRtnIFProtectMgr 30 }

    -- 1.3.6.1.4.1.2011.2.25.4.40.5.30.10
    optixRtnIF1j1PGSwitchTrap NOTIFICATION-TYPE
        OBJECTS{ optixRptRtn1j1PGID,optixRptRtn1j1PGCurrWorkBoardID,optixRptRtn1j1PGCurrWorkSubCardID,optixRptRtn1j1PGCurrWorkPortID,optixRptRtn1j1PGCurrWorkChannel,optixRptRtn1j1PGMainBoardState,optixRptRtn1j1PGBackupBoardState,optixRptRtn1j1PGSwitchRequest }
        STATUS current
        DESCRIPTION
            "Indicates an IF 1+1 protection group switching event."
        ::= { optixRtnTrap 10 }

    -- 1.3.6.1.4.1.2011.2.25.4.40.5.30.20
    optixRtnIFNj1PGSwitchTrap NOTIFICATION-TYPE
        OBJECTS{ optixRptRtnNj1PGID,optixRptRtnNj1Channel,optixRptRtnNj1PGSwitchRequest,optixRptRtnNj1PGSwitchState,optixRptRtnNj1PGProtectedPath,optixRptRtnNj1PGFarNearIndicate,optixRptRtnNj1PGSwitchReason }
        STATUS current
        DESCRIPTION
            "Indicates an IF N+1 protection group switching event."
        ::= { optixRtnTrap 20 }

    -- 1.3.6.1.4.1.2011.2.25.4.40.5.30.21
    optixRtnIFNj1PGFarNoResponseTrap NOTIFICATION-TYPE
        OBJECTS{ optixRptRtnNj1PGID,optixRptRtnNj1PGProtectedPath,optixRptRtnNj1PGSwitchRequest }
        STATUS current
        DESCRIPTION
            "Indicates an IF N+1 protection group no far-end response event."
        ::= { optixRtnTrap 21 }

    -- 1.3.6.1.4.1.2011.2.25.4.40.5.30.30
    optixRtnIFPhyLagPGSwitchTrap NOTIFICATION-TYPE
        OBJECTS{ optixRptRtnPLAPGID,optixRptRtnPLAPGMainBoardID,optixRptRtnPLAPGMainSubCardID,optixRptRtnPLAPGMainPortID,optixRptRtnPLAPGMainHardStatus,optixRptRtnPLAPGMainLinkStatus,optixRptRtnPLAPGMainWorkStatus,optixRptRtnPLAPGSlavePortNum,optixRptRtnPLAPGSlaveBoardID,optixRptRtnPLAPGSlaveSubCardID,optixRptRtnPLAPGSlavePortID,optixRptRtnPLAPGSlaveHardStatus,optixRptRtnPLAPGSlaveLinkStatus,optixRptRtnPLAPGSlaveWorkStatus }
        STATUS current
        DESCRIPTION
            "Indicates an IF PLA group switching event."
        ::= { optixRtnTrap 30 }

    -- 1.3.6.1.4.1.2011.2.25.4.40.5.30.40
    optixRtnIFCascading1j1PGSwitchTrap NOTIFICATION-TYPE
        OBJECTS{ optixRptRtnC1j1PGID,optixRptRtnC1j1PGWorkNEID,optixRptRtnC1j1PGWorkBoardID,optixRptRtnC1j1PGWorkSubCardID,optixRptRtnC1j1PGWorkPortID,optixRptRtnC1j1PGCurrWorkChannel,optixRptRtnC1j1PGWorkBoardState,optixRptRtnC1j1PGProtectBoardState,optixRptRtnC1j1PGSwtichRequest }
        STATUS current
        DESCRIPTION
            "Indicates a cascading IF 1+1 protection group switching event."
        ::= { optixRtnTrap 40 }

    -- 1.3.6.1.4.1.2011.2.25.4.40.5.30.41
    optixRtnNonCascade1j1PGSwitchTrap NOTIFICATION-TYPE
        OBJECTS{ optixRtnNonCascade1J1GPID,optixRtnNonCascade1J1BoardID,optixRtnNonCascade1J1SubCardID,optixRtnNonCascade1J1PortID,optixRtnNonCascade1J1DevWorkBoardProperty,optixRtnNonCascade1J1WorkBoardDevState,optixRtnNonCascade1J1ProtBoardDevState,optixRtnNonCascade1J1DevSwtichRequest }
        STATUS current
        DESCRIPTION
            "Indicates a none-cascading IF 1+1 protection group switching event."
        ::= { optixRtnTrap 41 }

    -- 1.3.6.1.4.1.2011.2.25.4.40.5.30.43
    optixRtnIFBitErrorCodeTestTrap NOTIFICATION-TYPE
        OBJECTS{ optixRtnIFBECTBoardId,optixRtnIFBECTSubCardId,optixRtnIFBECTPortId,optixRtnIFBECTType,optixRtnIFBECTPathId,optixRtnIFBECTDirection,optixRtnIFBECTMode,optixRtnIFBECTTimeStamp,optixRtnIFBECTStartTime,optixRtnIFBECTCurTime,optixRtnIFBECTProgress,optixRtnIFBECTDataTypeNum,optixRtnIFBECTType1,optixRtnIFBECTTestResult1,optixRtnIFBECTType2,optixRtnIFBECTTestResult2,optixRtnIFBECTType3,optixRtnIFBECTTestResult3,optixRtnIFBECTType4,optixRtnIFBECTTestResult4,optixRtnIFBECTType5,optixRtnIFBECTTestResult5,optixRtnIFBECTType6,optixRtnIFBECTTestResult6 }
        STATUS current
        DESCRIPTION
            "Indicates IF bit errors."
        ::= { optixRtnTrap 43 }
		
    -- 1.3.6.1.4.1.2011.2.25.4.40.5.30.46
    optixRtnIFBitOldTestTrap NOTIFICATION-TYPE
        OBJECTS{ optixRtnBECTBoardId,optixRtnBECTSubCardId,optixRtnBECTPortId,optixRtnBECTTimeStamp,optixRtnBECTErrorNum}
        STATUS current
        DESCRIPTION
            "Indicates IF bit errors."
        ::= { optixRtnTrap 46 }
	
    -- 1.3.6.1.4.1.2011.2.25.4.40.5.30.47
    optixRtnIFBitTestTrap NOTIFICATION-TYPE
        OBJECTS{ optixRtnIFBITTESTBoardId,optixRtnIFBITTESTSubCardId,optixRtnIFBITTESTPortId,optixRtnIFBITTESTMode,optixRtnIFBITTESTTimeStamp,optixRtnIFBITTESTStartTime,optixRtnIFBITTESTCurTime,optixRtnIFBITTESTProgress,optixRtnIFBITTESTDataTypeNum,optixRtnIFBITTESTType1,optixRtnIFBITTESTTestResult1,optixRtnIFBITTESTType2,optixRtnIFBITTESTTestResult2,optixRtnIFBITTESTType3,optixRtnIFBITTESTTestResult3,optixRtnIFBITTESTType4,optixRtnIFBITTESTTestResult4,optixRtnIFBITTESTType5,optixRtnIFBITTESTTestResult5,optixRtnIFBITTESTType6,optixRtnIFBITTESTTestResult6}
        STATUS current
        DESCRIPTION
            "Indicates IF bit errors."
        ::= { optixRtnTrap 47 }	

    -- 1.3.6.1.4.1.2011.2.25.4.40.5.30.48
    optixRtnIFBitErrorCodeExTestTrap NOTIFICATION-TYPE
        OBJECTS{ optixRtnIFBitEXTestBoardId,optixRtnIFBitEXTestSubCardId,optixRtnIFBitEXTestPortId,optixRtnIFBitEXTestMode,optixRtnIFBitEXTestTimeStamp,optixRtnIFBitEXTestStartTime,optixRtnIFBitEXTestCurTime,optixRtnIFBitEXTestProgress,optixRtnIFBitEXTestDataTypeNum,optixRtnIFBitEXTestType1,optixRtnIFBitEXTestTestResult1,optixRtnIFBitEXTestType2,optixRtnIFBitEXTestTestResult2 }
        STATUS current
        DESCRIPTION
            "Indicates IF bit errors."
        ::= { optixRtnTrap 48 }

    -- 1.3.6.1.4.1.2011.2.25.4.40.5.30.49
    optixRtnE1PRBSTestTrap NOTIFICATION-TYPE
        OBJECTS{ optixRtnE1PRBSBoardId,optixRtnE1PRBSSubCardId,optixRtnE1PRBSPortId,optixRtnE1PRBSPathId,optixRtnE1PRBSDirection,optixRtnE1PRBSMode,optixRtnE1PRBSTimeStamp,optixRtnE1PRBSStartTime,optixRtnE1PRBSCurTime,optixRtnE1PRBSProgress,optixRtnE1PRBSDataTypeNum,optixRtnE1PRBSType1,optixRtnE1PRBSTestResult1,optixRtnE1PRBSType2,optixRtnE1PRBSTestResult2,optixRtnE1PRBSType3,optixRtnE1PRBSTestResult3,optixRtnE1PRBSType4,optixRtnE1PRBSTestResult4,optixRtnE1PRBSType5,optixRtnE1PRBSTestResult5,optixRtnE1PRBSType6,optixRtnE1PRBSTestResult6 }
        STATUS current
        DESCRIPTION
            "Indicates result of the E1prbs extension interface."
        ::= { optixRtnTrap 49 }

    -- 1.3.6.1.4.1.2011.2.25.4.40.5.30.50
    optixRtnIFCascadingPhyLagPGSwitchTrap NOTIFICATION-TYPE
        OBJECTS{ optixRptRtnCPLAPGID,optixRptRtnCPLAPGMainNEID,optixRptRtnCPLAPGMainBoardID,optixRptRtnCPLAPGMainSubID,optixRptRtnCPLAPGMainPortID,optixRptRtnCPLAPGMainHardStatus,optixRptRtnCPLAPGMainLinkStatus,optixRptRtnCPLAPGMainMSStatus,optixRptRtnCPLAPGSlavePuNum,optixRptRtnCPLAPGPu1NEID,optixRptRtnCPLAPGPu1BoardID,optixRptRtnCPLAPGPu1SubCardID,optixRptRtnCPLAPGPu1PortID,optixRptRtnCPLAPGPu1HardStatus,optixRptRtnCPLAPGPu1LinkStatus,optixRptRtnCPLAPGPu1MSStatus }
        STATUS current
        DESCRIPTION
            "Indicates a cascading PLA group switching event."
        ::= { optixRtnTrap 50 }

    -- 1.3.6.1.4.1.2011.2.25.4.40.5.30.60
    optixRtnIFCascadingPhyLagPGSwitchTrapExt NOTIFICATION-TYPE
        OBJECTS{ optixRptRtnCPLAPGID,optixRptRtnCPLAPGMainNEID,optixRptRtnCPLAPGMainBoardID,optixRptRtnCPLAPGMainSubID,optixRptRtnCPLAPGMainPortID,optixRptRtnCPLAPGMainHardStatus,optixRptRtnCPLAPGMainLinkStatus,optixRptRtnCPLAPGMainMSStatus }
        STATUS current
        DESCRIPTION
            "Indicates a cascading PLA group switching event."
        ::= { optixRtnTrap 60 }

    -- 1.3.6.1.4.1.2011.2.25.4.40.5.30.90
    optixRtnIFPhyAggMemberStateSwitchTrapExt NOTIFICATION-TYPE
        OBJECTS{ optixRptRtnMSGroupID,optixRptRtnMSGroupType,optixRptRtnMSBoardID,optixRptRtnMSSubBoardID,optixRptRtnMSPortID,optixRptRtnMSChannelID,optixRptRtnMSHardState,optixRptRtnMSLinkState,optixRptRtnMSMasterSlaveState }
        STATUS current
        DESCRIPTION
            "Indicates the member state switching event of a PLA group"
        ::= { optixRtnTrap 90 }

    -- 1.3.6.1.4.1.2011.2.25.4.40.5.30.240
    optixRtnIFPhyLagPGScheduleModeChangeTrap NOTIFICATION-TYPE
        OBJECTS{ optixRptRtnPLAPGId,optixRptRtnPLAPGType,optixRptRtnPLAPGCfgMode,optixRptRtnPLAPGWorkMode}
        STATUS current
        DESCRIPTION
            "Indicates an IF PLA group schedule mode change event."
        ::= { optixRtnTrap 240 }

    -- 1.3.6.1.4.1.2011.2.25.4.40.5.30.100
    optixRtnIFPhyAggMemberPriSwitchTrapExt NOTIFICATION-TYPE
        OBJECTS{ optixRptRtnEPLAGroupID,optixRptRtnEPLAGroupType,optixRptRtnEPLABoardID,optixRptRtnEPLASubBoardID,optixRptRtnEPLAPortID,optixRptRtnEPLAChannelID,optixRptRtnEPLACfgPri,optixRptRtnEPLAWorkPri }
        STATUS current
        DESCRIPTION
            "Indicates the member priority switching event of a PLA group"
        ::= { optixRtnTrap 100 }

    -- 1.3.6.1.4.1.2011.2.25.4.40.5.40
    optixRtnCCDPParaMgr OBJECT IDENTIFIER ::= { optixRtnIFProtectMgr 40 }

    -- 1.3.6.1.4.1.2011.2.25.4.40.5.40.1
    optixRtnCCDPTable OBJECT-TYPE
        SYNTAX SEQUENCE OF OptixRtnCCDPEntry
        MAX-ACCESS not-accessible
        STATUS current
        DESCRIPTION
            "Indicates the CCDP cascading port number table."
        ::= { optixRtnCCDPParaMgr 1 }

    -- 1.3.6.1.4.1.2011.2.25.4.40.5.40.1.1
    optixRtnCCDPEntry OBJECT-TYPE
        SYNTAX OptixRtnCCDPEntry
        MAX-ACCESS not-accessible
        STATUS current
        DESCRIPTION
            "CCDP ENTRY"
        INDEX{ optixRtnBoardID,optixRtnSubCardID,optixRtnPortID }
        ::= { optixRtnCCDPTable 1 }

    OptixRtnCCDPEntry ::=
        SEQUENCE {
            optixRtnCascadingPortId
                Unsigned32
        }

    -- 1.3.6.1.4.1.2011.2.25.4.40.5.40.1.1.2
    optixRtnCascadingPortId OBJECT-TYPE
        SYNTAX Unsigned32
        MAX-ACCESS read-write
        STATUS current
        DESCRIPTION
            "CCDP cascading port number"
        ::= { optixRtnCCDPEntry 2 }

    -- 1.3.6.1.4.1.2011.2.25.4.40.5.41
    optixRtnDfhParaMgr OBJECT IDENTIFIER ::= { optixRtnIFProtectMgr 41 }

    -- 1.3.6.1.4.1.2011.2.25.4.40.5.41.1
    optixRtnDfhTable OBJECT-TYPE
        SYNTAX SEQUENCE OF OptixRtnDfhEntry
        MAX-ACCESS not-accessible
        STATUS current
        DESCRIPTION
            "Indicates the RtnDfhParaMgr"
        ::= { optixRtnDfhParaMgr 1 }

    -- 1.3.6.1.4.1.2011.2.25.4.40.5.41.1.1
    optixRtnDfhEntry OBJECT-TYPE
        SYNTAX OptixRtnDfhEntry
        MAX-ACCESS not-accessible
        STATUS current
        DESCRIPTION
            "Indicates the Dfh ENTRY"
        INDEX{ optixRtnBoardID,optixRtnSubCardID,optixRtnPortID }
        ::= { optixRtnDfhTable 1 }

    OptixRtnDfhEntry ::=
        SEQUENCE {
            optixRtnDfhMode
                INTEGER,
            optixRtnDfhEnable
                INTEGER,
            optixRtnDfhFreq
                Unsigned32,
            optixRtnDfhState
                INTEGER,
            optixRtnTddRatio
                Unsigned32,
            optixRtnRealTddRatio
                Unsigned32,
            optixRtnAllValidFreq
                OCTET STRING,
            optixRtnTxFreqRgNum
                Unsigned32,
            optixRtnTxFreqRange
                OCTET STRING,
            optixRtnRslScanResult
                OCTET STRING,
            optixRtnAllTddRatio
                OCTET STRING,
            optixRtnActiveRslScan
                Unsigned32
        }

    -- 1.3.6.1.4.1.2011.2.25.4.40.5.41.1.1.1
    optixRtnDfhMode OBJECT-TYPE
        SYNTAX INTEGER
        {
            master(1),
            slave(2)
        }
        MAX-ACCESS read-write
        STATUS current
        DESCRIPTION
            "Indicates the Dfh mode"
        ::= { optixRtnDfhEntry 1 }

    -- 1.3.6.1.4.1.2011.2.25.4.40.5.41.1.1.2
    optixRtnDfhEnable OBJECT-TYPE
        SYNTAX INTEGER
        {
            disable(0),
            enable(1)
        }
        MAX-ACCESS read-write
        STATUS current
        DESCRIPTION
            "Indicates the Dfh enable"
        ::= { optixRtnDfhEntry 2 }

    -- 1.3.6.1.4.1.2011.2.25.4.40.5.41.1.1.3
    optixRtnDfhFreq OBJECT-TYPE
        SYNTAX Unsigned32
        MAX-ACCESS read-write
        STATUS current
        DESCRIPTION
            "Indicates the Dfh frequency"
        ::= { optixRtnDfhEntry 3 }

    -- 1.3.6.1.4.1.2011.2.25.4.40.5.41.1.1.4
    optixRtnDfhState OBJECT-TYPE
        SYNTAX INTEGER
        {
            unlocked(1),
            locked(2),
            paused(3)
        }
        MAX-ACCESS read-write
        STATUS current
        DESCRIPTION
            "Indicates the Dfh state"
        ::= { optixRtnDfhEntry 4 }

    -- 1.3.6.1.4.1.2011.2.25.4.40.5.41.1.1.5
    optixRtnTddRatio OBJECT-TYPE
        SYNTAX Unsigned32
        MAX-ACCESS read-write
        STATUS current
        DESCRIPTION
            "Indicates the tdd ratio"
        ::= { optixRtnDfhEntry 5 }

    -- 1.3.6.1.4.1.2011.2.25.4.40.5.41.1.1.6
    optixRtnRealTddRatio OBJECT-TYPE
        SYNTAX Unsigned32
        MAX-ACCESS read-write
        STATUS current
        DESCRIPTION
            "Indicates the real tdd ratio"
        ::= { optixRtnDfhEntry 6 }

    -- 1.3.6.1.4.1.2011.2.25.4.40.5.41.1.1.7
    optixRtnAllValidFreq OBJECT-TYPE
        SYNTAX OCTET STRING
        MAX-ACCESS read-only
        STATUS current
        DESCRIPTION
            "Indicates all valid frequency"
        ::= { optixRtnDfhEntry 7 }

    -- 1.3.6.1.4.1.2011.2.25.4.40.5.41.1.1.8
    optixRtnTxFreqRgNum OBJECT-TYPE
        SYNTAX Unsigned32
        MAX-ACCESS read-write
        STATUS current
        DESCRIPTION
            "Indicates num of tx frequency range"
        ::= { optixRtnDfhEntry 8 }

    -- 1.3.6.1.4.1.2011.2.25.4.40.5.41.1.1.9
    optixRtnTxFreqRange OBJECT-TYPE
        SYNTAX OCTET STRING
        MAX-ACCESS read-write
        STATUS current
        DESCRIPTION
            "Indicates all tx frequency range"
        ::= { optixRtnDfhEntry 9 }

    -- 1.3.6.1.4.1.2011.2.25.4.40.5.41.1.1.10
    optixRtnRslScanResult OBJECT-TYPE
        SYNTAX OCTET STRING
        MAX-ACCESS read-only
        STATUS current
        DESCRIPTION
            "Indicates all rsl scan result"
        ::= { optixRtnDfhEntry 10 }

    -- 1.3.6.1.4.1.2011.2.25.4.40.5.41.1.1.11
    optixRtnAllTddRatio OBJECT-TYPE
        SYNTAX OCTET STRING
        MAX-ACCESS read-only
        STATUS current
        DESCRIPTION
            "Indicates all tdd ratio"
        ::= { optixRtnDfhEntry 11 }

    -- 1.3.6.1.4.1.2011.2.25.4.40.5.41.1.1.12
    optixRtnActiveRslScan OBJECT-TYPE
        SYNTAX Unsigned32
        MAX-ACCESS read-write
        STATUS current
        DESCRIPTION
            "Indicates the conduct active rsl scan"
        ::= { optixRtnDfhEntry 12 }

    -- 1.3.6.1.4.1.2011.2.25.4.40.5.10.270
    optixRtnXPICLinkDelayStateTable OBJECT-TYPE
       	SYNTAX SEQUENCE OF OptixRtnXPICLinkDelayStateEntry
        MAX-ACCESS not-accessible
        STATUS current
        DESCRIPTION
          "Describes the state of the LinkDelay Status parameter in an XPIC protection group."
        ::= { optixRtnIFProtect 270 } 
        
   -- 1.3.6.1.4.1.2011.2.25.4.40.5.10.270.1
   optixRtnXPICLinkDelayStateEntry OBJECT-TYPE
        SYNTAX OptixRtnXPICLinkDelayStateEntry
        MAX-ACCESS not-accessible
        STATUS current
        DESCRIPTION
            "Indicats the protection xpic LinkDelay Status Entry"
        INDEX{ optixRtnIndex1 }
        ::= { optixRtnXPICLinkDelayStateTable 1 } 
            
    OptixRtnXPICLinkDelayStateEntry ::=
    	SEQUENCE {
            optixRtnXPICLinkDelayState
            	INTEGER              
    	} 
   
    -- 1.3.6.1.4.1.2011.2.25.4.40.5.10.270.1.1
	optixRtnXPICLinkDelayState OBJECT-TYPE
        SYNTAX INTEGER
        {
            disable(0),
            enable(1)
        }        
        MAX-ACCESS read-write
        STATUS current
        DESCRIPTION
            "Indicats the protection xpic link delay state."
        ::= { optixRtnXPICLinkDelayStateEntry 1 }

    -- 1.3.6.1.4.1.2011.2.25.4.40.5.10.310
    optixRtnDualprotEplaTable OBJECT-TYPE
        SYNTAX SEQUENCE OF OptixRtnDualprotEplaEntry
        MAX-ACCESS not-accessible
        STATUS current
        DESCRIPTION
            "Describes configuration parameters for the working board and protection board in a cascading PLA/EPLA protection group."
        ::= { optixRtnIFProtect 310 }

    -- 1.3.6.1.4.1.2011.2.25.4.40.5.10.310.1
    optixRtnDualprotEplaEntry OBJECT-TYPE
        SYNTAX OptixRtnDualprotEplaEntry
        MAX-ACCESS not-accessible
        STATUS current
        DESCRIPTION
            "Indicates the parameter entry for a cascading PLA/EPLA protection group."
        INDEX{ optixRtnDualprotEplaID }
        ::= { optixRtnDualprotEplaTable 1 }

    OptixRtnDualprotEplaEntry ::=
        SEQUENCE {
            optixRtnDualprotEplaType
                OPTIXRtnPhyLagPGType,
            optixRtnDualprotEplaMainSlotID
                Unsigned32,
            optixRtnDualprotEplaMainSubCardID
                Unsigned32,
            optixRtnDualprotEplaMainPortID
                Unsigned32,
            optixRtnDualprotEplaSlaveMemsInfo
                OCTET STRING,
            optixRtnDualprotEplaRole
                OPTIXRtnCascadingPLAPGRoleType,
            optixRtnDualprotEplaProtectType
                OPTIXRtnCascadingPhyLagPGProtectTypeExt,
            optixRtnDualprotEplaLcConMemsInfo
                OCTET STRING,
            optixRtnDualprotEplaNbConMemsInfo
                OCTET STRING,
            optixRtnDualprotEplaSrvNbsrvMapInfo
                OCTET STRING,
            optixRtnDualprotEplaCfgRowStatus
                RowStatus
        }

    -- 1.3.6.1.4.1.2011.2.25.4.40.5.10.310.1.1
    optixRtnDualprotEplaType OBJECT-TYPE
        SYNTAX OPTIXRtnPhyLagPGType
        MAX-ACCESS read-create
        STATUS current
        DESCRIPTION
            "Indicates the protection group type. Values: 0: PLA 1: EPLA 2: cascading PLA 3:cascading EPLA"
        ::= { optixRtnDualprotEplaEntry 1 }

    -- 1.3.6.1.4.1.2011.2.25.4.40.5.10.310.1.2
    optixRtnDualprotEplaMainSlotID OBJECT-TYPE
        SYNTAX Unsigned32
        MAX-ACCESS read-create
        STATUS current
        DESCRIPTION
            "Indicates the slot ID of the main port."
        ::= { optixRtnDualprotEplaEntry 2 }

    -- 1.3.6.1.4.1.2011.2.25.4.40.5.10.310.1.3
    optixRtnDualprotEplaMainSubCardID OBJECT-TYPE
        SYNTAX Unsigned32
        MAX-ACCESS read-create
        STATUS current
        DESCRIPTION
            "Indicates the subboard ID of the main port."
        ::= { optixRtnDualprotEplaEntry 3 }

    -- 1.3.6.1.4.1.2011.2.25.4.40.5.10.310.1.4
    optixRtnDualprotEplaMainPortID OBJECT-TYPE
        SYNTAX Unsigned32
        MAX-ACCESS read-create
        STATUS current
        DESCRIPTION
            "Indicates the port number of the main port."
        ::= { optixRtnDualprotEplaEntry 4 }

    -- 1.3.6.1.4.1.2011.2.25.4.40.5.10.310.1.5
    optixRtnDualprotEplaSlaveMemsInfo OBJECT-TYPE
        SYNTAX OCTET STRING
        MAX-ACCESS read-create
        STATUS current
        DESCRIPTION
            "Indicates the slave port information of the protection group."
        ::= { optixRtnDualprotEplaEntry 5 }

    -- 1.3.6.1.4.1.2011.2.25.4.40.5.10.310.1.6
    optixRtnDualprotEplaRole OBJECT-TYPE
        SYNTAX OPTIXRtnCascadingPLAPGRoleType
        MAX-ACCESS read-create
        STATUS current
        DESCRIPTION
            "Indicates the role of the current NE in the protection group. Values: 0: slave NE 1: master NE"
        ::= { optixRtnDualprotEplaEntry 6 }

    -- 1.3.6.1.4.1.2011.2.25.4.40.5.10.310.1.7
    optixRtnDualprotEplaProtectType OBJECT-TYPE
        SYNTAX OPTIXRtnCascadingPhyLagPGProtectTypeExt
        MAX-ACCESS read-create
        STATUS current
        DESCRIPTION
            "Indicates the protection group type. Values: 0: no protection 1: LAG protection 2: optical splitter protection"
        ::= { optixRtnDualprotEplaEntry 7 }

    -- 1.3.6.1.4.1.2011.2.25.4.40.5.10.310.1.8
    optixRtnDualprotEplaLcConMemsInfo OBJECT-TYPE
        SYNTAX OCTET STRING
        MAX-ACCESS read-create
        STATUS current
        DESCRIPTION
            "Indicates the local NE information of the protection group."
        ::= { optixRtnDualprotEplaEntry 8 }

    -- 1.3.6.1.4.1.2011.2.25.4.40.5.10.310.1.9
    optixRtnDualprotEplaNbConMemsInfo OBJECT-TYPE
        SYNTAX OCTET STRING
        MAX-ACCESS read-create
        STATUS current
        DESCRIPTION
            "Indicates the neighbor NE information of the protection group."
        ::= { optixRtnDualprotEplaEntry 9 }

    -- 1.3.6.1.4.1.2011.2.25.4.40.5.10.310.1.10
    optixRtnDualprotEplaSrvNbsrvMapInfo OBJECT-TYPE
        SYNTAX OCTET STRING
        MAX-ACCESS read-create
        STATUS current
        DESCRIPTION
            "Indicates the cascade port information of the keep-alive cascade PLA service."
        ::= { optixRtnDualprotEplaEntry 10 }

    -- 1.3.6.1.4.1.2011.2.25.4.40.5.10.310.1.50
    optixRtnDualprotEplaCfgRowStatus OBJECT-TYPE
        SYNTAX RowStatus
        MAX-ACCESS read-create
        STATUS current
        DESCRIPTION
            "Indicates the row status of the protection group."
        DEFVAL{ active }
        ::= { optixRtnDualprotEplaEntry 50 }

    -- 1.3.6.1.4.1.2011.2.25.4.40.5.10.330
    optixRtnEplaBusBandwidthTable OBJECT-TYPE
        SYNTAX SEQUENCE OF OptixRtnEplaBusBandwidthEntry
        MAX-ACCESS not-accessible
        STATUS current
        DESCRIPTION
            "Queries or sets the bus bandwidth of an EPLA member."
        ::= { optixRtnIFProtect 330 }

    -- 1.3.6.1.4.1.2011.2.25.4.40.5.10.330.1
    optixRtnEplaBusBandwidthEntry OBJECT-TYPE
        SYNTAX OptixRtnEplaBusBandwidthEntry
        MAX-ACCESS not-accessible
        STATUS current
        DESCRIPTION
            "Queries or sets the bus bandwidth of an EPLA member."
        INDEX{ optixRtnPhyLagMemPriPGID,optixRtnPhyLagMemBoardId,optixRtnPhyLagMemSubCardId,optixRtnPhyLagMemPortId,optixRtnPhyLagMemChannelId }
        ::= { optixRtnEplaBusBandwidthTable 1 }
    
    OptixRtnEplaBusBandwidthEntry ::=
        SEQUENCE {
            optixRtnConfigBusBandwidth
                Unsigned32,
            optixRtnCurBusBandwidth
                Unsigned32,
            optixRtnMaxBusBandwidth
                Unsigned32
        }
    
    -- 1.3.6.1.4.1.2011.2.25.4.40.5.10.330.1.1
    optixRtnConfigBusBandwidth OBJECT-TYPE
        SYNTAX Unsigned32
        MAX-ACCESS read-write
        STATUS current
        DESCRIPTION
            "Indicates the bus bandwidth set by the user."
        ::= { optixRtnEplaBusBandwidthEntry 1 }

    -- 1.3.6.1.4.1.2011.2.25.4.40.5.10.330.1.2
    optixRtnCurBusBandwidth OBJECT-TYPE
        SYNTAX Unsigned32
        MAX-ACCESS read-only
        STATUS current
        DESCRIPTION
            "Current bus bandwidth."
        ::= { optixRtnEplaBusBandwidthEntry 2 }

    -- 1.3.6.1.4.1.2011.2.25.4.40.5.10.330.1.3
    optixRtnMaxBusBandwidth OBJECT-TYPE
        SYNTAX Unsigned32
        MAX-ACCESS read-only
        STATUS current
        DESCRIPTION
            "Indicates the maximum bandwidth that can be configured."
        ::= { optixRtnEplaBusBandwidthEntry 3 }
END
