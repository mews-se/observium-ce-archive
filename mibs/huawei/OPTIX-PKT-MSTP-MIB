-- OPTIX-PKT-MSTP-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-MSTP-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,NOTIFICATION-TYPE
            FROM SNMPv2-SMI
        RowStatus
            FROM SNMPv2-TC
        optixLogBoardId,optixLogSubCardId
            FROM OPTIX-BOARD-MANAGE-MIB
        optixEtyPortId
            FROM OPTIX-ETY-PORT-MIB
        optixVlanPortId
            FROM OPTIX-PKT-PORT-MIB
        ;

    optixPktMstp MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the ERPS configuration information of a device."
        REVISION "201204200000Z"
        DESCRIPTION
            "The initial revision of this MIB module1."
        ::={ optixProvisionPtn 40 }

    -- 1.3.6.1.4.1.2011.2.25.4.50.40.6
    optixPktMstpGroup OBJECT IDENTIFIER ::= { optixPktMstp 6 }

    -- 1.3.6.1.4.1.2011.2.25.4.50.40.6.1
    optixMSTPTable OBJECT-TYPE
        SYNTAX SEQUENCE OF OptixMSTPEntry
        MAX-ACCESS not-accessible
        STATUS current
        DESCRIPTION
            "This table describes the basic MSTP configuration informationin the Layer 2 protocol."
        ::= { optixPktMstpGroup 1 }

    -- 1.3.6.1.4.1.2011.2.25.4.50.40.6.1.1
    optixMSTPEntry OBJECT-TYPE
        SYNTAX OptixMSTPEntry
        MAX-ACCESS not-accessible
        STATUS current
        DESCRIPTION
            "This entry describes the basic MSTP configuration information in the Layer 2 protocol."
        INDEX{ optixMSTPPortGroupId }
        ::= { optixMSTPTable 1 }

    OptixMSTPEntry ::=
        SEQUENCE {
            optixMSTPPortGroupId
                Unsigned32,
            optixMSTPRegionName
                OCTET STRING,
            optixMSTPRevisionLevel
                Unsigned32,
            optixMSTPMaxHop
                Unsigned32,
            optixMSTPHelloTime
                Unsigned32,
            optixMSTPMaxAge
                Unsigned32,
            optixMSTPForwardDelay
                Unsigned32,
            optixMSTPDiameter
                Unsigned32,
            optixMSTPProtocolEn
                INTEGER,
            optixMSTPMode
                INTEGER,
            optixMSTPBridgePri
                Unsigned32,
            optixMSTPBridgeMac
                OCTET STRING,
            optixMSTPRootPri
                Unsigned32,
            optixMSTPRootMac
                OCTET STRING,
            optixMSTPErpc
                Unsigned32,
            optixMSTPRegionRootPri
                Unsigned32,
            optixMSTPRegionRootMac
                OCTET STRING,
            optixMSTPIrpc
                Unsigned32,
            optixMSTPRootPortPri
                Unsigned32,
            optixMSTPRootPortBoard
                Unsigned32,
            optixMSTPRootPortSubboard
                Unsigned32,
            optixMSTPRootPortPort
                Unsigned32,
            optixMSTPTc
                Unsigned32,
            optixMSTPTimeSinceLastTc
                Unsigned32,
            optixMSTPTcNum
                Unsigned32,
            optixMSTPPGPortNum
                Unsigned32,
            optixMSTPPGPortList
                OCTET STRING,
            optixMSTPVlanMap
                Unsigned32,
            optixMSTPRowStatus
                RowStatus
        }

    -- 1.3.6.1.4.1.2011.2.25.4.50.40.6.1.1.1
    optixMSTPPortGroupId OBJECT-TYPE
        SYNTAX Unsigned32
        MAX-ACCESS not-accessible
        STATUS current
        DESCRIPTION
            "This object indicates the MSTP port group ID. Value: 1"
        ::= { optixMSTPEntry 1 }

    -- 1.3.6.1.4.1.2011.2.25.4.50.40.6.1.1.2
    optixMSTPRegionName OBJECT-TYPE
        SYNTAX OCTET STRING(SIZE(0..32))
        MAX-ACCESS read-create
        STATUS current
        DESCRIPTION
            "This object indicates the MSTP MST domain name."
        ::= { optixMSTPEntry 2 }

    -- 1.3.6.1.4.1.2011.2.25.4.50.40.6.1.1.3
    optixMSTPRevisionLevel OBJECT-TYPE
        SYNTAX Unsigned32
        MAX-ACCESS read-create
        STATUS current
        DESCRIPTION
            "This object indicates the MSTP revision level. Value range: 0 to 65535."
        ::= { optixMSTPEntry 3 }

    -- 1.3.6.1.4.1.2011.2.25.4.50.40.6.1.1.4
    optixMSTPMaxHop OBJECT-TYPE
        SYNTAX Unsigned32
        MAX-ACCESS read-create
        STATUS current
        DESCRIPTION
            "This object indicates the maximum number of hops in the MSTP MST domain. Value range: 1 to 40. The default value is 20."
        ::= { optixMSTPEntry 4 }

    -- 1.3.6.1.4.1.2011.2.25.4.50.40.6.1.1.5
    optixMSTPHelloTime OBJECT-TYPE
        SYNTAX Unsigned32
        MAX-ACCESS read-create
        STATUS current
        DESCRIPTION
            "This object indicates the MSTP hello time. Value range: 1 to 10 (unit: s). The default value is 2."
        ::= { optixMSTPEntry 5 }

    -- 1.3.6.1.4.1.2011.2.25.4.50.40.6.1.1.6
    optixMSTPMaxAge OBJECT-TYPE
        SYNTAX Unsigned32
        MAX-ACCESS read-create
        STATUS current
        DESCRIPTION
            "This object indicates the maximum MSTP aging time. Value range: 6 to 40 (unit: s). The default value is 20."
        ::= { optixMSTPEntry 6 }

    -- 1.3.6.1.4.1.2011.2.25.4.50.40.6.1.1.7
    optixMSTPForwardDelay OBJECT-TYPE
        SYNTAX Unsigned32
        MAX-ACCESS read-create
        STATUS current
        DESCRIPTION
            "This object indicates the MSTP forwarding delaytime. Value range: 4 to 30 (unit: s). The default value is 15."
        ::= { optixMSTPEntry 7 }

    -- 1.3.6.1.4.1.2011.2.25.4.50.40.6.1.1.8
    optixMSTPDiameter OBJECT-TYPE
        SYNTAX Unsigned32
        MAX-ACCESS read-create
        STATUS current
        DESCRIPTION
            "This object indicates the MSTP network exchanging diameter. Value range: 2 to 7. The default value is 7. The value 0xff indicates that the diameter is invalid."
        ::= { optixMSTPEntry 8 }

    -- 1.3.6.1.4.1.2011.2.25.4.50.40.6.1.1.9
    optixMSTPProtocolEn OBJECT-TYPE
        SYNTAX INTEGER
        {
            disable(0),
            enable(1)
        }
        MAX-ACCESS read-create
        STATUS current
        DESCRIPTION
            "This object indicates the enable status of the MSTP protocol tree. 0: disable, 1: enable"
        ::= { optixMSTPEntry 9 }

    -- 1.3.6.1.4.1.2011.2.25.4.50.40.6.1.1.10
    optixMSTPMode OBJECT-TYPE
        SYNTAX INTEGER
        {
            stp(0),
            mstp(3)
        }
        MAX-ACCESS read-create
        STATUS current
        DESCRIPTION
            "This object indicates the MSTP working mode. 0: STP, 3: MSTP"
        ::= { optixMSTPEntry 10 }

    -- 1.3.6.1.4.1.2011.2.25.4.50.40.6.1.1.11
    optixMSTPBridgePri OBJECT-TYPE
        SYNTAX Unsigned32
        MAX-ACCESS read-create
        STATUS current
        DESCRIPTION
            "This object indicates the CIST bridge priority of the MSTP. Value range: 0 to 61440. The default value is 32768 and the step length is 4096."
        ::= { optixMSTPEntry 11 }

    -- 1.3.6.1.4.1.2011.2.25.4.50.40.6.1.1.12
    optixMSTPBridgeMac OBJECT-TYPE
        SYNTAX OCTET STRING (SIZE(0..24))
        MAX-ACCESS read-only
        STATUS current
        DESCRIPTION
            "This object indicates the MAC address of the MSTP CIST bridge."
        ::= { optixMSTPEntry 12 }

    -- 1.3.6.1.4.1.2011.2.25.4.50.40.6.1.1.13
    optixMSTPRootPri OBJECT-TYPE
        SYNTAX Unsigned32
        MAX-ACCESS read-only
        STATUS current
        DESCRIPTION
            "This object indicates the root CIST bridge priority of the MSTP. Value range: 0 to 61440. The step length is 4096."
        ::= { optixMSTPEntry 13 }

    -- 1.3.6.1.4.1.2011.2.25.4.50.40.6.1.1.14
    optixMSTPRootMac OBJECT-TYPE
        SYNTAX OCTET STRING (SIZE(0..24))
        MAX-ACCESS read-only
        STATUS current
        DESCRIPTION
            "This object indicates the MAC address of the root MSTP CIST bridge."
        ::= { optixMSTPEntry 14 }

    -- 1.3.6.1.4.1.2011.2.25.4.50.40.6.1.1.15
    optixMSTPErpc OBJECT-TYPE
        SYNTAX Unsigned32
        MAX-ACCESS read-only
        STATUS current
        DESCRIPTION
            "This object indicates the MSTP ERPC. Value range: 0 to 0xffffffff."
        ::= { optixMSTPEntry 15 }

    -- 1.3.6.1.4.1.2011.2.25.4.50.40.6.1.1.16
    optixMSTPRegionRootPri OBJECT-TYPE
        SYNTAX Unsigned32
        MAX-ACCESS read-only
        STATUS current
        DESCRIPTION
            "This object indicates the root CIST bridge priority of the MSTP CIST domain. Value range: 0 to 61440. The step length is 4096."
        ::= { optixMSTPEntry 16 }

    -- 1.3.6.1.4.1.2011.2.25.4.50.40.6.1.1.17
    optixMSTPRegionRootMac OBJECT-TYPE
        SYNTAX OCTET STRING (SIZE(0..24))
        MAX-ACCESS read-only
        STATUS current
        DESCRIPTION
            "This object indicates the MAC address of the root MSTP CIST bridge."
        ::= { optixMSTPEntry 17 }

    -- 1.3.6.1.4.1.2011.2.25.4.50.40.6.1.1.18
    optixMSTPIrpc OBJECT-TYPE
        SYNTAX Unsigned32
        MAX-ACCESS read-only
        STATUS current
        DESCRIPTION
            "This object indicates the MSTP IRPC. Value range: 0 to 0xffffffff."
        ::= { optixMSTPEntry 18 }

    -- 1.3.6.1.4.1.2011.2.25.4.50.40.6.1.1.19
    optixMSTPRootPortPri OBJECT-TYPE
        SYNTAX Unsigned32
        MAX-ACCESS read-only
        STATUS current
        DESCRIPTION
            "This object indicates the root CISTport priority of the MSTP. Value range: 0 to 240 (a smaller value indicates a higher priority). The default value is 128 and the step length is 16."
        ::= { optixMSTPEntry 19 }

    -- 1.3.6.1.4.1.2011.2.25.4.50.40.6.1.1.20
    optixMSTPRootPortBoard OBJECT-TYPE
        SYNTAX Unsigned32
        MAX-ACCESS read-only
        STATUS current
        DESCRIPTION
            "This object indicates the slot ID of the root MSTP CIST port."
        ::= { optixMSTPEntry 20 }

    -- 1.3.6.1.4.1.2011.2.25.4.50.40.6.1.1.21
    optixMSTPRootPortSubboard OBJECT-TYPE
        SYNTAX Unsigned32
        MAX-ACCESS read-only
        STATUS current
        DESCRIPTION
            "This object indicates the subboard ID of the root MSTP CIST port."
        ::= { optixMSTPEntry 21 }

    -- 1.3.6.1.4.1.2011.2.25.4.50.40.6.1.1.22
    optixMSTPRootPortPort OBJECT-TYPE
        SYNTAX Unsigned32
        MAX-ACCESS read-only
        STATUS current
        DESCRIPTION
            "This object indicates the port number of the root MSTP CIST port."
        ::= { optixMSTPEntry 22 }

    -- 1.3.6.1.4.1.2011.2.25.4.50.40.6.1.1.23
    optixMSTPTc OBJECT-TYPE
        SYNTAX Unsigned32
        MAX-ACCESS read-only
        STATUS current
        DESCRIPTION
            "This object indicates the MSTP topology change. Value range: 0 and 1. 0: no change, 1: change"
        ::= { optixMSTPEntry 23 }

    -- 1.3.6.1.4.1.2011.2.25.4.50.40.6.1.1.24
    optixMSTPTimeSinceLastTc OBJECT-TYPE
        SYNTAX Unsigned32
        MAX-ACCESS read-only
        STATUS current
        DESCRIPTION
            "This object indicates the last topology change duration of the MSTP. Value range: 0 to 0xffffffff (unit: s)."
        ::= { optixMSTPEntry 24 }

    -- 1.3.6.1.4.1.2011.2.25.4.50.40.6.1.1.25
    optixMSTPTcNum OBJECT-TYPE
        SYNTAX Unsigned32
        MAX-ACCESS read-only
        STATUS current
        DESCRIPTION
            "This object indicates the number of MSTP topology changes. Value range: 0 to 0xffffffff."
        ::= { optixMSTPEntry 25 }

    -- 1.3.6.1.4.1.2011.2.25.4.50.40.6.1.1.26
    optixMSTPPGPortNum OBJECT-TYPE
        SYNTAX Unsigned32
        MAX-ACCESS read-create
        STATUS current
        DESCRIPTION
            "This object indicates the port number of the MSTP port group. Value range: 0 to 512."
        ::= { optixMSTPEntry 26 }

    -- 1.3.6.1.4.1.2011.2.25.4.50.40.6.1.1.27
    optixMSTPPGPortList OBJECT-TYPE
        SYNTAX OCTET STRING
        MAX-ACCESS read-create
        STATUS current
        DESCRIPTION
            "This object indicates the port list of the MSTP port group"
        ::= { optixMSTPEntry 27 }

    -- 1.3.6.1.4.1.2011.2.25.4.50.40.6.1.1.28
    optixMSTPVlanMap OBJECT-TYPE
        SYNTAX Unsigned32
        MAX-ACCESS read-create
        STATUS current
        DESCRIPTION
            "This object indicates the vlan map value of the MSTP port group. Value range: 1 to 48 and 0xFF. The default value is 0xFF, indicating that the value is invalid."
        ::= { optixMSTPEntry 28 }

    -- 1.3.6.1.4.1.2011.2.25.4.50.40.6.1.1.255
    optixMSTPRowStatus OBJECT-TYPE
        SYNTAX RowStatus
        MAX-ACCESS read-create
        STATUS current
        DESCRIPTION
            "This object indicates the row status of the MSTP."
        ::= { optixMSTPEntry 255 }

    -- 1.3.6.1.4.1.2011.2.25.4.50.40.6.2
    optixMSTPVlanTable OBJECT-TYPE
        SYNTAX SEQUENCE OF OptixMSTPVlanEntry
        MAX-ACCESS not-accessible
        STATUS current
        DESCRIPTION
            "This table describes the basic MSTP VLAN configurations."
        ::= { optixPktMstpGroup 2 }

    -- 1.3.6.1.4.1.2011.2.25.4.50.40.6.2.1
    optixMSTPVlanEntry OBJECT-TYPE
        SYNTAX OptixMSTPVlanEntry
        MAX-ACCESS not-accessible
        STATUS current
        DESCRIPTION
            "This entry describes the basic MSTP VLAN configurations."
        INDEX{ optixMSTPPortGroupId,optixVlanPortId }
        ::= { optixMSTPVlanTable 1 }

    OptixMSTPVlanEntry ::=
        SEQUENCE {
            optixMSTPVlanMstiId
                Unsigned32
        }

    -- 1.3.6.1.4.1.2011.2.25.4.50.40.6.2.1.2
    optixMSTPVlanMstiId OBJECT-TYPE
        SYNTAX Unsigned32
        MAX-ACCESS read-write
        STATUS current
        DESCRIPTION
            "This object indicates the MSTP MSTI ID. Value range: 0 to 48. The value 0 indicates CIST."
        ::= { optixMSTPVlanEntry 2 }

    -- 1.3.6.1.4.1.2011.2.25.4.50.40.6.3
    optixMSTPCistTable OBJECT-TYPE
        SYNTAX SEQUENCE OF OptixMSTPCistEntry
        MAX-ACCESS not-accessible
        STATUS current
        DESCRIPTION
            "This table describes the basic MSTP CIST configuration information in the Layer 2 protocol."
        ::= { optixPktMstpGroup 3 }

    -- 1.3.6.1.4.1.2011.2.25.4.50.40.6.3.1
    optixMSTPCistEntry OBJECT-TYPE
        SYNTAX OptixMSTPCistEntry
        MAX-ACCESS not-accessible
        STATUS current
        DESCRIPTION
            "This entry describes the basic MSTP CIST configuration information in the Layer 2 protocol."
        INDEX{ optixMSTPPortGroupId,optixLogBoardId,optixLogSubCardId,optixEtyPortId }
        ::= { optixMSTPCistTable 1 }

    OptixMSTPCistEntry ::=
        SEQUENCE {
            optixMSTPCistProtocolEn
                INTEGER,
            optixMSTPCistPortRole
                INTEGER,
            optixMSTPCistPortState
                INTEGER,
            optixMSTPCistPortPri
                Unsigned32,
            optixMSTPCistPortPathCost
                Unsigned32,
            optixMSTPCistDesgBridgePri
                Unsigned32,
            optixMSTPCisDesgBridgeMac
                OCTET STRING,
            optixMSTPCistDesgPortPri
                Unsigned32,
            optixMSTPCistAdminEdge
                INTEGER,
            optixMSTPCistOperEdge
                INTEGER,
            optixMSTPCistAdminPtop
                INTEGER,
            optixMSTPCistOperPtop
                INTEGER,
            optixMSTPCistTransmitLimit
                Unsigned32,
            optixMSTPCistMessageAge
                Unsigned32,
            optixMSTPCistRemainHop
                Unsigned32,
            optixMSTPCistPortEnable
                INTEGER,
            optixMSTPCistHelloTime
                Unsigned32,
            optixMSTPCistMaxAge
                Unsigned32,
            optixMSTPCistForwardDelay
                Unsigned32,
            optixMSTPCistDesPort
                Unsigned32,
            optixMSTPCistSetMCheck
                INTEGER,
            optixMSTPCistWorkMode
                INTEGER,
            optixMSTPCistRowStatus
                RowStatus
        }

    -- 1.3.6.1.4.1.2011.2.25.4.50.40.6.3.1.1
    optixMSTPCistProtocolEn OBJECT-TYPE
        SYNTAX INTEGER
        {
            disable(0),
            enable(1)
        }
        MAX-ACCESS read-only
        STATUS current
        DESCRIPTION
            "This object indicates the enable status of the MSTP CIST port protocol. 0: disable, 1: enable"
        ::= { optixMSTPCistEntry 1 }

    -- 1.3.6.1.4.1.2011.2.25.4.50.40.6.3.1.2
    optixMSTPCistPortRole OBJECT-TYPE
        SYNTAX INTEGER
        {
            root(0),
            designated(1),
            alternate(2),
            backup(3),
            master(4),
            disabled(5)
        }
        MAX-ACCESS read-only
        STATUS current
        DESCRIPTION
            "This object indicates the MTSP CIST port role. 0: root, 1: designated, 2: alternate, 3: backup, 4: master, 5: disabled"
        ::= { optixMSTPCistEntry 2 }

    -- 1.3.6.1.4.1.2011.2.25.4.50.40.6.3.1.3
    optixMSTPCistPortState OBJECT-TYPE
        SYNTAX INTEGER
        {
            discarding(0),
            learning(1),
            forwarding(2)
        }
        MAX-ACCESS read-only
        STATUS current
        DESCRIPTION
            "This object indicates the MTSP CIST port status. 0: discarding, 1: learning, 2: forwarding"
        ::= { optixMSTPCistEntry 3 }

    -- 1.3.6.1.4.1.2011.2.25.4.50.40.6.3.1.4
    optixMSTPCistPortPri OBJECT-TYPE
        SYNTAX Unsigned32
        MAX-ACCESS read-create
        STATUS current
        DESCRIPTION
            "This object indicates the MSTP CIST port priority. Value range: 0 to 240 (a smaller value indicates a higher priority). The default value is 128 and the step length is 16."
        ::= { optixMSTPCistEntry 4 }

    -- 1.3.6.1.4.1.2011.2.25.4.50.40.6.3.1.5
    optixMSTPCistPortPathCost OBJECT-TYPE
        SYNTAX Unsigned32
        MAX-ACCESS read-create
        STATUS current
        DESCRIPTION
            "This object indicates the path overhead of the MSTP CIST port. Value range: 200000000, 2000000, 200000, 20000, 2000, 1."
        ::= { optixMSTPCistEntry 5 }

    -- 1.3.6.1.4.1.2011.2.25.4.50.40.6.3.1.6
    optixMSTPCistDesgBridgePri OBJECT-TYPE
        SYNTAX Unsigned32
        MAX-ACCESS read-only
        STATUS current
        DESCRIPTION
            "This object indicates the specified CIST bridge priority of the MSTP. Value range: 0 to 61440. The default value is 32768 and the step length is 4096."
        ::= { optixMSTPCistEntry 6 }

    -- 1.3.6.1.4.1.2011.2.25.4.50.40.6.3.1.7
    optixMSTPCisDesgBridgeMac OBJECT-TYPE
        SYNTAX OCTET STRING(SIZE(0..32))
        MAX-ACCESS read-only
        STATUS current
        DESCRIPTION
            "This object indicates the MAC address of the specified MSTP CIST bridge."
        ::= { optixMSTPCistEntry 7 }

    -- 1.3.6.1.4.1.2011.2.25.4.50.40.6.3.1.8
    optixMSTPCistDesgPortPri OBJECT-TYPE
        SYNTAX Unsigned32
        MAX-ACCESS read-only
        STATUS current
        DESCRIPTION
            "This object indicates the specified MSTP CIST port priority. Value range: 0 to 240 (a smaller value indicates a higher priority). The default value is 128 and the step length is 16."
        ::= { optixMSTPCistEntry 8 }

    -- 1.3.6.1.4.1.2011.2.25.4.50.40.6.3.1.9
    optixMSTPCistAdminEdge OBJECT-TYPE
        SYNTAX INTEGER
        {
            disable(0),
            enable(1)
        }
        MAX-ACCESS read-create
        STATUS current
        DESCRIPTION
            "This object indicates the CIST administration edge port attribute of the MSTP. 0: disable, 1: enable"
        ::= { optixMSTPCistEntry 9 }

    -- 1.3.6.1.4.1.2011.2.25.4.50.40.6.3.1.10
    optixMSTPCistOperEdge OBJECT-TYPE
        SYNTAX INTEGER
        {
            disable(0),
            enable(1)
        }
        MAX-ACCESS read-only
        STATUS current
        DESCRIPTION
            "This object indicates the actual CISTedge port attribute of the MSTP. 0: disable, 1: enable"
        ::= { optixMSTPCistEntry 10 }

    -- 1.3.6.1.4.1.2011.2.25.4.50.40.6.3.1.11
    optixMSTPCistAdminPtop OBJECT-TYPE
        SYNTAX INTEGER
        {
            forceFalse(0),
            forceTrue(1),
            auto(2)
        }
        MAX-ACCESS read-create
        STATUS current
        DESCRIPTION
            "This object indicates the CIST administration edge port attribute of the MSTP in the point-to-point mode. 0: forceFalse, 1: forceTrue, 2: auto"
        ::= { optixMSTPCistEntry 11 }

    -- 1.3.6.1.4.1.2011.2.25.4.50.40.6.3.1.12
    optixMSTPCistOperPtop OBJECT-TYPE
        SYNTAX INTEGER
        {
            false(0),
            true(1)
        }
        MAX-ACCESS read-only
        STATUS current
        DESCRIPTION
            "This object indicates the actual CIST port attribute of the MSTP in the point-to-point mode. 0: false, 1: true"
        ::= { optixMSTPCistEntry 12 }

    -- 1.3.6.1.4.1.2011.2.25.4.50.40.6.3.1.13
    optixMSTPCistTransmitLimit OBJECT-TYPE
        SYNTAX Unsigned32
        MAX-ACCESS read-create
        STATUS current
        DESCRIPTION
            "This object indicates the maximum number of packets that can be transmitted by the CIST port of the MSTP."
        ::= { optixMSTPCistEntry 13 }

    -- 1.3.6.1.4.1.2011.2.25.4.50.40.6.3.1.14
    optixMSTPCistMessageAge OBJECT-TYPE
        SYNTAX Unsigned32
        MAX-ACCESS read-only
        STATUS current
        DESCRIPTION
            "This object indicates the aging time of MSTP CIST messages. Value range: 0 to 255."
        ::= { optixMSTPCistEntry 14 }

    -- 1.3.6.1.4.1.2011.2.25.4.50.40.6.3.1.15
    optixMSTPCistRemainHop OBJECT-TYPE
        SYNTAX Unsigned32
        MAX-ACCESS read-only
        STATUS current
        DESCRIPTION
            "This object indicates the number of remaining hops in the MSTP CIST MST domain. Value range: 0 to 255."
        ::= { optixMSTPCistEntry 15 }

    -- 1.3.6.1.4.1.2011.2.25.4.50.40.6.3.1.16
    optixMSTPCistPortEnable OBJECT-TYPE
        SYNTAX INTEGER
        {
            disable(0),
            enable(1)
        }
        MAX-ACCESS read-create
        STATUS current
        DESCRIPTION
            "This object indicates the port enable state in the MSTP. 0: disable, 1: enable"
        ::= { optixMSTPCistEntry 16 }

    -- 1.3.6.1.4.1.2011.2.25.4.50.40.6.3.1.17
    optixMSTPCistHelloTime OBJECT-TYPE
        SYNTAX Unsigned32
        MAX-ACCESS read-only
        STATUS current
        DESCRIPTION
            "This object indicates the MSTP running hello time. Value range: 1 and 2 (unit: s)."
        ::= { optixMSTPCistEntry 17 }

    -- 1.3.6.1.4.1.2011.2.25.4.50.40.6.3.1.18
    optixMSTPCistMaxAge OBJECT-TYPE
        SYNTAX Unsigned32
        MAX-ACCESS read-only
        STATUS current
        DESCRIPTION
            "This object indicates the MSTP running max age. Value range: 6 to 40 (unit: s)."
        ::= { optixMSTPCistEntry 18 }

    -- 1.3.6.1.4.1.2011.2.25.4.50.40.6.3.1.19
    optixMSTPCistForwardDelay OBJECT-TYPE
        SYNTAX Unsigned32
        MAX-ACCESS read-only
        STATUS current
        DESCRIPTION
            "This object indicates the MSTP running forward delay. Value range: 4 to 30 (unit: s)."
        ::= { optixMSTPCistEntry 19 }

    -- 1.3.6.1.4.1.2011.2.25.4.50.40.6.3.1.20
    optixMSTPCistDesPort OBJECT-TYPE
        SYNTAX Unsigned32
        MAX-ACCESS read-only
        STATUS current
        DESCRIPTION
            "This object indicates destined port in the MSTP. Value range: 0 to 65535."
        ::= { optixMSTPCistEntry 20 }

    -- 1.3.6.1.4.1.2011.2.25.4.50.40.6.3.1.21
    optixMSTPCistSetMCheck OBJECT-TYPE
        SYNTAX INTEGER
        {
            invalid(0),
            setMCheck(1)
        }
        MAX-ACCESS read-create
        STATUS current
        DESCRIPTION
            "This object sets MSTP port protocol transfer information and cannot be queried."
        ::= { optixMSTPCistEntry 21 }

    -- 1.3.6.1.4.1.2011.2.25.4.50.40.6.3.1.22
    optixMSTPCistWorkMode OBJECT-TYPE
        SYNTAX INTEGER
        {
            stp(0),
            mstp(3)
        }
        MAX-ACCESS read-only
        STATUS current
        DESCRIPTION
            "This object indicates the work mode of MSTP cist. 0: STP, 3: MSTP"
        ::= { optixMSTPCistEntry 22 }

    -- 1.3.6.1.4.1.2011.2.25.4.50.40.6.3.1.255
    optixMSTPCistRowStatus OBJECT-TYPE
        SYNTAX RowStatus
        MAX-ACCESS read-create
        STATUS current
        DESCRIPTION
            "This object indicates the row status of the cist."
        ::= { optixMSTPCistEntry 255 }

    -- 1.3.6.1.4.1.2011.2.25.4.50.40.6.4
    optixMSTPPortStatusTrapMember OBJECT IDENTIFIER ::= { optixPktMstpGroup 4 }

    -- 1.3.6.1.4.1.2011.2.25.4.50.40.6.4.1
    optixMSTPPortStatusGroupId OBJECT-TYPE
        SYNTAX Unsigned32
        MAX-ACCESS accessible-for-notify
        STATUS current
        DESCRIPTION
            "This object indicates the port group ID of the reported event. Value: 1."
        ::= { optixMSTPPortStatusTrapMember 1 }

    -- 1.3.6.1.4.1.2011.2.25.4.50.40.6.4.2
    optixMSTPPortStatusBdId OBJECT-TYPE
        SYNTAX Unsigned32
        MAX-ACCESS accessible-for-notify
        STATUS current
        DESCRIPTION
            "This object indicates the slot ID of the reported event."
        ::= { optixMSTPPortStatusTrapMember 2 }

    -- 1.3.6.1.4.1.2011.2.25.4.50.40.6.4.3
    optixMSTPPortStatusSubId OBJECT-TYPE
        SYNTAX Unsigned32
        MAX-ACCESS accessible-for-notify
        STATUS current
        DESCRIPTION
            "This object indicates the subboard ID of the reported event."
        ::= { optixMSTPPortStatusTrapMember 3 }

    -- 1.3.6.1.4.1.2011.2.25.4.50.40.6.4.4
    optixMSTPPortStatusPortId OBJECT-TYPE
        SYNTAX Unsigned32
        MAX-ACCESS accessible-for-notify
        STATUS current
        DESCRIPTION
            "This object indicates the port number of the reported event."
        ::= { optixMSTPPortStatusTrapMember 4 }

    -- 1.3.6.1.4.1.2011.2.25.4.50.40.6.4.5
    optixMSTPPortStatusMstiId OBJECT-TYPE
        SYNTAX Unsigned32
        MAX-ACCESS accessible-for-notify
        STATUS current
        DESCRIPTION
            "This object indicates the MSTI ID of the reported event. Value range: 0 to 48. The value 0 indicates CIST."
        ::= { optixMSTPPortStatusTrapMember 5 }

    -- 1.3.6.1.4.1.2011.2.25.4.50.40.6.4.6
    optixMSTPPortStatus OBJECT-TYPE
        SYNTAX INTEGER
        {
            discarding(0),
            learning(1),
            forwarding(2)
        }
        MAX-ACCESS accessible-for-notify
        STATUS current
        DESCRIPTION
            "This object indicates the port status of the reported event. 0: discarding, 1: learning, 2: forwarding"
        ::= { optixMSTPPortStatusTrapMember 6 }

    -- 1.3.6.1.4.1.2011.2.25.4.50.40.6.5
    optixMSTPPortStatusTrapReport OBJECT IDENTIFIER ::= { optixPktMstpGroup 5 }

    -- 1.3.6.1.4.1.2011.2.25.4.50.40.6.5.1
    optixMSTPPortStatusTrap NOTIFICATION-TYPE
        OBJECTS{ optixMSTPPortStatusGroupId,optixMSTPPortStatusBdId,optixMSTPPortStatusSubId,optixMSTPPortStatusPortId,optixMSTPPortStatusMstiId,optixMSTPPortStatus }
        STATUS current
        DESCRIPTION
            "This object is used to report MSTP port status change events."
        ::= { optixMSTPPortStatusTrapReport 1 }

    -- 1.3.6.1.4.1.2011.2.25.4.50.40.6.6
    optixMSTPMstiTable OBJECT-TYPE
        SYNTAX SEQUENCE OF OptixMSTPMstiEntry
        MAX-ACCESS not-accessible
        STATUS current
        DESCRIPTION
            "This table describes the basic MSTP MSTI configuration informationin the Layer 2 protocol."
        ::= { optixPktMstpGroup 6 }

    -- 1.3.6.1.4.1.2011.2.25.4.50.40.6.6.1
    optixMSTPMstiEntry OBJECT-TYPE
        SYNTAX OptixMSTPMstiEntry
        MAX-ACCESS not-accessible
        STATUS current
        DESCRIPTION
            "This entry describes the basic MSTP MSTI configuration information in the Layer 2 protocol."
        INDEX{ optixMSTPPortGroupId,optixMSTPMstiID }
        ::= { optixMSTPMstiTable 1 }

    OptixMSTPMstiEntry ::=
        SEQUENCE {
            optixMSTPMstiID
                Unsigned32,
            optixMSTPMstiCreated
                INTEGER,
            optixMSTPMstiBridgePri
                Unsigned32,
            optixMSTPMstiBridgeMac
                OCTET STRING,
            optixMSTPMstiRootPri
                Unsigned32,
            optixMSTPMstiRootMac
                OCTET STRING,
            optixMSTPMstiIrpc
                Unsigned32,
            optixMSTPMstiRootPortPri
                Unsigned32,
            optixMSTPMstiRootPortBoard
                Unsigned32,
            optixMSTPMstiRootPortSubboard
                Unsigned32,
            optixMSTPMstiRootPortPort
                Unsigned32,
            optixMSTPMstiMastBridgePri
                Unsigned32,
            optixMSTPMstiMastBridgeMac
                OCTET STRING,
            optixMSTPMstiMrpc
                Unsigned32,
            optixMSTPMstiTc
                Unsigned32,
            optixMSTPMstiTimeSinceLastTc
                Unsigned32,
            optixMSTPMstiTcNum
                Unsigned32
        }

    -- 1.3.6.1.4.1.2011.2.25.4.50.40.6.6.1.1
    optixMSTPMstiID OBJECT-TYPE
        SYNTAX Unsigned32
        MAX-ACCESS not-accessible
        STATUS current
        DESCRIPTION
            "This object indicates the MSTI MSTI ID of the MSTP. Value range: 0 to 48. The value 0 indicates CIST."
        ::= { optixMSTPMstiEntry 1 }

    -- 1.3.6.1.4.1.2011.2.25.4.50.40.6.6.1.2
    optixMSTPMstiCreated OBJECT-TYPE
        SYNTAX INTEGER
        {
            false(0),
            etrue(1)
        }
        MAX-ACCESS read-only
        STATUS current
        DESCRIPTION
            "This object indicates the created of the MSTP. 0: false, 1: true"
        ::= { optixMSTPMstiEntry 2 }

    -- 1.3.6.1.4.1.2011.2.25.4.50.40.6.6.1.3
    optixMSTPMstiBridgePri OBJECT-TYPE
        SYNTAX Unsigned32
        MAX-ACCESS read-write
        STATUS current
        DESCRIPTION
            "This object indicates the MSTI bridge priority of the MSTP. Value range: 0 to 61440. The default value is 32768 and the step length is 4096."
        ::= { optixMSTPMstiEntry 3 }

    -- 1.3.6.1.4.1.2011.2.25.4.50.40.6.6.1.4
    optixMSTPMstiBridgeMac OBJECT-TYPE
        SYNTAX OCTET STRING (SIZE(0..24))
        MAX-ACCESS read-only
        STATUS current
        DESCRIPTION
            "This object indicates the MAC address of theMSTP MSTI bridge."
        ::= { optixMSTPMstiEntry 4 }

    -- 1.3.6.1.4.1.2011.2.25.4.50.40.6.6.1.5
    optixMSTPMstiRootPri OBJECT-TYPE
        SYNTAX Unsigned32
        MAX-ACCESS read-only
        STATUS current
        DESCRIPTION
            "This object indicates the root MSTI bridge priority of the MSTP. Value range: 0 to 61440. The default value is 32768 and the step length is 4096."
        ::= { optixMSTPMstiEntry 5 }

    -- 1.3.6.1.4.1.2011.2.25.4.50.40.6.6.1.6
    optixMSTPMstiRootMac OBJECT-TYPE
        SYNTAX OCTET STRING (SIZE(0..24))
        MAX-ACCESS read-only
        STATUS current
        DESCRIPTION
            "This object indicates the MAC address of the root MSTP MSTI bridge."
        ::= { optixMSTPMstiEntry 6 }

    -- 1.3.6.1.4.1.2011.2.25.4.50.40.6.6.1.7
    optixMSTPMstiIrpc OBJECT-TYPE
        SYNTAX Unsigned32
        MAX-ACCESS read-only
        STATUS current
        DESCRIPTION
            "This object indicates the MSTP IRPC. Value range: 0 to 0xffffffff."
        ::= { optixMSTPMstiEntry 7 }

    -- 1.3.6.1.4.1.2011.2.25.4.50.40.6.6.1.8
    optixMSTPMstiRootPortPri OBJECT-TYPE
        SYNTAX Unsigned32
        MAX-ACCESS read-only
        STATUS current
        DESCRIPTION
            "This object indicates the root MSTI port priority of the MSTP. Value range: 0 to 240 (a smaller value indicates a higher priority). The default value is 128 and the step length is 16."
        ::= { optixMSTPMstiEntry 8 }

    -- 1.3.6.1.4.1.2011.2.25.4.50.40.6.6.1.9
    optixMSTPMstiRootPortBoard OBJECT-TYPE
        SYNTAX Unsigned32
        MAX-ACCESS read-only
        STATUS current
        DESCRIPTION
            "This object indicates the slot ID of the root MSTP MSTI port."
        ::= { optixMSTPMstiEntry 9 }

    -- 1.3.6.1.4.1.2011.2.25.4.50.40.6.6.1.10
    optixMSTPMstiRootPortSubboard OBJECT-TYPE
        SYNTAX Unsigned32
        MAX-ACCESS read-only
        STATUS current
        DESCRIPTION
            "This object indicates the subboard ID of the root MSTP MSTI port."
        ::= { optixMSTPMstiEntry 10 }

    -- 1.3.6.1.4.1.2011.2.25.4.50.40.6.6.1.11
    optixMSTPMstiRootPortPort OBJECT-TYPE
        SYNTAX Unsigned32
        MAX-ACCESS read-only
        STATUS current
        DESCRIPTION
            "This object indicates the port number of the root MSTP MSTI port."
        ::= { optixMSTPMstiEntry 11 }

    -- 1.3.6.1.4.1.2011.2.25.4.50.40.6.6.1.12
    optixMSTPMstiMastBridgePri OBJECT-TYPE
        SYNTAX Unsigned32
        MAX-ACCESS read-only
        STATUS current
        DESCRIPTION
            "This object indicates the root MSTI bridge priority of the MSTP MSTI domain. Value range: 0 to 61440. The default value is 32768 and the step length is 4096."
        ::= { optixMSTPMstiEntry 12 }

    -- 1.3.6.1.4.1.2011.2.25.4.50.40.6.6.1.13
    optixMSTPMstiMastBridgeMac OBJECT-TYPE
        SYNTAX OCTET STRING (SIZE(0..24))
        MAX-ACCESS read-only
        STATUS current
        DESCRIPTION
            "This object indicates the MAC address of the root MSTP MSTI bridge."
        ::= { optixMSTPMstiEntry 13 }

    -- 1.3.6.1.4.1.2011.2.25.4.50.40.6.6.1.14
    optixMSTPMstiMrpc OBJECT-TYPE
        SYNTAX Unsigned32
        MAX-ACCESS read-only
        STATUS current
        DESCRIPTION
            "This object indicates the MSTP MRPC. Value range: 0 to 0xffffffff."
        ::= { optixMSTPMstiEntry 14 }

    -- 1.3.6.1.4.1.2011.2.25.4.50.40.6.6.1.15
    optixMSTPMstiTc OBJECT-TYPE
        SYNTAX Unsigned32
        MAX-ACCESS read-only
        STATUS current
        DESCRIPTION
            "This object indicates the MSTP topology change. Value range: 0 and 1. 0: no change, 1: change"
        ::= { optixMSTPMstiEntry 15 }

    -- 1.3.6.1.4.1.2011.2.25.4.50.40.6.6.1.16
    optixMSTPMstiTimeSinceLastTc OBJECT-TYPE
        SYNTAX Unsigned32
        MAX-ACCESS read-only
        STATUS current
        DESCRIPTION
            "This object indicates the last topology change duration of the MSTP. Value range: 0 to 0xffffffff (unit: s)."
        ::= { optixMSTPMstiEntry 16 }

    -- 1.3.6.1.4.1.2011.2.25.4.50.40.6.6.1.17
    optixMSTPMstiTcNum OBJECT-TYPE
        SYNTAX Unsigned32
        MAX-ACCESS read-only
        STATUS current
        DESCRIPTION
            "This object indicates the number of MSTP topology changes. Value range: 0 to 0xffffffff."
        ::= { optixMSTPMstiEntry 17 }

    -- 1.3.6.1.4.1.2011.2.25.4.50.40.6.7
    optixMSTPMstiPortTable OBJECT-TYPE
        SYNTAX SEQUENCE OF OptixMSTPMstiPortEntry
        MAX-ACCESS not-accessible
        STATUS current
        DESCRIPTION
            "This table describes the basic MSTP Port configurations."
        ::= { optixPktMstpGroup 7 }

    -- 1.3.6.1.4.1.2011.2.25.4.50.40.6.7.1
    optixMSTPMstiPortEntry OBJECT-TYPE
        SYNTAX OptixMSTPMstiPortEntry
        MAX-ACCESS not-accessible
        STATUS current
        DESCRIPTION
            "This entry describes the basic MSTP Port configurations."
        INDEX{ optixMSTPPortGroupId,optixMSTPMstiID,optixLogBoardId,optixLogSubCardId,optixEtyPortId }
        ::= { optixMSTPMstiPortTable 1 }

    OptixMSTPMstiPortEntry ::=
        SEQUENCE {
            optixMSTPMstiPortPri
                Unsigned32,
            optixMSTPMstiPortPathCost
                Unsigned32,
            optixMSTPMstiPortRole
                INTEGER,
            optixMSTPMstiPortState
                INTEGER,
            optixMSTPMstiDesBridgePri
                Unsigned32,
            optixMSTPMstiDesBridgeMac
                OCTET STRING,
            optixMSTPMstiDesPortPri
                Unsigned32,
            optixMSTPMstiDesPort
                Unsigned32,
            optixMSTPMstiRemainHop
                Unsigned32
        }

    -- 1.3.6.1.4.1.2011.2.25.4.50.40.6.7.1.1
    optixMSTPMstiPortPri OBJECT-TYPE
        SYNTAX Unsigned32
        MAX-ACCESS read-write
        STATUS current
        DESCRIPTION
            "This object indicates the MSTP MSTI port priority. Value range: 0 to 240 (a smaller value indicates a higher priority). The default value is 128 and the step length is 16."
        ::= { optixMSTPMstiPortEntry 1 }

    -- 1.3.6.1.4.1.2011.2.25.4.50.40.6.7.1.2
    optixMSTPMstiPortPathCost OBJECT-TYPE
        SYNTAX Unsigned32
        MAX-ACCESS read-write
        STATUS current
        DESCRIPTION
            "This object indicates the path overhead of the MSTP MSTI port. Value range: 200000000, 2000000, 200000, 20000, 2000, 1"
        ::= { optixMSTPMstiPortEntry 2 }

    -- 1.3.6.1.4.1.2011.2.25.4.50.40.6.7.1.3
    optixMSTPMstiPortRole OBJECT-TYPE
        SYNTAX INTEGER
        {
            root(0),
            designated(1),
            alternate(2),
            backup(3),
            master(4),
            disabled(5)
        }
        MAX-ACCESS read-only
        STATUS current
        DESCRIPTION
            "This object indicates the MTSP MSTI port role. 0: root, 1: designated, 2: alternate, 3: backup, 4: master, 5: disabled"
        ::= { optixMSTPMstiPortEntry 3 }

    -- 1.3.6.1.4.1.2011.2.25.4.50.40.6.7.1.4
    optixMSTPMstiPortState OBJECT-TYPE
        SYNTAX INTEGER
        {
            discarding(0),
            learning(1),
            forwarding(2)
        }
        MAX-ACCESS read-only
        STATUS current
        DESCRIPTION
            "This object indicates the MTSP MSTI port status. 0: discarding, 1: learning, 2: forwarding"
        ::= { optixMSTPMstiPortEntry 4 }

    -- 1.3.6.1.4.1.2011.2.25.4.50.40.6.7.1.5
    optixMSTPMstiDesBridgePri OBJECT-TYPE
        SYNTAX Unsigned32
        MAX-ACCESS read-only
        STATUS current
        DESCRIPTION
            "This object indicates the specified MSTI bridge priority of the MSTP. Value range: 0 to 61440. The default value is 32768 and the step length is 4096."
        ::= { optixMSTPMstiPortEntry 5 }

    -- 1.3.6.1.4.1.2011.2.25.4.50.40.6.7.1.6
    optixMSTPMstiDesBridgeMac OBJECT-TYPE
        SYNTAX OCTET STRING (SIZE(0..24))
        MAX-ACCESS read-only
        STATUS current
        DESCRIPTION
            "This object indicates the MAC address of thespecified MSTP MSTI bridge."
        ::= { optixMSTPMstiPortEntry 6 }

    -- 1.3.6.1.4.1.2011.2.25.4.50.40.6.7.1.7
    optixMSTPMstiDesPortPri OBJECT-TYPE
        SYNTAX Unsigned32
        MAX-ACCESS read-only
        STATUS current
        DESCRIPTION
            "This object indicates the specified MSTP MSTI port priority. Value range: 0 to 240 (a smaller value indicates a higher priority). The default value is 128 and the step length is 16."
        ::= { optixMSTPMstiPortEntry 7 }

    -- 1.3.6.1.4.1.2011.2.25.4.50.40.6.7.1.8
    optixMSTPMstiDesPort OBJECT-TYPE
        SYNTAX Unsigned32
        MAX-ACCESS read-only
        STATUS current
        DESCRIPTION
            "This object indicates the design port of MSTP. Value range: 0 to 65535."
        ::= { optixMSTPMstiPortEntry 8 }

    -- 1.3.6.1.4.1.2011.2.25.4.50.40.6.7.1.9
    optixMSTPMstiRemainHop OBJECT-TYPE
        SYNTAX Unsigned32
        MAX-ACCESS read-only
        STATUS current
        DESCRIPTION
            "This object indicates thenumber of remaining hops in the MSTP MSTI MST domain. Value range: 1 to 40."
        ::= { optixMSTPMstiPortEntry 9 }

END
