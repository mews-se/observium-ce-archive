-- OPTIX-ATMIMA-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-ATMIMA-MIB DEFINITIONS ::= BEGIN
    IMPORTS
        OBJECT-GROUP,MODULE-COMPLIANCE
            FROM SNMPv2-CONF
        MODULE-IDENTITY,OBJECT-TYPE,Unsigned32,Integer32,IpAddress,NOTIFICATION-TYPE
            FROM SNMPv2-SMI
        RowStatus
            FROM SNMPv2-TC
        optixProvisionPtn
            FROM OPTIX-OID-MIB
        ;

    optixAtmImaMod MODULE-IDENTITY
        LAST-UPDATED "201204140000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is usedto configure and manageATM/IMA services. The asynchronous transfer mode(ATM) is used to carryservice data by encoding them into ATM cells for trasmission. Combined with advantages of circuit switching and packet switching, the ATM can carry multiple messages and communication services through a single network with a good QoS. The inverse multiplexing for ATM (IMA) separates aggregate ATM cell streams to multiple low-speed links for transmission and multiplexes these low-speed links at the remote end in a flexible and simple manner to restore the ATM cell streams in the original sequence."
        REVISION "201204140000Z"
        DESCRIPTION
            "Initial version of this MIB module"
        ::={ optixProvisionPtn 1 }

    -- 1.3.6.1.4.1.2011.2.25.4.50.1.1
    optixAtmImaObject OBJECT IDENTIFIER ::= { optixAtmImaMod 1 }

    -- 1.3.6.1.4.1.2011.2.25.4.50.1.1.1
    optixAtmOamCnCodeOne OBJECT-TYPE
        SYNTAX Unsigned32
        MAX-ACCESS read-write
        STATUS current
        DESCRIPTION
            "This object indicates the first four bytes of the ATM OAM loopback location identifier (LLID), composed of country code and network code."
        DEFVAL{ 0 }
        ::= { optixAtmImaObject 1 }

    -- 1.3.6.1.4.1.2011.2.25.4.50.1.1.2
    optixAtmOamCnCodeTwo OBJECT-TYPE
        SYNTAX Unsigned32
        MAX-ACCESS read-write
        STATUS current
        DESCRIPTION
            "This object indicates the second four bytes of the ATM OAM LLID."
        DEFVAL{ 0 }
        ::= { optixAtmImaObject 2 }

    -- 1.3.6.1.4.1.2011.2.25.4.50.1.1.3
    optixAtmOamCnCodeThree OBJECT-TYPE
        SYNTAX Unsigned32
        MAX-ACCESS read-write
        STATUS current
        DESCRIPTION
            "This object indicates the third four bytes of the ATM OAM LLID."
        DEFVAL{ 0 }
        ::= { optixAtmImaObject 3 }

    -- 1.3.6.1.4.1.2011.2.25.4.50.1.1.4
    optixAtmOamCnCodeFour OBJECT-TYPE
        SYNTAX Unsigned32
        MAX-ACCESS read-write
        STATUS current
        DESCRIPTION
            "This object indicates the fourth four bytes of the ATM OAM LLID."
        DEFVAL{ 0 }
        ::= { optixAtmImaObject 4 }

    -- 1.3.6.1.4.1.2011.2.25.4.50.1.1.5
    optixAtmOamInsertEnable OBJECT-TYPE
        SYNTAX INTEGER
        {
            disable(0),
            enable(1)
        }
        MAX-ACCESS read-write
        STATUS current
        DESCRIPTION
            "This object indicates the enable/disable status of inserting ATM OAM cells. 0: disable 1: enable"
        DEFVAL{ 1 }
        ::= { optixAtmImaObject 5 }

    -- 1.3.6.1.4.1.2011.2.25.4.50.1.1.6
    optixUnitoUniAtmSrvTable OBJECT-TYPE
        SYNTAX SEQUENCE OF OptixUnitoUniAtmSrvEntry
        MAX-ACCESS not-accessible
        STATUS current
        DESCRIPTION
            "This table implements the configurations of the local private ATM line service, which is a private line service transmitted between two UNIson the same deivce, skipping the PSN network.These configurations include the service name and information about two UNIs (such as slot IDs, subboard IDs, port numbers, VPIs and VCIs)."
        ::= { optixAtmImaObject 6 }

    -- 1.3.6.1.4.1.2011.2.25.4.50.1.1.6.1
    optixUnitoUniAtmSrvEntry OBJECT-TYPE
        SYNTAX OptixUnitoUniAtmSrvEntry
        MAX-ACCESS not-accessible
        STATUS current
        DESCRIPTION
            "This entry indicates the local ATM private line parameter table."
        INDEX{ optixUnitoUniAtmSrvIndex,optixUnitoUniAtmFirstUniId,optixUnitoUniAtmSecondUniId }
        ::= { optixUnitoUniAtmSrvTable 1 }

    OptixUnitoUniAtmSrvEntry ::=
        SEQUENCE {
            optixUnitoUniAtmSrvIndex
                Unsigned32,
            optixUnitoUniAtmFirstUniId
                Unsigned32,
            optixUnitoUniAtmSecondUniId
                Unsigned32,
            optixUnitoUniAtmSrvId
                Unsigned32,
            optixUnitoUniAtmSrvName
                OCTET STRING,
            optixUnitoUniAtmFirstUniBid
                Unsigned32,
            optixUnitoUniAtmFirstUniSubBid
                Unsigned32,
            optixUnitoUniAtmFirstUniPortId
                Unsigned32,
            optixUnitoUniFirstUniVpiVciNum
                Unsigned32,
            optixUnitoUniFirstUniVpilist
                OCTET STRING,
            optixUnitoUniFirstUniVcilist
                OCTET STRING,
            optixUnitoUniAtmSecondUniBid
                Unsigned32,
            optixUnitoUniAtmSecondUniSubBid
                Unsigned32,
            optixUnitoUniAtmSecondUniPortId
                Unsigned32,
            optixUnitoUniSecondUniVpiVciNum
                Unsigned32,
            optixUnitoUniSecondUniVpilist
                OCTET STRING,
            optixUnitoUniSecondUniVcilist
                OCTET STRING,
            optixUnitoUniAtmSrvRowStatus
                RowStatus
        }

    -- 1.3.6.1.4.1.2011.2.25.4.50.1.1.6.1.1
    optixUnitoUniAtmSrvIndex OBJECT-TYPE
        SYNTAX Unsigned32
        MAX-ACCESS not-accessible
        STATUS current
        DESCRIPTION
            "This object indicates the service index."
        ::= { optixUnitoUniAtmSrvEntry 1 }

    -- 1.3.6.1.4.1.2011.2.25.4.50.1.1.6.1.2
    optixUnitoUniAtmFirstUniId OBJECT-TYPE
        SYNTAX Unsigned32(1..65535)
        MAX-ACCESS not-accessible
        STATUS current
        DESCRIPTION
            "This object indicates the first V-UNI ID of the service. Value range: 1 to 65535"
        ::= { optixUnitoUniAtmSrvEntry 2 }

    -- 1.3.6.1.4.1.2011.2.25.4.50.1.1.6.1.3
    optixUnitoUniAtmSecondUniId OBJECT-TYPE
        SYNTAX Unsigned32(1..65535)
        MAX-ACCESS not-accessible
        STATUS current
        DESCRIPTION
            "This object indicates the second V-UNI ID of the service. Value range: 1 to 65535"
        ::= { optixUnitoUniAtmSrvEntry 3 }

    -- 1.3.6.1.4.1.2011.2.25.4.50.1.1.6.1.4
    optixUnitoUniAtmSrvId OBJECT-TYPE
        SYNTAX Unsigned32
        MAX-ACCESS read-create
        STATUS current
        DESCRIPTION
            "This object indicates the service ID."
        ::= { optixUnitoUniAtmSrvEntry 4 }

    -- 1.3.6.1.4.1.2011.2.25.4.50.1.1.6.1.5
    optixUnitoUniAtmSrvName OBJECT-TYPE
        SYNTAX OCTET STRING(SIZE(0..64))
        MAX-ACCESS read-create
        STATUS current
        DESCRIPTION
            "This object indicates the service name, which is a character string in 64 bytes."
        DEFVAL{ "" }
        ::= { optixUnitoUniAtmSrvEntry 5 }

    -- 1.3.6.1.4.1.2011.2.25.4.50.1.1.6.1.6
    optixUnitoUniAtmFirstUniBid OBJECT-TYPE
        SYNTAX Unsigned32(1..65535)
        MAX-ACCESS read-create
        STATUS current
        DESCRIPTION
            "This object indicates the first V-UNI slot ID of the service. Value range: 1 to 65535"
        ::= { optixUnitoUniAtmSrvEntry 6 }

    -- 1.3.6.1.4.1.2011.2.25.4.50.1.1.6.1.7
    optixUnitoUniAtmFirstUniSubBid OBJECT-TYPE
        SYNTAX Unsigned32(1..255)
        MAX-ACCESS read-create
        STATUS current
        DESCRIPTION
            "This object indicates the first V-UNI subboard ID of the service. Value range: 1 to 255"
        ::= { optixUnitoUniAtmSrvEntry 7 }

    -- 1.3.6.1.4.1.2011.2.25.4.50.1.1.6.1.8
    optixUnitoUniAtmFirstUniPortId OBJECT-TYPE
        SYNTAX Unsigned32(1..65535)
        MAX-ACCESS read-create
        STATUS current
        DESCRIPTION
            "This object indicates the first V-UNI port number of the service. Value range: 1 to 65535"
        ::= { optixUnitoUniAtmSrvEntry 8 }

    -- 1.3.6.1.4.1.2011.2.25.4.50.1.1.6.1.9
    optixUnitoUniFirstUniVpiVciNum OBJECT-TYPE
        SYNTAX Unsigned32(1..255)
        MAX-ACCESS read-create
        STATUS current
        DESCRIPTION
            "This object indicates the number of VPIs/VCIs of the first service V-UNI.Value range: 1 to 255."
        ::= { optixUnitoUniAtmSrvEntry 9 }

    -- 1.3.6.1.4.1.2011.2.25.4.50.1.1.6.1.10
    optixUnitoUniFirstUniVpilist OBJECT-TYPE
        SYNTAX OCTET STRING(SIZE(1..1020))
        MAX-ACCESS read-create
        STATUS current
        DESCRIPTION
            "This object indicates the VPI list of the first V-UNI. Each VPI occupies 4 bytes."
        ::= { optixUnitoUniAtmSrvEntry 10 }

    -- 1.3.6.1.4.1.2011.2.25.4.50.1.1.6.1.11
    optixUnitoUniFirstUniVcilist OBJECT-TYPE
        SYNTAX OCTET STRING(SIZE(1..1020))
        MAX-ACCESS read-create
        STATUS current
        DESCRIPTION
            "This object indicates the VCI list of the first V-UNI. Each VCI occupies 4 bytes."
        ::= { optixUnitoUniAtmSrvEntry 11 }

    -- 1.3.6.1.4.1.2011.2.25.4.50.1.1.6.1.12
    optixUnitoUniAtmSecondUniBid OBJECT-TYPE
        SYNTAX Unsigned32(1..65535)
        MAX-ACCESS read-create
        STATUS current
        DESCRIPTION
            "This object indicates the second V-UNI slot ID of the service. Value range: 1 to 65535"
        ::= { optixUnitoUniAtmSrvEntry 12 }

    -- 1.3.6.1.4.1.2011.2.25.4.50.1.1.6.1.13
    optixUnitoUniAtmSecondUniSubBid OBJECT-TYPE
        SYNTAX Unsigned32(1..255)
        MAX-ACCESS read-create
        STATUS current
        DESCRIPTION
            "This object indicates the second V-UNI subboard ID of the service. Value range: 1 to 255"
        ::= { optixUnitoUniAtmSrvEntry 13 }

    -- 1.3.6.1.4.1.2011.2.25.4.50.1.1.6.1.14
    optixUnitoUniAtmSecondUniPortId OBJECT-TYPE
        SYNTAX Unsigned32(1..65535)
        MAX-ACCESS read-create
        STATUS current
        DESCRIPTION
            "This object indicates the second V-UNI port number of the service. Value range: 1 to 65535"
        ::= { optixUnitoUniAtmSrvEntry 14 }

    -- 1.3.6.1.4.1.2011.2.25.4.50.1.1.6.1.15
    optixUnitoUniSecondUniVpiVciNum OBJECT-TYPE
        SYNTAX Unsigned32(0..4094)
        MAX-ACCESS read-create
        STATUS current
        DESCRIPTION
            "This object indicates the number of VLANs of the second V-UNI (0: VLAN number of the port). Value range: 1 to 4094"
        ::= { optixUnitoUniAtmSrvEntry 15 }

    -- 1.3.6.1.4.1.2011.2.25.4.50.1.1.6.1.16
    optixUnitoUniSecondUniVpilist OBJECT-TYPE
        SYNTAX OCTET STRING(SIZE(1..1020))
        MAX-ACCESS read-create
        STATUS current
        DESCRIPTION
            "This object indicates the VPI list of the second V-UNI. Each VPI occupies 4 bytes."
        ::= { optixUnitoUniAtmSrvEntry 16 }

    -- 1.3.6.1.4.1.2011.2.25.4.50.1.1.6.1.17
    optixUnitoUniSecondUniVcilist OBJECT-TYPE
        SYNTAX OCTET STRING(SIZE(1..1020))
        MAX-ACCESS read-create
        STATUS current
        DESCRIPTION
            "This object indicates the VCI list of the second V-UNI. Each VCI occupies 4 bytes."
        ::= { optixUnitoUniAtmSrvEntry 17 }

    -- 1.3.6.1.4.1.2011.2.25.4.50.1.1.6.1.255
    optixUnitoUniAtmSrvRowStatus OBJECT-TYPE
        SYNTAX RowStatus
        MAX-ACCESS read-create
        STATUS current
        DESCRIPTION
            "This object indicates the row status. 1: active,4: createAndGo,6: destroy"
        ::= { optixUnitoUniAtmSrvEntry 255 }

    -- 1.3.6.1.4.1.2011.2.25.4.50.1.1.7
    optixUnitoNniAtmSrvTable OBJECT-TYPE
        SYNTAX SEQUENCE OF OptixUnitoNniAtmSrvEntry
        MAX-ACCESS not-accessible
        STATUS current
        DESCRIPTION
            "This table implements the configurations of the remote ATM private line service, which is a private line service transmitted between a Layer 2 UNI and a PW NNI, passing through the PSN network.These configurations include the service name and information about the UNI (such as the slot ID, subboard ID, port number, VPI and VCI) and PW carried by the NNI."
        ::= { optixAtmImaObject 7 }

    -- 1.3.6.1.4.1.2011.2.25.4.50.1.1.7.1
    optixUnitoNniAtmSrvEntry OBJECT-TYPE
        SYNTAX OptixUnitoNniAtmSrvEntry
        MAX-ACCESS not-accessible
        STATUS current
        DESCRIPTION
            "This entry indicates the remote ATM private line parameter table."
        INDEX{ optixUnitoNniAtmSrvIndex,optixUnitoNniAtmSrvUniId,optixUnitoNniAtmSrvNniId }
        ::= { optixUnitoNniAtmSrvTable 1 }

    OptixUnitoNniAtmSrvEntry ::=
        SEQUENCE {
            optixUnitoNniAtmSrvIndex
                Unsigned32,
            optixUnitoNniAtmSrvUniId
                Unsigned32,
            optixUnitoNniAtmSrvNniId
                Unsigned32,
            optixUnitoNniAtmSrvId
                Unsigned32,
            optixUnitoNniAtmSrvName
                OCTET STRING,
            optixUnitoNniAtmSrvUniBid
                Unsigned32,
            optixUnitoNniAtmSrvUniSubBid
                Unsigned32,
            optixUnitoNniAtmSrvUniPortId
                Unsigned32,
            optixUnitoNniAtmSrvUniVpiVciNum
                Unsigned32,
            optixUnitoNniAtmSrvUniVpilist
                OCTET STRING,
            optixUnitoNniAtmSrvUniVcilist
                OCTET STRING,
            optixUnitoNniAtmSrvNniPwIndex
                Unsigned32,
            optixUnitoNniAtmSrvRowStatus
                RowStatus
        }

    -- 1.3.6.1.4.1.2011.2.25.4.50.1.1.7.1.1
    optixUnitoNniAtmSrvIndex OBJECT-TYPE
        SYNTAX Unsigned32
        MAX-ACCESS not-accessible
        STATUS current
        DESCRIPTION
            "This object indicates the service index."
        ::= { optixUnitoNniAtmSrvEntry 1 }

    -- 1.3.6.1.4.1.2011.2.25.4.50.1.1.7.1.2
    optixUnitoNniAtmSrvUniId OBJECT-TYPE
        SYNTAX Unsigned32(1..65535)
        MAX-ACCESS not-accessible
        STATUS current
        DESCRIPTION
            "This object indicates the service V-UNI ID. Value range: 1 to 65535"
        ::= { optixUnitoNniAtmSrvEntry 2 }

    -- 1.3.6.1.4.1.2011.2.25.4.50.1.1.7.1.3
    optixUnitoNniAtmSrvNniId OBJECT-TYPE
        SYNTAX Unsigned32(1..65535)
        MAX-ACCESS not-accessible
        STATUS current
        DESCRIPTION
            "This object indicates the service V-NNI ID. Value range: 1 to 65535"
        ::= { optixUnitoNniAtmSrvEntry 3 }

    -- 1.3.6.1.4.1.2011.2.25.4.50.1.1.7.1.4
    optixUnitoNniAtmSrvId OBJECT-TYPE
        SYNTAX Unsigned32
        MAX-ACCESS read-create
        STATUS current
        DESCRIPTION
            "This object indicates the service ID."
        ::= { optixUnitoNniAtmSrvEntry 4 }

    -- 1.3.6.1.4.1.2011.2.25.4.50.1.1.7.1.5
    optixUnitoNniAtmSrvName OBJECT-TYPE
        SYNTAX OCTET STRING(SIZE(0..64))
        MAX-ACCESS read-create
        STATUS current
        DESCRIPTION
            "This object indicates the service name, which is a character string in 64 bytes."
        DEFVAL{ "" }
        ::= { optixUnitoNniAtmSrvEntry 5 }

    -- 1.3.6.1.4.1.2011.2.25.4.50.1.1.7.1.6
    optixUnitoNniAtmSrvUniBid OBJECT-TYPE
        SYNTAX Unsigned32(1..65535)
        MAX-ACCESS read-create
        STATUS current
        DESCRIPTION
            "This object indicates the slot ID of the service V-UNI. Value range: 1 to 65535"
        ::= { optixUnitoNniAtmSrvEntry 6 }

    -- 1.3.6.1.4.1.2011.2.25.4.50.1.1.7.1.7
    optixUnitoNniAtmSrvUniSubBid OBJECT-TYPE
        SYNTAX Unsigned32(1..255)
        MAX-ACCESS read-create
        STATUS current
        DESCRIPTION
            "This object indicates the subboard ID of the service V-UNI. Value range: 1 to 255"
        ::= { optixUnitoNniAtmSrvEntry 7 }

    -- 1.3.6.1.4.1.2011.2.25.4.50.1.1.7.1.8
    optixUnitoNniAtmSrvUniPortId OBJECT-TYPE
        SYNTAX Unsigned32(1..65535)
        MAX-ACCESS read-create
        STATUS current
        DESCRIPTION
            "This object indicates the port number of the service V-UNI. Value range: 1 to 65535"
        ::= { optixUnitoNniAtmSrvEntry 8 }

    -- 1.3.6.1.4.1.2011.2.25.4.50.1.1.7.1.9
    optixUnitoNniAtmSrvUniVpiVciNum OBJECT-TYPE
        SYNTAX Unsigned32(1..255)
        MAX-ACCESS read-create
        STATUS current
        DESCRIPTION
            "This object indicates the number of VPIs/VCIs of the first service V-UNI. Valid values:1-255."
        ::= { optixUnitoNniAtmSrvEntry 9 }

    -- 1.3.6.1.4.1.2011.2.25.4.50.1.1.7.1.10
    optixUnitoNniAtmSrvUniVpilist OBJECT-TYPE
        SYNTAX OCTET STRING(SIZE(1..1020))
        MAX-ACCESS read-create
        STATUS current
        DESCRIPTION
            "This object indicates the VPI list of the service V-UNI. Each VPI occupies 4 bytes."
        ::= { optixUnitoNniAtmSrvEntry 10 }

    -- 1.3.6.1.4.1.2011.2.25.4.50.1.1.7.1.11
    optixUnitoNniAtmSrvUniVcilist OBJECT-TYPE
        SYNTAX OCTET STRING(SIZE(1..1020))
        MAX-ACCESS read-create
        STATUS current
        DESCRIPTION
            "This object indicates the VCI list of the service V-UNI. Each VCI occupies 4 bytes."
        ::= { optixUnitoNniAtmSrvEntry 11 }

    -- 1.3.6.1.4.1.2011.2.25.4.50.1.1.7.1.12
    optixUnitoNniAtmSrvNniPwIndex OBJECT-TYPE
        SYNTAX Unsigned32
        MAX-ACCESS read-create
        STATUS current
        DESCRIPTION
            "This object indicates the PW index carried by the NNI."
        ::= { optixUnitoNniAtmSrvEntry 12 }

    -- 1.3.6.1.4.1.2011.2.25.4.50.1.1.7.1.255
    optixUnitoNniAtmSrvRowStatus OBJECT-TYPE
        SYNTAX RowStatus
        MAX-ACCESS read-create
        STATUS current
        DESCRIPTION
            "This object indicates the row status. 1: active,4: createAndGo,6: destroy"
        ::= { optixUnitoNniAtmSrvEntry 255 }

    -- 1.3.6.1.4.1.2011.2.25.4.50.1.1.8
    optixAtmAggregateTable OBJECT-TYPE
        SYNTAX SEQUENCE OF OptixAtmAggregateEntry
        MAX-ACCESS not-accessible
        STATUS current
        DESCRIPTION
            "This table implements the configurations of the ATM aggregate services, which are transmitted between multiple Layer 2 UNIs and one PW NNI, passing through the PSN network.These configurations include the service name and ID."
        ::= { optixAtmImaObject 8 }

    -- 1.3.6.1.4.1.2011.2.25.4.50.1.1.8.1
    optixAtmAggregateEntry OBJECT-TYPE
        SYNTAX OptixAtmAggregateEntry
        MAX-ACCESS not-accessible
        STATUS current
        DESCRIPTION
            "This entry indicates the configuration table of the ATM-AGGR service."
        INDEX{ optixAtmAggregateIndex }
        ::= { optixAtmAggregateTable 1 }

    OptixAtmAggregateEntry ::=
        SEQUENCE {
            optixAtmAggregateIndex
                Unsigned32,
            optixAtmAggregateId
                Unsigned32,
            optixAtmAggregateName
                OCTET STRING,
            optixAtmAggregateRowStatus
                RowStatus
        }

    -- 1.3.6.1.4.1.2011.2.25.4.50.1.1.8.1.1
    optixAtmAggregateIndex OBJECT-TYPE
        SYNTAX Unsigned32
        MAX-ACCESS not-accessible
        STATUS current
        DESCRIPTION
            "This object indicates the service index."
        ::= { optixAtmAggregateEntry 1 }

    -- 1.3.6.1.4.1.2011.2.25.4.50.1.1.8.1.2
    optixAtmAggregateId OBJECT-TYPE
        SYNTAX Unsigned32
        MAX-ACCESS read-create
        STATUS current
        DESCRIPTION
            "This object indicates the service ID."
        ::= { optixAtmAggregateEntry 2 }

    -- 1.3.6.1.4.1.2011.2.25.4.50.1.1.8.1.3
    optixAtmAggregateName OBJECT-TYPE
        SYNTAX OCTET STRING(SIZE(0..64))
        MAX-ACCESS read-create
        STATUS current
        DESCRIPTION
            "This object indicates the service name, which is a character string in 64 bytes."
        DEFVAL{ "" }
        ::= { optixAtmAggregateEntry 3 }

    -- 1.3.6.1.4.1.2011.2.25.4.50.1.1.8.1.255
    optixAtmAggregateRowStatus OBJECT-TYPE
        SYNTAX RowStatus
        MAX-ACCESS read-create
        STATUS current
        DESCRIPTION
            "This object indicates the row status. 1: active,4: createAndGo,6: destroy"
        ::= { optixAtmAggregateEntry 255 }

    -- 1.3.6.1.4.1.2011.2.25.4.50.1.1.9
    optixAtmAggregateUniTable OBJECT-TYPE
        SYNTAX SEQUENCE OF OptixAtmAggregateUniEntry
        MAX-ACCESS not-accessible
        STATUS current
        DESCRIPTION
            "This table implements the configurations of the ATM convergence services carried through Layer 2 logical UNIs.These configurations include the logical UNI role, slot ID, subboard ID, port number, VPI and VCI."
        ::= { optixAtmImaObject 9 }

    -- 1.3.6.1.4.1.2011.2.25.4.50.1.1.9.1
    optixAtmAggregateUniEntry OBJECT-TYPE
        SYNTAX OptixAtmAggregateUniEntry
        MAX-ACCESS not-accessible
        STATUS current
        DESCRIPTION
            "This entry indicates the configuration table of the logical UNIs for the ATM-AGGR service."
        INDEX{ optixAtmAggregateIndex,optixAtmAggregateUniId }
        ::= { optixAtmAggregateUniTable 1 }

    OptixAtmAggregateUniEntry ::=
        SEQUENCE {
            optixAtmAggregateUniId
                Unsigned32,
            optixAtmAggregateUniRole
                INTEGER,
            optixAtmAggregateUniBid
                Unsigned32,
            optixAtmAggregateUniSubBid
                Unsigned32,
            optixAtmAggregateUniPortId
                Unsigned32,
            optixAtmAggregateUniVpiVciNum
                Unsigned32,
            optixAtmAggregateUniVpilist
                OCTET STRING,
            optixAtmAggregateUniVcilist
                OCTET STRING,
            optixAtmAggregateUniRowStatus
                RowStatus
        }

    -- 1.3.6.1.4.1.2011.2.25.4.50.1.1.9.1.1
    optixAtmAggregateUniId OBJECT-TYPE
        SYNTAX Unsigned32(1..65535)
        MAX-ACCESS not-accessible
        STATUS current
        DESCRIPTION
            "This object indicates the service V-UNI ID. Value range: 1 to 65535"
        ::= { optixAtmAggregateUniEntry 1 }

    -- 1.3.6.1.4.1.2011.2.25.4.50.1.1.9.1.2
    optixAtmAggregateUniRole OBJECT-TYPE
        SYNTAX INTEGER
        {
            root(1),
            leaf(2)
        }
        MAX-ACCESS read-create
        STATUS current
        DESCRIPTION
            "This object indicates the role of the logical interface. 1: root 2: leaf"
        ::= { optixAtmAggregateUniEntry 2 }

    -- 1.3.6.1.4.1.2011.2.25.4.50.1.1.9.1.3
    optixAtmAggregateUniBid OBJECT-TYPE
        SYNTAX Unsigned32(1..65535)
        MAX-ACCESS read-create
        STATUS current
        DESCRIPTION
            "This object indicates the slot ID of the service V-UNI. Value range: 1 to 65535"
        ::= { optixAtmAggregateUniEntry 3 }

    -- 1.3.6.1.4.1.2011.2.25.4.50.1.1.9.1.4
    optixAtmAggregateUniSubBid OBJECT-TYPE
        SYNTAX Unsigned32(1..255)
        MAX-ACCESS read-create
        STATUS current
        DESCRIPTION
            "This object indicates the subboard ID of the service V-UNI. Value range: 1 to 255"
        ::= { optixAtmAggregateUniEntry 4 }

    -- 1.3.6.1.4.1.2011.2.25.4.50.1.1.9.1.5
    optixAtmAggregateUniPortId OBJECT-TYPE
        SYNTAX Unsigned32(1..65535)
        MAX-ACCESS read-create
        STATUS current
        DESCRIPTION
            "This object indicates the port number of the service V-UNI. Value range: 1 to 65535"
        ::= { optixAtmAggregateUniEntry 5 }

    -- 1.3.6.1.4.1.2011.2.25.4.50.1.1.9.1.6
    optixAtmAggregateUniVpiVciNum OBJECT-TYPE
        SYNTAX Unsigned32(1..255)
        MAX-ACCESS read-create
        STATUS current
        DESCRIPTION
            "This object indicates the number of VPIs/VCIs of the service V-UNI. Valid values: 1-255."
        ::= { optixAtmAggregateUniEntry 6 }

    -- 1.3.6.1.4.1.2011.2.25.4.50.1.1.9.1.7
    optixAtmAggregateUniVpilist OBJECT-TYPE
        SYNTAX OCTET STRING(SIZE(1..1020))
        MAX-ACCESS read-create
        STATUS current
        DESCRIPTION
            "This object indicates the VPI list of the service V-UNI. Each VPI occupies 4 bytes."
        ::= { optixAtmAggregateUniEntry 7 }

    -- 1.3.6.1.4.1.2011.2.25.4.50.1.1.9.1.8
    optixAtmAggregateUniVcilist OBJECT-TYPE
        SYNTAX OCTET STRING(SIZE(1..1020))
        MAX-ACCESS read-create
        STATUS current
        DESCRIPTION
            "This object indicates the VCI list of the service V-UNI. Each VCI occupies 4 bytes."
        ::= { optixAtmAggregateUniEntry 8 }

    -- 1.3.6.1.4.1.2011.2.25.4.50.1.1.9.1.255
    optixAtmAggregateUniRowStatus OBJECT-TYPE
        SYNTAX RowStatus
        MAX-ACCESS read-create
        STATUS current
        DESCRIPTION
            "This object indicates the row status. 1: active,4: createAndGo,6: destroy"
        ::= { optixAtmAggregateUniEntry 255 }

    -- 1.3.6.1.4.1.2011.2.25.4.50.1.1.10
    optixAtmAggregateNniTable OBJECT-TYPE
        SYNTAX SEQUENCE OF OptixAtmAggregateNniEntry
        MAX-ACCESS not-accessible
        STATUS current
        DESCRIPTION
            "This table implements the configurations of the ATM aggregate services carried through logical PW NNIs. These configurations include the logical NNI role and PW index."
        ::= { optixAtmImaObject 10 }

    -- 1.3.6.1.4.1.2011.2.25.4.50.1.1.10.1
    optixAtmAggregateNniEntry OBJECT-TYPE
        SYNTAX OptixAtmAggregateNniEntry
        MAX-ACCESS not-accessible
        STATUS current
        DESCRIPTION
            "This entry indicates the configuration table of the NNIs for the ATM-AGGR service."
        INDEX{ optixAtmAggregateIndex,optixAtmAggregateNniId }
        ::= { optixAtmAggregateNniTable 1 }

    OptixAtmAggregateNniEntry ::=
        SEQUENCE {
            optixAtmAggregateNniId
                Unsigned32,
            optixAtmAggregateNniRole
                INTEGER,
            optixAtmAggregateNniPwIndex
                Unsigned32,
            optixAtmAggregateNniRowStatus
                RowStatus
        }

    -- 1.3.6.1.4.1.2011.2.25.4.50.1.1.10.1.1
    optixAtmAggregateNniId OBJECT-TYPE
        SYNTAX Unsigned32
        MAX-ACCESS not-accessible
        STATUS current
        DESCRIPTION
            "This object indicates the service V-NNI ID."
        ::= { optixAtmAggregateNniEntry 1 }

    -- 1.3.6.1.4.1.2011.2.25.4.50.1.1.10.1.2
    optixAtmAggregateNniRole OBJECT-TYPE
        SYNTAX INTEGER
        {
            root(1),
            leaf(2)
        }
        MAX-ACCESS read-create
        STATUS current
        DESCRIPTION
            "This object indicates the role of the logical interface. 1: root 2: leaf"
        ::= { optixAtmAggregateNniEntry 2 }

    -- 1.3.6.1.4.1.2011.2.25.4.50.1.1.10.1.3
    optixAtmAggregateNniPwIndex OBJECT-TYPE
        SYNTAX Unsigned32
        MAX-ACCESS read-create
        STATUS current
        DESCRIPTION
            "This object indicates the PW index carried by the NNI."
        ::= { optixAtmAggregateNniEntry 3 }

    -- 1.3.6.1.4.1.2011.2.25.4.50.1.1.10.1.255
    optixAtmAggregateNniRowStatus OBJECT-TYPE
        SYNTAX RowStatus
        MAX-ACCESS read-create
        STATUS current
        DESCRIPTION
            "This object indicates the row status. 1: active,4: createAndGo,6: destroy"
        ::= { optixAtmAggregateNniEntry 255 }

    -- 1.3.6.1.4.1.2011.2.25.4.50.1.1.11
    optixAtmConnectTable OBJECT-TYPE
        SYNTAX SEQUENCE OF OptixAtmConnectEntry
        MAX-ACCESS not-accessible
        STATUS current
        DESCRIPTION
            "This table implements the configurations of ATM connections which create VPI and VCI exchanging paths between the ingress and egress of the ATM service.These configurations include the name and ATM QoS policies between logical ingress and egress, VPIs, and VCIs, and on the connections."
        ::= { optixAtmImaObject 11 }

    -- 1.3.6.1.4.1.2011.2.25.4.50.1.1.11.1
    optixAtmConnectEntry OBJECT-TYPE
        SYNTAX OptixAtmConnectEntry
        MAX-ACCESS not-accessible
        STATUS current
        DESCRIPTION
            "This entry indicates the configuration table of the ATM connections."
        INDEX{ optixAtmSrvIndex,optixAtmConnectId }
        ::= { optixAtmConnectTable 1 }

    OptixAtmConnectEntry ::=
        SEQUENCE {
            optixAtmSrvIndex
                Unsigned32,
            optixAtmConnectId
                Unsigned32,
            optixAtmConnectName
                OCTET STRING,
            optixAtmConnectInPortType
                INTEGER,
            optixAtmConnectInPortId
                Unsigned32,
            optixAtmConnectInVpi
                Unsigned32,
            optixAtmConnectInVci
                Unsigned32,
            optixAtmConnectOutPortType
                INTEGER,
            optixAtmConnectOutPortId
                Unsigned32,
            optixAtmConnectOutVpi
                Unsigned32,
            optixAtmConnectOutVci
                Unsigned32,
            optixAtmConnectUpPolicyId
                Unsigned32,
            optixAtmConnectDownPolicyId
                Unsigned32,
            optixAtmConnectDir
                INTEGER,
            optixAtmConnectSegend
                INTEGER,
            optixAtmConnectrllid
                OCTET STRING,
            optixAtmConnectRowStatus
                RowStatus
        }

    -- 1.3.6.1.4.1.2011.2.25.4.50.1.1.11.1.1
    optixAtmSrvIndex OBJECT-TYPE
        SYNTAX Unsigned32
        MAX-ACCESS not-accessible
        STATUS current
        DESCRIPTION
            "This object indicates the ATM service index."
        ::= { optixAtmConnectEntry 1 }

    -- 1.3.6.1.4.1.2011.2.25.4.50.1.1.11.1.2
    optixAtmConnectId OBJECT-TYPE
        SYNTAX Unsigned32
        MAX-ACCESS not-accessible
        STATUS current
        DESCRIPTION
            "This object indicates the ATM connection ID."
        ::= { optixAtmConnectEntry 2 }

    -- 1.3.6.1.4.1.2011.2.25.4.50.1.1.11.1.3
    optixAtmConnectName OBJECT-TYPE
        SYNTAX OCTET STRING(SIZE(0..64))
        MAX-ACCESS read-create
        STATUS current
        DESCRIPTION
            "This object indicates the ATM connection name, which is a character string in a maximum of 64 bytes."
        DEFVAL{ "" }
        ::= { optixAtmConnectEntry 3 }

    -- 1.3.6.1.4.1.2011.2.25.4.50.1.1.11.1.4
    optixAtmConnectInPortType OBJECT-TYPE
        SYNTAX INTEGER
        {
            vuni(0),
            vnni(1)
        }
        MAX-ACCESS read-create
        STATUS current
        DESCRIPTION
            "This object indicates the logical input interface type. 0: vuni 1: vnni"
        ::= { optixAtmConnectEntry 4 }

    -- 1.3.6.1.4.1.2011.2.25.4.50.1.1.11.1.5
    optixAtmConnectInPortId OBJECT-TYPE
        SYNTAX Unsigned32(1..65535)
        MAX-ACCESS read-create
        STATUS current
        DESCRIPTION
            "This object indicates the logical input port number. Value range: 1 to 65535"
        ::= { optixAtmConnectEntry 5 }

    -- 1.3.6.1.4.1.2011.2.25.4.50.1.1.11.1.6
    optixAtmConnectInVpi OBJECT-TYPE
        SYNTAX Unsigned32
        MAX-ACCESS read-create
        STATUS current
        DESCRIPTION
            "This object indicates the input VPI."
        ::= { optixAtmConnectEntry 6 }

    -- 1.3.6.1.4.1.2011.2.25.4.50.1.1.11.1.7
    optixAtmConnectInVci OBJECT-TYPE
        SYNTAX Unsigned32
        MAX-ACCESS read-create
        STATUS current
        DESCRIPTION
            "This object indicates the input VCI."
        ::= { optixAtmConnectEntry 7 }

    -- 1.3.6.1.4.1.2011.2.25.4.50.1.1.11.1.8
    optixAtmConnectOutPortType OBJECT-TYPE
        SYNTAX INTEGER
        {
            vuni(0),
            vnni(1)
        }
        MAX-ACCESS read-create
        STATUS current
        DESCRIPTION
            "This object indicates the logical output interface type. 0: vuni 1: vnni"
        ::= { optixAtmConnectEntry 8 }

    -- 1.3.6.1.4.1.2011.2.25.4.50.1.1.11.1.9
    optixAtmConnectOutPortId OBJECT-TYPE
        SYNTAX Unsigned32(1..65535)
        MAX-ACCESS read-create
        STATUS current
        DESCRIPTION
            "This object indicates the logical output port number. Value range: 1 to 65535"
        ::= { optixAtmConnectEntry 9 }

    -- 1.3.6.1.4.1.2011.2.25.4.50.1.1.11.1.10
    optixAtmConnectOutVpi OBJECT-TYPE
        SYNTAX Unsigned32
        MAX-ACCESS read-create
        STATUS current
        DESCRIPTION
            "This object indicates the output VPI."
        ::= { optixAtmConnectEntry 10 }

    -- 1.3.6.1.4.1.2011.2.25.4.50.1.1.11.1.11
    optixAtmConnectOutVci OBJECT-TYPE
        SYNTAX Unsigned32
        MAX-ACCESS read-create
        STATUS current
        DESCRIPTION
            "This object indicates the output VCI."
        ::= { optixAtmConnectEntry 11 }

    -- 1.3.6.1.4.1.2011.2.25.4.50.1.1.11.1.12
    optixAtmConnectUpPolicyId OBJECT-TYPE
        SYNTAX Unsigned32(1..65535)
        MAX-ACCESS read-create
        STATUS current
        DESCRIPTION
            "This object indicates the upstream ATM policy ID. Value range: 1 to 65535"
        ::= { optixAtmConnectEntry 12 }

    -- 1.3.6.1.4.1.2011.2.25.4.50.1.1.11.1.13
    optixAtmConnectDownPolicyId OBJECT-TYPE
        SYNTAX Unsigned32(1..65535)
        MAX-ACCESS read-create
        STATUS current
        DESCRIPTION
            "This object indicates the downstream ATM policy ID. Value range: 1 to 65535"
        ::= { optixAtmConnectEntry 13 }

    -- 1.3.6.1.4.1.2011.2.25.4.50.1.1.11.1.14
    optixAtmConnectDir OBJECT-TYPE
        SYNTAX INTEGER
        {
            fwd(1),
            bwd(2)
        }
        MAX-ACCESS read-create
        STATUS current
        DESCRIPTION
            "This object indicates the ATM connection direction."
        ::= { optixAtmConnectEntry 14 }

    -- 1.3.6.1.4.1.2011.2.25.4.50.1.1.11.1.15
    optixAtmConnectSegend OBJECT-TYPE
        SYNTAX INTEGER
        {
            none(0),
            seg(1),
            end(2),
            segend(3)
        }
        MAX-ACCESS read-create
        STATUS current
        DESCRIPTION
            "This object indicates the ATM connection segment type. {none(0),seg(1),end(2),segend(3)}"
        ::= { optixAtmConnectEntry 15 }

    -- 1.3.6.1.4.1.2011.2.25.4.50.1.1.11.1.16
    optixAtmConnectrllid OBJECT-TYPE
        SYNTAX OCTET STRING
        MAX-ACCESS read-create
        STATUS current
        DESCRIPTION
            "This object indicates the LLID of the ATM connection."
        ::= { optixAtmConnectEntry 16 }

    -- 1.3.6.1.4.1.2011.2.25.4.50.1.1.11.1.255
    optixAtmConnectRowStatus OBJECT-TYPE
        SYNTAX RowStatus
        MAX-ACCESS read-create
        STATUS current
        DESCRIPTION
            "This object indicates the row status. 1: active,4: createAndGo,6: destroy"
        ::= { optixAtmConnectEntry 255 }

    -- 1.3.6.1.4.1.2011.2.25.4.50.1.1.12
    optixAtmOamTable OBJECT-TYPE
        SYNTAX SEQUENCE OF OptixAtmOamEntry
        MAX-ACCESS not-accessible
        STATUS current
        DESCRIPTION
            "This table implements the configurations of the ATM OAM, which is an OAM function for ATM services in the end-to-end mode. This function supports the quality detection of ATM links that span multiple NEs. These ATM OAM attributes include segment and end attributes of the connection point, CC segment and end attributes, and activation status."
        ::= { optixAtmImaObject 12 }

    -- 1.3.6.1.4.1.2011.2.25.4.50.1.1.12.1
    optixAtmOamEntry OBJECT-TYPE
        SYNTAX OptixAtmOamEntry
        MAX-ACCESS not-accessible
        STATUS current
        DESCRIPTION
            "This entry indicates the configuration table of the ATM OAM."
        INDEX{ optixAtmSrvIndex,optixAtmConnectId,optixAtmOamDirection }
        ::= { optixAtmOamTable 1 }

    OptixAtmOamEntry ::=
        SEQUENCE {
            optixAtmOamDirection
                INTEGER,
            optixAtmOamSegend
                INTEGER,
            optixAtmOamCcSegend
                INTEGER,
            optixAtmOamCcState
                INTEGER
        }

    -- 1.3.6.1.4.1.2011.2.25.4.50.1.1.12.1.1
    optixAtmOamDirection OBJECT-TYPE
        SYNTAX INTEGER
        {
            fwd(1),
            bwd(2)
        }
        MAX-ACCESS not-accessible
        STATUS current
        DESCRIPTION
            "This object indicates the ATM OAM direction. 1: fwd 2: bwd"
        ::= { optixAtmOamEntry 1 }

    -- 1.3.6.1.4.1.2011.2.25.4.50.1.1.12.1.2
    optixAtmOamSegend OBJECT-TYPE
        SYNTAX INTEGER
        {
            none(0),
            seg(1),
            end(2),
            segend(3)
        }
        MAX-ACCESS read-write
        STATUS current
        DESCRIPTION
            "This object indicates the end and segment attribute of the connection point. 0: none 1: seg 2: end 3: segend"
        ::= { optixAtmOamEntry 2 }

    -- 1.3.6.1.4.1.2011.2.25.4.50.1.1.12.1.3
    optixAtmOamCcSegend OBJECT-TYPE
        SYNTAX INTEGER
        {
            seg(1),
            end(2)
        }
        MAX-ACCESS read-write
        STATUS current
        DESCRIPTION
            "This object indicates the CC end and segment attribute. 1: seg 2: end"
        ::= { optixAtmOamEntry 3 }

    -- 1.3.6.1.4.1.2011.2.25.4.50.1.1.12.1.4
    optixAtmOamCcState OBJECT-TYPE
        SYNTAX INTEGER
        {
            clear(0),
            source(1),
            sink(2),
            srcsink(3)
        }
        MAX-ACCESS read-write
        STATUS current
        DESCRIPTION
            "This object indicates the CC activation flag. 0: clear 1: source 2: sink 3: srcsink"
        ::= { optixAtmOamEntry 4 }

    -- 1.3.6.1.4.1.2011.2.25.4.50.1.1.13
    optixAtmTrunkAttrTable OBJECT-TYPE
        SYNTAX SEQUENCE OF OptixAtmTrunkAttrEntry
        MAX-ACCESS not-accessible
        STATUS current
        DESCRIPTION
            "This table implements the configurations of ATM Trunk attributes, which multiplex multiple low-speed links to one logical high-speed link. These attributes include the IMA enable status, protocol version,symmetry mode, length of transmitted frames, delay tolerance, and number of activated links."
        ::= { optixAtmImaObject 13 }

    -- 1.3.6.1.4.1.2011.2.25.4.50.1.1.13.1
    optixAtmTrunkAttrEntry OBJECT-TYPE
        SYNTAX OptixAtmTrunkAttrEntry
        MAX-ACCESS not-accessible
        STATUS current
        DESCRIPTION
            "This entry indicates the configuration table of the ATM Trunk attributes."
        INDEX{ optixAtmTrunkAttrBid,optixAtmTrunkAttrSubBid,optixAtmTrunkAttrTrunkId }
        ::= { optixAtmTrunkAttrTable 1 }

    OptixAtmTrunkAttrEntry ::=
        SEQUENCE {
            optixAtmTrunkAttrBid
                Unsigned32,
            optixAtmTrunkAttrSubBid
                Unsigned32,
            optixAtmTrunkAttrTrunkId
                Unsigned32,
            optixAtmTrunkAttrImaEnable
                INTEGER,
            optixAtmTrunkAttrVersion
                INTEGER,
            optixAtmTrunkAttrFrmlenth
                Unsigned32,
            optixAtmTrunkAttrSymmod
                INTEGER,
            optixAtmTrunkAttrMaxDelaytime
                Unsigned32,
            optixAtmTrunkAttrTxMinLinkNum
                Unsigned32,
            optixAtmTrunkAttrRxMinLinkNum
                Unsigned32,
            optixAtmTrunkAttrClockMode
                INTEGER,
            optixAtmTrunkAttrReStart
                INTEGER
        }

    -- 1.3.6.1.4.1.2011.2.25.4.50.1.1.13.1.1
    optixAtmTrunkAttrBid OBJECT-TYPE
        SYNTAX Unsigned32(1..65535)
        MAX-ACCESS not-accessible
        STATUS current
        DESCRIPTION
            "This object indicates the slot ID of the ATM Trunk. Value range: 1 to 65535"
        ::= { optixAtmTrunkAttrEntry 1 }

    -- 1.3.6.1.4.1.2011.2.25.4.50.1.1.13.1.2
    optixAtmTrunkAttrSubBid OBJECT-TYPE
        SYNTAX Unsigned32(1..255)
        MAX-ACCESS not-accessible
        STATUS current
        DESCRIPTION
            "This object indicates the subboard ID of the ATM Trunk. Value range: 1 to 255"
        ::= { optixAtmTrunkAttrEntry 2 }

    -- 1.3.6.1.4.1.2011.2.25.4.50.1.1.13.1.3
    optixAtmTrunkAttrTrunkId OBJECT-TYPE
        SYNTAX Unsigned32(1..65535)
        MAX-ACCESS not-accessible
        STATUS current
        DESCRIPTION
            "This object indicates the ATM Trunk ID. Value range: 1 to 65535"
        ::= { optixAtmTrunkAttrEntry 3 }

    -- 1.3.6.1.4.1.2011.2.25.4.50.1.1.13.1.4
    optixAtmTrunkAttrImaEnable OBJECT-TYPE
        SYNTAX INTEGER
        {
            disable(0),
            enable(1)
        }
        MAX-ACCESS read-write
        STATUS current
        DESCRIPTION
            "This object indicates whether the IMA is enabled. 1: enable 0: disable"
        DEFVAL{ 1 }
        ::= { optixAtmTrunkAttrEntry 4 }

    -- 1.3.6.1.4.1.2011.2.25.4.50.1.1.13.1.5
    optixAtmTrunkAttrVersion OBJECT-TYPE
        SYNTAX INTEGER
        {
            v0(0),
            v1(1)
        }
        MAX-ACCESS read-write
        STATUS current
        DESCRIPTION
            "This object indicates the IMA protocol version. 0: version 1.0 1: version 1.1"
        DEFVAL{ 1 }
        ::= { optixAtmTrunkAttrEntry 5 }

    -- 1.3.6.1.4.1.2011.2.25.4.50.1.1.13.1.6
    optixAtmTrunkAttrFrmlenth OBJECT-TYPE
        SYNTAX Unsigned32(1..65535)
        MAX-ACCESS read-write
        STATUS current
        DESCRIPTION
            "This object indicates the frame length at the IMA transmit end. Value range: 1 to 65535"
        DEFVAL{ 128 }
        ::= { optixAtmTrunkAttrEntry 6 }

    -- 1.3.6.1.4.1.2011.2.25.4.50.1.1.13.1.7
    optixAtmTrunkAttrSymmod OBJECT-TYPE
        SYNTAX INTEGER
        {
            symcfgandop(0),
            symcfgandasymop(1),
            asymcfgandasymop(2)
        }
        MAX-ACCESS read-write
        STATUS current
        DESCRIPTION
            "This object indicates the symmetry mode. 0: symcfgandop 1: symcfgandasymop 2: asymcfgandasymop"
        DEFVAL{ 0 }
        ::= { optixAtmTrunkAttrEntry 7 }

    -- 1.3.6.1.4.1.2011.2.25.4.50.1.1.13.1.8
    optixAtmTrunkAttrMaxDelaytime OBJECT-TYPE
        SYNTAX Unsigned32(1..120)
        MAX-ACCESS read-write
        STATUS current
        DESCRIPTION
            "This object indicates the maximum delay time between links. Value range: 1 to 120"
        DEFVAL{ 25 }
        ::= { optixAtmTrunkAttrEntry 8 }

    -- 1.3.6.1.4.1.2011.2.25.4.50.1.1.13.1.9
    optixAtmTrunkAttrTxMinLinkNum OBJECT-TYPE
        SYNTAX Unsigned32(1..32)
        MAX-ACCESS read-write
        STATUS current
        DESCRIPTION
            "This object indicates the minimum number of the TX active links. Value range: 1 to 32"
        DEFVAL{ 1 }
        ::= { optixAtmTrunkAttrEntry 9 }

    -- 1.3.6.1.4.1.2011.2.25.4.50.1.1.13.1.10
    optixAtmTrunkAttrRxMinLinkNum OBJECT-TYPE
        SYNTAX Unsigned32(1..32)
        MAX-ACCESS read-write
        STATUS current
        DESCRIPTION
            "This object indicates the minimum number of the RX active links. Value range: 1 to 32"
        DEFVAL{ 1 }
        ::= { optixAtmTrunkAttrEntry 10 }

    -- 1.3.6.1.4.1.2011.2.25.4.50.1.1.13.1.11
    optixAtmTrunkAttrClockMode OBJECT-TYPE
        SYNTAX INTEGER
        {
            ctc(0),
            itc(1)
        }
        MAX-ACCESS read-write
        STATUS current
        DESCRIPTION
            "This object indicates the clock mode. 0: ctc 1: itc"
        DEFVAL{ 0 }
        ::= { optixAtmTrunkAttrEntry 11 }

    -- 1.3.6.1.4.1.2011.2.25.4.50.1.1.13.1.12
    optixAtmTrunkAttrReStart OBJECT-TYPE
        SYNTAX INTEGER
        {
            restart(1)
        }
        MAX-ACCESS read-write
        STATUS current
        DESCRIPTION
            "This object indicates that the IMA protocol is to be restarted."
        ::= { optixAtmTrunkAttrEntry 12 }

    -- 1.3.6.1.4.1.2011.2.25.4.50.1.1.14
    optixAtmTrunkMbrTable OBJECT-TYPE
        SYNTAX SEQUENCE OF OptixAtmTrunkMbrEntry
        MAX-ACCESS not-accessible
        STATUS current
        DESCRIPTION
            "This table implements the configurations of ATM Trunk members. These configurations include the slot ID, subboard ID, port number, and high-/low-order channel ID."
        ::= { optixAtmImaObject 14 }

    -- 1.3.6.1.4.1.2011.2.25.4.50.1.1.14.1
    optixAtmTrunkMbrEntry OBJECT-TYPE
        SYNTAX OptixAtmTrunkMbrEntry
        MAX-ACCESS not-accessible
        STATUS current
        DESCRIPTION
            "This entry is used to configure ATM Trunk members."
        INDEX{ optixAtmTrunkMbrImaBid,optixAtmTrunkMbrImaSubBid,optixAtmTrunkMbrImaTrunkId,optixAtmTrunkMbrBid,optixAtmTrunkMbrSubBid,optixAtmTrunkMbrPortId,optixAtmTrunkMbrHpPath,optixAtmTrunkMbrLpPath }
        ::= { optixAtmTrunkMbrTable 1 }

    OptixAtmTrunkMbrEntry ::=
        SEQUENCE {
            optixAtmTrunkMbrImaBid
                Unsigned32,
            optixAtmTrunkMbrImaSubBid
                Unsigned32,
            optixAtmTrunkMbrImaTrunkId
                Unsigned32,
            optixAtmTrunkMbrBid
                Unsigned32,
            optixAtmTrunkMbrSubBid
                Unsigned32,
            optixAtmTrunkMbrPortId
                Unsigned32,
            optixAtmTrunkMbrHpPath
                Unsigned32,
            optixAtmTrunkMbrLpPath
                Unsigned32,
            optixAtmTrunkMbrRowStatus
                RowStatus
        }

    -- 1.3.6.1.4.1.2011.2.25.4.50.1.1.14.1.1
    optixAtmTrunkMbrImaBid OBJECT-TYPE
        SYNTAX Unsigned32(1..65535)
        MAX-ACCESS not-accessible
        STATUS current
        DESCRIPTION
            "This object indicates the slot ID of the ATM Trunk. Value range: 1 to 65535"
        ::= { optixAtmTrunkMbrEntry 1 }

    -- 1.3.6.1.4.1.2011.2.25.4.50.1.1.14.1.2
    optixAtmTrunkMbrImaSubBid OBJECT-TYPE
        SYNTAX Unsigned32(1..255)
        MAX-ACCESS not-accessible
        STATUS current
        DESCRIPTION
            "This object indicates the subboard ID of the ATM Trunk. Value range: 1 to 255"
        ::= { optixAtmTrunkMbrEntry 2 }

    -- 1.3.6.1.4.1.2011.2.25.4.50.1.1.14.1.3
    optixAtmTrunkMbrImaTrunkId OBJECT-TYPE
        SYNTAX Unsigned32(1..65535)
        MAX-ACCESS not-accessible
        STATUS current
        DESCRIPTION
            "This object indicates the ATM Trunk ID. Value range: 1 to 65535"
        ::= { optixAtmTrunkMbrEntry 3 }

    -- 1.3.6.1.4.1.2011.2.25.4.50.1.1.14.1.4
    optixAtmTrunkMbrBid OBJECT-TYPE
        SYNTAX Unsigned32(1..65535)
        MAX-ACCESS not-accessible
        STATUS current
        DESCRIPTION
            "This object indicates the slot ID of the ATM Trunk member. Value range: 1 to 65535"
        ::= { optixAtmTrunkMbrEntry 4 }

    -- 1.3.6.1.4.1.2011.2.25.4.50.1.1.14.1.5
    optixAtmTrunkMbrSubBid OBJECT-TYPE
        SYNTAX Unsigned32(1..255)
        MAX-ACCESS not-accessible
        STATUS current
        DESCRIPTION
            "This object indicates the subboard ID of the ATM Trunk member. Value range: 1 to 255"
        ::= { optixAtmTrunkMbrEntry 5 }

    -- 1.3.6.1.4.1.2011.2.25.4.50.1.1.14.1.6
    optixAtmTrunkMbrPortId OBJECT-TYPE
        SYNTAX Unsigned32(1..65535)
        MAX-ACCESS not-accessible
        STATUS current
        DESCRIPTION
            "This object indicates the port number of the ATM Trunk member. Value range: 1 to 255"
        ::= { optixAtmTrunkMbrEntry 6 }

    -- 1.3.6.1.4.1.2011.2.25.4.50.1.1.14.1.7
    optixAtmTrunkMbrHpPath OBJECT-TYPE
        SYNTAX Unsigned32(1..65535)
        MAX-ACCESS not-accessible
        STATUS current
        DESCRIPTION
            "This object indicates the high-order channel ID of the ATM Trunk member. Value range: 1 to 65535"
        ::= { optixAtmTrunkMbrEntry 7 }

    -- 1.3.6.1.4.1.2011.2.25.4.50.1.1.14.1.8
    optixAtmTrunkMbrLpPath OBJECT-TYPE
        SYNTAX Unsigned32(1..65535)
        MAX-ACCESS not-accessible
        STATUS current
        DESCRIPTION
            "This object indicates the low-order channel ID of the ATM Trunk member. Value range: 1 to 65535"
        ::= { optixAtmTrunkMbrEntry 8 }

    -- 1.3.6.1.4.1.2011.2.25.4.50.1.1.14.1.255
    optixAtmTrunkMbrRowStatus OBJECT-TYPE
        SYNTAX RowStatus
        MAX-ACCESS read-create
        STATUS current
        DESCRIPTION
            "This object indicates the row status. 1: active,4: createAndGo,6: destroy"
        ::= { optixAtmTrunkMbrEntry 255 }

    -- 1.3.6.1.4.1.2011.2.25.4.50.1.1.15
    optixAtmTrunkStatusTable OBJECT-TYPE
        SYNTAX SEQUENCE OF OptixAtmTrunkStatusEntry
        MAX-ACCESS not-accessible
        STATUS current
        DESCRIPTION
            "This table implements thestatus queryof ATM Trunk members. The queried states include the status of remote/local groups, rates of receiving and transmitting cells, and number of received and transmitted links."
        ::= { optixAtmImaObject 15 }

    -- 1.3.6.1.4.1.2011.2.25.4.50.1.1.15.1
    optixAtmTrunkStatusEntry OBJECT-TYPE
        SYNTAX OptixAtmTrunkStatusEntry
        MAX-ACCESS not-accessible
        STATUS current
        DESCRIPTION
            "This entry is used to query the ATM Trunk status."
        INDEX{ optixAtmTrunkStatusBid,optixAtmTrunkStatusSubBid,optixAtmTrunkStatusTrunkId }
        ::= { optixAtmTrunkStatusTable 1 }

    OptixAtmTrunkStatusEntry ::=
        SEQUENCE {
            optixAtmTrunkStatusBid
                Unsigned32,
            optixAtmTrunkStatusSubBid
                Unsigned32,
            optixAtmTrunkStatusTrunkId
                Unsigned32,
            optixAtmTrunkLocalGroupStatus
                INTEGER,
            optixAtmTrunkPeerGroupStatus
                INTEGER,
            optixAtmTrunkStatusTxCellSpeed
                Unsigned32,
            optixAtmTrunkStatusRxeCellSpeed
                Unsigned32,
            optixAtmTrunkStatusTxLinksCfg
                Unsigned32,
            optixAtmTrunkStatusRxLinksCfg
                Unsigned32,
            optixAtmTrunkStatusTxAckLinks
                Unsigned32,
            optixAtmTrunkStatusRxAckLinks
                Unsigned32
        }

    -- 1.3.6.1.4.1.2011.2.25.4.50.1.1.15.1.1
    optixAtmTrunkStatusBid OBJECT-TYPE
        SYNTAX Unsigned32(1..65535)
        MAX-ACCESS not-accessible
        STATUS current
        DESCRIPTION
            "This object indicates the slot ID of the ATM Trunk. Value range: 1 to 65535"
        ::= { optixAtmTrunkStatusEntry 1 }

    -- 1.3.6.1.4.1.2011.2.25.4.50.1.1.15.1.2
    optixAtmTrunkStatusSubBid OBJECT-TYPE
        SYNTAX Unsigned32(1..255)
        MAX-ACCESS not-accessible
        STATUS current
        DESCRIPTION
            "This object indicates the subboard ID of the ATM Trunk. Value range: 1 to 255"
        ::= { optixAtmTrunkStatusEntry 2 }

    -- 1.3.6.1.4.1.2011.2.25.4.50.1.1.15.1.3
    optixAtmTrunkStatusTrunkId OBJECT-TYPE
        SYNTAX Unsigned32(1..65535)
        MAX-ACCESS not-accessible
        STATUS current
        DESCRIPTION
            "This object indicates the ATM Trunk ID. Value range: 1 to 65535"
        ::= { optixAtmTrunkStatusEntry 3 }

    -- 1.3.6.1.4.1.2011.2.25.4.50.1.1.15.1.4
    optixAtmTrunkLocalGroupStatus OBJECT-TYPE
        SYNTAX INTEGER
        {
            noconfigured(1),
            startup(2),
            startupack(3),
            configaborted(4),
            configabortedsym(5),
            configabortedother(6),
            insufficientlinks(7),
            blocked(8),
            operational(9),
            configabortedver(10)
        }
        MAX-ACCESS read-only
        STATUS current
        DESCRIPTION
            "This object indicates the status of the local group state machine."
        ::= { optixAtmTrunkStatusEntry 4 }

    -- 1.3.6.1.4.1.2011.2.25.4.50.1.1.15.1.5
    optixAtmTrunkPeerGroupStatus OBJECT-TYPE
        SYNTAX INTEGER
        {
            noconfigured(1),
            startup(2),
            startupack(3),
            configaborted(4),
            configabortedsym(5),
            configabortedother(6),
            insufficientlinks(7),
            blocked(8),
            operational(9),
            configabortedver(10)
        }
        MAX-ACCESS read-only
        STATUS current
        DESCRIPTION
            "This object indicates the status of the remote group state machine. 1: noconfigured 2: startup 3: startupack 4: configaborted 5: configabortedsym 6: configabortedother 7: insufficientlinks 8: blocked 9: operational 10: configabortedver"
        ::= { optixAtmTrunkStatusEntry 5 }

    -- 1.3.6.1.4.1.2011.2.25.4.50.1.1.15.1.6
    optixAtmTrunkStatusTxCellSpeed OBJECT-TYPE
        SYNTAX Unsigned32
        MAX-ACCESS read-only
        STATUS current
        DESCRIPTION
            "This object indicates the rate of transmitting cells. Unit: cells/s"
        ::= { optixAtmTrunkStatusEntry 6 }

    -- 1.3.6.1.4.1.2011.2.25.4.50.1.1.15.1.7
    optixAtmTrunkStatusRxeCellSpeed OBJECT-TYPE
        SYNTAX Unsigned32
        MAX-ACCESS read-only
        STATUS current
        DESCRIPTION
            "This object indicates the rate of receiving cells. Unit: cells/s"
        ::= { optixAtmTrunkStatusEntry 7 }

    -- 1.3.6.1.4.1.2011.2.25.4.50.1.1.15.1.8
    optixAtmTrunkStatusTxLinksCfg OBJECT-TYPE
        SYNTAX Unsigned32
        MAX-ACCESS read-only
        STATUS current
        DESCRIPTION
            "This object indicates the configured number of transmit links."
        ::= { optixAtmTrunkStatusEntry 8 }

    -- 1.3.6.1.4.1.2011.2.25.4.50.1.1.15.1.9
    optixAtmTrunkStatusRxLinksCfg OBJECT-TYPE
        SYNTAX Unsigned32
        MAX-ACCESS read-only
        STATUS current
        DESCRIPTION
            "This object indicates the configured number of receive links."
        ::= { optixAtmTrunkStatusEntry 9 }

    -- 1.3.6.1.4.1.2011.2.25.4.50.1.1.15.1.10
    optixAtmTrunkStatusTxAckLinks OBJECT-TYPE
        SYNTAX Unsigned32
        MAX-ACCESS read-only
        STATUS current
        DESCRIPTION
            "This object indicates the activated number of transmit links."
        ::= { optixAtmTrunkStatusEntry 10 }

    -- 1.3.6.1.4.1.2011.2.25.4.50.1.1.15.1.11
    optixAtmTrunkStatusRxAckLinks OBJECT-TYPE
        SYNTAX Unsigned32
        MAX-ACCESS read-only
        STATUS current
        DESCRIPTION
            "This object indicates the activated number of receive links."
        ::= { optixAtmTrunkStatusEntry 11 }

    -- 1.3.6.1.4.1.2011.2.25.4.50.1.1.16
    optixImaLinkStatusTable OBJECT-TYPE
        SYNTAX SEQUENCE OF OptixImaLinkStatusEntry
        MAX-ACCESS not-accessible
        STATUS current
        DESCRIPTION
            "This table implements the status query of IMA link members in the ATM Trunk. These information includes the slot ID, subboard ID, port number, high-/low-order channel ID, link delay, and receiving and transmitting states of remote/local IMA links."
        ::= { optixAtmImaObject 16 }

    -- 1.3.6.1.4.1.2011.2.25.4.50.1.1.16.1
    optixImaLinkStatusEntry OBJECT-TYPE
        SYNTAX OptixImaLinkStatusEntry
        MAX-ACCESS not-accessible
        STATUS current
        DESCRIPTION
            "This entry is used to query the IMA link status."
        INDEX{ optixImaLinkStatusImaBid,optixImaLinkStatusImaSubBid,optixImaLinkStatusImaTrunkId }
        ::= { optixImaLinkStatusTable 1 }

    OptixImaLinkStatusEntry ::=
        SEQUENCE {
            optixImaLinkStatusImaBid
                Unsigned32,
            optixImaLinkStatusImaSubBid
                Unsigned32,
            optixImaLinkStatusImaTrunkId
                Unsigned32,
            optixImaLinkStatusBid
                Unsigned32,
            optixImaLinkStatusSubBid
                Unsigned32,
            optixImaLinkStatusPortId
                Unsigned32,
            optixImaLinkStatusHpPath
                Unsigned32,
            optixImaLinkStatusLpPath
                Unsigned32,
            optixImaLinkStatusDelayStatus
                INTEGER,
            optixImaLinkStatusLocalRxStatus
                INTEGER,
            optixImaLinkStatusLocalTxStatus
                INTEGER,
            optixImaLinkStatusPeerRxStatus
                INTEGER,
            optixImaLinkStatusPeerTxStatus
                INTEGER
        }

    -- 1.3.6.1.4.1.2011.2.25.4.50.1.1.16.1.1
    optixImaLinkStatusImaBid OBJECT-TYPE
        SYNTAX Unsigned32(1..65535)
        MAX-ACCESS not-accessible
        STATUS current
        DESCRIPTION
            "This object indicates the slot ID of the ATM Trunk. Value range: 1 to 65535"
        ::= { optixImaLinkStatusEntry 1 }

    -- 1.3.6.1.4.1.2011.2.25.4.50.1.1.16.1.2
    optixImaLinkStatusImaSubBid OBJECT-TYPE
        SYNTAX Unsigned32(1..255)
        MAX-ACCESS not-accessible
        STATUS current
        DESCRIPTION
            "This object indicates the subboard ID of the ATM Trunk. Value range: 1 to 255"
        ::= { optixImaLinkStatusEntry 2 }

    -- 1.3.6.1.4.1.2011.2.25.4.50.1.1.16.1.3
    optixImaLinkStatusImaTrunkId OBJECT-TYPE
        SYNTAX Unsigned32(1..65535)
        MAX-ACCESS not-accessible
        STATUS current
        DESCRIPTION
            "This leaf indicates the ATM Trunk ID. Value range: 1 to 65535"
        ::= { optixImaLinkStatusEntry 3 }

    -- 1.3.6.1.4.1.2011.2.25.4.50.1.1.16.1.4
    optixImaLinkStatusBid OBJECT-TYPE
        SYNTAX Unsigned32(1..65535)
        MAX-ACCESS read-only
        STATUS current
        DESCRIPTION
            "This object indicates the slot ID of the ATM Trunk member. Value range: 1 to 65535"
        ::= { optixImaLinkStatusEntry 4 }

    -- 1.3.6.1.4.1.2011.2.25.4.50.1.1.16.1.5
    optixImaLinkStatusSubBid OBJECT-TYPE
        SYNTAX Unsigned32(1..255)
        MAX-ACCESS read-only
        STATUS current
        DESCRIPTION
            "This object indicates the subboard ID of the ATM Trunk member. Value range: 1 to 255"
        ::= { optixImaLinkStatusEntry 5 }

    -- 1.3.6.1.4.1.2011.2.25.4.50.1.1.16.1.6
    optixImaLinkStatusPortId OBJECT-TYPE
        SYNTAX Unsigned32(1..65535)
        MAX-ACCESS read-only
        STATUS current
        DESCRIPTION
            "This object indicates the port number of the ATM Trunk member. Value range: 1 to 65535"
        ::= { optixImaLinkStatusEntry 6 }

    -- 1.3.6.1.4.1.2011.2.25.4.50.1.1.16.1.7
    optixImaLinkStatusHpPath OBJECT-TYPE
        SYNTAX Unsigned32(1..65535)
        MAX-ACCESS read-only
        STATUS current
        DESCRIPTION
            "This object indicates the high-order channel ID of the ATM Trunk member. Value range: 1 to 65535"
        ::= { optixImaLinkStatusEntry 7 }

    -- 1.3.6.1.4.1.2011.2.25.4.50.1.1.16.1.8
    optixImaLinkStatusLpPath OBJECT-TYPE
        SYNTAX Unsigned32(1..65535)
        MAX-ACCESS read-only
        STATUS current
        DESCRIPTION
            "This object indicates the low-order channel ID of the ATM Trunk member. Value range: 1 to 65535"
        ::= { optixImaLinkStatusEntry 8 }

    -- 1.3.6.1.4.1.2011.2.25.4.50.1.1.16.1.9
    optixImaLinkStatusDelayStatus OBJECT-TYPE
        SYNTAX INTEGER
        {
            unknown(0),
            effective(1),
            noeffective(2)
        }
        MAX-ACCESS read-only
        STATUS current
        DESCRIPTION
            "This object indicates the delay status of the IMA link. 0: unknown delay 1: valid delay 2: invalid delay"
        ::= { optixImaLinkStatusEntry 9 }

    -- 1.3.6.1.4.1.2011.2.25.4.50.1.1.16.1.10
    optixImaLinkStatusLocalRxStatus OBJECT-TYPE
        SYNTAX INTEGER
        {
            notingroup(1),
            nocause(2),
            fault(3),
            misconnection(4),
            inhibit(5),
            failed(6),
            usable(7),
            acctive(8)
        }
        MAX-ACCESS read-only
        STATUS current
        DESCRIPTION
            "This object indicates the status of receive IMA links at the local end. 0xff: invalid status 1: notingroup 2: nocause 3: fault 4: misconnection 5: inhibit 6: failed 7: usable 8: acctive"
        ::= { optixImaLinkStatusEntry 10 }

    -- 1.3.6.1.4.1.2011.2.25.4.50.1.1.16.1.11
    optixImaLinkStatusLocalTxStatus OBJECT-TYPE
        SYNTAX INTEGER
        {
            notingroup(1),
            nocause(2),
            fault(3),
            misconnection(4),
            inhibit(5),
            failed(6),
            usable(7),
            acctive(8)
        }
        MAX-ACCESS read-only
        STATUS current
        DESCRIPTION
            "This object indicates the status of transmit IMA links at the local end. 0xff: invalid status 1: notingroup 2: nocause 3: fault 4: misconnection 5: inhibit 6: failed 7: usable 8: acctive"
        ::= { optixImaLinkStatusEntry 11 }

    -- 1.3.6.1.4.1.2011.2.25.4.50.1.1.16.1.12
    optixImaLinkStatusPeerRxStatus OBJECT-TYPE
        SYNTAX INTEGER
        {
            notingroup(1),
            nocause(2),
            fault(3),
            misconnection(4),
            inhibit(5),
            failed(6),
            usable(7),
            acctive(8)
        }
        MAX-ACCESS read-only
        STATUS current
        DESCRIPTION
            "This object indicates the status of receive IMA links at the remote end. 0xff: invalid status 1: notingroup 2: nocause 3: fault 4: misconnection 5: inhibit 6: failed 7: usable 8: acctive"
        ::= { optixImaLinkStatusEntry 12 }

    -- 1.3.6.1.4.1.2011.2.25.4.50.1.1.16.1.13
    optixImaLinkStatusPeerTxStatus OBJECT-TYPE
        SYNTAX INTEGER
        {
            notingroup(1),
            nocause(2),
            fault(3),
            misconnection(4),
            inhibit(5),
            failed(6),
            usable(7),
            acctive(8)
        }
        MAX-ACCESS read-only
        STATUS current
        DESCRIPTION
            "This object indicates the status of transmit IMA links at the remote end. 0xff: invalid status 1: notingroup 2: nocause 3: fault 4: misconnection 5: inhibit 6: failed 7: usable 8: acctive"
        ::= { optixImaLinkStatusEntry 13 }

    -- 1.3.6.1.4.1.2011.2.25.4.50.1.2
    optixAtmImaTrap OBJECT IDENTIFIER ::= { optixAtmImaMod 2 }

    -- 1.3.6.1.4.1.2011.2.25.4.50.1.2.1
    optixAtmImaMember OBJECT IDENTIFIER ::= { optixAtmImaTrap 1 }

    -- 1.3.6.1.4.1.2011.2.25.4.50.1.2.1.1
    optixAtmTrunkStatusEvtBid OBJECT-TYPE
        SYNTAX Unsigned32(1..65535)
        MAX-ACCESS accessible-for-notify
        STATUS current
        DESCRIPTION
            "This object indicates the slot ID of the ATM Trunk."
        ::= { optixAtmImaMember 1 }

    -- 1.3.6.1.4.1.2011.2.25.4.50.1.2.1.2
    optixAtmTrunkStatusEvtSubBid OBJECT-TYPE
        SYNTAX Unsigned32(1..255)
        MAX-ACCESS accessible-for-notify
        STATUS current
        DESCRIPTION
            "This object indicates the subboard ID of the ATM Trunk."
        ::= { optixAtmImaMember 2 }

    -- 1.3.6.1.4.1.2011.2.25.4.50.1.2.1.3
    optixAtmTrunkStatusEvtTrunkId OBJECT-TYPE
        SYNTAX Unsigned32(1..65535)
        MAX-ACCESS accessible-for-notify
        STATUS current
        DESCRIPTION
            "This object indicates the ATM Trunk ID."
        ::= { optixAtmImaMember 3 }

    -- 1.3.6.1.4.1.2011.2.25.4.50.1.2.1.4
    optixAtmTrunkEvtLocalGroupStatus OBJECT-TYPE
        SYNTAX INTEGER
        {
            noconfigured(1),
            startup(2),
            startupack(3),
            configaborted(4),
            configabortedsym(5),
            configabortedother(6),
            insufficientlinks(7),
            blocked(8),
            operational(9),
            configabortedver(10)
        }
        MAX-ACCESS accessible-for-notify
        STATUS current
        DESCRIPTION
            "This object indicates the status of the local group state machine."
        ::= { optixAtmImaMember 4 }

    -- 1.3.6.1.4.1.2011.2.25.4.50.1.2.1.5
    optixAtmTrunkEvtPeerGroupStatus OBJECT-TYPE
        SYNTAX INTEGER
        {
            noconfigured(1),
            startup(2),
            startupack(3),
            configaborted(4),
            configabortedsym(5),
            configabortedother(6),
            insufficientlinks(7),
            blocked(8),
            operational(9),
            configabortedver(10)
        }
        MAX-ACCESS accessible-for-notify
        STATUS current
        DESCRIPTION
            "This object indicates the status of the remote group state machine."
        ::= { optixAtmImaMember 5 }

    -- 1.3.6.1.4.1.2011.2.25.4.50.1.2.1.6
    optixAtmTrunkEvtTxCellSpeed OBJECT-TYPE
        SYNTAX Unsigned32
        MAX-ACCESS accessible-for-notify
        STATUS current
        DESCRIPTION
            "This object indicates the rate of transmitting cells. Unit: cells/s"
        ::= { optixAtmImaMember 6 }

    -- 1.3.6.1.4.1.2011.2.25.4.50.1.2.1.7
    optixAtmTrunkEvtRxeCellSpeed OBJECT-TYPE
        SYNTAX Unsigned32
        MAX-ACCESS accessible-for-notify
        STATUS current
        DESCRIPTION
            "This object indicates the rate of receiving cells. Unit: cells/s"
        ::= { optixAtmImaMember 7 }

    -- 1.3.6.1.4.1.2011.2.25.4.50.1.2.1.8
    optixAtmTrunkEvtTxLinksCfg OBJECT-TYPE
        SYNTAX Unsigned32
        MAX-ACCESS accessible-for-notify
        STATUS current
        DESCRIPTION
            "This object indicates the configured number of transmit links."
        ::= { optixAtmImaMember 8 }

    -- 1.3.6.1.4.1.2011.2.25.4.50.1.2.1.9
    optixAtmTrunkEvtRxLinksCfg OBJECT-TYPE
        SYNTAX Unsigned32
        MAX-ACCESS accessible-for-notify
        STATUS current
        DESCRIPTION
            "This object indicates the configured number of receive links."
        ::= { optixAtmImaMember 9 }

    -- 1.3.6.1.4.1.2011.2.25.4.50.1.2.1.10
    optixAtmTrunkStatusEvtTxAckLinks OBJECT-TYPE
        SYNTAX Unsigned32
        MAX-ACCESS accessible-for-notify
        STATUS current
        DESCRIPTION
            "This object indicates the activated number of transmitted links."
        ::= { optixAtmImaMember 10 }

    -- 1.3.6.1.4.1.2011.2.25.4.50.1.2.1.11
    optixAtmTrunkStatusEvtRxAckLinks OBJECT-TYPE
        SYNTAX Unsigned32
        MAX-ACCESS accessible-for-notify
        STATUS current
        DESCRIPTION
            "This object indicates the activated number of receive links."
        ::= { optixAtmImaMember 11 }

    -- 1.3.6.1.4.1.2011.2.25.4.50.1.2.1.12
    optixImaLinkStatusTrapImaBid OBJECT-TYPE
        SYNTAX Unsigned32(1..65535)
        MAX-ACCESS accessible-for-notify
        STATUS current
        DESCRIPTION
            "This object indicates the slot ID of the ATM Trunk."
        ::= { optixAtmImaMember 12 }

    -- 1.3.6.1.4.1.2011.2.25.4.50.1.2.1.13
    optixImaLinkStatusTrapImaSubBid OBJECT-TYPE
        SYNTAX Unsigned32(1..255)
        MAX-ACCESS accessible-for-notify
        STATUS current
        DESCRIPTION
            "This object indicates the subboard ID of the ATM Trunk."
        ::= { optixAtmImaMember 13 }

    -- 1.3.6.1.4.1.2011.2.25.4.50.1.2.1.14
    optixImaLinkStatusTrapImaTrunkId OBJECT-TYPE
        SYNTAX Unsigned32(1..65535)
        MAX-ACCESS accessible-for-notify
        STATUS current
        DESCRIPTION
            "This object indicates the ATM Trunk ID."
        ::= { optixAtmImaMember 14 }

    -- 1.3.6.1.4.1.2011.2.25.4.50.1.2.1.15
    optixImaLinkStatusTrapBid OBJECT-TYPE
        SYNTAX Unsigned32(1..65535)
        MAX-ACCESS accessible-for-notify
        STATUS current
        DESCRIPTION
            "This object indicates the slot ID of the ATM Trunk member."
        ::= { optixAtmImaMember 15 }

    -- 1.3.6.1.4.1.2011.2.25.4.50.1.2.1.16
    optixImaLinkStatusTrapSubBid OBJECT-TYPE
        SYNTAX Unsigned32(1..255)
        MAX-ACCESS accessible-for-notify
        STATUS current
        DESCRIPTION
            "This object indicates the subboard ID of the ATM Trunk member."
        ::= { optixAtmImaMember 16 }

    -- 1.3.6.1.4.1.2011.2.25.4.50.1.2.1.17
    optixImaLinkStatusTrapPortId OBJECT-TYPE
        SYNTAX Unsigned32(1..65535)
        MAX-ACCESS accessible-for-notify
        STATUS current
        DESCRIPTION
            "This object indicates the port number of the ATM Trunk member."
        ::= { optixAtmImaMember 17 }

    -- 1.3.6.1.4.1.2011.2.25.4.50.1.2.1.18
    optixImaLinkStatusTrapHpPath OBJECT-TYPE
        SYNTAX Unsigned32(1..65535)
        MAX-ACCESS accessible-for-notify
        STATUS current
        DESCRIPTION
            "This object indicates the high-order channel ID of the ATM Trunk member."
        ::= { optixAtmImaMember 18 }

    -- 1.3.6.1.4.1.2011.2.25.4.50.1.2.1.19
    optixImaLinkStatusTrapLpPath OBJECT-TYPE
        SYNTAX Unsigned32(1..65535)
        MAX-ACCESS accessible-for-notify
        STATUS current
        DESCRIPTION
            "This object indicates the low-order channel ID of the ATM Trunk member."
        ::= { optixAtmImaMember 19 }

    -- 1.3.6.1.4.1.2011.2.25.4.50.1.2.1.20
    optixImaLinkTrapDelayStatus OBJECT-TYPE
        SYNTAX INTEGER
        {
            unknown(0),
            effective(1),
            noeffective(2)
        }
        MAX-ACCESS accessible-for-notify
        STATUS current
        DESCRIPTION
            "This object indicates the delay status of the IMA link. 0: unknown delay 1: valid delay 2: invalid delay"
        ::= { optixAtmImaMember 20 }

    -- 1.3.6.1.4.1.2011.2.25.4.50.1.2.1.21
    optixImaLinkTrapLocalRxStatus OBJECT-TYPE
        SYNTAX INTEGER
        {
            notingroup(1),
            nocause(2),
            fault(3),
            misconnection(4),
            inhibit(5),
            failed(6),
            usable(7),
            acctive(8)
        }
        MAX-ACCESS accessible-for-notify
        STATUS current
        DESCRIPTION
            "This object indicates the status of receive IMA links at the local end. 0xff: invalid status"
        ::= { optixAtmImaMember 21 }

    -- 1.3.6.1.4.1.2011.2.25.4.50.1.2.1.22
    optixImaLinkTrapLocalTxStatus OBJECT-TYPE
        SYNTAX INTEGER
        {
            notingroup(1),
            nocause(2),
            fault(3),
            misconnection(4),
            inhibit(5),
            failed(6),
            usable(7),
            acctive(8)
        }
        MAX-ACCESS accessible-for-notify
        STATUS current
        DESCRIPTION
            "This object indicates the status of transmit IMA links at the local end. 0xff: invalid status"
        ::= { optixAtmImaMember 22 }

    -- 1.3.6.1.4.1.2011.2.25.4.50.1.2.1.23
    optixImaLinkTrapPeerRxStatus OBJECT-TYPE
        SYNTAX INTEGER
        {
            notingroup(1),
            nocause(2),
            fault(3),
            misconnection(4),
            inhibit(5),
            failed(6),
            usable(7),
            acctive(8)
        }
        MAX-ACCESS accessible-for-notify
        STATUS current
        DESCRIPTION
            "This object indicates the status of receive IMA links at the remote end. 0xff: invalid status"
        ::= { optixAtmImaMember 23 }

    -- 1.3.6.1.4.1.2011.2.25.4.50.1.2.1.24
    optixImaLinkTrapPeerTxStatus OBJECT-TYPE
        SYNTAX INTEGER
        {
            notingroup(1),
            nocause(2),
            fault(3),
            misconnection(4),
            inhibit(5),
            failed(6),
            usable(7),
            acctive(8)
        }
        MAX-ACCESS accessible-for-notify
        STATUS current
        DESCRIPTION
            "This object indicates the status of transmit IMA links at the remote end. 0xff: invalid status"
        ::= { optixAtmImaMember 24 }

    -- 1.3.6.1.4.1.2011.2.25.4.50.1.2.1.25
    optixAtmLbServiceIndex OBJECT-TYPE
        SYNTAX Unsigned32
        MAX-ACCESS accessible-for-notify
        STATUS current
        DESCRIPTION
            "This object indicates the ATM service index."
        ::= { optixAtmImaMember 25 }

    -- 1.3.6.1.4.1.2011.2.25.4.50.1.2.1.26
    optixAtmLbConnectionID OBJECT-TYPE
        SYNTAX Unsigned32
        MAX-ACCESS accessible-for-notify
        STATUS current
        DESCRIPTION
            "This object indicates the ID of the ATM loopback."
        ::= { optixAtmImaMember 26 }

    -- 1.3.6.1.4.1.2011.2.25.4.50.1.2.1.27
    optixAtmLbDir OBJECT-TYPE
        SYNTAX INTEGER
        {
            fwd(1),
            bwd(2)
        }
        MAX-ACCESS accessible-for-notify
        STATUS current
        DESCRIPTION
            "This object indicates the direction of the ATM loopback."
        ::= { optixAtmImaMember 27 }

    -- 1.3.6.1.4.1.2011.2.25.4.50.1.2.1.28
    optixAtmLbSegEndType OBJECT-TYPE
        SYNTAX INTEGER
        {
            none(0),
            seg(1),
            end(2),
            segend(3)
        }
        MAX-ACCESS accessible-for-notify
        STATUS current
        DESCRIPTION
            "This object indicates the segment or end type."
        ::= { optixAtmImaMember 28 }

    -- 1.3.6.1.4.1.2011.2.25.4.50.1.2.1.29
    optixAtmLbLLID OBJECT-TYPE
        SYNTAX OCTET STRING
        MAX-ACCESS accessible-for-notify
        STATUS current
        DESCRIPTION
            "This object indicates the loopback LLID."
        ::= { optixAtmImaMember 29 }

    -- 1.3.6.1.4.1.2011.2.25.4.50.1.2.1.30
    optixAtmLbResult OBJECT-TYPE
        SYNTAX Unsigned32
        MAX-ACCESS accessible-for-notify
        STATUS current
        DESCRIPTION
            "This object indicates the success or failure."
        ::= { optixAtmImaMember 30 }

    -- 1.3.6.1.4.1.2011.2.25.4.50.1.2.2
    optixAtmImaTrapReport OBJECT IDENTIFIER ::= { optixAtmImaTrap 2 }

    -- 1.3.6.1.4.1.2011.2.25.4.50.1.2.2.1
    optixAtmTrunkStatusTrap NOTIFICATION-TYPE
        OBJECTS{ optixAtmTrunkStatusEvtBid,optixAtmTrunkStatusEvtSubBid,optixAtmTrunkStatusEvtTrunkId,optixAtmTrunkEvtLocalGroupStatus,optixAtmTrunkEvtPeerGroupStatus,optixAtmTrunkEvtTxCellSpeed,optixAtmTrunkEvtRxeCellSpeed,optixAtmTrunkEvtTxLinksCfg,optixAtmTrunkEvtRxLinksCfg,optixAtmTrunkStatusEvtTxAckLinks,optixAtmTrunkStatusEvtRxAckLinks }
        STATUS current
        DESCRIPTION
            "This object is used to report ATM Trunk status events when the number of link members of the IMA group increases/decreases, the negotiation status changes, and rates of receiving and transmitting cells change."
        ::= { optixAtmImaTrapReport 1 }

    -- 1.3.6.1.4.1.2011.2.25.4.50.1.2.2.2
    optixImaLinkStatusTrap NOTIFICATION-TYPE
        OBJECTS{ optixImaLinkStatusTrapImaBid,optixImaLinkStatusTrapImaSubBid,optixImaLinkStatusTrapImaTrunkId,optixImaLinkStatusTrapBid,optixImaLinkStatusTrapSubBid,optixImaLinkStatusTrapPortId,optixImaLinkStatusTrapHpPath,optixImaLinkStatusTrapLpPath,optixImaLinkTrapDelayStatus,optixImaLinkTrapLocalRxStatus,optixImaLinkTrapLocalTxStatus,optixImaLinkTrapPeerRxStatus,optixImaLinkTrapPeerTxStatus }
        STATUS current
        DESCRIPTION
            "This object is used to report IMA link status events when the delay of member links in the IMA group, or the receive/transmit status of remote/local IMA links changes."
        ::= { optixAtmImaTrapReport 2 }

    -- 1.3.6.1.4.1.2011.2.25.4.50.1.2.2.3
    optixAtmLbTrap NOTIFICATION-TYPE
        OBJECTS{ optixAtmLbServiceIndex,optixAtmLbConnectionID,optixAtmLbDir,optixAtmLbSegEndType,optixAtmLbLLID,optixAtmLbResult }
        STATUS current
        DESCRIPTION
            "This object is used to report ATM loopback status events."
        ::= { optixAtmImaTrapReport 3 }

END
