-- OPTIX-RTN-IFBOARD-ATTRIB-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-IFBOARD-ATTRIB-MIB DEFINITIONS ::= BEGIN
    IMPORTS
        OBJECT-GROUP,MODULE-COMPLIANCE
            FROM SNMPv2-CONF
        Unsigned32,OBJECT-TYPE,MODULE-IDENTITY
            FROM SNMPv2-SMI
        TEXTUAL-CONVENTION
            FROM SNMPv2-TC
        optixRtnOduIndex1,optixRtnOduIndex2
            FROM OPTIX-RTN-ODU-MGR-MIB
        optixProvisionRtn
            FROM OPTIX-OID-MIB
        OPTIXRtnEnableStateType,optixRtnIndex1,optixRtnIndex2,optixRtnIndex3,optixRtnIndex4
            FROM OPTIX-RTN-GENNERAL-MIB
        ;

    optixRtnIFBoardAttr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query IF board related parameters required in radio link configuration and preventive maintenance, including the IF board modulation mode, bandwidth, AM management, and link identifier."
        REVISION "201204160935Z"
        DESCRIPTION
            "The initial revision of this MIB module1."
        ::={ optixProvisionRtn 3 }

    OPTIXRtnE1AisToTuAisEnableType ::= TEXTUAL-CONVENTION
        STATUS current
        DESCRIPTION
            "Indicates whether the E1_AIS is inserted to the TU_AIS. The value can be 0 (disabled), 1 (enabled), or 2 (automatic)."
        SYNTAX INTEGER
        {
            disable(0),
            enable(1),
            auto(2)
        }

    OPTIXRtnIFAcmDirType ::= TEXTUAL-CONVENTION
        STATUS current
        DESCRIPTION
            "Indicates the ACM direction"
        SYNTAX INTEGER
        {
            tx(0),
            rx(1),
            bi(2)
        }

    OPTIXRtnRunModeType ::= TEXTUAL-CONVENTION
        STATUS current
        DESCRIPTION
            "Running mode supported by the IF port. Its value is 0-IS2, 1-IS3, 2-ACCP, 3-NONACCP, 4-IS6, 5-shaccp, 6-is6-plus, 7-eband-common, 8-eband-enhanced, 9-is8, 12-eband-light, 13-is8-plus 15-lh-accp-plus."
        SYNTAX INTEGER
        {
            is2(0),
            is3(1),
            accp(2),
            nonaccp(3),
            is6(4),
            shaccp(5),
            is6-plus(6),
            eband-common(7),
            eband-enhanced(8),
            is8(9),
            eband-light(12),
            is8-plus(13),
            lh-accp-plus(15)
        }

    OPTIXRtnIFLoopMode ::= TEXTUAL-CONVENTION
        STATUS current
        DESCRIPTION
            "Indicates the modem loop mode .it has three mode type : noloop and inloop,outloop"
        SYNTAX INTEGER
        {
            inloop(1),
            noloop(0),
            outloop(2)
        }

    OPTIXRtnBandWidthType ::= TEXTUAL-CONVENTION
        STATUS current
        DESCRIPTION
            "Describes the channel spacing supported by an IF board. Values: 1: 3.5M 2: 7.0M 3: 14M 4: 28M 5: 40M 6: 56M 7: FCC30M 8: FCC40M 9: FCC50M 10: 250M; 11: 500M; 12:750M; 16: 62P5M; 17:125M; 18: bw1000M;
 22:bw200M; 23:112M; 24:FCC10M; 25:FCC20M; 26:bw1500M; 27:bw2000M; 28:bwFCC60M; 30:bw13P75M; 31:bw27P5M; 32:bw55M; 33:bw110M; 34:80M;"
        SYNTAX INTEGER
        {
            bw3P5M(1),
            bw7M(2),
            bw14M(3),
            bw28M(4),
            bw40M(5),
            bw56M(6),
            bwFCC30M(7),
            bwFCC40M(8),
            bwFCC50M(9),
            bw250M(10),
            bw500M(11),
            bw750M(12),
            bw62P5M(16),
            bw125M(17),
            bw1000M(18),
            bw200M(22),
            bw112M(23),
            bwFCC10M(24),
            bwFCC20M(25),
            bw1500M(26),
            bw2000M(27),
            bwFCC60M(28),
            bw14MACCP(30),
            bw28MACCP(31),
            bw56MACCP(32),
            bw112MACCP(33),
			bw80M(34)
        }

    OPTIXRtnModulateModeType ::= TEXTUAL-CONVENTION
        STATUS current
        DESCRIPTION
            "Describes the modulation mode supported by an IF board. Values: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 14:QPSKStrong250M; 15: QPSKStrong500M; 16:QPSKStrong750M; 17 QPSKStrong62P5M; 18: QPSKStrong125M; 20: 4096QAM;
21:modeBPSK; 22:modeBPSK250M; 23:modeBPSK500M; 24:modeBPSK750M; 25:modeBPSK1000M; 26:modeBPSK1500M; 27:modeBPSK2000M; 28: 2048QAMLIGHT; 29:modeBPSK62P5M; 30:modeBPSK125M; 31:mode8PSK; 32:mode8192QAM; 33:mode16384QAM; -1: NULL."
        SYNTAX INTEGER
        {
            modeQPSK(1),
            mode16QAM(2),
            mode32QAM(3),
            mode64QAM(4),
            mode128QAM(5),
            mode256QAM(6),
            mode512QAM(7),
            mode1024QAM(8),
            modeQPSKSTRONG(9),
            mode16QAMSTRONG(10),
            mode512QAMLIGHT(11),
            mode1024QAMLIGHT(12),
            mode2048QAM(13),
            modeQPSKStrong250M(14),
            modeQPSKStrong500M(15),
            modeQPSKStrong750M(16),
            modeQPSKStrong62P5M(17),
            modeQPSKStrong125M(18),
            mode4096QAM(20),
            modeBPSK(21),
            modeBPSK250M(22),
            modeBPSK500M(23),
            modeBPSK750M(24),
            modeBPSK1000M(25),
            modeBPSK1500M(26),
            modeBPSK2000M(27),
            mode2048QAMLIGHT(28),
            modeBPSK62P5M(29),
            modeBPSK125M(30),
            mode8PSK(31),
            mode8192QAM(32),
            mode16384QAM(33),
            modeNULL(-1)
        }

    OPTIXRtnIFServiceType ::= TEXTUAL-CONVENTION
        STATUS current
        DESCRIPTION
            "Indicates the IF service mode. The values: 1: Hybrid (Native E1+ETH), indicating that the IF port carries hybrid services that integrate the Native E1 and Ethernet services. 2: Hybrid (Native STM-1+ETH), indicating that the IF port carries hybrid services that integrate the Native STM-1 and Ethernet services. 3: SDH, indicating that the IF port carries SDH services."
        SYNTAX INTEGER
        {
            e1AndEth(1),
            sdhAndEth(2),
            sdh(3)
        }  

    OPTIXRtnIFAcmModType ::= TEXTUAL-CONVENTION
        STATUS current
        DESCRIPTION
            "Indicates the ACM mod.Values:modeClear(0),modeQPSK(1),mode16QAM(2),mode32QAM(3),mode64QAM(4),mode128QAM(5),mode256QAM(6),mode512QAM(7),mode1024QAM(8),modeQPSKSTRONG(9),mode16QAMSTRONG(10),
mode512QAMLIGHT(11),mode1024QAMLIGHT(12),mode2048QAM(13),modeQPSKStrong250M(14),modeQPSKStrong500M(15),modeQPSKStrong750M(16),modeQPSKStrong62P5M(17),modeQPSKStrong125M(18),
mode4096QAM(20)modeBPSK(21),modeBPSK250M(22),modeBPSK500M(23),modeBPSK750M(24),modeBPSK1000M(25),modeBPSK1500M(26),modeBPSK2000M(27),mode2048QAMLIGHT(28),modeBPSK62P5M(29),modeBPSK125M(30),
mode8PSK(31),mode8192QAM(32),modeNULL(255)"
        SYNTAX INTEGER
        {
            modeClear(0),
            modeQPSK(1),
            mode16QAM(2),
            mode32QAM(3),
            mode64QAM(4),
            mode128QAM(5),
            mode256QAM(6),
            mode512QAM(7),
            mode1024QAM(8),
            modeQPSKSTRONG(9),
            mode16QAMSTRONG(10),
            mode512QAMLIGHT(11),
            mode1024QAMLIGHT(12),
            mode2048QAM(13),
            modeQPSKStrong250M(14),
            modeQPSKStrong500M(15),
            modeQPSKStrong750M(16),
            modeQPSKStrong62P5M(17),
            modeQPSKStrong125M(18),
            mode4096QAM(20),
            modeBPSK(21),
            modeBPSK250M(22),
            modeBPSK500M(23),
            modeBPSK750M(24),
            modeBPSK1000M(25),
            modeBPSK1500M(26),
            modeBPSK2000M(27),
            mode2048QAMLIGHT(28),
            modeBPSK62P5M(29),
            modeBPSK125M(30),
            mode8PSK(31),
            mode8192QAM(32),
            modeNULL(255)
        }

    OPTIXRtnBoardType ::= TEXTUAL-CONVENTION
        STATUS current
        DESCRIPTION
            "Describes the board type of peer NE. shxa2:  2454, shuf3:  2484, v1shua2:  3343, mxuf4: 3344, sxa3: 3372, dmc5a: 3415, dmc4b: 3416, mxui5: 3442, isv3: 3062, isu3: 2474, isv3: 2468, mxii5: 3549, mxxi4b: 4216, mxxi4: 4192, dmd4d: 4146, mxug4: 4125, cshp: 3058"
        SYNTAX INTEGER
        {
            shxa2(2454),
            shuf3(2484),
            v1shua2(3343),
            mxuf4(3344),
            sxa3(3372),
            dmc5a(3415),
            dmc4b(3416),
            mxui5(3442),
            sld3isv3(3062),
            isu3(2474),
            sl91isv3(2468),
            mxxi5(3549),
            mxxi4b(4216),
            mxxi4(4192),
            dmd4d(4146),
            mxug4(4125),
            cshp(3058)
        }

    -- 1.3.6.1.4.1.2011.2.25.4.40.3.1
    optixRtnIFPortModemFeatureTable OBJECT-TYPE
        SYNTAX SEQUENCE OF OptixRtnIFPortModemFeatureEntry
        MAX-ACCESS not-accessible
        STATUS current
        DESCRIPTION
            "Describes AM parameters of an IF board, including the AM status."
        ::= { optixRtnIFBoardAttr 1 }

    -- 1.3.6.1.4.1.2011.2.25.4.40.3.1.1
    optixRtnIFPortModemFeatureEntry OBJECT-TYPE
        SYNTAX OptixRtnIFPortModemFeatureEntry
        MAX-ACCESS not-accessible
        STATUS current
        DESCRIPTION
            "Indicates the management entry for the AM parameters of an IF port."
        INDEX{ optixRtnBoardID,optixRtnSubCardID,optixRtnPortID }
        ::= { optixRtnIFPortModemFeatureTable 1 }

    OptixRtnIFPortModemFeatureEntry ::=
        SEQUENCE {
            optixRtnIFPortIFLoopMode
                OPTIXRtnIFLoopMode,
            optixRtnIFPortAmbooster
                OPTIXRtnEnableStateType,		
            optixRtnIFPortCarrierOutputState
                INTEGER
        }


    -- 1.3.6.1.4.1.2011.2.25.4.40.3.1.1.2
    optixRtnIFPortIFLoopMode OBJECT-TYPE
        SYNTAX OPTIXRtnIFLoopMode
        MAX-ACCESS read-write
        STATUS current
        DESCRIPTION
            "Indicates the modem loop mode .it has three mode type : noloop and inloop,outloop"
        ::= { optixRtnIFPortModemFeatureEntry 2 }

    -- 1.3.6.1.4.1.2011.2.25.4.40.3.1.1.3
    optixRtnIFPortAmbooster OBJECT-TYPE
        SYNTAX OPTIXRtnEnableStateType
        MAX-ACCESS read-write
        STATUS current
        DESCRIPTION
            "Indicates the Ambooster work mode.It has two mode type :disable and enable(nonsupport)"
        ::= { optixRtnIFPortModemFeatureEntry 3 }	

    -- 1.3.6.1.4.1.2011.2.25.4.40.3.1.1.4
    optixRtnIFPortCarrierOutputState OBJECT-TYPE
        SYNTAX INTEGER
        {
            disable(0),
            enable(1)
        }
        MAX-ACCESS read-write
        STATUS current
        DESCRIPTION
            "Indicates the if carrier output state"
        ::= { optixRtnIFPortModemFeatureEntry 4 }

    -- 1.3.6.1.4.1.2011.2.25.4.40.3.3
    optixRtnIFPortStateTable OBJECT-TYPE
        SYNTAX SEQUENCE OF OptixRtnIFPortStateEntry
        MAX-ACCESS not-accessible
        STATUS current
        DESCRIPTION
            "Describes AM parameters of an IF board, including the AM status."
        ::= { optixRtnIFBoardAttr 3 }

    -- 1.3.6.1.4.1.2011.2.25.4.40.3.3.1
    optixRtnIFPortStateEntry OBJECT-TYPE
        SYNTAX OptixRtnIFPortStateEntry
        MAX-ACCESS not-accessible
        STATUS current
        DESCRIPTION
            "Indicates the management entry for the AM parameters of an IF port."
        INDEX{ optixRtnBoardID,optixRtnSubCardID,optixRtnPortID }
        ::= { optixRtnIFPortStateTable 1 }

    OptixRtnIFPortStateEntry ::=
        SEQUENCE {
            optixRtnIFPortState
                INTEGER
        }

    -- 1.3.6.1.4.1.2011.2.25.4.40.3.3.1.1
    optixRtnIFPortState OBJECT-TYPE
        SYNTAX INTEGER
        {
            disable(0),
            enable(1)
        }
        MAX-ACCESS read-write
        STATUS current
        DESCRIPTION
            "Indicates the if port state"
        ::= { optixRtnIFPortStateEntry 1 }

    -- 1.3.6.1.4.1.2011.2.25.4.40.3.4
    optixRtnIfConfluxPortRfMapTable OBJECT-TYPE
        SYNTAX SEQUENCE OF OptixRtnIfConfluxPortRfMapEntry
        MAX-ACCESS not-accessible
        STATUS current
        DESCRIPTION
            "Describes parameters of the modu."
        ::= { optixRtnIFBoardAttr 4 }

    -- 1.3.6.1.4.1.2011.2.25.4.40.3.4.1
    optixRtnIfConfluxPortRfMapEntry OBJECT-TYPE
        SYNTAX OptixRtnIfConfluxPortRfMapEntry
        MAX-ACCESS not-accessible
        STATUS current
        DESCRIPTION
            "Indicates the parameter entry for the modu."
        INDEX{ optixRtnBoardID,optixRtnSubCardID,optixRtnPortID }
        ::= { optixRtnIfConfluxPortRfMapTable 1 }

    OptixRtnIfConfluxPortRfMapEntry ::=
        SEQUENCE {
            optixRtnIfConfluxRole
                Unsigned32,		
            optixRtnIfConfluxBoardId
                Unsigned32,
            optixRtnIfConfluxSubCardId 
                Unsigned32,
            optixRtnIfConfluxPortId
                Unsigned32,
            optixRtnIfConfluxPosition
                Unsigned32,
            optixRtnIfConfluxMode
                Unsigned32,
            optixRtnRfMapBoardId
                Unsigned32,
            optixRtnRfMapSubCardId 
                Unsigned32,	
            optixRtnRfMapPortId
                Unsigned32,	
            optixRtnRfMapCarrier
                Unsigned32,
            optixRtnRfMapPosition
                Unsigned32
        }

    -- 1.3.6.1.4.1.2011.2.25.4.40.3.4.1.4
    optixRtnIfConfluxRole OBJECT-TYPE
        SYNTAX Unsigned32
	{
            src(0),
            dst(1)
        }
        MAX-ACCESS read-write
        STATUS current
        DESCRIPTION
            "Indicates a role."
        ::= { optixRtnIfConfluxPortRfMapEntry 4 }	

    -- 1.3.6.1.4.1.2011.2.25.4.40.3.4.1.5
    optixRtnIfConfluxBoardId OBJECT-TYPE
        SYNTAX Unsigned32
        MAX-ACCESS read-write
        STATUS current
        DESCRIPTION
            "Indicates the IF unit board ID."
        ::= { optixRtnIfConfluxPortRfMapEntry 5 }	

    -- 1.3.6.1.4.1.2011.2.25.4.40.3.4.1.6
    optixRtnIfConfluxSubCardId OBJECT-TYPE
        SYNTAX Unsigned32
        MAX-ACCESS read-write
        STATUS current
        DESCRIPTION
           "Indicates the subboard ID."
        ::= { optixRtnIfConfluxPortRfMapEntry 6 }

    -- 1.3.6.1.4.1.2011.2.25.4.40.3.4.1.7
    optixRtnIfConfluxPortId OBJECT-TYPE
        SYNTAX Unsigned32
        MAX-ACCESS read-write
        STATUS current
        DESCRIPTION
            "Indicates the Port ID."
        ::= { optixRtnIfConfluxPortRfMapEntry 7 }

    -- 1.3.6.1.4.1.2011.2.25.4.40.3.4.1.8
    optixRtnIfConfluxPosition OBJECT-TYPE
        SYNTAX Unsigned32
        {
            local(0),
            adjacency(1)
        }
        MAX-ACCESS read-write
        STATUS current
        DESCRIPTION
            "Indicates the Position."
        ::= { optixRtnIfConfluxPortRfMapEntry 8 }	

    -- 1.3.6.1.4.1.2011.2.25.4.40.3.4.1.9
    optixRtnIfConfluxMode OBJECT-TYPE
        SYNTAX Unsigned32
        MAX-ACCESS read-write
        STATUS current
        DESCRIPTION
             "Indicates the if conflux mode."
        ::= { optixRtnIfConfluxPortRfMapEntry 9 }

    -- 1.3.6.1.4.1.2011.2.25.4.40.3.4.1.10
    optixRtnRfMapBoardId OBJECT-TYPE
        SYNTAX Unsigned32
        MAX-ACCESS read-only
        STATUS current
        DESCRIPTION
            "Indicates the RF unit board ID."
        ::= { optixRtnIfConfluxPortRfMapEntry 10 }	

    -- 1.3.6.1.4.1.2011.2.25.4.40.3.4.1.11
    optixRtnRfMapSubCardId OBJECT-TYPE
        SYNTAX Unsigned32
        MAX-ACCESS read-only
        STATUS current
        DESCRIPTION
             "Indicates the subboard ID."
        ::= { optixRtnIfConfluxPortRfMapEntry 11 }

    -- 1.3.6.1.4.1.2011.2.25.4.40.3.4.1.12
    optixRtnRfMapPortId OBJECT-TYPE
        SYNTAX Unsigned32
        MAX-ACCESS read-only
        STATUS current
        DESCRIPTION
             "Indicates the Port ID."
        ::= { optixRtnIfConfluxPortRfMapEntry 12 }

    -- 1.3.6.1.4.1.2011.2.25.4.40.3.4.1.13
    optixRtnRfMapCarrier OBJECT-TYPE
        SYNTAX Unsigned32
        MAX-ACCESS read-only
        STATUS current
        DESCRIPTION
            "Indicates the Carrier."
        ::= { optixRtnIfConfluxPortRfMapEntry 13 }

    -- 1.3.6.1.4.1.2011.2.25.4.40.3.4.1.14
    optixRtnRfMapPosition OBJECT-TYPE
        SYNTAX Unsigned32
        {
            local(0),
            adjacency(1)
        }
        MAX-ACCESS read-only
        STATUS current
        DESCRIPTION
            "Indicates the Position."
        ::= { optixRtnIfConfluxPortRfMapEntry 14 }

    -- 1.3.6.1.4.1.2011.2.25.4.40.3.5
    optixRtnIFPortSnrMsethNewTable OBJECT-TYPE
        SYNTAX SEQUENCE OF OptixRtnIFPortSnrMsethNewEntry
        MAX-ACCESS not-accessible
        STATUS current
        DESCRIPTION
            "Describes AM parameters of an IF board, including the AM status."
        ::= { optixRtnIFBoardAttr 5 }

    -- 1.3.6.1.4.1.2011.2.25.4.40.3.5.1
    optixRtnIFPortSnrMsethNewEntry OBJECT-TYPE
        SYNTAX OptixRtnIFPortSnrMsethNewEntry
        MAX-ACCESS not-accessible
        STATUS current
        DESCRIPTION
            "Indicates the management entry for the AM parameters of an IF port."
        INDEX{ optixRtnBoardID,optixRtnSubCardID,optixRtnPortID }
        ::= { optixRtnIFPortSnrMsethNewTable 1 }

    OptixRtnIFPortSnrMsethNewEntry ::=
        SEQUENCE {
            optixRtnIFPortSnrBandWidth
                OPTIXRtnBandWidthType,
            optixRtnIFPortSnrBottomMod
                OPTIXRtnModulateModeType,
            optixRtnIFPortSnrGuaranteeMseValue
                Unsigned32,
            optixRtnIFPortSnrPeakMod
                OPTIXRtnModulateModeType,
            optixRtnIFPortSnrPeakMseValue
                Unsigned32
        }

    -- 1.3.6.1.4.1.2011.2.25.4.40.3.5.1.1
    optixRtnIFPortSnrBandWidth OBJECT-TYPE
        SYNTAX OPTIXRtnBandWidthType
        MAX-ACCESS read-only
        STATUS current
        DESCRIPTION
            "Indicates the BandWidth of the Channel.Values: 1: 3.5M 2: 7.0M 3: 14M 4: 28M 5: 40M 6: 56M 7: FCC30M 8: FCC40M 9: FCC50M 10: 250M; 11: 500M; 12:750M; 16: 62P5M; 17:125M; 18: bw1000M;
 22:bw200M; 23:112M; 24:FCC10M; 25:FCC20M; 26:bw1500M; 27:bw2000M; 28:bwFCC60M;"
        ::= { optixRtnIFPortSnrMsethNewEntry 1 }

    -- 1.3.6.1.4.1.2011.2.25.4.40.3.5.1.2
    optixRtnIFPortSnrBottomMod OBJECT-TYPE
        SYNTAX OPTIXRtnModulateModeType
        MAX-ACCESS read-only
        STATUS current
        DESCRIPTION
            "Indicates the bottom modulation mode.Values:modeClear(0),modeQPSK(1),mode16QAM(2),mode32QAM(3),mode64QAM(4),mode128QAM(5),mode256QAM(6),mode512QAM(7),mode1024QAM(8),modeQPSKSTRONG(9),mode16QAMSTRONG(10),
mode512QAMLIGHT(11),mode1024QAMLIGHT(12),mode2048QAM(13),modeQPSKStrong250M(14),modeQPSKStrong500M(15),modeQPSKStrong750M(16),modeQPSKStrong62P5M(17),modeQPSKStrong125M(18),
mode4096QAM(20)modeBPSK(21),modeBPSK250M(22),modeBPSK500M(23),modeBPSK750M(24),modeBPSK1000M(25),modeBPSK1500M(26),modeBPSK2000M(27),mode2048QAMLIGHT(28),modeBPSK62P5M(29),modeBPSK125M(30),
mode8PSK(31),mode8192QAM(32),modeNULL(255)"
        ::= { optixRtnIFPortSnrMsethNewEntry 2 }

    -- 1.3.6.1.4.1.2011.2.25.4.40.3.5.1.3
    optixRtnIFPortSnrGuaranteeMseValue OBJECT-TYPE
        SYNTAX Unsigned32 (0..65535)
        MAX-ACCESS read-only
        STATUS current
        DESCRIPTION
            "Indicates the MSE thresholds in the guaranteed capacity modulation mode. Unit: 0.1 db"
        ::= { optixRtnIFPortSnrMsethNewEntry 3 }

    -- 1.3.6.1.4.1.2011.2.25.4.40.3.5.1.4
    optixRtnIFPortSnrPeakMod OBJECT-TYPE
        SYNTAX OPTIXRtnModulateModeType
        MAX-ACCESS read-only
        STATUS current
        DESCRIPTION
            "Indicates the peak modulation mode.Values:modeClear(0),modeQPSK(1),mode16QAM(2),mode32QAM(3),mode64QAM(4),mode128QAM(5),mode256QAM(6),mode512QAM(7),mode1024QAM(8),modeQPSKSTRONG(9),mode16QAMSTRONG(10),
mode512QAMLIGHT(11),mode1024QAMLIGHT(12),mode2048QAM(13),modeQPSKStrong250M(14),modeQPSKStrong500M(15),modeQPSKStrong750M(16),modeQPSKStrong62P5M(17),modeQPSKStrong125M(18),
mode4096QAM(20)modeBPSK(21),modeBPSK250M(22),modeBPSK500M(23),modeBPSK750M(24),modeBPSK1000M(25),modeBPSK1500M(26),modeBPSK2000M(27),mode2048QAMLIGHT(28),modeBPSK62P5M(29),modeBPSK125M(30),
mode8PSK(31),mode8192QAM(32),modeNULL(255)"
        ::= { optixRtnIFPortSnrMsethNewEntry 4 }

    -- 1.3.6.1.4.1.2011.2.25.4.40.3.5.1.5
    optixRtnIFPortSnrPeakMseValue OBJECT-TYPE
        SYNTAX Unsigned32 (0..65535)
        MAX-ACCESS read-only
        STATUS current
        DESCRIPTION
            "Indicates the MSE thresholds in the full capability modulation mode. Unit: 0.1 db"
        ::= { optixRtnIFPortSnrMsethNewEntry 5 }

    -- 1.3.6.1.4.1.2011.2.25.4.40.3.10
    optixISBoardAttr OBJECT IDENTIFIER ::= { optixRtnIFBoardAttr 10 }

    -- 1.3.6.1.4.1.2011.2.25.4.40.3.10.1
    optixRtnIFPortAlmToAisTable OBJECT-TYPE
        SYNTAX SEQUENCE OF OptixRtnIFPortAlmToAisEntry
        MAX-ACCESS not-accessible
        STATUS current
        DESCRIPTION
            "Describes whether the link alarm AIS insertion of the IF board is enabled."
        ::= { optixISBoardAttr 1 }

    -- 1.3.6.1.4.1.2011.2.25.4.40.3.10.1.1
    optixRtnIFPortAlmToAisEntry OBJECT-TYPE
        SYNTAX OptixRtnIFPortAlmToAisEntry
        MAX-ACCESS not-accessible
        STATUS current
        DESCRIPTION
            "Indicates whether the link alarm AIS insertion of the IF board is enabled."
        INDEX{ optixRtnBoardID,optixRtnSubCardID,optixRtnPortID,optixRtnIFPortAlmID }
        ::= { optixRtnIFPortAlmToAisTable 1 }

    OptixRtnIFPortAlmToAisEntry ::=
        SEQUENCE {
            optixRtnIFPortAlmID
                Unsigned32,
            optixRtnIFPortAlmToAisEnable
                OPTIXRtnEnableStateType
        }

    -- 1.3.6.1.4.1.2011.2.25.4.40.3.10.1.1.1
    optixRtnIFPortAlmID OBJECT-TYPE
        SYNTAX Unsigned32
        MAX-ACCESS read-write
        STATUS current
        DESCRIPTION
            "Indicates the ID of a link alarm."
        ::= { optixRtnIFPortAlmToAisEntry 1 }

    -- 1.3.6.1.4.1.2011.2.25.4.40.3.10.1.1.2
    optixRtnIFPortAlmToAisEnable OBJECT-TYPE
        SYNTAX OPTIXRtnEnableStateType
        MAX-ACCESS read-write
        STATUS current
        DESCRIPTION
            "Indicates whether the alarm AIS insertion is enabled."
        ::= { optixRtnIFPortAlmToAisEntry 2 }

    -- 1.3.6.1.4.1.2011.2.25.4.40.3.10.2
    optixRtnIFPortE1AisToTuAisTable OBJECT-TYPE
        SYNTAX SEQUENCE OF OptixRtnIFPortE1AisToTuAisEntry
        MAX-ACCESS not-accessible
        STATUS current
        DESCRIPTION
            "Describes whether the E1_AIS is inserted to the TU_AIS in an IF E1 channel."
        ::= { optixISBoardAttr 2 }

    -- 1.3.6.1.4.1.2011.2.25.4.40.3.10.2.1
    optixRtnIFPortE1AisToTuAisEntry OBJECT-TYPE
        SYNTAX OptixRtnIFPortE1AisToTuAisEntry
        MAX-ACCESS not-accessible
        STATUS current
        DESCRIPTION
            "Indicates whether the E1_AIS is inserted to the TU_AIS in an IF E1 channel."
        INDEX{ optixRtnBoardID,optixRtnSubCardID,optixRtnPortID,optixRtnIFPortHPid,optixRtnIFPortLPid }
        ::= { optixRtnIFPortE1AisToTuAisTable 1 }

    OptixRtnIFPortE1AisToTuAisEntry ::=
        SEQUENCE {
            optixRtnIFPortHPid
                Unsigned32,
            optixRtnIFPortLPid
                Unsigned32,
            optixRtnIFPortE1AisToTuAisEnable
                OPTIXRtnE1AisToTuAisEnableType
        }

    -- 1.3.6.1.4.1.2011.2.25.4.40.3.10.2.1.1
    optixRtnIFPortHPid OBJECT-TYPE
        SYNTAX Unsigned32
        MAX-ACCESS read-write
        STATUS current
        DESCRIPTION
            "Indicates the ID of an higher order E1 channel."
        ::= { optixRtnIFPortE1AisToTuAisEntry 1 }

    -- 1.3.6.1.4.1.2011.2.25.4.40.3.10.2.1.2
    optixRtnIFPortLPid OBJECT-TYPE
        SYNTAX Unsigned32
        MAX-ACCESS not-accessible
        STATUS current
        DESCRIPTION
            "Indicates the ID of an lower order E1 channel."
        ::= { optixRtnIFPortE1AisToTuAisEntry 2 }

    -- 1.3.6.1.4.1.2011.2.25.4.40.3.10.2.1.3
    optixRtnIFPortE1AisToTuAisEnable OBJECT-TYPE
        SYNTAX OPTIXRtnE1AisToTuAisEnableType
        MAX-ACCESS read-write
        STATUS current
        DESCRIPTION
            "Indicates whether the E1_AIS is inserted to the TU_AIS.Values: disable(0), enable(1), auto(2)"
        ::= { optixRtnIFPortE1AisToTuAisEntry 3 }

    -- 1.3.6.1.4.1.2011.2.25.4.40.3.10.8
    optixRtnIFPortXPICFeatureExtTable OBJECT-TYPE
        SYNTAX SEQUENCE OF OptixRtnIFPortXPICFeatureExtEntry
        MAX-ACCESS not-accessible
        STATUS current
        DESCRIPTION
            "Include some command about XPIC, such as:set/get XPIC state, set/get XPIC bdPolar, set/get XPIC linkId and Synchronization information to adjoin link."
        ::= { optixISBoardAttr 8 }

    -- 1.3.6.1.4.1.2011.2.25.4.40.3.10.8.1
    optixRtnIFPortXPICFeatureExtEntry OBJECT-TYPE
        SYNTAX OptixRtnIFPortXPICFeatureExtEntry
        MAX-ACCESS not-accessible
        STATUS current
        DESCRIPTION
            "Describe some command about XPIC"
        INDEX{ optixRtnBoardID,optixRtnSubCardID,optixRtnPortID }
        ::= { optixRtnIFPortXPICFeatureExtTable 1 }

    OptixRtnIFPortXPICFeatureExtEntry ::=
        SEQUENCE {
            optixRtnIFPortXPICBdPolarExt
                Unsigned32,
            optixRtnIFPortXPICAjoinLinkIdExt
                Unsigned32,
            optixRtnIFPortXPICSyncAjoinInfoExt
                INTEGER
        }

    -- 1.3.6.1.4.1.2011.2.25.4.40.3.10.8.1.2
    optixRtnIFPortXPICBdPolarExt OBJECT-TYPE
        SYNTAX Unsigned32
        {
            h(0),
            v(1),
            null(255)
        }
        MAX-ACCESS read-write
        STATUS current
        DESCRIPTION
            "Describe the bdpolar of XPIC and set the bdpolar of XPIC."
        ::= { optixRtnIFPortXPICFeatureExtEntry 2 }

    -- 1.3.6.1.4.1.2011.2.25.4.40.3.10.8.1.3
    optixRtnIFPortXPICAjoinLinkIdExt OBJECT-TYPE
        SYNTAX Unsigned32 (1..4094)
        MAX-ACCESS read-write
        STATUS current
        DESCRIPTION
            "Describes the XPIC adjoin link Id and set the XPIC adjoin link Id"
        ::= { optixRtnIFPortXPICFeatureExtEntry 3 }

    -- 1.3.6.1.4.1.2011.2.25.4.40.3.10.8.1.4
    optixRtnIFPortXPICSyncAjoinInfoExt OBJECT-TYPE
        SYNTAX INTEGER
        {
            synType(0)
        }
        MAX-ACCESS read-write
        STATUS current
        DESCRIPTION
            "synchronism the local NE information to adjoin NE.(nonsupport)"
        ::= { optixRtnIFPortXPICFeatureExtEntry 4 }

    -- 1.3.6.1.4.1.2011.2.25.4.40.3.10.4
    optixRtnLineFindTable OBJECT-TYPE
        SYNTAX SEQUENCE OF OptixRtnLineFindEntry
        MAX-ACCESS not-accessible
        STATUS current
        DESCRIPTION
            "This table describes information about fiber and cable search."
        ::= { optixISBoardAttr 4 }

    -- 1.3.6.1.4.1.2011.2.25.4.40.3.10.4.1
    optixRtnLineFindEntry OBJECT-TYPE
        SYNTAX OptixRtnLineFindEntry
        MAX-ACCESS not-accessible
        STATUS current
        DESCRIPTION
            "Management entry of fiber and cable search."
        INDEX{ optixRtnBoardID,optixRtnSubCardID,optixRtnPortID }
        ::= { optixRtnLineFindTable 1 }

    OptixRtnLineFindEntry ::=
        SEQUENCE {
            optixRtnLineFindOutNeid
                Unsigned32,
            optixRtnLineFindOutBid
                Unsigned32,
            optixRtnLineFindOutSubcardId
                Unsigned32,
            optixRtnLineFindOutPid
                Unsigned32,
            optixRtnLineFindInNeid
                Unsigned32,
            optixRtnLineFindInBid
                Unsigned32,
            optixRtnLineFindInSubcardId
                Unsigned32,
            optixRtnLineFindInPid
                Unsigned32,
            optixRtnLineFindStartNode
                INTEGER
        }

    -- 1.3.6.1.4.1.2011.2.25.4.40.3.10.4.1.5
    optixRtnLineFindOutNeid OBJECT-TYPE
        SYNTAX Unsigned32
        MAX-ACCESS read-only
        STATUS current
        DESCRIPTION
            "Source NE ID"
        ::= { optixRtnLineFindEntry 5 }

    -- 1.3.6.1.4.1.2011.2.25.4.40.3.10.4.1.6
    optixRtnLineFindOutBid OBJECT-TYPE
        SYNTAX Unsigned32
        MAX-ACCESS read-only
        STATUS current
        DESCRIPTION
            "Source board id"
        ::= { optixRtnLineFindEntry 6 }

    -- 1.3.6.1.4.1.2011.2.25.4.40.3.10.4.1.7
    optixRtnLineFindOutSubcardId OBJECT-TYPE
        SYNTAX Unsigned32
        MAX-ACCESS read-only
        STATUS current
        DESCRIPTION
            "Source subcard id"
        ::= { optixRtnLineFindEntry 7 }

    -- 1.3.6.1.4.1.2011.2.25.4.40.3.10.4.1.8
    optixRtnLineFindOutPid OBJECT-TYPE
        SYNTAX Unsigned32
        MAX-ACCESS read-only
        STATUS current
        DESCRIPTION
            "Source port id"
        ::= { optixRtnLineFindEntry 8 }

    -- 1.3.6.1.4.1.2011.2.25.4.40.3.10.4.1.9
    optixRtnLineFindInNeid OBJECT-TYPE
        SYNTAX Unsigned32
        MAX-ACCESS read-only
        STATUS current
        DESCRIPTION
            "Sink NE ID"
        ::= { optixRtnLineFindEntry 9 }

    -- 1.3.6.1.4.1.2011.2.25.4.40.3.10.4.1.10
    optixRtnLineFindInBid OBJECT-TYPE
        SYNTAX Unsigned32
        MAX-ACCESS read-only
        STATUS current
        DESCRIPTION
            "Sink board id"
        ::= { optixRtnLineFindEntry 10 }

    -- 1.3.6.1.4.1.2011.2.25.4.40.3.10.4.1.11
    optixRtnLineFindInSubcardId OBJECT-TYPE
        SYNTAX Unsigned32
        MAX-ACCESS read-only
        STATUS current
        DESCRIPTION
            "Sink subcard id"
        ::= { optixRtnLineFindEntry 11 }

    -- 1.3.6.1.4.1.2011.2.25.4.40.3.10.4.1.12
    optixRtnLineFindInPid OBJECT-TYPE
        SYNTAX Unsigned32
        MAX-ACCESS read-only
        STATUS current
        DESCRIPTION
            "Sink port id"
        ::= { optixRtnLineFindEntry 12 }

    -- 1.3.6.1.4.1.2011.2.25.4.40.3.10.4.1.13
    optixRtnLineFindStartNode OBJECT-TYPE
        SYNTAX INTEGER
        {
            start(1)
        }
        MAX-ACCESS read-write
        STATUS current
        DESCRIPTION
            "Start linefind"
        ::= { optixRtnLineFindEntry 13 }

    -- 1.3.6.1.4.1.2011.2.25.4.40.3.10.5
    optixRtnIFPortQueueAttribTable OBJECT-TYPE
        SYNTAX SEQUENCE OF OptixRtnIFPortQueueAttribEntry
        MAX-ACCESS not-accessible
        STATUS current
        DESCRIPTION
            "Describes general attributes of an IF board."
        ::= { optixISBoardAttr 5 }

    -- 1.3.6.1.4.1.2011.2.25.4.40.3.10.5.1
    optixRtnIFPortQueueAttribEntry OBJECT-TYPE
        SYNTAX OptixRtnIFPortQueueAttribEntry
        MAX-ACCESS not-accessible
        STATUS current
        DESCRIPTION
            "Indicates management entry for the attributes of an IF port queue."
        INDEX{ optixRtnBoardID,optixRtnSubCardID,optixRtnPortID,optixRtnQueueType }
        ::= { optixRtnIFPortQueueAttribTable 1 }

    OptixRtnIFPortQueueAttribEntry ::=
        SEQUENCE {
            optixRtnQueueType
                INTEGER,
            optixRtnEnhancedCompressEnableStatus
                OPTIXRtnEnableStateType
        }

    -- 1.3.6.1.4.1.2011.2.25.4.40.3.10.5.1.1
    optixRtnQueueType OBJECT-TYPE
        SYNTAX INTEGER
        {
            all(0),
            cs7(1),
            cs6(2),
            ef(3),
            af4(4),
            af3(5),
            af2(6),
            af1(7),
            be(8)
        }
        MAX-ACCESS not-accessible
        STATUS current
        DESCRIPTION
            "This object indicates the queue type of the IF Board."
        ::= { optixRtnIFPortQueueAttribEntry 1 }

    -- 1.3.6.1.4.1.2011.2.25.4.40.3.10.5.1.2
    optixRtnEnhancedCompressEnableStatus OBJECT-TYPE
        SYNTAX OPTIXRtnEnableStateType
        MAX-ACCESS read-write
        STATUS current
        DESCRIPTION
            "Indicates whether to compress the payload and packet headers. Compressing the payload and packet headers can save bandwidth and increase service transmission traffic, but requires a license. Values: 0: disabled 1: enabled"
        DEFVAL{ 0 }
        ::= { optixRtnIFPortQueueAttribEntry 2 }

    -- 1.3.6.1.4.1.2011.2.25.4.40.3.10.6
    optixRtnLinkInfoTable OBJECT-TYPE
        SYNTAX SEQUENCE OF OptixRtnLinkInfoEntry
        MAX-ACCESS not-accessible
        STATUS current
        DESCRIPTION
            "Describes attributes associated with link monitoring."
        ::= { optixISBoardAttr 6 }

    -- 1.3.6.1.4.1.2011.2.25.4.40.3.10.6.1
    optixRtnLinkInfoEntry OBJECT-TYPE
        SYNTAX OptixRtnLinkInfoEntry
        MAX-ACCESS not-accessible
        STATUS current
        DESCRIPTION
            "Indicates a link monitoring management entry."
        INDEX{ optixRtnBoardID,optixRtnSubCardID,optixRtnPortID }
        ::= { optixRtnLinkInfoTable 1 }

    OptixRtnLinkInfoEntry ::=
        SEQUENCE {
            optixRtnLinkWatch
                OPTIXRtnEnableStateType,
            optixRtnStartTime
                OCTET STRING,
            optixRtnCurrentRecordNum
                Unsigned32,
            optixRtnCurrentRslNum
                Unsigned32,
            optixRtnCurrentLinkInfo
                OCTET STRING
        }

    -- 1.3.6.1.4.1.2011.2.25.4.40.3.10.6.1.4
    optixRtnLinkWatch OBJECT-TYPE
        SYNTAX OPTIXRtnEnableStateType
        MAX-ACCESS read-write
        STATUS current
        DESCRIPTION
            "Specifies the status of link monitoring."
        ::= { optixRtnLinkInfoEntry 4 }

    -- 1.3.6.1.4.1.2011.2.25.4.40.3.10.6.1.5
    optixRtnStartTime OBJECT-TYPE
        SYNTAX OCTET STRING
        MAX-ACCESS read-only
        STATUS current
        DESCRIPTION
            "Indicates the start time for link monitoring."
        ::= { optixRtnLinkInfoEntry 5 }

    -- 1.3.6.1.4.1.2011.2.25.4.40.3.10.6.1.6
    optixRtnCurrentRecordNum OBJECT-TYPE
        SYNTAX Unsigned32
        MAX-ACCESS read-only
        STATUS current
        DESCRIPTION
            "Indicates the total number of link monitoring records."
        ::= { optixRtnLinkInfoEntry 6 }

    -- 1.3.6.1.4.1.2011.2.25.4.40.3.10.6.1.7
    optixRtnCurrentRslNum OBJECT-TYPE
        SYNTAX Unsigned32
        MAX-ACCESS read-only
        STATUS current
        DESCRIPTION
            "Indicates the number of RSL links in link monitoring."
        ::= { optixRtnLinkInfoEntry 7 }

    -- 1.3.6.1.4.1.2011.2.25.4.40.3.10.6.1.8
    optixRtnCurrentLinkInfo OBJECT-TYPE
        SYNTAX OCTET STRING
        MAX-ACCESS read-only
        STATUS current
        DESCRIPTION
            "Indicates the MSE and RSL link monitoring information."
        ::= { optixRtnLinkInfoEntry 8 }

    -- 1.3.6.1.4.1.2011.2.25.4.40.3.10.7
    optixRtnStdLinkInfoTable OBJECT-TYPE
        SYNTAX SEQUENCE OF OptixRtnStdLinkInfoEntry
        MAX-ACCESS not-accessible
        STATUS current
        DESCRIPTION
            "Describes attributes associated with link monitoring."
        ::= { optixISBoardAttr 7 }

    -- 1.3.6.1.4.1.2011.2.25.4.40.3.10.7.1
    optixRtnStdLinkInfoEntry OBJECT-TYPE
        SYNTAX OptixRtnStdLinkInfoEntry
        MAX-ACCESS not-accessible
        STATUS current
        DESCRIPTION
            "Indicates a link monitoring management entry."
        INDEX{ optixRtnBoardID,optixRtnSubCardID,optixRtnPortID }
        ::= { optixRtnStdLinkInfoTable 1 }

    OptixRtnStdLinkInfoEntry ::=
        SEQUENCE {
            optixRtnStandardRecordNum
                Unsigned32,
            optixRtnStandardLinkInfo
                OCTET STRING
		}

    -- 1.3.6.1.4.1.2011.2.25.4.40.3.10.7.1.2
    optixRtnStandardRecordNum OBJECT-TYPE
        SYNTAX Unsigned32
        MAX-ACCESS read-only
        STATUS current
        DESCRIPTION
            "Indicates the standard number of RSL links in link monitoring."
        DEFVAL{ 1 }
        ::= { optixRtnStdLinkInfoEntry 2 }

    -- 1.3.6.1.4.1.2011.2.25.4.40.3.10.7.1.3
    optixRtnStandardLinkInfo OBJECT-TYPE
        SYNTAX OCTET STRING
        MAX-ACCESS read-only
        STATUS current
        DESCRIPTION
            "Indicates the standard MSE and RSL link monitoring information."
        ::= { optixRtnStdLinkInfoEntry 3 }
		
    -- 1.3.6.1.4.1.2011.2.25.4.40.3.10.10
    optixRtnPortIndexTable OBJECT-TYPE
        SYNTAX SEQUENCE OF OptixRtnPortIndexEntry
        MAX-ACCESS not-accessible
        STATUS current
        DESCRIPTION
            "Used as the public index table for IF board attribute tables."
        ::= { optixISBoardAttr 10 }

    -- 1.3.6.1.4.1.2011.2.25.4.40.3.10.10.1
    optixRtnPortIndexEntry OBJECT-TYPE
        SYNTAX OptixRtnPortIndexEntry
        MAX-ACCESS not-accessible
        STATUS current
        DESCRIPTION
            "Indicates the index entry for IF ports."
        INDEX{ optixRtnBoardID,optixRtnSubCardID,optixRtnPortID }
        ::= { optixRtnPortIndexTable 1 }

    OptixRtnPortIndexEntry ::=
        SEQUENCE {
            optixRtnBoardID
                Unsigned32,
            optixRtnSubCardID
                Unsigned32,
            optixRtnPortID
                Unsigned32
        }

    -- 1.3.6.1.4.1.2011.2.25.4.40.3.10.10.1.1
    optixRtnBoardID OBJECT-TYPE
        SYNTAX Unsigned32
        MAX-ACCESS not-accessible
        STATUS current
        DESCRIPTION
            "Indicates the slot ID."
        ::= { optixRtnPortIndexEntry 1 }

    -- 1.3.6.1.4.1.2011.2.25.4.40.3.10.10.1.2
    optixRtnSubCardID OBJECT-TYPE
        SYNTAX Unsigned32
        MAX-ACCESS not-accessible
        STATUS current
        DESCRIPTION
            "Indicates the subboard ID."
        ::= { optixRtnPortIndexEntry 2 }

    -- 1.3.6.1.4.1.2011.2.25.4.40.3.10.10.1.3
    optixRtnPortID OBJECT-TYPE
        SYNTAX Unsigned32
        MAX-ACCESS not-accessible
        STATUS current
        DESCRIPTION
            "Indicates the port ID."
        ::= { optixRtnPortIndexEntry 3 }

    -- 1.3.6.1.4.1.2011.2.25.4.40.3.10.20
    optixRtnIFPortGeneralAttribTable OBJECT-TYPE
        SYNTAX SEQUENCE OF OptixRtnIFPortGeneralAttribEntry
        MAX-ACCESS not-accessible
        STATUS current
        DESCRIPTION
            "Describes general attributes of an IF board, including the link ID and the XPIC status."
        ::= { optixISBoardAttr 20 }

    -- 1.3.6.1.4.1.2011.2.25.4.40.3.10.20.1
    optixRtnIFPortGeneralAttribEntry OBJECT-TYPE
        SYNTAX OptixRtnIFPortGeneralAttribEntry
        MAX-ACCESS not-accessible
        STATUS current
        DESCRIPTION
            "Indicates the management entry for the general attributes of an IF port."
        INDEX{ optixRtnBoardID,optixRtnSubCardID,optixRtnPortID }
        ::= { optixRtnIFPortGeneralAttribTable 1 }

    OptixRtnIFPortGeneralAttribEntry ::=
        SEQUENCE {
            optixRtnIFPortCfgLinkID
                Unsigned32,
            optixRtnIFPortRealLinkID
                Unsigned32,
            optixRtnIFPort1588OHEnableStatus
                OPTIXRtnEnableStateType,
            optixRtnIFPortServiceType
                OPTIXRtnIFServiceType,
            optixRtnIFPortBipOverThreshold
                Unsigned32,
            optixRtnIFPortBipSDThreshold
                Unsigned32,
            optixRtnIFPortRunMode
                OPTIXRtnRunModeType,
            optixRtnIFPortMuxLoopMode
                OPTIXRtnIFLoopMode,
            optixRtnMwPortAlmPerEn
                OPTIXRtnEnableStateType
        }

    -- 1.3.6.1.4.1.2011.2.25.4.40.3.10.20.1.1
    optixRtnIFPortCfgLinkID OBJECT-TYPE
        SYNTAX Unsigned32
        MAX-ACCESS read-write
        STATUS current
        DESCRIPTION
            "Indicates the current radio link ID. As an identifier of a radio link, this parameter is used to prevent incorrect connections of radio links between sites. Value range: 1 to 4094"
        DEFVAL{ 1 }
        ::= { optixRtnIFPortGeneralAttribEntry 1 }

    -- 1.3.6.1.4.1.2011.2.25.4.40.3.10.20.1.2
    optixRtnIFPortRealLinkID OBJECT-TYPE
        SYNTAX Unsigned32
        MAX-ACCESS read-only
        STATUS current
        DESCRIPTION
            "Indicates the received radio link ID. If the received link ID is the same as that at the local end, the received signal is valid; otherwise, the local end inserts the AIS signal to the downstream direction of the service and reports an alarm to the NMS, indicating that the link IDs do not match."
        ::= { optixRtnIFPortGeneralAttribEntry 2 }

    -- 1.3.6.1.4.1.2011.2.25.4.40.3.10.20.1.3
    optixRtnIFPort1588OHEnableStatus OBJECT-TYPE
        SYNTAX OPTIXRtnEnableStateType
        MAX-ACCESS read-write
        STATUS current
        DESCRIPTION
            "Indicates whether the IEEE-1588 timeslot is enabled. If the RTN equipment and other packet equipment adopt the clock tracing by the IEEE 1588 protocol, the parameter is set to enabled; otherwise, the parameter is set to disabled. Values: 0: disabled 1: enabled"
        DEFVAL{ 1 }
        ::= { optixRtnIFPortGeneralAttribEntry 3 }

    -- 1.3.6.1.4.1.2011.2.25.4.40.3.10.20.1.4
    optixRtnIFPortServiceType OBJECT-TYPE
        SYNTAX OPTIXRtnIFServiceType
        MAX-ACCESS read-write
        STATUS current
        DESCRIPTION
            "Indicates the IF service type. The values: 1: Hybrid (Native E1+ETH), indicating that the IF port carries hybrid services that integrate the Native E1 and Ethernet services. 2: Hybrid (Native STM-1+ETH), indicating that the IF port carries hybrid services that integrate the Native STM-1 and Ethernet services. 3: SDH, indicating that the IF port carries SDH services."
        DEFVAL{ 1 }
        ::= { optixRtnIFPortGeneralAttribEntry 4 }

    -- 1.3.6.1.4.1.2011.2.25.4.40.3.10.20.1.6
    optixRtnIFPortBipOverThreshold OBJECT-TYPE
        SYNTAX Unsigned32
        MAX-ACCESS read-write
        STATUS current
        DESCRIPTION
            "Indicates the threshold of error codes that trigger signal failures on an IF port."
        ::= { optixRtnIFPortGeneralAttribEntry 6 }

    -- 1.3.6.1.4.1.2011.2.25.4.40.3.10.20.1.7
    optixRtnIFPortBipSDThreshold OBJECT-TYPE
        SYNTAX Unsigned32
        MAX-ACCESS read-write
        STATUS current
        DESCRIPTION
            "Indicates the threshold of error codes that trigger signal degradations on an IF port."
        ::= { optixRtnIFPortGeneralAttribEntry 7 }

    -- 1.3.6.1.4.1.2011.2.25.4.40.3.10.20.1.8
    optixRtnIFPortRunMode OBJECT-TYPE
        SYNTAX OPTIXRtnRunModeType
        MAX-ACCESS read-write
        STATUS current
        DESCRIPTION
            "Describes the running mode supported by an IF board. Values: 0: IS2 1: IS3 2: ACCP 3: NONACCP 4:IS6 5:SHACCP 6:IS6-PLUS 7:eband-common 8:eband-enhanced 9:IS8 12:eband-light 13:IS8-PLUS 15:LH-ACCP-PLUS"
        DEFVAL{ 1 }
        ::= { optixRtnIFPortGeneralAttribEntry 8 }

    -- 1.3.6.1.4.1.2011.2.25.4.40.3.10.20.1.9
    optixRtnIFPortMuxLoopMode OBJECT-TYPE
        SYNTAX OPTIXRtnIFLoopMode
        MAX-ACCESS read-write
        STATUS current
        DESCRIPTION
            "Indicates a loopback at a multiplex port.it has three mode type : noloop and inloop,outloop"
        ::= { optixRtnIFPortGeneralAttribEntry 9 }

    -- 1.3.6.1.4.1.2011.2.25.4.40.3.10.20.1.10
    optixRtnMwPortAlmPerEn OBJECT-TYPE
        SYNTAX OPTIXRtnEnableStateType
        MAX-ACCESS read-write
        STATUS current
        DESCRIPTION
            "Indicates whether an MW port's alarm and performance is enabled to report. Values: 0: disabled 1: enabled"
        DEFVAL{ 1 }
        ::= { optixRtnIFPortGeneralAttribEntry 10 }

    -- 1.3.6.1.4.1.2011.2.25.4.40.3.10.21
    optixRtnIFPortBandWidthTable OBJECT-TYPE
        SYNTAX SEQUENCE OF OptixRtnIFPortBandWidthEntry
        MAX-ACCESS not-accessible
        STATUS current
        DESCRIPTION
            "Describes BandWidth of an IF board"
        ::= { optixISBoardAttr 21 }

    -- 1.3.6.1.4.1.2011.2.25.4.40.3.10.21.1
    optixRtnIFPortBandWidthEntry OBJECT-TYPE
        SYNTAX OptixRtnIFPortBandWidthEntry
        MAX-ACCESS not-accessible
        STATUS current
        DESCRIPTION
            "Indicates the management entry for the BandWidth of an IF port."
        INDEX{ optixRtnBoardID,optixRtnSubCardID,optixRtnPortID }
        ::= { optixRtnIFPortBandWidthTable 1 }

    OptixRtnIFPortBandWidthEntry ::=
        SEQUENCE {
            optixRtnIFPortBandWidth
                OPTIXRtnBandWidthType
        }

    -- 1.3.6.1.4.1.2011.2.25.4.40.3.10.21.1.1
    optixRtnIFPortBandWidth OBJECT-TYPE
        SYNTAX OPTIXRtnBandWidthType
        MAX-ACCESS read-write
        STATUS current
        DESCRIPTION
            "Indicates the bandwidth. This parameter varies with the equipment version. Values: 1: 3.5M 2: 7.0M 3: 14M 4: 28M 5: 40M 6: 56M 7: FCC30M 8: FCC40M 9: FCC50M  10: 250M 11: 500M 12: 750M 16: 62.5M 17: 125M 18: 1000M 22: 200M 23: 112M 24: FCC10M 25: FCC20M 26: 1500M 27: 2000M 28: FCC60M"
        ::= { optixRtnIFPortBandWidthEntry 1 }

    -- 1.3.6.1.4.1.2011.2.25.4.40.3.10.30
    optixRtnIFPortAdvanceAttribTable OBJECT-TYPE
        SYNTAX SEQUENCE OF OptixRtnIFPortAdvanceAttribEntry
        MAX-ACCESS not-accessible
        STATUS current
        DESCRIPTION
            "Describes general attributes of an IF board, including whether error frame discarding is enabled."
        ::= { optixISBoardAttr 30 }

    -- 1.3.6.1.4.1.2011.2.25.4.40.3.10.30.1
    optixRtnIFPortAdvanceAttribEntry OBJECT-TYPE
        SYNTAX OptixRtnIFPortAdvanceAttribEntry
        MAX-ACCESS not-accessible
        STATUS current
        DESCRIPTION
            "Indicates management entry for advanced attributes of an IF port."
        INDEX{ optixRtnBoardID,optixRtnSubCardID,optixRtnPortID }
        ::= { optixRtnIFPortAdvanceAttribTable 1 }

    OptixRtnIFPortAdvanceAttribEntry ::=
        SEQUENCE {
            optixRtnIFPortErrorFrameDiscardStatus
                OPTIXRtnEnableStateType,
            optixRtnIFPortEthL2CompressEnableStatus
                OPTIXRtnEnableStateType,
            optixRtnIFPortEthL3CompressEnableStatus
                OPTIXRtnEnableStateType
        }

    -- 1.3.6.1.4.1.2011.2.25.4.40.3.10.30.1.1
    optixRtnIFPortErrorFrameDiscardStatus OBJECT-TYPE
        SYNTAX OPTIXRtnEnableStateType
        MAX-ACCESS read-write
        STATUS current
        DESCRIPTION
            "Indicates whether error frame discarding is enabled or not.'enabled' indicates that the Ethernet packet is discarded if error frames are found. 'disable' indicates the Ethernet packet remains when error frames are found. Because E1 services are monitored by bit error rate, it is recommended to disable error frame discarding. Set this parameter to the default value for other services. Values: 0: disabled 1: enabled"
        DEFVAL{ 1 }
        ::= { optixRtnIFPortAdvanceAttribEntry 1 }

    -- 1.3.6.1.4.1.2011.2.25.4.40.3.10.30.1.2
    optixRtnIFPortEthL2CompressEnableStatus OBJECT-TYPE
        SYNTAX OPTIXRtnEnableStateType
        MAX-ACCESS read-write
        STATUS current
        DESCRIPTION
            "Indicates whether to compress the MAC address header. Compressing the packet header can save bandwidth to transmit more services, but requires a license. Values: 0: disabled 1: enabled"
        DEFVAL{ 0 }
        ::= { optixRtnIFPortAdvanceAttribEntry 2 }

    -- 1.3.6.1.4.1.2011.2.25.4.40.3.10.30.1.3
    optixRtnIFPortEthL3CompressEnableStatus OBJECT-TYPE
        SYNTAX OPTIXRtnEnableStateType
        MAX-ACCESS read-write
        STATUS current
        DESCRIPTION
            "Indicates whether to compress the IP address header. Compressing the packet header can save bandwidth to transmit more services, but requires a license. Values: 0: disabled 1: enabled"
        DEFVAL{ 0 }
        ::= { optixRtnIFPortAdvanceAttribEntry 3 }

    -- 1.3.6.1.4.1.2011.2.25.4.40.3.10.40
    optixRtnIFPortAMParameterTable OBJECT-TYPE
        SYNTAX SEQUENCE OF OptixRtnIFPortAMParameterEntry
        MAX-ACCESS not-accessible
        STATUS current
        DESCRIPTION
            "Describes AM parameters of an IF board, including the AM status."
        ::= { optixISBoardAttr 40 }

    -- 1.3.6.1.4.1.2011.2.25.4.40.3.10.40.1
    optixRtnIFPortAMParameterEntry OBJECT-TYPE
        SYNTAX OptixRtnIFPortAMParameterEntry
        MAX-ACCESS not-accessible
        STATUS current
        DESCRIPTION
            "Indicates the management entry for the AM parameters of an IF port."
        INDEX{ optixRtnBoardID,optixRtnSubCardID,optixRtnPortID }
        ::= { optixRtnIFPortAMParameterTable 1 }

    OptixRtnIFPortAMParameterEntry ::=
        SEQUENCE {
            optixRtnIFPortAMEnableStatus
                OPTIXRtnEnableStateType,
            optixRtnIFPortAMBottomMod
                OPTIXRtnModulateModeType,
            optixRtnIFPortAMPeakMod
                OPTIXRtnModulateModeType,
            optixRtnIFPortAMManualMod
                OPTIXRtnModulateModeType,
            optixRtnIFPortE1PriorStatus
                OPTIXRtnEnableStateType
        }

    -- 1.3.6.1.4.1.2011.2.25.4.40.3.10.40.1.2
    optixRtnIFPortAMEnableStatus OBJECT-TYPE
        SYNTAX OPTIXRtnEnableStateType
        MAX-ACCESS read-write
        STATUS current
        DESCRIPTION
            "Indicates whether an IF port is enabled with AM. When the parameter is set to enabled, the radio link uses the corresponding modulation scheme according to the channel conditions. When the parameter is set to disabled, the radio link uses only a specified modulation scheme. In this case, you need to select Manually Specified Modulation Mode. Values: 0: disabled 1: enabled"
        DEFVAL{ 0 }
        ::= { optixRtnIFPortAMParameterEntry 2 }

    -- 1.3.6.1.4.1.2011.2.25.4.40.3.10.40.1.3
    optixRtnIFPortAMBottomMod OBJECT-TYPE
        SYNTAX OPTIXRtnModulateModeType
        MAX-ACCESS read-write
        STATUS current
        DESCRIPTION
            "Indicates the lowest-order modulation scheme that the AM function supports.
Values:
310: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; -1: NULL;
320: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 20: 4096QAM; -1: NULL;
360: 1: QPSK; 2: 16QAM; 3: 32QAM; -1: NULL;
380: 1: QPSK; 2: 16QAM; 3: 32QAM; 4: 64QAM; 9: QPSKSTRONG; 10: 16QAMSTRONG; 14:QPSKStrong250M; 15: QPSKStrong500M; 16:QPSKStrong750M; 17 QPSKStrong62P5M; 18: QPSKStrong125M; -1: NULL;
380A: 1: QPSK; 2: 16QAM; 3: 32QAM; 4: 64QAM; 5: 128QAM; 6: 256QAM; 7: 512QAM; 22:modeBPSK250M; 23:modeBPSK500M; 24:modeBPSK750M; 25:modeBPSK1000M; 29:modeBPSK62P5M; 30:modeBPSK125M; 31:mode8PSK; -1: NULL;
380AX: 1: QPSK; 2: 16QAM; 3: 32QAM; 4: 64QAM; 5: 128QAM; 6: 256QAM; 7: 512QAM; 8: 1024QAM; 10: 16QAMSTRONG; 22:modeBPSK250M; 23:modeBPSK500M; 24:modeBPSK750M; 25:modeBPSK1000M; 26:modeBPSK1500M; 27:modeBPSK2000M; 29:modeBPSK62P5M; 30:modeBPSK125M; 31:mode8PSK; -1: NULL;
380H: 1: QPSK; 2: 16QAM; 3: 32QAM; 4: 64QAM; 5: 128QAM; 6: 256QAM; 10: 16QAMSTRONG; 22:modeBPSK250M; 23:modeBPSK500M; 24:modeBPSK750M; 25:modeBPSK1000M; 26:modeBPSK1500M; 27:modeBPSK2000M; -1: NULL;
380HN: 1: QPSK; 2: 16QAM; 3: 32QAM; 4: 64QAM; 5: 128QAM; 6: 256QAM; 7: 512QAM; 8: 1024QAM; 22:modeBPSK250M; 23:modeBPSK500M; 24:modeBPSK750M; 25:modeBPSK1000M; 26:modeBPSK1500M; 27:modeBPSK2000M; 29:modeBPSK62P5M; 30:modeBPSK125M; 31:mode8PSK; -1: NULL;
3202F: 1: QPSK; 2: 16QAM; 3: 32QAM; 4: 64QAM; 5: 128QAM; 6: 256QAM; 7: 512QAM; 8: 1024QAM; 9: QPSKSTRONG; 11: 512QAMLIGHT; 12: 1024QAMLIGHT; 13: 2048QAM; 20: 4096QAM; 32:mode8192QAM; 33:mode16384QAM; -1: NULL;
900: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 20: 4096QAM; 28: 2048QAMLIGHT; 32:mode8192QAM; -1: NULL."
        ::= { optixRtnIFPortAMParameterEntry 3 }

    -- 1.3.6.1.4.1.2011.2.25.4.40.3.10.40.1.4
    optixRtnIFPortAMPeakMod OBJECT-TYPE
        SYNTAX OPTIXRtnModulateModeType
        MAX-ACCESS read-write
        STATUS current
        DESCRIPTION
            "Indicates the highest-order modulation scheme that the AM function supports.
Values:
310: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; -1: NULL;
320: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 20: 4096QAM; -1: NULL;
360: 1: QPSK; 2: 16QAM; 3: 32QAM; -1: NULL;
380: 1: QPSK; 2: 16QAM; 3: 32QAM; 4: 64QAM; 9: QPSKSTRONG; 10: 16QAMSTRONG; 14:QPSKStrong250M; 15: QPSKStrong500M; 16:QPSKStrong750M; 17 QPSKStrong62P5M; 18: QPSKStrong125M; -1: NULL;
380A: 1: QPSK; 2: 16QAM; 3: 32QAM; 4: 64QAM; 5: 128QAM; 6: 256QAM; 7: 512QAM; 22:modeBPSK250M; 23:modeBPSK500M; 24:modeBPSK750M; 25:modeBPSK1000M; 29:modeBPSK62P5M; 30:modeBPSK125M; 31:mode8PSK; -1: NULL;
380AX: 1: QPSK; 2: 16QAM; 3: 32QAM; 4: 64QAM; 5: 128QAM; 6: 256QAM; 7: 512QAM; 8: 1024QAM; 10: 16QAMSTRONG; 22:modeBPSK250M; 23:modeBPSK500M; 24:modeBPSK750M; 25:modeBPSK1000M; 26:modeBPSK1500M; 27:modeBPSK2000M; 29:modeBPSK62P5M; 30:modeBPSK125M; 31:mode8PSK; -1: NULL;
380H: 1: QPSK; 2: 16QAM; 3: 32QAM; 4: 64QAM; 5: 128QAM; 6: 256QAM; 10: 16QAMSTRONG; 22:modeBPSK250M; 23:modeBPSK500M; 24:modeBPSK750M; 25:modeBPSK1000M; 26:modeBPSK1500M; 27:modeBPSK2000M; -1: NULL;
380HN: 1: QPSK; 2: 16QAM; 3: 32QAM; 4: 64QAM; 5: 128QAM; 6: 256QAM; 7: 512QAM; 8: 1024QAM; 22:modeBPSK250M; 23:modeBPSK500M; 24:modeBPSK750M; 25:modeBPSK1000M; 26:modeBPSK1500M; 27:modeBPSK2000M; 29:modeBPSK62P5M; 30:modeBPSK125M; 31:mode8PSK; -1: NULL;
3202F: 1: QPSK; 2: 16QAM; 3: 32QAM; 4: 64QAM; 5: 128QAM; 6: 256QAM; 7: 512QAM; 8: 1024QAM; 9: QPSKSTRONG; 11: 512QAMLIGHT; 12: 1024QAMLIGHT; 13: 2048QAM; 20: 4096QAM; 32:mode8192QAM; 33:mode16384QAM; -1: NULL;
900: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 20: 4096QAM; 28: 2048QAMLIGHT; 32:mode8192QAM; -1: NULL."
        ::= { optixRtnIFPortAMParameterEntry 4 }

    -- 1.3.6.1.4.1.2011.2.25.4.40.3.10.40.1.5
    optixRtnIFPortAMManualMod OBJECT-TYPE
        SYNTAX OPTIXRtnModulateModeType
        MAX-ACCESS read-write
        STATUS current
        DESCRIPTION
            "Indicates the manually specified modulation scheme.
Values:
310: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; -1: NULL;
320: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 20: 4096QAM; -1: NULL;
360: 1: QPSK; 2: 16QAM; 3: 32QAM; -1: NULL;
380: 1: QPSK; 2: 16QAM; 3: 32QAM; 4: 64QAM; 9: QPSKSTRONG; 10: 16QAMSTRONG; 14:QPSKStrong250M; 15: QPSKStrong500M; 16:QPSKStrong750M; 17 QPSKStrong62P5M; 18: QPSKStrong125M; -1: NULL;
380A: 1: QPSK; 2: 16QAM; 3: 32QAM; 4: 64QAM; 5: 128QAM; 6: 256QAM; 7: 512QAM; 22:modeBPSK250M; 23:modeBPSK500M; 24:modeBPSK750M; 25:modeBPSK1000M; 29:modeBPSK62P5M; 30:modeBPSK125M; 31:mode8PSK; -1: NULL;
380AX: 1: QPSK; 2: 16QAM; 3: 32QAM; 4: 64QAM; 5: 128QAM; 6: 256QAM; 7: 512QAM; 8: 1024QAM; 21:modeBPSK; 22:modeBPSK250M; 23:modeBPSK500M; 24:modeBPSK750M; 25:modeBPSK1000M; 26:modeBPSK1500M; 27:modeBPSK2000M; 29:modeBPSK62P5M; 30:modeBPSK125M; 31:mode8PSK; -1: NULL;
380H: 1: QPSK; 2: 16QAM; 3: 32QAM; 4: 64QAM; 5: 128QAM; 6: 256QAM; 10: 16QAMSTRONG; 22:modeBPSK250M; 23:modeBPSK500M; 24:modeBPSK750M; 25:modeBPSK1000M; 26:modeBPSK1500M; 27:modeBPSK2000M; -1: NULL;
380HN: 1: QPSK; 2: 16QAM; 3: 32QAM; 4: 64QAM; 5: 128QAM; 6: 256QAM; 7: 512QAM; 8: 1024QAM; 22:modeBPSK250M; 23:modeBPSK500M; 24:modeBPSK750M; 25:modeBPSK1000M; 26:modeBPSK1500M; 27:modeBPSK2000M; 29:modeBPSK62P5M; 30:modeBPSK125M; 31:mode8PSK; -1: NULL;
3202F: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 20: 4096QAM; 32:mode8192QAM; 33:mode16384QAM; -1: NULL;
900: 1: QPSK; 2: 16QAM; 3: 32QAM; 4: 64QAM; 5: 128QAM; 6: 256QAM; 7: 512QAM; 8: 1024QAM; 9: QPSKSTRONG; 11: 512QAMLIGHT; 12: 1024QAMLIGHT; 13: 2048QAM; 20: 4096QAM; 28: 2048QAMLIGHT; 32:mode8192QAM; -1: NULL."
        ::= { optixRtnIFPortAMParameterEntry 5 }

    -- 1.3.6.1.4.1.2011.2.25.4.40.3.10.40.1.6
    optixRtnIFPortE1PriorStatus OBJECT-TYPE
        SYNTAX OPTIXRtnEnableStateType
        MAX-ACCESS read-write
        STATUS current
        DESCRIPTION
            "Indicates whether the E1 Priority is enabled. When the parameter is set to enabled, the NE processes E1 services based on the preset priority, that is, transmitting or discarding the service if channels experience fading. Values: 0: disabled 1: enabled"
        ::= { optixRtnIFPortAMParameterEntry 6 }

    -- 1.3.6.1.4.1.2011.2.25.4.40.3.10.41
    optixRtnIFPortAcmSymmetricTable OBJECT-TYPE
	SYNTAX SEQUENCE OF OptixRtnIFPortAcmSymmetricEntry
	MAX-ACCESS not-accessible
	STATUS current
	DESCRIPTION
	    "Indicates the symmetric or non symmetric mode of the acm."
	::= { optixISBoardAttr 41 }

    -- 1.3.6.1.4.1.2011.2.25.4.40.3.10.41.1
    optixRtnIFPortAcmSymmetricEntry OBJECT-TYPE
    	SYNTAX OptixRtnIFPortAcmSymmetricEntry
	MAX-ACCESS not-accessible
	STATUS current
	DESCRIPTION
	    "Indicates the symmetric or non symmetric mode of the acm."
	INDEX{ optixRtnBoardID,optixRtnSubCardID,optixRtnPortID }
	::= { optixRtnIFPortAcmSymmetricTable 1 }

    OptixRtnIFPortAcmSymmetricEntry ::=
        SEQUENCE { 
	    optixRtnIFPortAcmSymmetricValue
		Unsigned32 
		}
    -- 1.3.6.1.4.1.2011.2.25.4.40.3.10.41.1.4
    optixRtnIFPortAcmSymmetricValue OBJECT-TYPE
        SYNTAX Unsigned32 
	{
	     symmetric(0),
	     unsymmetric(1)
	}
	MAX-ACCESS read-write
	STATUS current
	DESCRIPTION
	    "The value of acm mode."
	::= { optixRtnIFPortAcmSymmetricEntry 4 } 

    -- 1.3.6.1.4.1.2011.2.25.4.40.3.10.42
    optixRtnIFPortRadioIfModeTable OBJECT-TYPE
        SYNTAX SEQUENCE OF OptixRtnIFPortRadioIfModeEntry
	MAX-ACCESS not-accessible
	STATUS current
	DESCRIPTION
	    "Describes AM parameters of an IF board, including the AM status."
	::= { optixISBoardAttr 42 }

    -- 1.3.6.1.4.1.2011.2.25.4.40.3.10.42.1
    optixRtnIFPortRadioIfModeEntry OBJECT-TYPE
        SYNTAX OptixRtnIFPortRadioIfModeEntry
	MAX-ACCESS not-accessible
	STATUS current
	DESCRIPTION
	    "Indicates the management entry for the AM parameters of an IF port."
	INDEX{ optixRtnBoardID,optixRtnSubCardID,optixRtnPortID }
	::= { optixRtnIFPortRadioIfModeTable 1 }

    OptixRtnIFPortRadioIfModeEntry ::=
	SEQUENCE { 
	optixRtnIFPortRadioAllIfMode
	OCTET STRING,
	optixRtnIFPortRadioIfMode
	Unsigned32
	}

    -- 1.3.6.1.4.1.2011.2.25.4.40.3.10.42.1.4
    optixRtnIFPortRadioAllIfMode OBJECT-TYPE
	SYNTAX OCTET STRING (SIZE(0..512))
	MAX-ACCESS read-only
	STATUS current
	DESCRIPTION
	    "Indicates the channel spacing. This parameter varies with the equipment version. Values: 1: 3.5M 2: 7.0M 3: 14M 4: 28M 5: 40M 6: 56M 7: FCC30M 8: FCC40M 9: FCC50M 23: 112M 24: FCC10M 25: FCC20M"
	::= { optixRtnIFPortRadioIfModeEntry 4 }

    -- 1.3.6.1.4.1.2011.2.25.4.40.3.10.42.1.5
    optixRtnIFPortRadioIfMode OBJECT-TYPE
	SYNTAX Unsigned32
	MAX-ACCESS read-write
	STATUS current
	DESCRIPTION
	    "Indicates whether an IF port is enabled with AM. When the parameter is set to enabled, the radio link uses the corresponding modulation scheme according to the channel conditions. When the parameter is set to disabled, the radio link uses only a specified modulation scheme. In this case, you need to select Manually Specified Modulation Mode. Values: 0: disabled 1: enabled"
	::= { optixRtnIFPortRadioIfModeEntry 5 }
	
    -- 1.3.6.1.4.1.2011.2.25.4.40.3.10.50
    optixRtnIFPortCurrCapacityTable OBJECT-TYPE
        SYNTAX SEQUENCE OF OptixRtnIFPortCurrCapacityEntry
        MAX-ACCESS not-accessible
        STATUS current
        DESCRIPTION
            "Describes the service capacities supported by an IF board in the current modulation mode."
        ::= { optixISBoardAttr 50 }

    -- 1.3.6.1.4.1.2011.2.25.4.40.3.10.50.1
    optixRtnIFPortCurrCapacityEntry OBJECT-TYPE
        SYNTAX OptixRtnIFPortCurrCapacityEntry
        MAX-ACCESS not-accessible
        STATUS current
        DESCRIPTION
            "Indicates the current service capacity entry for an IF port."
        INDEX{ optixRtnBoardID,optixRtnSubCardID,optixRtnPortID }
        ::= { optixRtnIFPortCurrCapacityTable 1 }

    OptixRtnIFPortCurrCapacityEntry ::=
        SEQUENCE {
            optixRtnIFPortCurrTxMode
                OPTIXRtnModulateModeType,
            optixRtnIFPortCurrRxMode
                OPTIXRtnModulateModeType,
            optixRtnIFPortAMGuaranteeRate
                Unsigned32,
            optixRtnIFPortAMPeakRate
                Unsigned32,
            optixRtnIFPortAMCurrSendRate
                Unsigned32,
            optixRtnIFPortAMCurrRxRate
                Unsigned32,
            optixRtnIFPortCurrE1Capacity
                Unsigned32,
            optixRtnIFPortMaxE1Capacity
                Unsigned32,
            optixRtnIFPortAMGuaranteeE1Num
                Unsigned32,
            optixRtnIFPortCurrSTM1Capacity
                Unsigned32,
            optixRtnIFPortMaxSTM1Capacity
                Unsigned32,
            optixRtnIFPortAMPeakE1Num
                Unsigned32,
            optixRtnIFPortAMEveryModeE1Num
                OCTET STRING
        }

    -- 1.3.6.1.4.1.2011.2.25.4.40.3.10.50.1.1
    optixRtnIFPortCurrTxMode OBJECT-TYPE
        SYNTAX OPTIXRtnModulateModeType
        MAX-ACCESS read-only
        STATUS current
        DESCRIPTION
            "Indicates the current modulation mode of the transmit end.Values: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 14:QPSKStrong250M; 15: QPSKStrong500M; 16:QPSKStrong750M; 17 QPSKStrong62P5M; 18: QPSKStrong125M; 20: 4096QAM;
21:modeBPSK; 22:modeBPSK250M; 23:modeBPSK500M; 24:modeBPSK750M; 25:modeBPSK1000M; 26:modeBPSK1500M; 27:modeBPSK2000M; 28: 2048QAMLIGHT; 29:modeBPSK62P5M; 30:modeBPSK125M; 31:mode8PSK; 32:mode8192QAM; 33:mode16384QAM; -1: NULL."
        ::= { optixRtnIFPortCurrCapacityEntry 1 }

    -- 1.3.6.1.4.1.2011.2.25.4.40.3.10.50.1.2
    optixRtnIFPortCurrRxMode OBJECT-TYPE
        SYNTAX OPTIXRtnModulateModeType
        MAX-ACCESS read-only
        STATUS current
        DESCRIPTION
            "Indicates the current modulation mode of the receive end.Values: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 14: QPSKStrong250M; 15: QPSKStrong500M; 16: QPSKStrong750M; 17: QPSKStrong62P5M; 18: QPSKStrong125M; 20: 4096QAM;
21: modeBPSK; 22: modeBPSK250M; 23: modeBPSK500M; 24: modeBPSK750M; 25: modeBPSK1000M; 26: modeBPSK1500M; 27: modeBPSK2000M; 28: 2048QAMLIGHT; 29: modeBPSK62P5M; 30: modeBPSK125M; 31: mode8PSK; 32: mode8192QAM; 33: mode16384QAM; -1: NULL; 0: modeClear."
        ::= { optixRtnIFPortCurrCapacityEntry 2 }

    -- 1.3.6.1.4.1.2011.2.25.4.40.3.10.50.1.3
    optixRtnIFPortAMGuaranteeRate OBJECT-TYPE
        SYNTAX Unsigned32
        MAX-ACCESS read-only
        STATUS current
        DESCRIPTION
            "Indicates the guaranteed AM service capacity. Unit: Mbit/s"
        ::= { optixRtnIFPortCurrCapacityEntry 3 }

    -- 1.3.6.1.4.1.2011.2.25.4.40.3.10.50.1.4
    optixRtnIFPortAMPeakRate OBJECT-TYPE
        SYNTAX Unsigned32
        MAX-ACCESS read-only
        STATUS current
        DESCRIPTION
            "Indicates the full AM service capacity. Unit: Mbit/s"
        ::= { optixRtnIFPortCurrCapacityEntry 4 }

    -- 1.3.6.1.4.1.2011.2.25.4.40.3.10.50.1.5
    optixRtnIFPortAMCurrSendRate OBJECT-TYPE
        SYNTAX Unsigned32
        MAX-ACCESS read-only
        STATUS current
        DESCRIPTION
            "Indicates the current transmit service capacity when the AM function is enabled. Unit: Mbit/s"
        ::= { optixRtnIFPortCurrCapacityEntry 5 }

    -- 1.3.6.1.4.1.2011.2.25.4.40.3.10.50.1.6
    optixRtnIFPortAMCurrRxRate OBJECT-TYPE
        SYNTAX Unsigned32
        MAX-ACCESS read-only
        STATUS current
        DESCRIPTION
            "Indicates the current receive service capacity when the AM function is enabled. Unit: Mbit/s"
        ::= { optixRtnIFPortCurrCapacityEntry 6 }

    -- 1.3.6.1.4.1.2011.2.25.4.40.3.10.50.1.7
    optixRtnIFPortCurrE1Capacity OBJECT-TYPE
        SYNTAX Unsigned32
        MAX-ACCESS read-write
        STATUS current
        DESCRIPTION
            "Indicates the number of E1s currently supported in hybrid mode."
        ::= { optixRtnIFPortCurrCapacityEntry 7 }

    -- 1.3.6.1.4.1.2011.2.25.4.40.3.10.50.1.8
    optixRtnIFPortMaxE1Capacity OBJECT-TYPE
        SYNTAX Unsigned32
        MAX-ACCESS read-only
        STATUS current
        DESCRIPTION
            "Indicates the maximum number of E1s currently supported in hybrid mode."
        ::= { optixRtnIFPortCurrCapacityEntry 8 }

    -- 1.3.6.1.4.1.2011.2.25.4.40.3.10.50.1.9
    optixRtnIFPortAMGuaranteeE1Num OBJECT-TYPE
        SYNTAX Unsigned32
        MAX-ACCESS read-write
        STATUS current
        DESCRIPTION
            "Indicates the number of E1s in guarantee capacity modulation mode when the E1 priority is enabled."
        ::= { optixRtnIFPortCurrCapacityEntry 9 }

    -- 1.3.6.1.4.1.2011.2.25.4.40.3.10.50.1.10
    optixRtnIFPortCurrSTM1Capacity OBJECT-TYPE
        SYNTAX Unsigned32
        MAX-ACCESS read-write
        STATUS current
        DESCRIPTION
            "Indicates the STM-1 capacity currently supported."
        ::= { optixRtnIFPortCurrCapacityEntry 10 }

    -- 1.3.6.1.4.1.2011.2.25.4.40.3.10.50.1.11
    optixRtnIFPortMaxSTM1Capacity OBJECT-TYPE
        SYNTAX Unsigned32
        MAX-ACCESS read-only
        STATUS current
        DESCRIPTION
            "Indicates the maximum STM-1 capacity."
        ::= { optixRtnIFPortCurrCapacityEntry 11 }

    -- 1.3.6.1.4.1.2011.2.25.4.40.3.10.50.1.14
    optixRtnIFPortAMPeakE1Num OBJECT-TYPE
        SYNTAX Unsigned32
        MAX-ACCESS read-write
        STATUS current
        DESCRIPTION
            "Indicates the number of E1s in peak capacity modulation mode when the E1 priority is enabled."
        ::= { optixRtnIFPortCurrCapacityEntry 14 }

    -- 1.3.6.1.4.1.2011.2.25.4.40.3.10.50.1.15
    optixRtnIFPortAMEveryModeE1Num OBJECT-TYPE
        SYNTAX OCTET STRING
        MAX-ACCESS read-write
        STATUS current
        DESCRIPTION
            "Indicates the number of E1s in each modulation mode when the E1 priority is enabled."
        ::= { optixRtnIFPortCurrCapacityEntry 15 }

    -- 1.3.6.1.4.1.2011.2.25.4.40.3.10.57
    optixRtnXPICAMBoostTable OBJECT-TYPE
        SYNTAX SEQUENCE OF OptixRtnXPICAMBoostEntry
        MAX-ACCESS not-accessible
        STATUS current
        DESCRIPTION
            "Describes configuration parameters for an IF XPIC AMBoost."
        ::= { optixISBoardAttr 57 }

    -- 1.3.6.1.4.1.2011.2.25.4.40.3.10.57.1
    optixRtnXPICAMBoostEntry OBJECT-TYPE
        SYNTAX OptixRtnXPICAMBoostEntry
        MAX-ACCESS not-accessible
        STATUS current
        DESCRIPTION
            "Indicates the parameter entry for an IF XPIC AMBoost."
        INDEX{ optixRtnXPICPGID }
        ::= { optixRtnXPICAMBoostTable 1 }

    OptixRtnXPICAMBoostEntry ::=
        SEQUENCE {
            optixRtnXPICAMBoostEn
                INTEGER
        }

    -- 1.3.6.1.4.1.2011.2.25.4.40.3.10.57.1.2
    optixRtnXPICAMBoostEn OBJECT-TYPE
        SYNTAX INTEGER
		{
            disable(0),
            enable(1)
        }
        MAX-ACCESS read-write
        STATUS current
        DESCRIPTION
            "Indicates the XPIC AMBoost enable."
        ::= { optixRtnXPICAMBoostEntry 2 }	

    -- 1.3.6.1.4.1.2011.2.25.4.40.3.10.61
    optixRtnIFPortAllModeCapacityE1NumTable OBJECT-TYPE
        SYNTAX SEQUENCE OF OptixRtnIFPortAllModeCapacityE1NumEntry
        MAX-ACCESS not-accessible
        STATUS current
        DESCRIPTION
            "Describes the service capacity supported by an IF board in each mode."
        ::= { optixISBoardAttr 61 }

    -- 1.3.6.1.4.1.2011.2.25.4.40.3.10.61.1
    optixRtnIFPortAllModeCapacityE1NumEntry OBJECT-TYPE
        SYNTAX OptixRtnIFPortAllModeCapacityE1NumEntry
        MAX-ACCESS not-accessible
        STATUS current
        DESCRIPTION
            "Indicates the query entry for service capacities of an IF port in each mode."
        INDEX{ optixRtnBoardID,optixRtnSubCardID,optixRtnPortID,optixRtnIFPortAcmBandWidth,optixRtnIFPortAcmModulationMode }
        ::= { optixRtnIFPortAllModeCapacityE1NumTable 1 }

    OptixRtnIFPortAllModeCapacityE1NumEntry ::=
        SEQUENCE {
            optixRtnIFPortAcmBandWidth
                Unsigned32,
            optixRtnIFPortAcmModulationMode
                OPTIXRtnModulateModeType,
            optixRtnIFPortAcmCapacity
                Unsigned32,
            optixRtnIFPortAcmMaxE1Num
                Unsigned32
        }

    -- 1.3.6.1.4.1.2011.2.25.4.40.3.10.61.1.1
    optixRtnIFPortAcmBandWidth OBJECT-TYPE
        SYNTAX Unsigned32
        {
            bw3P5M(1),
            bw7M(2),
            bw14M(3),
            bw28M(4),
            bw40M(5),
            bw56M(6),
            bwFCC30M(7),
            bwFCC40M(8),
            bwFCC50M(9),
            bw250M(10),
            bw500M(11),
            bw750M(12),
            bw62P5M(16),
            bw125M(17),
            bw112M(23),
            bwFCC10M(24),
            bwFCC20M(25),
            bwFCC60M(28),
	    bw80M(34)
        }
        MAX-ACCESS not-accessible
        STATUS current
        DESCRIPTION
            "Indicates the channel spacing."
        ::= { optixRtnIFPortAllModeCapacityE1NumEntry 1 }

    -- 1.3.6.1.4.1.2011.2.25.4.40.3.10.61.1.2
    optixRtnIFPortAcmModulationMode OBJECT-TYPE
        SYNTAX OPTIXRtnModulateModeType
        MAX-ACCESS not-accessible
        STATUS current
        DESCRIPTION
            "Indicates the port modulation mode.Values: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 14:QPSKStrong250M; 15: QPSKStrong500M; 16:QPSKStrong750M; 17 QPSKStrong62P5M; 18: QPSKStrong125M; 20: 4096QAM;
21:modeBPSK; 22:modeBPSK250M; 23:modeBPSK500M; 24:modeBPSK750M; 25:modeBPSK1000M; 26:modeBPSK1500M; 27:modeBPSK2000M; 28: 2048QAMLIGHT; 29:modeBPSK62P5M; 30:modeBPSK125M; 31:mode8PSK; 32:mode8192QAM; 33:mode16384QAM; -1: NULL."
        ::= { optixRtnIFPortAllModeCapacityE1NumEntry 2 }

    -- 1.3.6.1.4.1.2011.2.25.4.40.3.10.61.1.3
    optixRtnIFPortAcmCapacity OBJECT-TYPE
        SYNTAX Unsigned32
        MAX-ACCESS read-only
        STATUS current
        DESCRIPTION
            "Indicates the service capacity in a mode. Unit: M"
        ::= { optixRtnIFPortAllModeCapacityE1NumEntry 3 }

    -- 1.3.6.1.4.1.2011.2.25.4.40.3.10.61.1.4
    optixRtnIFPortAcmMaxE1Num OBJECT-TYPE
        SYNTAX Unsigned32
        MAX-ACCESS read-only
        STATUS current
        DESCRIPTION
            "Indicates the maximum number of E1s supported by a mode."
        ::= { optixRtnIFPortAllModeCapacityE1NumEntry 4 }

    -- 1.3.6.1.4.1.2011.2.25.4.40.3.10.62
    optixRtnIFPortAllModeCapacityExtTable OBJECT-TYPE
        SYNTAX SEQUENCE OF OptixRtnIFPortAllModeCapacityExtEntry
        MAX-ACCESS not-accessible
        STATUS current
        DESCRIPTION
            "Describes the service capacity supported by an IF board in each mode."
        ::= { optixISBoardAttr 62 }

    -- 1.3.6.1.4.1.2011.2.25.4.40.3.10.62.1
    optixRtnIFPortAllModeCapacityExtEntry OBJECT-TYPE
        SYNTAX OptixRtnIFPortAllModeCapacityExtEntry
        MAX-ACCESS not-accessible
        STATUS current
        DESCRIPTION
            "Indicates the query entry for service capacities of an IF port in each mode."
        INDEX{ optixRtnBoardID,optixRtnSubCardID,optixRtnPortID,optixRtnIFPortlist }
        ::= { optixRtnIFPortAllModeCapacityExtTable 1 }

    OptixRtnIFPortAllModeCapacityExtEntry ::=
        SEQUENCE {
            optixRtnIFPortAMCapacityExt
                OCTET STRING
        }

    -- 1.3.6.1.4.1.2011.2.25.4.40.3.10.62.1.5
    optixRtnIFPortAMCapacityExt OBJECT-TYPE
        SYNTAX OCTET STRING
        MAX-ACCESS read-only
        STATUS current
        DESCRIPTION
            "Indicates the service capacity in a mode. Unit: M"
        ::= { optixRtnIFPortAllModeCapacityExtEntry 5 }

    -- 1.3.6.1.4.1.2011.2.25.4.40.3.10.71
    optixRtnIFPortAllModeXpicCapacityE1NumTable OBJECT-TYPE
        SYNTAX SEQUENCE OF OptixRtnIFPortAllModeXpicCapacityE1NumEntry
        MAX-ACCESS not-accessible
        STATUS current
        DESCRIPTION
            "Describes the service capacity supported by an IF board in each mode when the XPIC function is enabled."
        ::= { optixISBoardAttr 71 }

    -- 1.3.6.1.4.1.2011.2.25.4.40.3.10.71.1
    optixRtnIFPortAllModeXpicCapacityE1NumEntry OBJECT-TYPE
        SYNTAX OptixRtnIFPortAllModeXpicCapacityE1NumEntry
        MAX-ACCESS not-accessible
        STATUS current
        DESCRIPTION
            "Indicates the query entry for service capacities of an IF port in each mode when the XPIC function is enabled."
        INDEX{ optixRtnBoardID,optixRtnSubCardID,optixRtnPortID,optixRtnIFPortAcmBandWidth,optixRtnIFPortAcmModulationMode }
        ::= { optixRtnIFPortAllModeXpicCapacityE1NumTable 1 }

    OptixRtnIFPortAllModeXpicCapacityE1NumEntry ::=
        SEQUENCE {
            optixRtnIFPortAcmCapacityForXpic
                Unsigned32,
            optixRtnIFPortAcmMaxE1NumForXpic
                Unsigned32
        }

    -- 1.3.6.1.4.1.2011.2.25.4.40.3.10.71.1.1
    optixRtnIFPortAcmCapacityForXpic OBJECT-TYPE
        SYNTAX Unsigned32
        MAX-ACCESS read-only
        STATUS current
        DESCRIPTION
            "Indicates the service capacity supported by a mode when the XPIC function is enabled. Unit: M"
        ::= { optixRtnIFPortAllModeXpicCapacityE1NumEntry 1 }

    -- 1.3.6.1.4.1.2011.2.25.4.40.3.10.71.1.2
    optixRtnIFPortAcmMaxE1NumForXpic OBJECT-TYPE
        SYNTAX Unsigned32
        MAX-ACCESS read-only
        STATUS current
        DESCRIPTION
            "Indicates the maximum number of E1s supported by a mode when the XPIC function is enabled."
        ::= { optixRtnIFPortAllModeXpicCapacityE1NumEntry 2 }

    -- 1.3.6.1.4.1.2011.2.25.4.40.3.10.72
    optixRtnIFPortAllModeXpicCapacityExtTable OBJECT-TYPE
        SYNTAX SEQUENCE OF OptixRtnIFPortAllModeXpicCapacityExtEntry
        MAX-ACCESS not-accessible
        STATUS current
        DESCRIPTION
            "Describes the service capacity supported by an IF board in each mode when the XPIC function is enabled."
        ::= { optixISBoardAttr 72 }

    -- 1.3.6.1.4.1.2011.2.25.4.40.3.10.72.1
    optixRtnIFPortAllModeXpicCapacityExtEntry OBJECT-TYPE
        SYNTAX OptixRtnIFPortAllModeXpicCapacityExtEntry
        MAX-ACCESS not-accessible
        STATUS current
        DESCRIPTION
            "Indicates the query entry for service capacities of an IF port in each mode when the XPIC function is enabled."
        INDEX{ optixRtnBoardID,optixRtnSubCardID,optixRtnPortID }
        ::= { optixRtnIFPortAllModeXpicCapacityExtTable 1 }

    OptixRtnIFPortAllModeXpicCapacityExtEntry ::=
        SEQUENCE {
            optixRtnIFPortAmCapacityForXpicExt
                OCTET STRING
        }

    -- 1.3.6.1.4.1.2011.2.25.4.40.3.10.72.1.1
    optixRtnIFPortAmCapacityForXpicExt OBJECT-TYPE
        SYNTAX OCTET STRING
        MAX-ACCESS read-only
        STATUS current
        DESCRIPTION
            "Indicates the service capacity supported by a mode when the XPIC function is enabled. Unit: M"
        ::= { optixRtnIFPortAllModeXpicCapacityExtEntry 1 }

    -- 1.3.6.1.4.1.2011.2.25.4.40.3.10.73
    optixRtnIFPortXPICEnableTable OBJECT-TYPE
        SYNTAX SEQUENCE OF OptixRtnIFPortXPICEnableEntry
        MAX-ACCESS not-accessible
        STATUS current
        DESCRIPTION
            "Describes the XPIC status."
        ::= { optixISBoardAttr 73 }

    -- 1.3.6.1.4.1.2011.2.25.4.40.3.10.73.1
    optixRtnIFPortXPICEnableEntry OBJECT-TYPE
        SYNTAX OptixRtnIFPortXPICEnableEntry
        MAX-ACCESS not-accessible
        STATUS current
        DESCRIPTION
            "Indicates the XPIC status of an IF port."
        INDEX{ optixRtnBoardID,optixRtnSubCardID,optixRtnPortID }
        ::= { optixRtnIFPortXPICEnableTable 1 }

    OptixRtnIFPortXPICEnableEntry ::=
        SEQUENCE {

            optixRtnIFPortXPICEnableStatus
                OPTIXRtnEnableStateType
        }

    -- 1.3.6.1.4.1.2011.2.25.4.40.3.10.73.1.1
    optixRtnIFPortXPICEnableStatus OBJECT-TYPE
        SYNTAX OPTIXRtnEnableStateType
        MAX-ACCESS read-write
        STATUS current
        DESCRIPTION
            "Indicates whether an IF port is enabled with XPIC. Only the XPIC IF board supports this parameter. Values: 0: disabled 1: enabled"
        DEFVAL{ 0 }
        ::= { optixRtnIFPortXPICEnableEntry 1 }

    -- 1.3.6.1.4.1.2011.2.25.4.40.3.10.80
    optixRtnIFPortAMSwitchTable OBJECT-TYPE
        SYNTAX SEQUENCE OF OptixRtnIFPortAMSwitchEntry
        MAX-ACCESS not-accessible
        STATUS current
        DESCRIPTION
            "Describes the ACM switching function at an IF port."
        ::= { optixISBoardAttr 80 }

    -- 1.3.6.1.4.1.2011.2.25.4.40.3.10.80.1
    optixRtnIFPortAMSwitchEntry OBJECT-TYPE
        SYNTAX OptixRtnIFPortAMSwitchEntry
        MAX-ACCESS not-accessible
        STATUS current
        DESCRIPTION
            "Indicates the ACM switching management entry at an IF port."
        INDEX{ optixRtnBoardID,optixRtnSubCardID,optixRtnPortID }
        ::= { optixRtnIFPortAMSwitchTable 1 }

    OptixRtnIFPortAMSwitchEntry ::=
        SEQUENCE {
            optixRtnIFPortAMSwitchDir
                OPTIXRtnIFAcmDirType,
            optixRtnIFPortAMSwitchMod
                OPTIXRtnIFAcmModType
        }

    -- 1.3.6.1.4.1.2011.2.25.4.40.3.10.80.1.2
    optixRtnIFPortAMSwitchDir OBJECT-TYPE
        SYNTAX OPTIXRtnIFAcmDirType
        MAX-ACCESS read-write
        STATUS current
        DESCRIPTION
            "Indicates the ACM switching direction at an IF port.Values:tx(0),rx(1),bi(2)"
        DEFVAL{ 0 }
        ::= { optixRtnIFPortAMSwitchEntry 2 }

    -- 1.3.6.1.4.1.2011.2.25.4.40.3.10.80.1.3
    optixRtnIFPortAMSwitchMod OBJECT-TYPE
        SYNTAX OPTIXRtnIFAcmModType
        MAX-ACCESS read-write
        STATUS current
        DESCRIPTION
            "Indicates the ACM switching mode at an IF port.Values:modeClear(0),modeQPSK(1),mode16QAM(2),mode32QAM(3),mode64QAM(4),mode128QAM(5),mode256QAM(6),mode512QAM(7),mode1024QAM(8),modeQPSKSTRONG(9),mode16QAMSTRONG(10),
mode512QAMLIGHT(11),mode1024QAMLIGHT(12),mode2048QAM(13),modeQPSKStrong250M(14),modeQPSKStrong500M(15),modeQPSKStrong750M(16),modeQPSKStrong62P5M(17),modeQPSKStrong125M(18),
mode4096QAM(20)modeBPSK(21),modeBPSK250M(22),modeBPSK500M(23),modeBPSK750M(24),modeBPSK1000M(25),modeBPSK1500M(26),modeBPSK2000M(27),mode2048QAMLIGHT(28),modeBPSK62P5M(29),modeBPSK125M(30),
mode8PSK(31),mode8192QAM(32),modeNULL(255)"
        DEFVAL{ 0 }
        ::= { optixRtnIFPortAMSwitchEntry 3 }

    -- 1.3.6.1.4.1.2011.2.25.4.40.3.10.81
    optixRtnAntennaPolarTable OBJECT-TYPE
        SYNTAX SEQUENCE OF OptixRtnAntennaPolarEntry
        MAX-ACCESS not-accessible
        STATUS current
        DESCRIPTION
            "Indicates the polarization direction of an antenna"
        ::= { optixISBoardAttr 81 }

    -- 1.3.6.1.4.1.2011.2.25.4.40.3.10.81.1
    optixRtnAntennaPolarEntry OBJECT-TYPE
        SYNTAX OptixRtnAntennaPolarEntry
        MAX-ACCESS not-accessible
        STATUS current
        DESCRIPTION
            "Indicates the polarization direction of an antenna"
        INDEX{ optixRtnBoardID,optixRtnSubCardID,optixRtnPortID }
        ::= { optixRtnAntennaPolarTable 1 }

    OptixRtnAntennaPolarEntry ::=
        SEQUENCE {
            optixRtnAntennaPolarOrientation
                Unsigned32
        }

    -- 1.3.6.1.4.1.2011.2.25.4.40.3.10.81.1.1
    optixRtnAntennaPolarOrientation OBJECT-TYPE
        SYNTAX Unsigned32
        {
            horizontal(0),
            vertical(1),
            invalid(255)
        }
        MAX-ACCESS read-write
        STATUS current
        DESCRIPTION
            "Indicates the polarization direction.
Value: 0-H or 1-V
Default: 0"
        DEFVAL{ 0 }
        ::= { optixRtnAntennaPolarEntry 1 }

    -- 1.3.6.1.4.1.2011.2.25.4.40.3.10.82
    optixRtnFoAdjoinNeinfoTable OBJECT-TYPE
        SYNTAX SEQUENCE OF OptixRtnFoAdjoinNeinfoEntry
        MAX-ACCESS not-accessible
        STATUS current
        DESCRIPTION
            "Describes antenna polarization directions."
        ::= { optixISBoardAttr 82 }

    -- 1.3.6.1.4.1.2011.2.25.4.40.3.10.82.1
    optixRtnFoAdjoinNeinfoEntry OBJECT-TYPE
        SYNTAX OptixRtnFoAdjoinNeinfoEntry
        MAX-ACCESS not-accessible
        STATUS current
        DESCRIPTION
            "Indicates an antenna polarization direction entry."
        INDEX{ optixRtnBoardID,optixRtnSubCardID,optixRtnPortID }
        ::= { optixRtnFoAdjoinNeinfoTable 1 }

    OptixRtnFoAdjoinNeinfoEntry ::=
        SEQUENCE {
            optixRtnFoAdjoinNeighbourNeID
                Unsigned32,
            optixRtnFoAdjoinNeighbourNeName
                OCTET STRING,
            optixRtnFoAdjoinNeighbourNeBoardID
                Unsigned32,
            optixRtnFoAdjoinNeighbourNeBoardType
                OPTIXRtnBoardType,
            optixRtnFoAdjoinNeighbourNeSubCardID
                Unsigned32,
            optixRtnFoAdjoinNeighbourNePortID
                Unsigned32
        }

    -- 1.3.6.1.4.1.2011.2.25.4.40.3.10.82.1.1
    optixRtnFoAdjoinNeighbourNeID OBJECT-TYPE
        SYNTAX Unsigned32
        MAX-ACCESS read-only
        STATUS current
        DESCRIPTION
            "Indicates the ID of the adjacent NE in an XPIC/1+1/PLA group."
        ::= { optixRtnFoAdjoinNeinfoEntry 1 }

    -- 1.3.6.1.4.1.2011.2.25.4.40.3.10.82.1.2
    optixRtnFoAdjoinNeighbourNeName OBJECT-TYPE
        SYNTAX OCTET STRING
        MAX-ACCESS read-only
        STATUS current
        DESCRIPTION
            "Indicates the neighbor NE name in an XPIC/1+1/PLA group (64 characters)."
        ::= { optixRtnFoAdjoinNeinfoEntry 2 }

    -- 1.3.6.1.4.1.2011.2.25.4.40.3.10.82.1.3
    optixRtnFoAdjoinNeighbourNeBoardID OBJECT-TYPE
        SYNTAX Unsigned32
        MAX-ACCESS read-only
        STATUS current
        DESCRIPTION
            "Indicates the neighbor NE board ID in an XPIC/1+1/PLA group."
        ::= { optixRtnFoAdjoinNeinfoEntry 3 }

    -- 1.3.6.1.4.1.2011.2.25.4.40.3.10.82.1.4
    optixRtnFoAdjoinNeighbourNeBoardType OBJECT-TYPE
        SYNTAX OPTIXRtnBoardType
        MAX-ACCESS read-only
        STATUS current
        DESCRIPTION
            "Indicates the type of a logical board on the neighbor NE in an XPIC/1+1/PLA group.Values:  sxa3: 3372, d4d: 4146, dmc4b: 3416, dmc5a: 3415, mxxi4b: 4216, mxxi4: 4192, mxug4: 4125, mxuf4: 3344, mxxi5: 3549, mxui5: 3442, cshp: 3058"
        ::= { optixRtnFoAdjoinNeinfoEntry 4 }

    -- 1.3.6.1.4.1.2011.2.25.4.40.3.10.82.1.5
    optixRtnFoAdjoinNeighbourNeSubCardID OBJECT-TYPE
        SYNTAX Unsigned32
        MAX-ACCESS read-only
        STATUS current
        DESCRIPTION
            "Indicates the type of a subcard on the neighbor NE in an XPIC/1+1/PLA group."
        ::= { optixRtnFoAdjoinNeinfoEntry 5 }

    -- 1.3.6.1.4.1.2011.2.25.4.40.3.10.82.1.6
    optixRtnFoAdjoinNeighbourNePortID OBJECT-TYPE
        SYNTAX Unsigned32
        MAX-ACCESS read-only
        STATUS current
        DESCRIPTION
            "Indicates the ID of a port on the neighbor NE in an XPIC/1+1/PLA group."
        ::= { optixRtnFoAdjoinNeinfoEntry 6 }   

    -- 1.3.6.1.4.1.2011.2.25.4.40.3.10.85
    optixRtnIFPort2MWAYTable OBJECT-TYPE
        SYNTAX SEQUENCE OF OptixRtnIFPort2MWAYEntry
        MAX-ACCESS not-accessible
        STATUS current
        DESCRIPTION
            "Describes the status of IFPort 2MWAY."
        ::= { optixISBoardAttr 85 }

    -- 1.3.6.1.4.1.2011.2.25.4.40.3.10.85.1
    optixRtnIFPort2MWAYEntry OBJECT-TYPE
        SYNTAX OptixRtnIFPort2MWAYEntry
        MAX-ACCESS not-accessible
        STATUS current
        DESCRIPTION
            "Describes the status of IFPort 2MWAY."
        INDEX{ optixRtnBoardID,optixRtnSubCardID,optixRtnPortID }
        ::= { optixRtnIFPort2MWAYTable 1 }

    OptixRtnIFPort2MWAYEntry ::=
        SEQUENCE {
            optixRtnIFPortCfgStgBID
                Unsigned32,
            optixRtnIFPortCfgStgSub
                Unsigned32,
	    optixRtnIFPortCfgStgPid
                Unsigned32,
            optixRtnIFPortCfgStgEnable
                OPTIXRtnEnableStateType
        }

    -- 1.3.6.1.4.1.2011.2.25.4.40.3.10.85.1.1
    optixRtnIFPortCfgStgBID OBJECT-TYPE
        SYNTAX Unsigned32
        MAX-ACCESS read-write
        STATUS current
        DESCRIPTION
            "Indicates the BoardID of the clock."
        ::= { optixRtnIFPort2MWAYEntry 1 }

    -- 1.3.6.1.4.1.2011.2.25.4.40.3.10.85.1.2
    optixRtnIFPortCfgStgSub OBJECT-TYPE
        SYNTAX Unsigned32
        MAX-ACCESS read-write
        STATUS current
        DESCRIPTION
            "Indicates the SubCardID of the clock."
        ::= { optixRtnIFPort2MWAYEntry 2 }

    -- 1.3.6.1.4.1.2011.2.25.4.40.3.10.85.1.3
    optixRtnIFPortCfgStgPid OBJECT-TYPE
        SYNTAX Unsigned32
        MAX-ACCESS read-write
        STATUS current
        DESCRIPTION
            "Indicates the PortID of the clock."
        ::= { optixRtnIFPort2MWAYEntry 3 }
	
    -- 1.3.6.1.4.1.2011.2.25.4.40.3.10.85.1.4
    optixRtnIFPortCfgStgEnable OBJECT-TYPE
        SYNTAX OPTIXRtnEnableStateType
        MAX-ACCESS read-write
        STATUS current
        DESCRIPTION
            "Indicates the status of IFPort 2MWAY."
        ::= { optixRtnIFPort2MWAYEntry 4 }
	
    -- 1.3.6.1.4.1.2011.2.25.4.40.3.10.86
    optixRtnIFPortAllCapacityTable OBJECT-TYPE
        SYNTAX SEQUENCE OF OptixRtnIFPortAllCapacityEntry
        MAX-ACCESS not-accessible
        STATUS current
        DESCRIPTION
            "Describes the service E1 supported by an IF board in each mode."
        ::= { optixISBoardAttr 86}

    -- 1.3.6.1.4.1.2011.2.25.4.40.3.10.86.1
    optixRtnIFPortAllCapacityEntry OBJECT-TYPE
        SYNTAX OptixRtnIFPortAllCapacityEntry
        MAX-ACCESS not-accessible
        STATUS current
        DESCRIPTION
            "Indicates the query entry for service capacities of an IF port in each mode."
        INDEX{ optixRtnBoardID,optixRtnSubCardID,optixRtnPortID,optixRtnIFPortlist }
        ::= { optixRtnIFPortAllCapacityTable 1 }

    OptixRtnIFPortAllCapacityEntry ::=
        SEQUENCE {
            optixRtnIFPortlist
                Unsigned32,
            optixRtnIFPortAllBandWidth
                OPTIXRtnBandWidthType,
            optixRtnIFPortAllMode
                OPTIXRtnModulateModeType,
            optixRtnIFPortAllMaxE1Num
                Unsigned32
        }

    -- 1.3.6.1.4.1.2011.2.25.4.40.3.10.86.1.1
    optixRtnIFPortlist OBJECT-TYPE
        SYNTAX Unsigned32
        MAX-ACCESS not-accessible
        STATUS current
        DESCRIPTION
            "Indicates the list."
        ::= { optixRtnIFPortAllCapacityEntry 1 }

    -- 1.3.6.1.4.1.2011.2.25.4.40.3.10.86.1.2
    optixRtnIFPortAllBandWidth OBJECT-TYPE
        SYNTAX OPTIXRtnBandWidthType
        MAX-ACCESS read-only
        STATUS current
        DESCRIPTION
            "Indicates the channel spacing.Values: 1: 3.5M 2: 7.0M 3: 14M 4: 28M 5: 40M 6: 56M 7: FCC30M 8: FCC40M 9: FCC50M 10: 250M; 11: 500M; 12:750M; 16: 62P5M; 17:125M; 18: bw1000M;
 22:bw200M; 23:112M; 24:FCC10M; 25:FCC20M; 26:bw1500M; 27:bw2000M; 28:bwFCC60M;"
        ::= { optixRtnIFPortAllCapacityEntry 2 }

    -- 1.3.6.1.4.1.2011.2.25.4.40.3.10.86.1.3
    optixRtnIFPortAllMode OBJECT-TYPE
        SYNTAX OPTIXRtnModulateModeType
        MAX-ACCESS read-only
        STATUS current
        DESCRIPTION
            "Indicates the port modulation mode.Values: 1: QPSK; 2: 16QAM; 3: 32QAM; 4: 64QAM; 5: 128QAM; 6: 256QAM; 7: 512QAM; 8: 1024QAM; 9: QPSKSTRONG; 10: 16QAMSTRONG; 11: 512QAMLIGHT; 12: 1024QAMLIGHT; 13: 2048QAM; 14:QPSKStrong250M; 15: QPSKStrong500M; 16:QPSKStrong750M; 17 QPSKStrong62P5M; 18: QPSKStrong125M; 20: 4096QAM;
21:modeBPSK; 22:modeBPSK250M; 23:modeBPSK500M; 24:modeBPSK750M; 25:modeBPSK1000M; 26:modeBPSK1500M; 27:modeBPSK2000M; 28: 2048QAMLIGHT; 29:modeBPSK62P5M; 30:modeBPSK125M; 31:mode8PSK; 32:mode8192QAM; 33:mode16384QAM; -1: NULL."
        ::= { optixRtnIFPortAllCapacityEntry 3 }

    -- 1.3.6.1.4.1.2011.2.25.4.40.3.10.86.1.4
    optixRtnIFPortAllMaxE1Num OBJECT-TYPE
        SYNTAX Unsigned32
        MAX-ACCESS read-only
        STATUS current
        DESCRIPTION
            "Indicates the maximum number of E1s supported by a mode."
        ::= { optixRtnIFPortAllCapacityEntry 4 }		

    -- 1.3.6.1.4.1.2011.2.25.4.40.3.10.90
    optixRtnIFPortAMSwitchHistoryTable OBJECT-TYPE
        SYNTAX SEQUENCE OF OptixRtnIFPortAMSwitchHistoryEntry
        MAX-ACCESS not-accessible
        STATUS current
        DESCRIPTION
            "Describes the ACM switching history."
        ::= { optixISBoardAttr 90 }

    -- 1.3.6.1.4.1.2011.2.25.4.40.3.10.90.1
    optixRtnIFPortAMSwitchHistoryEntry OBJECT-TYPE
        SYNTAX OptixRtnIFPortAMSwitchHistoryEntry
        MAX-ACCESS not-accessible
        STATUS current
        DESCRIPTION
            "Indicates an ACM switching history entry."
        INDEX{ optixRtnBoardID,optixRtnSubCardID,optixRtnPortID,optixRtnIFPortAMSwitchEventID }
        ::= { optixRtnIFPortAMSwitchHistoryTable 1 }

    OptixRtnIFPortAMSwitchHistoryEntry ::=
        SEQUENCE {
            optixRtnIFPortAMSwitchEventID
                Unsigned32,
            optixRtnIFPortAMSwitchEventDate
                OCTET STRING,
            optixRtnIFPortAMSwitchEventValue
                INTEGER,
            optixRtnIFPortAMSwitchEventDir
                INTEGER,
            optixRtnIFPortAMSwitchEventPara
                OPTIXRtnIFAcmModType,
            optixRtnIFPortAMSwitchEventTimeStamp
                Unsigned32
        }

    -- 1.3.6.1.4.1.2011.2.25.4.40.3.10.90.1.4
    optixRtnIFPortAMSwitchEventID OBJECT-TYPE
        SYNTAX Unsigned32
        MAX-ACCESS not-accessible
        STATUS current
        DESCRIPTION
            "Indicates the ACM-switching event ID."
        DEFVAL{ 0 }
        ::= { optixRtnIFPortAMSwitchHistoryEntry 4 }

    -- 1.3.6.1.4.1.2011.2.25.4.40.3.10.90.1.5
    optixRtnIFPortAMSwitchEventDate OBJECT-TYPE
        SYNTAX OCTET STRING
        MAX-ACCESS read-only
        STATUS current
        DESCRIPTION
            "Indicates the ACM switching duration."
        ::= { optixRtnIFPortAMSwitchHistoryEntry 5 }

    -- 1.3.6.1.4.1.2011.2.25.4.40.3.10.90.1.6
    optixRtnIFPortAMSwitchEventValue OBJECT-TYPE
        SYNTAX INTEGER
        {
            acmAutoSwt(0),
            manualSwt(1)
        }
        MAX-ACCESS read-only
        STATUS current
        DESCRIPTION
            "Indicates an ACM switching event."
        DEFVAL{ 0 }
        ::= { optixRtnIFPortAMSwitchHistoryEntry 6 }

    -- 1.3.6.1.4.1.2011.2.25.4.40.3.10.90.1.7
    optixRtnIFPortAMSwitchEventDir OBJECT-TYPE
        SYNTAX INTEGER
        {
            positive(0),
            negative(1)
        }
        MAX-ACCESS read-only
        STATUS current
        DESCRIPTION
            "Indicates the ACM switching direction."
        DEFVAL{ 0 }
        ::= { optixRtnIFPortAMSwitchHistoryEntry 7 }

    -- 1.3.6.1.4.1.2011.2.25.4.40.3.10.90.1.8
    optixRtnIFPortAMSwitchEventPara OBJECT-TYPE
        SYNTAX OPTIXRtnIFAcmModType
        MAX-ACCESS read-only
        STATUS current
        DESCRIPTION
            "Indicates the ACM-switching event parameters.Values:modeClear(0),modeQPSK(1),mode16QAM(2),mode32QAM(3),mode64QAM(4),mode128QAM(5),mode256QAM(6),mode512QAM(7),mode1024QAM(8),modeQPSKSTRONG(9),mode16QAMSTRONG(10),
mode512QAMLIGHT(11),mode1024QAMLIGHT(12),mode2048QAM(13),modeQPSKStrong250M(14),modeQPSKStrong500M(15),modeQPSKStrong750M(16),modeQPSKStrong62P5M(17),modeQPSKStrong125M(18),
mode4096QAM(20)modeBPSK(21),modeBPSK250M(22),modeBPSK500M(23),modeBPSK750M(24),modeBPSK1000M(25),modeBPSK1500M(26),modeBPSK2000M(27),mode2048QAMLIGHT(28),modeBPSK62P5M(29),modeBPSK125M(30),
mode8PSK(31),mode8192QAM(32),modeNULL(255)"
        DEFVAL{ 0 }
        ::= { optixRtnIFPortAMSwitchHistoryEntry 8 }

    -- 1.3.6.1.4.1.2011.2.25.4.40.3.10.90.1.9
    optixRtnIFPortAMSwitchEventTimeStamp OBJECT-TYPE
        SYNTAX Unsigned32
        MAX-ACCESS read-only
        STATUS current
        DESCRIPTION
            "Indicates the ACM switching timestamp."
        DEFVAL{ 0 }
        ::= { optixRtnIFPortAMSwitchHistoryEntry 9 }

    -- 1.3.6.1.4.1.2011.2.25.4.40.3.10.91
    optixRtnIFPortE1NumTable OBJECT-TYPE
        SYNTAX SEQUENCE OF OptixRtnIFPortE1NumEntry
        MAX-ACCESS not-accessible
        STATUS current
        DESCRIPTION
            "Describes the number of E1s."
        ::= { optixISBoardAttr 91 }

    -- 1.3.6.1.4.1.2011.2.25.4.40.3.10.91.1
    optixRtnIFPortE1NumEntry OBJECT-TYPE
        SYNTAX OptixRtnIFPortE1NumEntry
        MAX-ACCESS not-accessible
        STATUS current
        DESCRIPTION
            "Indicates the E1 quantity management entry."
        INDEX{ optixRtnBoardID,optixRtnSubCardID,optixRtnPortID }
        ::= { optixRtnIFPortE1NumTable 1 }

    OptixRtnIFPortE1NumEntry ::=
        SEQUENCE {
            optixRtnIFPortE1Num
                OCTET STRING
        }

    -- 1.3.6.1.4.1.2011.2.25.4.40.3.10.91.1.1
    optixRtnIFPortE1Num OBJECT-TYPE
        SYNTAX OCTET STRING
        MAX-ACCESS read-only
        STATUS current
        DESCRIPTION
            "Indicates querying the number of E1s."
        ::= { optixRtnIFPortE1NumEntry 1 }

    -- 1.3.6.1.4.1.2011.2.25.4.40.3.10.92
    optixRtnNeighborNeinfoTable OBJECT-TYPE
        SYNTAX SEQUENCE OF OptixRtnNeighborNeinfoEntry
        MAX-ACCESS not-accessible
        STATUS current
        DESCRIPTION
            "Describes antenna polarization directions."
        ::= { optixISBoardAttr 92 }

    -- 1.3.6.1.4.1.2011.2.25.4.40.3.10.92.1
    optixRtnNeighborNeinfoEntry OBJECT-TYPE
        SYNTAX OptixRtnNeighborNeinfoEntry
        MAX-ACCESS not-accessible
        STATUS current
        DESCRIPTION
            "Indicates an antenna polarization direction entry."
        INDEX{ optixRtnBoardID,optixRtnSubCardID,optixRtnPortID }
        ::= { optixRtnNeighborNeinfoTable 1 }

    OptixRtnNeighborNeinfoEntry ::=
        SEQUENCE {
            optixRtnNeighbourNeID
                Unsigned32,
            optixRtnNeighbourNeName
                OCTET STRING,
            optixRtnNeighbourNeBoardID
                Unsigned32,
            optixRtnNeighbourNeBoardType
                Unsigned32,
            optixRtnNeighbourNeSubCardID
                Unsigned32,
            optixRtnNeighbourNePortID
                Unsigned32
        }

    -- 1.3.6.1.4.1.2011.2.25.4.40.3.10.92.1.1
    optixRtnNeighbourNeID OBJECT-TYPE
        SYNTAX Unsigned32
        MAX-ACCESS read-only
        STATUS current
        DESCRIPTION
            "Indicates the ID of the adjacent NE in an XPIC/1+1/PLA group."
        ::= { optixRtnNeighborNeinfoEntry 1 }

    -- 1.3.6.1.4.1.2011.2.25.4.40.3.10.92.1.2
    optixRtnNeighbourNeName OBJECT-TYPE
        SYNTAX OCTET STRING
        MAX-ACCESS read-only
        STATUS current
        DESCRIPTION
            "Indicates the neighbor NE name in an XPIC/1+1/PLA group (64 characters)."
        ::= { optixRtnNeighborNeinfoEntry 2 }

    -- 1.3.6.1.4.1.2011.2.25.4.40.3.10.92.1.3
    optixRtnNeighbourNeBoardID OBJECT-TYPE
        SYNTAX Unsigned32
        MAX-ACCESS read-only
        STATUS current
        DESCRIPTION
            "Indicates the neighbor NE board ID in an XPIC/1+1/PLA group."
        ::= { optixRtnNeighborNeinfoEntry 3 }

    -- 1.3.6.1.4.1.2011.2.25.4.40.3.10.92.1.4
    optixRtnNeighbourNeBoardType OBJECT-TYPE
        SYNTAX Unsigned32
        {
		ife2(1404),
		ifu2(2079),
		ifx2(2080),
		isu2(2266),
		isx2(2267),
		isu3(2474),
		sld1isv3(2475),
		sl91isv3(2468),
		sld3isv3(3062),
		sl91ism6(3382),
		slj1ism6(3414),
		sl91ism8(4101),
		sld4ism8(4103),
		slj1ism8(4201),
		bdtypenull(0)
        }
        MAX-ACCESS read-only
        STATUS current
        DESCRIPTION
            "Indicates the type of a logical board on the neighbor NE in an XPIC/1+1/PLA group."
        ::= { optixRtnNeighborNeinfoEntry 4 }

    -- 1.3.6.1.4.1.2011.2.25.4.40.3.10.92.1.5
    optixRtnNeighbourNeSubCardID OBJECT-TYPE
        SYNTAX Unsigned32
        MAX-ACCESS read-only
        STATUS current
        DESCRIPTION
            "Indicates the type of a subcard on the neighbor NE in an XPIC/1+1/PLA group."
        ::= { optixRtnNeighborNeinfoEntry 5 }

    -- 1.3.6.1.4.1.2011.2.25.4.40.3.10.92.1.6
    optixRtnNeighbourNePortID OBJECT-TYPE
        SYNTAX Unsigned32
        MAX-ACCESS read-only
        STATUS current
        DESCRIPTION
            "Indicates the ID of a port on the neighbor NE in an XPIC/1+1/PLA group."
        ::= { optixRtnNeighborNeinfoEntry 6 }

    -- 1.3.6.1.4.1.2011.2.25.4.40.3.10.93
    optixRtnLicenseTable OBJECT-TYPE
        SYNTAX SEQUENCE OF OptixRtnLicenseEntry
        MAX-ACCESS not-accessible
        STATUS current
        DESCRIPTION
            "Describes licenses"
        ::= { optixISBoardAttr 93 }

    -- 1.3.6.1.4.1.2011.2.25.4.40.3.10.93.1
    optixRtnLicenseEntry OBJECT-TYPE
        SYNTAX OptixRtnLicenseEntry
        MAX-ACCESS not-accessible
        STATUS current
        DESCRIPTION
            "Indicates the license entry"
        INDEX{ optixRtnBoardID,optixRtnSubCardID,optixRtnPortID }
        ::= { optixRtnLicenseTable 1 }

    OptixRtnLicenseEntry ::=
        SEQUENCE {
            optixRtnLicenseType
                Unsigned32,
            optixRtnLicenseLoadState
                Unsigned32,
            optixRtnLicenseCapacity
                Unsigned32,
            optixRtnIFPortLicenseCapacityUnit
                Unsigned32,
            optixRtnIFPortLicenseUsedCapacity
                Unsigned32,
            optixRtnIFPortLicenseUsedCapacityUnit
                Unsigned32
        }

    -- 1.3.6.1.4.1.2011.2.25.4.40.3.10.93.1.2
    optixRtnLicenseType OBJECT-TYPE
        SYNTAX Unsigned32
        {
            hybrid(2),
            clock1588v2(4),
            bwacc(9),
            port(11),
            erps(13),
            group1j1(17),
            qos(18),
            fdmg(22),
            amac(24),
            cpri1p25(35),
            cpri2p5(36),
            mext250(37),
            bwnf(52)
        }
        MAX-ACCESS read-only
        STATUS current
        DESCRIPTION
            "Indicates the license file type. 1: AM 2: HBRID 3: TDM 4: 1588v2 5: ATM/IMA 6: RADIO LAG 7: E1 Priority 8: Synchronous Ethernet 9: Air interface compression 10: MPLS 11: GE port 12: XPIC 13: ERPS 14: PLA 15: Number of E1 services 16: High capacity modification mode 18: WRED 19: Stacking 20: Second IF port 21: MPLS-TP OAM"
        ::= { optixRtnLicenseEntry 2 }

    -- 1.3.6.1.4.1.2011.2.25.4.40.3.10.93.1.3
    optixRtnLicenseLoadState OBJECT-TYPE
        SYNTAX Unsigned32
        {
            unload(0),
            load(1)
        }
        MAX-ACCESS read-only
        STATUS current
        DESCRIPTION
            "Indicates the license loading status. Values: 0: not loaded 1: loaded"
        ::= { optixRtnLicenseEntry 3 }

    -- 1.3.6.1.4.1.2011.2.25.4.40.3.10.93.1.4
    optixRtnLicenseCapacity OBJECT-TYPE
        SYNTAX Unsigned32
        MAX-ACCESS read-only
        STATUS current
        DESCRIPTION
            "Indicates the license capacity value. (The default capacity value is returned when the license is not loaded.)"
        ::= { optixRtnLicenseEntry 4 }

    -- 1.3.6.1.4.1.2011.2.25.4.40.3.10.93.1.5
    optixRtnIFPortLicenseCapacityUnit OBJECT-TYPE
        SYNTAX Unsigned32
        {
            mbps(0),
            e1(1),
            stm1(2),
            direction(3),
            port(4),
            board(5),
            invaild(255)
        }
        MAX-ACCESS read-only
        STATUS current
        DESCRIPTION
            "Indicates the license capacity unit. The values: 0: Mbps 1: E1 2: STM1 3: Board 4: Port 255: invalid When the license type is AM/E1 Priority/Air interface compression/Port control/XPIC/High capacity modification mode, the value of this parameter is 3. When the license type is 1588v2 ATM/IMA/RADIO LAG/Synchronous Ethernet/MPLS, the value of this parameter is an invalid value 255."
        ::= { optixRtnLicenseEntry 5 }

    -- 1.3.6.1.4.1.2011.2.25.4.40.3.10.93.1.6
    optixRtnIFPortLicenseUsedCapacity OBJECT-TYPE
        SYNTAX Unsigned32
        MAX-ACCESS read-only
        STATUS current
        DESCRIPTION
            "Indicates the used license capacity."
        ::= { optixRtnLicenseEntry 6 }

    -- 1.3.6.1.4.1.2011.2.25.4.40.3.10.93.1.7
    optixRtnIFPortLicenseUsedCapacityUnit OBJECT-TYPE
        SYNTAX Unsigned32
        {
            mbps(0),
            e1(1),
            stm1(2),
            direction(3),
            port(4),
            board(5),
            invaild(255)
        }
        MAX-ACCESS read-only
        STATUS current
        DESCRIPTION
            "Indicates the TDM capacity unit. 0: Mbps 1: E1 2: STM1 3: Board 4: Port -1: Invalid"
        ::= { optixRtnLicenseEntry 7 }

    -- 1.3.6.1.4.1.2011.2.25.4.40.3.10.95
    optixRtnXpicCascadepidTable OBJECT-TYPE
        SYNTAX SEQUENCE OF OptixRtnXpicCascadepidEntry
        MAX-ACCESS not-accessible
        STATUS current
        DESCRIPTION
            "Indicates the information of XPIC."
        ::= { optixISBoardAttr 95 }

    -- 1.3.6.1.4.1.2011.2.25.4.40.3.10.95.1
    optixRtnXpicCascadepidEntry OBJECT-TYPE
        SYNTAX OptixRtnXpicCascadepidEntry
        MAX-ACCESS not-accessible
        STATUS current
        DESCRIPTION
            "Indicates the information of XPIC."
        INDEX{ optixRtnBoardID,optixRtnSubCardID,optixRtnPortID }
        ::= { optixRtnXpicCascadepidTable 1 }

    OptixRtnXpicCascadepidEntry ::=
        SEQUENCE {
            optixRtnXpicCascadepid
                Unsigned32           
        }

    -- 1.3.6.1.4.1.2011.2.25.4.40.3.10.95.1.1
    optixRtnXpicCascadepid OBJECT-TYPE
        SYNTAX Unsigned32
        MAX-ACCESS read-write
        STATUS current
        DESCRIPTION
            "Indicates the information of XPIC."
        ::= { optixRtnXpicCascadepidEntry 1 }

    -- 1.3.6.1.4.1.2011.2.25.4.40.3.10.98
    optixRtnLaserTable OBJECT-TYPE
        SYNTAX SEQUENCE OF OptixRtnLaserEntry
        MAX-ACCESS not-accessible
        STATUS current
        DESCRIPTION
            "Indicates the laser status."
        ::= { optixISBoardAttr 98 }

    -- 1.3.6.1.4.1.2011.2.25.4.40.3.10.98.1
    optixRtnLaserEntry OBJECT-TYPE
        SYNTAX OptixRtnLaserEntry
        MAX-ACCESS not-accessible
        STATUS current
        DESCRIPTION
            "Indicates the laser status."
        INDEX{ optixRtnBoardID,optixRtnSubCardID,optixRtnPortID }
        ::= { optixRtnLaserTable 1 }

    OptixRtnLaserEntry ::=
        SEQUENCE {
            optixRtnlaserstate
                Unsigned32          
        }

    -- 1.3.6.1.4.1.2011.2.25.4.40.3.10.98.1.4
    optixRtnlaserstate OBJECT-TYPE
        SYNTAX Unsigned32
        {
            close(0),
            open(1)
        }
        MAX-ACCESS read-only
        STATUS current
        DESCRIPTION
            "Indicates the laser status."
        ::= { optixRtnLaserEntry 4 }

    -- 1.3.6.1.4.1.2011.2.25.4.40.3.11
    optixRtnFMTxPower OBJECT IDENTIFIER ::= { optixRtnIFBoardAttr 11 }

    -- 1.3.6.1.4.1.2011.2.25.4.40.3.11.7
    optixRtnFMTestODUBoardPowerTable OBJECT-TYPE
        SYNTAX SEQUENCE OF OptixRtnFMTestODUBoardPowerEntry
        MAX-ACCESS not-accessible
        STATUS current
        DESCRIPTION
            "Indicates setting the transmit power table of an ODU in the fade margin test."
        ::= { optixRtnFMTxPower 7 }

    -- 1.3.6.1.4.1.2011.2.25.4.40.3.11.7.1
    optixRtnFMTestODUBoardPowerEntry OBJECT-TYPE
        SYNTAX OptixRtnFMTestODUBoardPowerEntry
        MAX-ACCESS not-accessible
        STATUS current
        DESCRIPTION
            "Indicates setting the transmit power entry of an ODU in the fade margin test."
        INDEX{ optixRtnOduIndex1,optixRtnOduIndex2 }
        ::= { optixRtnFMTestODUBoardPowerTable 1 }

    OptixRtnFMTestODUBoardPowerEntry ::=
        SEQUENCE {
            optixRtnFadeMarginOduBoardTxPower
                INTEGER,
            optixRtnFadeMarginOduBoardWork
                INTEGER
        }

    -- 1.3.6.1.4.1.2011.2.25.4.40.3.11.7.1.1
    optixRtnFadeMarginOduBoardTxPower OBJECT-TYPE
        SYNTAX INTEGER
        MAX-ACCESS read-write
        STATUS current
        DESCRIPTION
            "Indicates the ODU transmit power. The value ranges from -100 to +350 in the unit of 0.1 dBm."
        ::= { optixRtnFMTestODUBoardPowerEntry 1 }

    -- 1.3.6.1.4.1.2011.2.25.4.40.3.11.7.1.2
    optixRtnFadeMarginOduBoardWork OBJECT-TYPE
        SYNTAX INTEGER
        {
            mute(0),
            unmute(1)
        }
        MAX-ACCESS read-write
        STATUS current
        DESCRIPTION
            "Indicates setting the working status of the ODU in the fade margin test."
        ::= { optixRtnFMTestODUBoardPowerEntry 2 }

    -- 1.3.6.1.4.1.2011.2.25.4.40.3.11.8
    optixRtnFMTestODUPortPowerTable OBJECT-TYPE
        SYNTAX SEQUENCE OF OptixRtnFMTestODUPortPowerEntry
        MAX-ACCESS not-accessible
        STATUS current
        DESCRIPTION
            "Indicates setting the transmit power table of an ODU in the fade margin test.(320/3202f)"
        ::= { optixRtnFMTxPower 8 }

    -- 1.3.6.1.4.1.2011.2.25.4.40.3.11.8.1
    optixRtnFMTestODUPortPowerEntry OBJECT-TYPE
        SYNTAX OptixRtnFMTestODUPortPowerEntry
        MAX-ACCESS not-accessible
        STATUS current
        DESCRIPTION
            "Indicates setting the transmit power entry of an ODU in the fade margin test.(320/3202f)"
        INDEX{ optixRtnBoardID,optixRtnSubCardID,optixRtnPortID }
        ::= { optixRtnFMTestODUPortPowerTable 1 }

    OptixRtnFMTestODUPortPowerEntry ::=
        SEQUENCE {
            optixRtnFadeMarginOduPortTxPower
                INTEGER,
            optixRtnFadeMarginOduPortWork
                INTEGER
        }

    -- 1.3.6.1.4.1.2011.2.25.4.40.3.11.8.1.1
    optixRtnFadeMarginOduPortTxPower OBJECT-TYPE
        SYNTAX INTEGER
        MAX-ACCESS read-write
        STATUS current
        DESCRIPTION
            "Indicates the ODU transmit power. The value ranges from -100 to +350 in the unit of 0.1 dBm.(320/3202f)"
        ::= { optixRtnFMTestODUPortPowerEntry 1 }

    -- 1.3.6.1.4.1.2011.2.25.4.40.3.11.8.1.2
    optixRtnFadeMarginOduPortWork OBJECT-TYPE
        SYNTAX INTEGER
        {
            mute(0),
            unmute(1)
        }
        MAX-ACCESS read-write
        STATUS current
        DESCRIPTION
            "Indicates setting the working status of the ODU in the fade margin test.(320/3202f)"
        ::= { optixRtnFMTestODUPortPowerEntry 2 }

    -- 1.3.6.1.4.1.2011.2.25.4.40.3.11.2
    optixRtnFMTestMSETable OBJECT-TYPE
        SYNTAX SEQUENCE OF OptixRtnFMTestMSEEntry
        MAX-ACCESS not-accessible
        STATUS current
        DESCRIPTION
            "Indicates the MSE value table in the fade margin test."
        ::= { optixRtnFMTxPower 2 }

    -- 1.3.6.1.4.1.2011.2.25.4.40.3.11.2.1
    optixRtnFMTestMSEEntry OBJECT-TYPE
        SYNTAX OptixRtnFMTestMSEEntry
        MAX-ACCESS not-accessible
        STATUS current
        DESCRIPTION
            "Indicates the MSE value entry in the fade margin test."
        INDEX{ optixRtnBoardID,optixRtnSubCardID,optixRtnPortID }
        ::= { optixRtnFMTestMSETable 1 }

    OptixRtnFMTestMSEEntry ::=
        SEQUENCE {
            optixRtnFadeMarginAcmMSE
                Unsigned32
        }

    -- 1.3.6.1.4.1.2011.2.25.4.40.3.11.2.1.1
    optixRtnFadeMarginAcmMSE OBJECT-TYPE
        SYNTAX Unsigned32
        MAX-ACCESS read-only
        STATUS current
        DESCRIPTION
            "Indicates the MSE value in the unit of 0.1 dB.The value 0xffff indicates a link interruption."
        ::= { optixRtnFMTestMSEEntry 1 }

    -- 1.3.6.1.4.1.2011.2.25.4.40.3.11.3
    optixRtnFMValueTable OBJECT-TYPE
        SYNTAX SEQUENCE OF OptixRtnFMValueEntry
        MAX-ACCESS not-accessible
        STATUS current
        DESCRIPTION
            "Indicates the fade margin value."
        ::= { optixRtnFMTxPower 3 }

    -- 1.3.6.1.4.1.2011.2.25.4.40.3.11.3.1
    optixRtnFMValueEntry OBJECT-TYPE
        SYNTAX OptixRtnFMValueEntry
        MAX-ACCESS not-accessible
        STATUS current
        DESCRIPTION
            "Indicates the fade margin value."
        INDEX{ optixRtnBoardID,optixRtnSubCardID,optixRtnPortID }
        ::= { optixRtnFMValueTable 1 }

    OptixRtnFMValueEntry ::=
        SEQUENCE {
            optixRtnFadeMarginExtRsl0
                INTEGER,
            optixRtnFadeMarginExtRslc
                INTEGER,
            optixRtnFadeMarginExtValue
                INTEGER,
            optixRtnFadeMarginMode
                INTEGER,
            optixRtnFadeMarginCurRsl
                INTEGER,
            optixRtnFadeMarginData
                OCTET STRING,
            optixRtnFadeMarginValue
                INTEGER
        }

    -- 1.3.6.1.4.1.2011.2.25.4.40.3.11.3.1.1
    optixRtnFadeMarginExtRsl0 OBJECT-TYPE
        SYNTAX INTEGER
        MAX-ACCESS read-write
        STATUS current
        DESCRIPTION
            "Indicates the initial receive power."
        ::= { optixRtnFMValueEntry 1 }

    -- 1.3.6.1.4.1.2011.2.25.4.40.3.11.3.1.2
    optixRtnFadeMarginExtRslc OBJECT-TYPE
        SYNTAX INTEGER
        MAX-ACCESS read-write
        STATUS current
        DESCRIPTION
            "Indicates the receive power when the ODU is muted."
        ::= { optixRtnFMValueEntry 2 }

    -- 1.3.6.1.4.1.2011.2.25.4.40.3.11.3.1.3
    optixRtnFadeMarginExtValue OBJECT-TYPE
        SYNTAX INTEGER
        MAX-ACCESS read-write
        STATUS current
        DESCRIPTION
            "Indicates the fade margin value."
        ::= { optixRtnFMValueEntry 3 }

    -- 1.3.6.1.4.1.2011.2.25.4.40.3.11.3.1.4
    optixRtnFadeMarginMode OBJECT-TYPE
        SYNTAX INTEGER
        MAX-ACCESS read-write
        STATUS current
        DESCRIPTION
            "Indicates the mode."
        ::= { optixRtnFMValueEntry 4 }

    -- 1.3.6.1.4.1.2011.2.25.4.40.3.11.3.1.5
    optixRtnFadeMarginCurRsl OBJECT-TYPE
        SYNTAX INTEGER
        MAX-ACCESS read-write
        STATUS current
        DESCRIPTION
            "Indicates the current RSL."
        ::= { optixRtnFMValueEntry 5 }

    -- 1.3.6.1.4.1.2011.2.25.4.40.3.11.3.1.6
    optixRtnFadeMarginData OBJECT-TYPE
        SYNTAX OCTET STRING
        MAX-ACCESS read-write
        STATUS current
        DESCRIPTION
            "Indicates the number of sampling points and the RSL and MSE groups."
        ::= { optixRtnFMValueEntry 6 }

    -- 1.3.6.1.4.1.2011.2.25.4.40.3.11.3.1.7
    optixRtnFadeMarginValue OBJECT-TYPE
        SYNTAX INTEGER
        MAX-ACCESS read-write
        STATUS current
        DESCRIPTION
            "Indicates the fade margin value."
        ::= { optixRtnFMValueEntry 7 }

    -- 1.3.6.1.4.1.2011.2.25.4.40.3.11.5
    optixRtnGatherFMTable OBJECT-TYPE
	SYNTAX SEQUENCE OF OptixRtnGatherFMEntry
	MAX-ACCESS not-accessible
	STATUS current
	DESCRIPTION
	"Indicates setting the transmit power table of an ODU in the fade margin test."
	::= { optixRtnFMTxPower 5 }

    -- 1.3.6.1.4.1.2011.2.25.4.40.3.11.5.1
    optixRtnGatherFMEntry OBJECT-TYPE
	SYNTAX OptixRtnGatherFMEntry
	MAX-ACCESS not-accessible
	STATUS current
	DESCRIPTION
	    "Indicates setting the transmit power entry of an ODU in the fade margin test."
	INDEX{ optixRtnBoardID,optixRtnSubCardID,optixRtnPortID}
	::= { optixRtnGatherFMTable 1 }

	OptixRtnGatherFMEntry ::=
	SEQUENCE {
	    optixRtnStartGatherFm
		INTEGER,
	    optixRtnFmRsl
		INTEGER
	}

    -- 1.3.6.1.4.1.2011.2.25.4.40.3.11.5.1.1
    optixRtnStartGatherFm OBJECT-TYPE
	SYNTAX INTEGER
	{
	    start(0)
	}
	MAX-ACCESS read-write
	STATUS current
	DESCRIPTION
	    "Start the near-far-end FadeMargin test using the rsl collection."
	DEFVAL{ 0 }
	::= { optixRtnGatherFMEntry 1 }

    -- 1.3.6.1.4.1.2011.2.25.4.40.3.11.5.1.2
    optixRtnFmRsl OBJECT-TYPE
	SYNTAX INTEGER
	MAX-ACCESS read-only
	STATUS current
	DESCRIPTION
	    "Query the received power during the fademargin test."
	::= { optixRtnGatherFMEntry 2 }

    -- 1.3.6.1.4.1.2011.2.25.4.40.3.12
    optixIFPRBSMgr OBJECT IDENTIFIER ::= { optixRtnIFBoardAttr 12 }

    -- 1.3.6.1.4.1.2011.2.25.4.40.3.12.1
    optixRtnIFPRBSTestControlTable OBJECT-TYPE
        SYNTAX SEQUENCE OF OptixRtnIFPRBSTestControlEntry
        MAX-ACCESS not-accessible
        STATUS current
        DESCRIPTION
            "Indicates the control table for starting or stopping the PRBS test."
        ::= { optixIFPRBSMgr 1 }

    -- 1.3.6.1.4.1.2011.2.25.4.40.3.12.1.1
    optixRtnIFPRBSTestControlEntry OBJECT-TYPE
        SYNTAX OptixRtnIFPRBSTestControlEntry
        MAX-ACCESS not-accessible
        STATUS current
        DESCRIPTION
            "Indicates the control entry for starting or stopping the PRBS test."
        INDEX{ optixRtnBoardID,optixRtnSubCardID,optixRtnPortID,optixRtnIFPRBSType,optixRtnIFPRBSPathId,optixRtnIFPRBSDirection }
        ::= { optixRtnIFPRBSTestControlTable 1 }

    OptixRtnIFPRBSTestControlEntry ::=
        SEQUENCE {
            optixRtnIFPRBSType
                INTEGER,
            optixRtnIFPRBSPathId
                Unsigned32,
            optixRtnIFPRBSDirection
                INTEGER,
            optixRtnIFPRBSAction
                INTEGER,
            optixRtnIFPRBSMode
                INTEGER,
            optixRtnIFPRBSTimeSpan
                Unsigned32
        }

    -- 1.3.6.1.4.1.2011.2.25.4.40.3.12.1.1.1
    optixRtnIFPRBSType OBJECT-TYPE
        SYNTAX INTEGER
        {
            if(2),
            cpri(3)
        }
        MAX-ACCESS not-accessible
        STATUS current
        DESCRIPTION
            "Indicates the PRBS test type: 
1-E1
2-IF
3-CPRI/OBSAI"
        ::= { optixRtnIFPRBSTestControlEntry 1 }

    -- 1.3.6.1.4.1.2011.2.25.4.40.3.12.1.1.2
    optixRtnIFPRBSPathId OBJECT-TYPE
        SYNTAX Unsigned32
        MAX-ACCESS not-accessible
        STATUS current
        DESCRIPTION
            "Indicates the ID of a path used in the PRBS test. Set the parameter to 0 if this field is not in use (applicable to RTN 310/320/360/380/380H working in Ethernet mode).Set the parameter to 0 for an RTN 380 working in CPRI mode. The value 0 corresponds to port 3.Set the parameter to 0, 1, 2 for an RTN 380H working in CPRI or OBSAI mode. The values 0, 1, 2 correspond to ports 5, 4, 3, respectively."
        ::= { optixRtnIFPRBSTestControlEntry 2 }

    -- 1.3.6.1.4.1.2011.2.25.4.40.3.12.1.1.3
    optixRtnIFPRBSDirection OBJECT-TYPE
        SYNTAX INTEGER
        {
            ingress(1),
            egress(2),
            ingressandegress(3)
        }
        MAX-ACCESS not-accessible
        STATUS current
        DESCRIPTION
            "Indicates the PRBS test direction. 
1-Ingress
2-Egress"
        ::= { optixRtnIFPRBSTestControlEntry 3 }

    -- 1.3.6.1.4.1.2011.2.25.4.40.3.12.1.1.4
    optixRtnIFPRBSAction OBJECT-TYPE
        SYNTAX INTEGER
        {
            stop(0),
            start(1)
        }
        MAX-ACCESS read-write
        STATUS current
        DESCRIPTION
            "Indicates an action in the PRBS test.
0-stop the test
1-start the test"
        ::= { optixRtnIFPRBSTestControlEntry 4 }

    -- 1.3.6.1.4.1.2011.2.25.4.40.3.12.1.1.5
    optixRtnIFPRBSMode OBJECT-TYPE
        SYNTAX INTEGER
        {
            shortTerm(1),
            longTerm(2),
            longlongTerm(3)
        }
        MAX-ACCESS read-write
        STATUS current
        DESCRIPTION
            "Indicates the PRBS test mode. 
1-short_term (short-term test, measured in seconds)
2-long_term (long-term test, measured in 10 minutes)
3-longlong_term (super-long-term test, measured in hours)"
        ::= { optixRtnIFPRBSTestControlEntry 5 }

    -- 1.3.6.1.4.1.2011.2.25.4.40.3.12.1.1.6
    optixRtnIFPRBSTimeSpan OBJECT-TYPE
        SYNTAX Unsigned32
        MAX-ACCESS read-write
        STATUS current
        DESCRIPTION
            "Indicates the PRBS test duration. 
Value range: 1-255
The test duration is measured in seconds in short-term tests, 10 minutes in long-term tests, and hours in super-long-term tests."
        ::= { optixRtnIFPRBSTestControlEntry 6 }

    -- 1.3.6.1.4.1.2011.2.25.4.40.3.12.2
    optixRtnIFPRBSTestResultTable OBJECT-TYPE
        SYNTAX SEQUENCE OF OptixRtnIFPRBSTestResultEntry
        MAX-ACCESS not-accessible
        STATUS current
        DESCRIPTION
            "Indicates the PRBS test result"
        ::= { optixIFPRBSMgr 2 }

    -- 1.3.6.1.4.1.2011.2.25.4.40.3.12.2.1
    optixRtnIFPRBSTestResultEntry OBJECT-TYPE
        SYNTAX OptixRtnIFPRBSTestResultEntry
        MAX-ACCESS not-accessible
        STATUS current
        DESCRIPTION
            "Indicates the PRBS test result"
        INDEX{ optixRtnBoardID,optixRtnSubCardID,optixRtnPortID,optixRtnIFPrbsType,optixRtnIFPrbsPathId,optixRtnIFPrbsDirection }
        ::= { optixRtnIFPRBSTestResultTable 1 }

    OptixRtnIFPRBSTestResultEntry ::=
        SEQUENCE {
            optixRtnIFPrbsMode
                INTEGER,
            optixRtnIFPrbsStartTime
                OCTET STRING,
            optixRtnIFPrbsEndTime
                OCTET STRING,
            optixRtnIFPrbsProgress
                Unsigned32,
            optixRtnIFPrbsPeriod
                Unsigned32,
            optixRtnIFPrbsDataTypeNum
                Unsigned32,
            optixRtnIFPrbsType1
                Unsigned32,
            optixRtnIFPrbsTestResult1
                Unsigned32,
            optixRtnIFPrbsType2
                Unsigned32,
            optixRtnIFPrbsTestResult2
                Unsigned32,
            optixRtnIFPrbsType3
                Unsigned32,
            optixRtnIFPrbsTestResult3
                Unsigned32,
            optixRtnIFPrbsType4
                Unsigned32,
            optixRtnIFPrbsTestResult4
                Unsigned32,
            optixRtnIFPrbsType5
                Unsigned32,
            optixRtnIFPrbsTestResult5
                Unsigned32,
            optixRtnIFPrbsType6
                Unsigned32,
            optixRtnIFPrbsTestResult6
                Unsigned32
        }

    -- 1.3.6.1.4.1.2011.2.25.4.40.3.12.2.1.11
    optixRtnIFPrbsMode OBJECT-TYPE
        SYNTAX INTEGER
        {
            shortTerm(1),
            longTerm(2),
            longlongTerm(3)
        }
        MAX-ACCESS read-only
        STATUS current
        DESCRIPTION
            "Indicates the test type. 
1: short-term test
2: long-term test
3: super long-term test"
        ::= { optixRtnIFPRBSTestResultEntry 11 }

    -- 1.3.6.1.4.1.2011.2.25.4.40.3.12.2.1.12
    optixRtnIFPrbsStartTime OBJECT-TYPE
        SYNTAX OCTET STRING
        MAX-ACCESS read-only
        STATUS current
        DESCRIPTION
            "Indicates the start time of a test in the format of YYYYMMDDHHMMSS and the time starts from the year 1990."
        ::= { optixRtnIFPRBSTestResultEntry 12 }

    -- 1.3.6.1.4.1.2011.2.25.4.40.3.12.2.1.13
    optixRtnIFPrbsEndTime OBJECT-TYPE
        SYNTAX OCTET STRING
        MAX-ACCESS read-only
        STATUS current
        DESCRIPTION
            "Indicates the end time of a test in the format of YYYYMMDDHHMMSS and the time starts from the year 1990."
        ::= { optixRtnIFPRBSTestResultEntry 13 }

    -- 1.3.6.1.4.1.2011.2.25.4.40.3.12.2.1.14
    optixRtnIFPrbsProgress OBJECT-TYPE
        SYNTAX Unsigned32
        MAX-ACCESS read-only
        STATUS current
        DESCRIPTION
            "Indicates the test progress. Value range: 1-100."
        ::= { optixRtnIFPRBSTestResultEntry 14 }

    -- 1.3.6.1.4.1.2011.2.25.4.40.3.12.2.1.15
    optixRtnIFPrbsPeriod OBJECT-TYPE
        SYNTAX Unsigned32
        MAX-ACCESS read-only
        STATUS current
        DESCRIPTION
            "Indicates the test Period."
        ::= { optixRtnIFPRBSTestResultEntry 15 }

    -- 1.3.6.1.4.1.2011.2.25.4.40.3.12.2.1.16
    optixRtnIFPrbsDataTypeNum OBJECT-TYPE
        SYNTAX Unsigned32
        MAX-ACCESS read-only
        STATUS current
        DESCRIPTION
            "Indicates the number of parameter types N (N >= 1 and currently N = 6). The data types are described as follows:"
        ::= { optixRtnIFPRBSTestResultEntry 16 }

    -- 1.3.6.1.4.1.2011.2.25.4.40.3.12.2.1.17
    optixRtnIFPrbsType1 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFPRBSTestResultEntry 17 }

    -- 1.3.6.1.4.1.2011.2.25.4.40.3.12.2.1.18
    optixRtnIFPrbsTestResult1 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFPRBSTestResultEntry 18 }

    -- 1.3.6.1.4.1.2011.2.25.4.40.3.12.2.1.19
    optixRtnIFPrbsType2 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFPRBSTestResultEntry 19 }

    -- 1.3.6.1.4.1.2011.2.25.4.40.3.12.2.1.20
    optixRtnIFPrbsTestResult2 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFPRBSTestResultEntry 20 }

    -- 1.3.6.1.4.1.2011.2.25.4.40.3.12.2.1.21
    optixRtnIFPrbsType3 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFPRBSTestResultEntry 21 }

    -- 1.3.6.1.4.1.2011.2.25.4.40.3.12.2.1.22
    optixRtnIFPrbsTestResult3 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFPRBSTestResultEntry 22 }

    -- 1.3.6.1.4.1.2011.2.25.4.40.3.12.2.1.23
    optixRtnIFPrbsType4 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFPRBSTestResultEntry 23 }

    -- 1.3.6.1.4.1.2011.2.25.4.40.3.12.2.1.24
    optixRtnIFPrbsTestResult4 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFPRBSTestResultEntry 24 }

    -- 1.3.6.1.4.1.2011.2.25.4.40.3.12.2.1.25
    optixRtnIFPrbsType5 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFPRBSTestResultEntry 25 }

    -- 1.3.6.1.4.1.2011.2.25.4.40.3.12.2.1.26
    optixRtnIFPrbsTestResult5 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFPRBSTestResultEntry 26 }

    -- 1.3.6.1.4.1.2011.2.25.4.40.3.12.2.1.27
    optixRtnIFPrbsType6 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFPRBSTestResultEntry 27 }

    -- 1.3.6.1.4.1.2011.2.25.4.40.3.12.2.1.28
    optixRtnIFPrbsTestResult6 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFPRBSTestResultEntry 28 }

    -- 1.3.6.1.4.1.2011.2.25.4.40.3.12.3
    optixRtnIFBitTestControlTable OBJECT-TYPE
        SYNTAX SEQUENCE OF OptixRtnIFBitTestControlEntry
        MAX-ACCESS not-accessible
        STATUS current
        DESCRIPTION
            "Indicates the control table for starting or stopping the bit test."
        ::= { optixIFPRBSMgr 3 }

    -- 1.3.6.1.4.1.2011.2.25.4.40.3.12.3.1
    optixRtnIFBitTestControlEntry OBJECT-TYPE
        SYNTAX OptixRtnIFBitTestControlEntry
        MAX-ACCESS not-accessible
        STATUS current
        DESCRIPTION
            "Indicates the control entry for starting or stopping the bit test."
        INDEX{ optixRtnBoardID,optixRtnSubCardID,optixRtnPortID }
        ::= { optixRtnIFBitTestControlTable 1 }

    OptixRtnIFBitTestControlEntry ::=
        SEQUENCE {
            optixRtnIFBitAction
                INTEGER,
            optixRtnIFBitMode
                INTEGER,
            optixRtnIFBitTimeSpan
                Unsigned32
        }

    -- 1.3.6.1.4.1.2011.2.25.4.40.3.12.3.1.4
    optixRtnIFBitAction OBJECT-TYPE
        SYNTAX INTEGER
        {
            stop(0),
            start(1)
        }
        MAX-ACCESS read-write
        STATUS current
        DESCRIPTION
            "Indicates an action in the bit test.
0-stop the test
1-start the test."
        ::= { optixRtnIFBitTestControlEntry 4 }

    -- 1.3.6.1.4.1.2011.2.25.4.40.3.12.3.1.5
    optixRtnIFBitMode OBJECT-TYPE
        SYNTAX INTEGER
        {
            shortTerm(1),
            longTerm(2),
            longlongTerm(3)
        }
        MAX-ACCESS read-write
        STATUS current
        DESCRIPTION
            "Indicates the bit test mode. 
1-short_term (short-term test, measured in seconds)
2-long_term (long-term test, measured in 10 minutes)
3-longlong_term (super-long-term test, measured in hours)"
        ::= { optixRtnIFBitTestControlEntry 5 }

    -- 1.3.6.1.4.1.2011.2.25.4.40.3.12.3.1.6
    optixRtnIFBitTimeSpan OBJECT-TYPE
        SYNTAX Unsigned32
        MAX-ACCESS read-write
        STATUS current
        DESCRIPTION
            "Indicates the bit test duration. 
Value range: 1-255
The test duration is measured in seconds in short-term tests, 10 minutes in long-term tests, and hours in super-long-term tests."
        ::= { optixRtnIFBitTestControlEntry 6 }

    -- 1.3.6.1.4.1.2011.2.25.4.40.3.12.4
    optixRtnIFBitTestResultTable OBJECT-TYPE
        SYNTAX SEQUENCE OF OptixRtnIFBitTestResultEntry
        MAX-ACCESS not-accessible
        STATUS current
        DESCRIPTION
            "Indicates the bit test result"
        ::= { optixIFPRBSMgr 4 }

    -- 1.3.6.1.4.1.2011.2.25.4.40.3.12.4.1
    optixRtnIFBitTestResultEntry OBJECT-TYPE
        SYNTAX OptixRtnIFBitTestResultEntry
        MAX-ACCESS not-accessible
        STATUS current
        DESCRIPTION
            "Indicates the bit test result"
        INDEX{ optixRtnBoardID,optixRtnSubCardID,optixRtnPortID }
        ::= { optixRtnIFBitTestResultTable 1 }

    OptixRtnIFBitTestResultEntry ::=
        SEQUENCE {
            optixRtnIFBitResultMode
                INTEGER,
	    optixRtnIFBitResultStartTime
                OCTET STRING,
            optixRtnIFBitResultEndTime
                OCTET STRING,
	    optixRtnIFBitResultProgress
                Unsigned32,
            optixRtnIFBitResultRealTestPeriod
                Unsigned32,  
            optixRtnIFBitResultDataTypeNum
                Unsigned32,
            optixRtnIFBitResultType1
                Unsigned32,
            optixRtnIFBitResultTestResult1
                Unsigned32,
            optixRtnIFBitResultType2
                Unsigned32,
            optixRtnIFBitResultTestResult2
                Unsigned32,
	    optixRtnIFBitResultType3
                Unsigned32,
            optixRtnIFBitResultTestResult3
                Unsigned32,
            optixRtnIFBitResultType4
                Unsigned32,
            optixRtnIFBitResultTestResult4
                Unsigned32,
	    optixRtnIFBitResultType5
                Unsigned32,
            optixRtnIFBitResultTestResult5
                Unsigned32,
            optixRtnIFBitResultType6
                Unsigned32,
            optixRtnIFBitResultTestResult6
                Unsigned32
        }

    -- 1.3.6.1.4.1.2011.2.25.4.40.3.12.4.1.4
    optixRtnIFBitResultMode OBJECT-TYPE
        SYNTAX INTEGER
        {
            shortTerm(1),
            longTerm(2),
            longlongTerm(3)
        }
        MAX-ACCESS read-only
        STATUS current
        DESCRIPTION
            "Indicates the test type. 
1: short-term test
2: long-term test
3: super long-term test"
        ::= { optixRtnIFBitTestResultEntry 4 }

    -- 1.3.6.1.4.1.2011.2.25.4.40.3.12.4.1.5
    optixRtnIFBitResultStartTime OBJECT-TYPE
        SYNTAX OCTET STRING
        MAX-ACCESS read-only
        STATUS current
        DESCRIPTION
            "Indicates the start time of a test in the format of YYYYMMDDHHMMSS and the time starts from the year 1990."
        ::= { optixRtnIFBitTestResultEntry 5}

    -- 1.3.6.1.4.1.2011.2.25.4.40.3.12.4.1.6
    optixRtnIFBitResultEndTime OBJECT-TYPE
        SYNTAX OCTET STRING
        MAX-ACCESS read-only
        STATUS current
        DESCRIPTION
            "Indicates the end time of a test in the format of YYYYMMDDHHMMSS and the time starts from the year 1990."
        ::= { optixRtnIFBitTestResultEntry 6 }

    -- 1.3.6.1.4.1.2011.2.25.4.40.3.12.4.1.7
    optixRtnIFBitResultProgress OBJECT-TYPE
        SYNTAX Unsigned32
        MAX-ACCESS read-only
        STATUS current
        DESCRIPTION
            "Indicates the test progress. Value range: 1-100"
        ::= { optixRtnIFBitTestResultEntry 7 }
				
    -- 1.3.6.1.4.1.2011.2.25.4.40.3.12.4.1.8
    optixRtnIFBitResultRealTestPeriod OBJECT-TYPE
        SYNTAX Unsigned32
        MAX-ACCESS read-only
        STATUS current
        DESCRIPTION
            "Indicates the real test period of test .Value range: 1-255."
        ::= { optixRtnIFBitTestResultEntry 8 }

    -- 1.3.6.1.4.1.2011.2.25.4.40.3.12.4.1.9
    optixRtnIFBitResultDataTypeNum OBJECT-TYPE
        SYNTAX Unsigned32
        MAX-ACCESS read-only
        STATUS current
        DESCRIPTION
            "Indicates the number of parameter types N (N >= 1 and currently N = 6; 360:N >= 1 and currently N = 2). The data types are described as follows:"
        ::= { optixRtnIFBitTestResultEntry 9 }

    -- 1.3.6.1.4.1.2011.2.25.4.40.3.12.4.1.10
    optixRtnIFBitResultType1 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitTestResultEntry 10 }

    -- 1.3.6.1.4.1.2011.2.25.4.40.3.12.4.1.11
    optixRtnIFBitResultTestResult1 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFBitTestResultEntry 11 }

    -- 1.3.6.1.4.1.2011.2.25.4.40.3.12.4.1.12
    optixRtnIFBitResultType2 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitTestResultEntry 12 }

    -- 1.3.6.1.4.1.2011.2.25.4.40.3.12.4.1.13
    optixRtnIFBitResultTestResult2 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFBitTestResultEntry 13 }
		
    -- 1.3.6.1.4.1.2011.2.25.4.40.3.12.4.1.14
    optixRtnIFBitResultType3 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitTestResultEntry 14 }

    -- 1.3.6.1.4.1.2011.2.25.4.40.3.12.4.1.15
    optixRtnIFBitResultTestResult3 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFBitTestResultEntry 15 }

    -- 1.3.6.1.4.1.2011.2.25.4.40.3.12.4.1.16
    optixRtnIFBitResultType4 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitTestResultEntry 16 }

    -- 1.3.6.1.4.1.2011.2.25.4.40.3.12.4.1.17
    optixRtnIFBitResultTestResult4 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFBitTestResultEntry 17 }

    -- 1.3.6.1.4.1.2011.2.25.4.40.3.12.4.1.18
    optixRtnIFBitResultType5 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitTestResultEntry 18 }

    -- 1.3.6.1.4.1.2011.2.25.4.40.3.12.4.1.19
    optixRtnIFBitResultTestResult5 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFBitTestResultEntry 19 }

    -- 1.3.6.1.4.1.2011.2.25.4.40.3.12.4.1.20
    optixRtnIFBitResultType6 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitTestResultEntry 20 }

    -- 1.3.6.1.4.1.2011.2.25.4.40.3.12.4.1.21
    optixRtnIFBitResultTestResult6 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnIFBitTestResultEntry 21 }
		
    -- 1.3.6.1.4.1.2011.2.25.4.40.3.12.5
    optixRtnIFBitOldTestControlTable OBJECT-TYPE
        SYNTAX SEQUENCE OF OptixRtnIFBitOldTestControlEntry
        MAX-ACCESS not-accessible
        STATUS current
        DESCRIPTION
            "Indicates the control table for starting or stopping the bit test."
        ::= { optixIFPRBSMgr 5 }

    -- 1.3.6.1.4.1.2011.2.25.4.40.3.12.5.1
    optixRtnIFBitOldTestControlEntry OBJECT-TYPE
        SYNTAX OptixRtnIFBitOldTestControlEntry
        MAX-ACCESS not-accessible
        STATUS current
        DESCRIPTION
            "Indicates the control entry for starting or stopping the bit test."
        INDEX{ optixRtnBoardID,optixRtnSubCardID,optixRtnPortID }
        ::= { optixRtnIFBitOldTestControlTable 1 }

    OptixRtnIFBitOldTestControlEntry ::=
        SEQUENCE {
            optixRtnOldIFBitAction
                INTEGER,
            optixRtnOldIFBitMode
                INTEGER,
            optixRtnOldIFBitTimeSpan
                Unsigned32
        }

    -- 1.3.6.1.4.1.2011.2.25.4.40.3.12.5.1.4
    optixRtnOldIFBitAction OBJECT-TYPE
        SYNTAX INTEGER
        {
            stop(0),
            start(1)
        }
        MAX-ACCESS read-write
        STATUS current
        DESCRIPTION
            "Indicates an action in the bit test.
0-stop the test
1-start the test"
        ::= { optixRtnIFBitOldTestControlEntry 4 }

    -- 1.3.6.1.4.1.2011.2.25.4.40.3.12.5.1.5
    optixRtnOldIFBitMode OBJECT-TYPE
        SYNTAX INTEGER
        {
            shortTerm(1),
            longTerm(2),
            longlongTerm(3)
        }
        MAX-ACCESS read-write
        STATUS current
        DESCRIPTION
            "Indicates the bit test mode. 
1-short_term (short-term test, measured in seconds)
2-long_term (long-term test, measured in 10 minutes)
3-longlong_term (super-long-term test, measured in hours)"
        ::= { optixRtnIFBitOldTestControlEntry 5 }

    -- 1.3.6.1.4.1.2011.2.25.4.40.3.12.5.1.6
    optixRtnOldIFBitTimeSpan OBJECT-TYPE
        SYNTAX Unsigned32
        MAX-ACCESS read-write
        STATUS current
        DESCRIPTION
            "Indicates the bit test duration. 
Value range: 1-255
The test duration is measured in seconds in short-term tests, 10 minutes in long-term tests, and hours in super-long-term tests."
        ::= { optixRtnIFBitOldTestControlEntry 6 }

    -- 1.3.6.1.4.1.2011.2.25.4.40.3.12.6
    optixRtnIFBitOldTestResultTable OBJECT-TYPE
        SYNTAX SEQUENCE OF OptixRtnIFBitOldTestResultEntry
        MAX-ACCESS not-accessible
        STATUS current
        DESCRIPTION
            "Indicates the bit test result"
        ::= { optixIFPRBSMgr 6 }

    -- 1.3.6.1.4.1.2011.2.25.4.40.3.12.6.1
    optixRtnIFBitOldTestResultEntry OBJECT-TYPE
        SYNTAX OptixRtnIFBitOldTestResultEntry
        MAX-ACCESS not-accessible
        STATUS current
        DESCRIPTION
            "Indicates the bit test result"
        INDEX{ optixRtnBoardID,optixRtnSubCardID,optixRtnPortID }
        ::= { optixRtnIFBitOldTestResultTable 1 }

    OptixRtnIFBitOldTestResultEntry ::=
        SEQUENCE {
            optixRtnOldIFBitResultMode
                INTEGER,
            optixRtnOldIFBitSTY
                Unsigned32,
            optixRtnOldIFBitSTMon
                Unsigned32,
            optixRtnOldIFBitSTD
                Unsigned32,
            optixRtnOldIFBitSTH
                Unsigned32,
            optixRtnOldIFBitSTMin
                Unsigned32,
            optixRtnOldIFBitSTS
                Unsigned32,
            optixRtnOldIFBitPeriodNum
                Unsigned32,
            optixRtnOldIFBitSerialNo
                Unsigned32,
            optixRtnOldIFBitErrNum
                Unsigned32
        }

    -- 1.3.6.1.4.1.2011.2.25.4.40.3.12.6.1.4
    optixRtnOldIFBitResultMode OBJECT-TYPE
        SYNTAX INTEGER
        {
            shortTerm(1),
            longTerm(2),
            longlongTerm(3)
        }
        MAX-ACCESS read-only
        STATUS current
        DESCRIPTION
            "Indicates the test type. 
1: short-term test
2: long-term test
3: super long-term test"
        ::= { optixRtnIFBitOldTestResultEntry 4 }

    -- 1.3.6.1.4.1.2011.2.25.4.40.3.12.6.1.5
    optixRtnOldIFBitSTY OBJECT-TYPE
        SYNTAX Unsigned32
        MAX-ACCESS read-only
        STATUS current
        DESCRIPTION
            "Indicates the testing timeyear."   
        ::= { optixRtnIFBitOldTestResultEntry 5 }

    -- 1.3.6.1.4.1.2011.2.25.4.40.3.12.6.1.6
    optixRtnOldIFBitSTMon OBJECT-TYPE
        SYNTAX Unsigned32
        MAX-ACCESS read-only
        STATUS current
        DESCRIPTION
            "Indicates the testing timemonth."
        ::= { optixRtnIFBitOldTestResultEntry 6 }

    -- 1.3.6.1.4.1.2011.2.25.4.40.3.12.6.1.7
    optixRtnOldIFBitSTD OBJECT-TYPE
        SYNTAX Unsigned32
        MAX-ACCESS read-only
        STATUS current
        DESCRIPTION
            "Indicates the testing timeday."
        ::= { optixRtnIFBitOldTestResultEntry 7 }

    -- 1.3.6.1.4.1.2011.2.25.4.40.3.12.6.1.8
    optixRtnOldIFBitSTH OBJECT-TYPE
        SYNTAX Unsigned32
        MAX-ACCESS read-only
        STATUS current
        DESCRIPTION
            "Indicates the testing timehour."
        ::= { optixRtnIFBitOldTestResultEntry 8 }

    -- 1.3.6.1.4.1.2011.2.25.4.40.3.12.6.1.9
    optixRtnOldIFBitSTMin OBJECT-TYPE
        SYNTAX Unsigned32
        MAX-ACCESS read-only
        STATUS current
        DESCRIPTION
            "Indicates the testing timeminute."
        ::= { optixRtnIFBitOldTestResultEntry 9 }

    -- 1.3.6.1.4.1.2011.2.25.4.40.3.12.6.1.10
    optixRtnOldIFBitSTS OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitOldTestResultEntry 10 }
		
    -- 1.3.6.1.4.1.2011.2.25.4.40.3.12.6.1.11
    optixRtnOldIFBitPeriodNum OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitOldTestResultEntry 11 }
		
    -- 1.3.6.1.4.1.2011.2.25.4.40.3.12.6.1.12
    optixRtnOldIFBitSerialNo OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitOldTestResultEntry 12 }
		
    -- 1.3.6.1.4.1.2011.2.25.4.40.3.12.6.1.13
    optixRtnOldIFBitErrNum OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnIFBitOldTestResultEntry 13 }
		
    -- 1.3.6.1.4.1.2011.2.25.4.40.3.13
    optixE1PRBSMgr OBJECT IDENTIFIER ::= { optixRtnIFBoardAttr 13 }

    -- 1.3.6.1.4.1.2011.2.25.4.40.3.13.1
    optixRtnE1PRBSControlTable OBJECT-TYPE
        SYNTAX SEQUENCE OF OptixRtnE1PRBSControlEntry
        MAX-ACCESS not-accessible
        STATUS current
        DESCRIPTION
            "Indicates the control table for starting or stopping the PRBS test."
        ::= { optixE1PRBSMgr 1 }

    -- 1.3.6.1.4.1.2011.2.25.4.40.3.13.1.1
    optixRtnE1PRBSControlEntry OBJECT-TYPE
        SYNTAX OptixRtnE1PRBSControlEntry
        MAX-ACCESS not-accessible
        STATUS current
        DESCRIPTION
            "Indicates the control entry for starting or stopping the PRBS test."
        INDEX{ optixRtnBoardID,optixRtnSubCardID,optixRtnPortID }
        ::= { optixRtnE1PRBSControlTable 1 }

    OptixRtnE1PRBSControlEntry ::=
        SEQUENCE {
            optixRtnE1PRBSControlPathId
                Unsigned32,
            optixRtnE1PRBSControlDirection
                INTEGER,
            optixRtnE1PRBSAction
                INTEGER,
            optixRtnE1PRBSControlMode
                INTEGER,
            optixRtnE1PRBSTimeSpan
                Unsigned32
        }

    -- 1.3.6.1.4.1.2011.2.25.4.40.3.13.1.1.2
    optixRtnE1PRBSControlPathId OBJECT-TYPE
        SYNTAX Unsigned32
        MAX-ACCESS read-write
        STATUS current
        DESCRIPTION
            "Indicates the ID of a path used in the PRBS test. Set the parameter to 0 if this field is not in use (applicable to RTN 310/320/360/380/380H working in Ethernet mode).Set the parameter to 0 for an RTN 380 working in CPRI mode. The value 0 corresponds to port 3.Set the parameter to 0, 1, 2 for an RTN 380H working in CPRI or OBSAI mode. The values 0, 1, 2 correspond to ports 5, 4, 3, respectively."
        ::= { optixRtnE1PRBSControlEntry 2 }

    -- 1.3.6.1.4.1.2011.2.25.4.40.3.13.1.1.3
    optixRtnE1PRBSControlDirection OBJECT-TYPE
        SYNTAX INTEGER
        {
            ingress(1),
            egress(2)
        }
        MAX-ACCESS read-write
        STATUS current
        DESCRIPTION
            "Indicates the PRBS test direction. 
1-Ingress
2-Egress"
        ::= { optixRtnE1PRBSControlEntry 3 }

    -- 1.3.6.1.4.1.2011.2.25.4.40.3.13.1.1.4
    optixRtnE1PRBSAction OBJECT-TYPE
        SYNTAX INTEGER
        {
            stop(0),
            start(1)
        }
        MAX-ACCESS read-write
        STATUS current
        DESCRIPTION
            "Indicates an action in the PRBS test.
0-stop the test
1-start the test"
        ::= { optixRtnE1PRBSControlEntry 4 }

    -- 1.3.6.1.4.1.2011.2.25.4.40.3.13.1.1.5
    optixRtnE1PRBSControlMode OBJECT-TYPE
        SYNTAX INTEGER
        {
            shortTerm(1),
            longTerm(2),
            longlongTerm(3)
        }
        MAX-ACCESS read-write
        STATUS current
        DESCRIPTION
            "Indicates the PRBS test mode. 
1-short_term (short-term test, measured in seconds)
2-long_term (long-term test, measured in 10 minutes)
3-superlong_term (super-long-term test, measured in hours)"
        ::= { optixRtnE1PRBSControlEntry 5 }

    -- 1.3.6.1.4.1.2011.2.25.4.40.3.13.1.1.6
    optixRtnE1PRBSTimeSpan OBJECT-TYPE
        SYNTAX Unsigned32
        MAX-ACCESS read-write
        STATUS current
        DESCRIPTION
            "Indicates the PRBS test duration. 
Value range: 1-255
The test duration is measured in seconds in short-term tests, 10 minutes in long-term tests, and hours in super-long-term tests."
        ::= { optixRtnE1PRBSControlEntry 6 }

    -- 1.3.6.1.4.1.2011.2.25.4.40.3.13.2
    optixRtnE1PRBSResultTable OBJECT-TYPE
        SYNTAX SEQUENCE OF OptixRtnE1PRBSResultEntry
        MAX-ACCESS not-accessible
        STATUS current
        DESCRIPTION
            "Indicates the PRBS test result"
        ::= { optixE1PRBSMgr 2 }

    -- 1.3.6.1.4.1.2011.2.25.4.40.3.13.2.1
    optixRtnE1PRBSResultEntry OBJECT-TYPE
        SYNTAX OptixRtnE1PRBSResultEntry
        MAX-ACCESS not-accessible
        STATUS current
        DESCRIPTION
            "Indicates the PRBS test result"
        INDEX{ optixRtnBoardID,optixRtnSubCardID,optixRtnPortID }
        ::= { optixRtnE1PRBSResultTable 1 }

    OptixRtnE1PRBSResultEntry ::=
        SEQUENCE {
            optixRtnE1PRBSPathId
                Unsigned32,
            optixRtnE1PRBSDirection
                INTEGER,
            optixRtnE1PRBSMode
                INTEGER,
            optixRtnE1PRBSStartTime
                OCTET STRING,
            optixRtnE1PRBSEndTime
                OCTET STRING,
            optixRtnE1PRBSProgress
                Unsigned32,
			optixRtnE1PRBSRealTestPeriod
                Unsigned32,
            optixRtnE1PRBSDataTypeNum
                Unsigned32,
            optixRtnE1PRBSType1
                Unsigned32,
            optixRtnE1PRBSTestResult1
                Unsigned32,
            optixRtnE1PRBSType2
                Unsigned32,
            optixRtnE1PRBSTestResult2
                Unsigned32,
            optixRtnE1PRBSType3
                Unsigned32,
            optixRtnE1PRBSTestResult3
                Unsigned32,
            optixRtnE1PRBSType4
                Unsigned32,
            optixRtnE1PRBSTestResult4
                Unsigned32,
            optixRtnE1PRBSType5
                Unsigned32,
            optixRtnE1PRBSTestResult5
                Unsigned32,
            optixRtnE1PRBSType6
                Unsigned32,
            optixRtnE1PRBSTestResult6
                Unsigned32
        }

    -- 1.3.6.1.4.1.2011.2.25.4.40.3.13.2.1.1
    optixRtnE1PRBSPathId OBJECT-TYPE
        SYNTAX Unsigned32
        MAX-ACCESS read-only
        STATUS current
        DESCRIPTION
            "Indicates the path ID.
Set the parameter to 0 if this field is not in use."
        ::= { optixRtnE1PRBSResultEntry 1 }

    -- 1.3.6.1.4.1.2011.2.25.4.40.3.13.2.1.2
    optixRtnE1PRBSDirection OBJECT-TYPE
        SYNTAX INTEGER
        {
            ingressDir(1),
            egressDir(2)
        }
        MAX-ACCESS read-only
        STATUS current
        DESCRIPTION
            "Indicates the test direction:
1-Ingress
2-Egress"
        ::= { optixRtnE1PRBSResultEntry 2 }

    -- 1.3.6.1.4.1.2011.2.25.4.40.3.13.2.1.3
    optixRtnE1PRBSMode OBJECT-TYPE
        SYNTAX INTEGER
        {
            shortTerm(1),
            longTerm(2),
            longlongTerm(3)
        }
        MAX-ACCESS read-only
        STATUS current
        DESCRIPTION
            "Indicates the test type. 
1: short-term test
2: long-term test
3: super long-term test"
        ::= { optixRtnE1PRBSResultEntry 3 }

    -- 1.3.6.1.4.1.2011.2.25.4.40.3.13.2.1.4
    optixRtnE1PRBSStartTime OBJECT-TYPE
        SYNTAX OCTET STRING
        MAX-ACCESS read-only
        STATUS current
        DESCRIPTION
            "Indicates the start time of a test in the format of YYYYMMDDHHMMSS and the time starts from the year 1990."
        ::= { optixRtnE1PRBSResultEntry 4 }

    -- 1.3.6.1.4.1.2011.2.25.4.40.3.13.2.1.5
    optixRtnE1PRBSEndTime OBJECT-TYPE
        SYNTAX OCTET STRING
        MAX-ACCESS read-only
        STATUS current
        DESCRIPTION
            "Indicates the end time of a test in the format of YYYYMMDDHHMMSS and the time starts from the year 1990."
        ::= { optixRtnE1PRBSResultEntry 5 }

    -- 1.3.6.1.4.1.2011.2.25.4.40.3.13.2.1.6
    optixRtnE1PRBSProgress OBJECT-TYPE
        SYNTAX Unsigned32
        MAX-ACCESS read-only
        STATUS current
        DESCRIPTION
            "Indicates the test progress. Value range: 1-100"
        ::= { optixRtnE1PRBSResultEntry 6 }
		
	-- 1.3.6.1.4.1.2011.2.25.4.40.3.13.2.1.7
    optixRtnE1PRBSRealTestPeriod OBJECT-TYPE
        SYNTAX Unsigned32
        MAX-ACCESS read-only
        STATUS current
        DESCRIPTION
           "Indicates the real test period of test .Value range: 1-255."
        ::= { optixRtnE1PRBSResultEntry 7 }

    -- 1.3.6.1.4.1.2011.2.25.4.40.3.13.2.1.8
    optixRtnE1PRBSDataTypeNum OBJECT-TYPE
        SYNTAX Unsigned32
        MAX-ACCESS read-only
        STATUS current
        DESCRIPTION
            "Indicates the number of parameter types N (N >= 1 and currently N = 6). The data types are described as follows:"
        ::= { optixRtnE1PRBSResultEntry 8 }

    -- 1.3.6.1.4.1.2011.2.25.4.40.3.13.2.1.9
    optixRtnE1PRBSType1 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnE1PRBSResultEntry 9 }

    -- 1.3.6.1.4.1.2011.2.25.4.40.3.13.2.1.10
    optixRtnE1PRBSTestResult1 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnE1PRBSResultEntry 10 }

    -- 1.3.6.1.4.1.2011.2.25.4.40.3.13.2.1.11
    optixRtnE1PRBSType2 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnE1PRBSResultEntry 11 }

    -- 1.3.6.1.4.1.2011.2.25.4.40.3.13.2.1.12
    optixRtnE1PRBSTestResult2 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnE1PRBSResultEntry 12 }

    -- 1.3.6.1.4.1.2011.2.25.4.40.3.13.2.1.13
    optixRtnE1PRBSType3 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnE1PRBSResultEntry 13 }

    -- 1.3.6.1.4.1.2011.2.25.4.40.3.13.2.1.14
    optixRtnE1PRBSTestResult3 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnE1PRBSResultEntry 14 }

    -- 1.3.6.1.4.1.2011.2.25.4.40.3.13.2.1.15
    optixRtnE1PRBSType4 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnE1PRBSResultEntry 15 }

    -- 1.3.6.1.4.1.2011.2.25.4.40.3.13.2.1.16
    optixRtnE1PRBSTestResult4 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnE1PRBSResultEntry 16 }

    -- 1.3.6.1.4.1.2011.2.25.4.40.3.13.2.1.17
    optixRtnE1PRBSType5 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnE1PRBSResultEntry 17 }

    -- 1.3.6.1.4.1.2011.2.25.4.40.3.13.2.1.18
        optixRtnE1PRBSTestResult5 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnE1PRBSResultEntry 18 }

    -- 1.3.6.1.4.1.2011.2.25.4.40.3.13.2.1.19
    optixRtnE1PRBSType6 OBJECT-TYPE
        SYNTAX Unsigned32
        MAX-ACCESS read-only
        STATUS current
        DESCRIPTION
            "The data types are as follows:
1: number of bit errors
2: BER (calculated based on the number of bit errors)
3: errored second
4: severely errored second
5: unavailable second
6: background block error"
        ::= { optixRtnE1PRBSResultEntry 19 }

    -- 1.3.6.1.4.1.2011.2.25.4.40.3.13.2.1.20
    optixRtnE1PRBSTestResult6 OBJECT-TYPE
        SYNTAX Unsigned32
        MAX-ACCESS read-only
        STATUS current
        DESCRIPTION
            "Indicates the statistics. 
Each 5-byte string represents the accumulative value for a certain type of statistics data. The first byte indicates the data type and the other four bytes indicate the accumulative value."
        ::= { optixRtnE1PRBSResultEntry 20 }
		
    -- 1.3.6.1.4.1.2011.2.25.4.40.3.10.117
    optixRtnEthRateBymodTable OBJECT-TYPE
        SYNTAX SEQUENCE OF OptixRtnEthRateBymodEntry
        MAX-ACCESS not-accessible
        STATUS current
        DESCRIPTION
            "Indicates the Eth Rate Bymod"
        ::= { optixISBoardAttr 117 }

	-- 1.3.6.1.4.1.2011.2.25.4.40.3.10.117.1
    optixRtnEthRateBymodEntry OBJECT-TYPE
        SYNTAX OptixRtnEthRateBymodEntry
        MAX-ACCESS not-accessible
        STATUS current
        DESCRIPTION
            "Indicates the index entry for Eth Rate Bymod."
        INDEX{ optixRtnIndex1,optixRtnIndex2,optixRtnIndex3 }
        ::= { optixRtnEthRateBymodTable 1 }

    OptixRtnEthRateBymodEntry ::=
        SEQUENCE {
            optixRtnEthRateBymodBandwidth
                Unsigned32,
            optixRtnEthRateBymodAM
                Unsigned32,
	    optixRtnEthRateBymodE1NUM
                Unsigned32,
	    optixRtnEthRate
		Unsigned32
        }	

    -- 1.3.6.1.4.1.2011.2.25.4.40.3.10.117.1.1
    optixRtnEthRateBymodBandwidth OBJECT-TYPE
        SYNTAX Unsigned32
	{
		bw3P5M(1),
		bw7M(2),
		bw14M(3),
		bw28M(4),
		bw40M(5),
		bw56M(6),
		bwFcc30M(7),
		bwFcc40M(8),
		bwFcc50M(9),
		bw112M(23),
		bwFcc10M(24),
		bwFcc20M(25),
		bwFcc60M(28),
		bw14MACCP(30),
		bw28MACCP(31),
		bw56MACCP(32),
		bw112MACCP(33),
		bw80M(34)
	}
        MAX-ACCESS read-write
        STATUS current
        DESCRIPTION
            "Indicates the Eth Rate Bymod Bandwidth."
        ::= { optixRtnEthRateBymodEntry 1 }

    -- 1.3.6.1.4.1.2011.2.25.4.40.3.10.117.1.2
    optixRtnEthRateBymodAM OBJECT-TYPE
        SYNTAX Unsigned32
	{
		amQPSK(1),
		am16QAM(2),
		am32QAM(3),
		am64QAM(4),
		am128QAM(5),
		am256QAM(6),
		am512QAM(7),
		am1204QAM(8),
		amQPSKSTRONG(9),
		am16QAMSTRONG(10),
		am512QAMLIGHT(11),
		am1024QAMLIGHT(12),
		am2048QAM(13),
		am4096QAM(20),
                am2048QAMLIGHT(28),
                am8192QAM(32)
	}
        MAX-ACCESS read-write
        STATUS current
        DESCRIPTION
            "Indicates the Eth Rate Bymod AM."
        ::= { optixRtnEthRateBymodEntry 2 }

    -- 1.3.6.1.4.1.2011.2.25.4.40.3.10.117.1.3
    optixRtnEthRateBymodE1NUM OBJECT-TYPE
        SYNTAX Unsigned32
        MAX-ACCESS read-write
        STATUS current
        DESCRIPTION
            "Indicates the Rate Bymod E1 number."
        ::= { optixRtnEthRateBymodEntry 3 }	
		
    -- 1.3.6.1.4.1.2011.2.25.4.40.3.10.117.1.4
    optixRtnEthRate OBJECT-TYPE
        SYNTAX Unsigned32
        MAX-ACCESS read-only
        STATUS current
        DESCRIPTION
            "Indicates the Eth Rate."
        ::= { optixRtnEthRateBymodEntry 4 }
		
    -- 1.3.6.1.4.1.2011.2.25.4.40.3.10.119
    optixRtnHybridCapacityTable OBJECT-TYPE
        SYNTAX SEQUENCE OF OptixRtnHybridCapacityEntry
        MAX-ACCESS not-accessible
        STATUS current
        DESCRIPTION
            "Indicates the Hybrid Capacity value"
        ::= { optixISBoardAttr 119 }

    -- 1.3.6.1.4.1.2011.2.25.4.40.3.10.119.1
    optixRtnHybridCapacityEntry OBJECT-TYPE
        SYNTAX OptixRtnHybridCapacityEntry
        MAX-ACCESS not-accessible
        STATUS current
        DESCRIPTION
            "Indicates the index entry."
        INDEX{ optixRtnIndex1,optixRtnIndex2,optixRtnIndex3,optixRtnIndex4 }
        ::= { optixRtnHybridCapacityTable 1 }

    OptixRtnHybridCapacityEntry ::=
        SEQUENCE {
            optixRtnHybridE1Capacity
                Unsigned32,
	    optixRtnHybridETHCapacity
                Unsigned32,
            optixRtnHybridPKTLength
                Unsigned32,
            optixRtnHybridPKTThroughput
                Unsigned32				
        }	

    -- 1.3.6.1.4.1.2011.2.25.4.40.3.10.119.1.5
    optixRtnHybridE1Capacity OBJECT-TYPE
        SYNTAX Unsigned32
        MAX-ACCESS read-only
        STATUS current
        DESCRIPTION
            "Hybrid E1-Capacity."
        ::= { optixRtnHybridCapacityEntry 5 }	

    -- 1.3.6.1.4.1.2011.2.25.4.40.3.10.119.1.6
    optixRtnHybridETHCapacity OBJECT-TYPE
        SYNTAX Unsigned32
        MAX-ACCESS read-only
        STATUS current
        DESCRIPTION
            "Hybrid ETH-Capacity."
        ::= { optixRtnHybridCapacityEntry 6 }

    -- 1.3.6.1.4.1.2011.2.25.4.40.3.10.119.1.7
    optixRtnHybridPKTLength OBJECT-TYPE
        SYNTAX Unsigned32
        MAX-ACCESS read-only
        STATUS current
        DESCRIPTION
            "Hybrid PKT-Length."
        ::= { optixRtnHybridCapacityEntry 7 }

    -- 1.3.6.1.4.1.2011.2.25.4.40.3.10.119.1.8
    optixRtnHybridPKTThroughput OBJECT-TYPE
        SYNTAX Unsigned32
        MAX-ACCESS read-only
        STATUS current
        DESCRIPTION
            "Hybrid PKT-Throughput."
        ::= { optixRtnHybridCapacityEntry 8 }		
		
 -- 1.3.6.1.4.1.2011.2.25.4.40.3.10.120
    optixRtnLinkDelayStateTable OBJECT-TYPE
        SYNTAX SEQUENCE OF OptixRtnLinkDelayStateEntry
        MAX-ACCESS not-accessible
        STATUS current
        DESCRIPTION
            "Indicates the LinkDelay Status Table."
        ::= { optixISBoardAttr 120 }

	-- 1.3.6.1.4.1.2011.2.25.4.40.3.10.120.1
    optixRtnLinkDelayStateEntry OBJECT-TYPE
        SYNTAX OptixRtnLinkDelayStateEntry
        MAX-ACCESS not-accessible
        STATUS current
        DESCRIPTION
            "Indicates the LinkDelay Status Entry."
        INDEX{ optixRtnBoardID,optixRtnSubCardID,optixRtnPortID }
        ::= { optixRtnLinkDelayStateTable 1 }

    OptixRtnLinkDelayStateEntry ::=
        SEQUENCE {
            optixRtnLinkDelayStateSwitch
                Unsigned32				
        }	

    -- 1.3.6.1.4.1.2011.2.25.4.40.3.10.120.1.4
    optixRtnLinkDelayStateSwitch OBJECT-TYPE
        SYNTAX Unsigned32
        {
            normal(0),
            lowdelay(1)
        }
        MAX-ACCESS read-write
        STATUS current
        DESCRIPTION
            "The delay state."
        ::= { optixRtnLinkDelayStateEntry 4 }	

    -- 1.3.6.1.4.1.2011.2.25.4.40.3.10.130
    optixRtnLpAlm2AisTable OBJECT-TYPE
        SYNTAX SEQUENCE OF OptixRtnLpAlm2AisEntry
        MAX-ACCESS not-accessible
        STATUS current
        DESCRIPTION
            "Indicates the Alm Status Table"
        ::= { optixISBoardAttr 130 }

    -- 1.3.6.1.4.1.2011.2.25.4.40.3.10.130.1
    optixRtnLpAlm2AisEntry OBJECT-TYPE
        SYNTAX OptixRtnLpAlm2AisEntry
        MAX-ACCESS not-accessible
        STATUS current
        DESCRIPTION
            "Indicates the Alm Status Entry"
        INDEX{ optixRtnBoardID,optixRtnSubCardID,optixRtnPortID,optixRtnIFPortHPid,optixRtnIFPortAlmID }
        ::= { optixRtnLpAlm2AisTable 1 }

    OptixRtnLpAlm2AisEntry ::=
        SEQUENCE {
            optixRtnLpAlm2AisSwitch
                Unsigned32
        }

    -- 1.3.6.1.4.1.2011.2.25.4.40.3.10.130.1.6
    optixRtnLpAlm2AisSwitch OBJECT-TYPE
        SYNTAX Unsigned32
        {
            disable(0),
            enable(1)
        }
        MAX-ACCESS read-write
        STATUS current
        DESCRIPTION
            "Alm Status"
        ::= { optixRtnLpAlm2AisEntry 6 }
		
END
