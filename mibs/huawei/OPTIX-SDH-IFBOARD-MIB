-- OPTIX-SDH-IFBOARD-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-IFBOARD-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        optixSdhHP,optixSdhLP
            FROM OPTIX-SDH-LINEBOARD-MIB
        optixPortId
            FROM OPTIX-PORT-MANAGE-MIB
        ;

    optixIfBoard MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations of IF board management."
        REVISION "201204200000Z"
        DESCRIPTION
            "The initial revision of this MIB module1."
        ::={ optixProvisionSdh 39 }

    -- 1.3.6.1.4.1.2011.2.25.4.10.39.1
    optixIfBoardGroup OBJECT IDENTIFIER ::= { optixIfBoard 1 }

    -- 1.3.6.1.4.1.2011.2.25.4.10.39.1.1
    optixSdhIfBoardTable OBJECT-TYPE
        SYNTAX SEQUENCE OF OptixSdhIfBoardEntry
        MAX-ACCESS not-accessible
        STATUS current
        DESCRIPTION
            "This table describes the enable status ofoverhead byte managementfor the SDH IF board."
        ::= { optixIfBoardGroup 1 }

    -- 1.3.6.1.4.1.2011.2.25.4.10.39.1.1.1
    optixSdhIfBoardEntry OBJECT-TYPE
        SYNTAX OptixSdhIfBoardEntry
        MAX-ACCESS not-accessible
        STATUS current
        DESCRIPTION
            "Thisentry describes the enable status ofoverhead byte managementfor the SDH IF board."
        INDEX{ optixLogBoardId }
        ::= { optixSdhIfBoardTable 1 }

    OptixSdhIfBoardEntry ::=
        SEQUENCE {
            optixSdhIfBoardTohEnable
                INTEGER
        }

    -- 1.3.6.1.4.1.2011.2.25.4.10.39.1.1.1.1
    optixSdhIfBoardTohEnable OBJECT-TYPE
        SYNTAX INTEGER
        {
            disable(0),
            enable(1)
        }
        MAX-ACCESS read-write
        STATUS current
        DESCRIPTION
            "This object indicates the enable status ofoverhead byte management for the SDH IF board. 0: disable, 1: enable"
        ::= { optixSdhIfBoardEntry 1 }

    -- 1.3.6.1.4.1.2011.2.25.4.10.39.1.2
    optixSdhIFBoardVC12Table OBJECT-TYPE
        SYNTAX SEQUENCE OF OptixSdhIFBoardVC12Entry
        MAX-ACCESS not-accessible
        STATUS current
        DESCRIPTION
            "This table describes configurations of VC12 timeslot management of the SDH IF board."
        ::= { optixIfBoardGroup 2 }

    -- 1.3.6.1.4.1.2011.2.25.4.10.39.1.2.1
    optixSdhIFBoardVC12Entry OBJECT-TYPE
        SYNTAX OptixSdhIFBoardVC12Entry
        MAX-ACCESS not-accessible
        STATUS current
        DESCRIPTION
            "This entry describes configurations of VC12 timeslot management of the SDH IF board."
        INDEX{ optixLogBoardId,optixLogSubCardId,optixPortId,optixSdhHP,optixSdhLP }
        ::= { optixSdhIFBoardVC12Table 1 }

    OptixSdhIFBoardVC12Entry ::=
        SEQUENCE {
            optixSdhIFBoardE1ToTuais
                INTEGER,
            optixSdhIFBoardSRJ2Mode
                Unsigned32,
            optixSdhIFBoardSRJ2Value
                OCTET STRING,
            optixSdhIFBoardSTJ2Mode
                Unsigned32,
            optixSdhIFBoardSTJ2Value
                OCTET STRING,
            optixSdhIFBoardSRV5Value
                Unsigned32,
            optixSdhIFBoardSTV5Value
                Unsigned32,
            optixSdhIFBoardRJ2Mode
                Unsigned32,
            optixSdhIFBoardRJ2Value
                OCTET STRING,
            optixSdhIFBoardRV5Value
                Unsigned32
        }

    -- 1.3.6.1.4.1.2011.2.25.4.10.39.1.2.1.1
    optixSdhIFBoardE1ToTuais OBJECT-TYPE
        SYNTAX INTEGER
        {
            disable(0),
            enable(1),
            auto(2)
        }
        MAX-ACCESS read-write
        STATUS current
        DESCRIPTION
            "This object indicates the enable status of E1_AIS to TU_AIS for the SDH IF board. 0: disable, 1: enable, 2: auto"
        ::= { optixSdhIFBoardVC12Entry 1 }

    -- 1.3.6.1.4.1.2011.2.25.4.10.39.1.2.1.2
    optixSdhIFBoardSRJ2Mode OBJECT-TYPE
        SYNTAX Unsigned32
        MAX-ACCESS read-write
        STATUS current
        DESCRIPTION
            "This object indicates the J2 byte to be received mode ."
        ::= { optixSdhIFBoardVC12Entry 2 }

    -- 1.3.6.1.4.1.2011.2.25.4.10.39.1.2.1.3
    optixSdhIFBoardSRJ2Value OBJECT-TYPE
        SYNTAX OCTET STRING (SIZE(0..16))
        MAX-ACCESS read-write
        STATUS current
        DESCRIPTION
            "This object indicates the value of the J2 byte to be received."
        ::= { optixSdhIFBoardVC12Entry 3 }

    -- 1.3.6.1.4.1.2011.2.25.4.10.39.1.2.1.4
    optixSdhIFBoardSTJ2Mode OBJECT-TYPE
        SYNTAX Unsigned32
        MAX-ACCESS read-write
        STATUS current
        DESCRIPTION
            "This object indicates the J2 byte to be transmitted mode ."
        ::= { optixSdhIFBoardVC12Entry 4 }

    -- 1.3.6.1.4.1.2011.2.25.4.10.39.1.2.1.5
    optixSdhIFBoardSTJ2Value OBJECT-TYPE
        SYNTAX OCTET STRING (SIZE(0..16))
        MAX-ACCESS read-write
        STATUS current
        DESCRIPTION
            "This object indicates the value of the J2 byte to be transmitted."
        ::= { optixSdhIFBoardVC12Entry 5 }

    -- 1.3.6.1.4.1.2011.2.25.4.10.39.1.2.1.6
    optixSdhIFBoardSRV5Value OBJECT-TYPE
        SYNTAX Unsigned32
        MAX-ACCESS read-write
        STATUS current
        DESCRIPTION
            "This object indicates the value of theV5 byte to be received."
        ::= { optixSdhIFBoardVC12Entry 6 }

    -- 1.3.6.1.4.1.2011.2.25.4.10.39.1.2.1.7
    optixSdhIFBoardSTV5Value OBJECT-TYPE
        SYNTAX Unsigned32
        MAX-ACCESS read-write
        STATUS current
        DESCRIPTION
            "This object indicates the value of theV5 byte to be transmitted."
        ::= { optixSdhIFBoardVC12Entry 7 }

    -- 1.3.6.1.4.1.2011.2.25.4.10.39.1.2.1.8
    optixSdhIFBoardRJ2Mode OBJECT-TYPE
        SYNTAX Unsigned32
        MAX-ACCESS read-only
        STATUS current
        DESCRIPTION
            "This object indicates the received J2 byte mode"
        ::= { optixSdhIFBoardVC12Entry 8 }

    -- 1.3.6.1.4.1.2011.2.25.4.10.39.1.2.1.9
    optixSdhIFBoardRJ2Value OBJECT-TYPE
        SYNTAX OCTET STRING (SIZE(0..16))
        MAX-ACCESS read-only
        STATUS current
        DESCRIPTION
            "This object indicates the value of the received J2 byte"
        ::= { optixSdhIFBoardVC12Entry 9 }

    -- 1.3.6.1.4.1.2011.2.25.4.10.39.1.2.1.10
    optixSdhIFBoardRV5Value OBJECT-TYPE
        SYNTAX Unsigned32
        MAX-ACCESS read-only
        STATUS current
        DESCRIPTION
            "This object indicates the value of the received V5 byte"
        ::= { optixSdhIFBoardVC12Entry 10 }

    -- 1.3.6.1.4.1.2011.2.25.4.10.39.1.3
    optixSdhIfBoardVC4Table OBJECT-TYPE
        SYNTAX SEQUENCE OF OptixSdhIfBoardVC4Entry
        MAX-ACCESS not-accessible
        STATUS current
        DESCRIPTION
            "This table describes configurations ofVC4 timeslot management of the SDH If board."
        ::= { optixIfBoardGroup 3 }

    -- 1.3.6.1.4.1.2011.2.25.4.10.39.1.3.1
    optixSdhIfBoardVC4Entry OBJECT-TYPE
        SYNTAX OptixSdhIfBoardVC4Entry
        MAX-ACCESS not-accessible
        STATUS current
        DESCRIPTION
            "Thisentry describes configurations of VC4 timeslot management of the SDH If board."
        INDEX{ optixLogBoardId,optixLogSubCardId,optixPortId,optixSdhIfHP }
        ::= { optixSdhIfBoardVC4Table 1 }

    OptixSdhIfBoardVC4Entry ::=
        SEQUENCE {
            optixSdhIfHP
                Unsigned32,
            optixSdhIfBoardSRJ1Mode
                Unsigned32,
            optixSdhIfBoardSRJ1Value
                OCTET STRING,
            optixSdhIfBoardSTJ1Mode
                Unsigned32,
            optixSdhIfBoardSTJ1Value
                OCTET STRING,
            optixSdhIfBoardRJ1Mode
                Unsigned32,
            optixSdhIfBoardRJ1Value
                OCTET STRING,
            optixSdhIfBoardSRC2Value
                INTEGER,
            optixSdhIfBoardSTC2Value
                INTEGER,
            optixSdhIfBoardRC2Value
                INTEGER,
            optixSdhIfBoardPassmode
                INTEGER,
            optixSdhIfBoardSRJ1Mask
                OCTET STRING,
            optixSdhIfBoardSTJ1Mask
                OCTET STRING
        }

    -- 1.3.6.1.4.1.2011.2.25.4.10.39.1.3.1.1
    optixSdhIfHP OBJECT-TYPE
        SYNTAX Unsigned32
        MAX-ACCESS not-accessible
        STATUS current
        DESCRIPTION
            "This object indicates the high-order channel ID."
        ::= { optixSdhIfBoardVC4Entry 1 }

    -- 1.3.6.1.4.1.2011.2.25.4.10.39.1.3.1.2
    optixSdhIfBoardSRJ1Mode OBJECT-TYPE
        SYNTAX Unsigned32
        MAX-ACCESS read-write
        STATUS current
        DESCRIPTION
            "This object indicates the J1 byte to be received mode ."
        ::= { optixSdhIfBoardVC4Entry 2 }

    -- 1.3.6.1.4.1.2011.2.25.4.10.39.1.3.1.3
    optixSdhIfBoardSRJ1Value OBJECT-TYPE
        SYNTAX OCTET STRING (SIZE(0..64))
        MAX-ACCESS read-write
        STATUS current
        DESCRIPTION
            "This object indicates the value of the J1 byte to be received."
        ::= { optixSdhIfBoardVC4Entry 3 }

    -- 1.3.6.1.4.1.2011.2.25.4.10.39.1.3.1.4
    optixSdhIfBoardSTJ1Mode OBJECT-TYPE
        SYNTAX Unsigned32
        MAX-ACCESS read-write
        STATUS current
        DESCRIPTION
            "This object indicates the J1 byte to be transmitted mode ."
        ::= { optixSdhIfBoardVC4Entry 4 }

    -- 1.3.6.1.4.1.2011.2.25.4.10.39.1.3.1.5
    optixSdhIfBoardSTJ1Value OBJECT-TYPE
        SYNTAX OCTET STRING (SIZE(0..64))
        MAX-ACCESS read-write
        STATUS current
        DESCRIPTION
            "This object indicates the value of the J1 byte to be transmitted."
        ::= { optixSdhIfBoardVC4Entry 5 }

    -- 1.3.6.1.4.1.2011.2.25.4.10.39.1.3.1.6
    optixSdhIfBoardRJ1Mode OBJECT-TYPE
        SYNTAX Unsigned32
        MAX-ACCESS read-only
        STATUS current
        DESCRIPTION
            "This object indicates the received J1 byte mode ."
        ::= { optixSdhIfBoardVC4Entry 6 }

    -- 1.3.6.1.4.1.2011.2.25.4.10.39.1.3.1.7
    optixSdhIfBoardRJ1Value OBJECT-TYPE
        SYNTAX OCTET STRING (SIZE(0..64))
        MAX-ACCESS read-only
        STATUS current
        DESCRIPTION
            "This object indicates the value of the received J1 byte."
        ::= { optixSdhIfBoardVC4Entry 7 }

    -- 1.3.6.1.4.1.2011.2.25.4.10.39.1.3.1.8
    optixSdhIfBoardSRC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-write
        STATUS current
        DESCRIPTION
            "This object indicates the value of theC2 byte to be received."
        ::= { optixSdhIfBoardVC4Entry 8 }

    -- 1.3.6.1.4.1.2011.2.25.4.10.39.1.3.1.9
    optixSdhIfBoardSTC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-write
        STATUS current
        DESCRIPTION
            "This object indicates the value of theC2 byte to be transmitted."
        ::= { optixSdhIfBoardVC4Entry 9 }

    -- 1.3.6.1.4.1.2011.2.25.4.10.39.1.3.1.10
    optixSdhIfBoardRC2Value OBJECT-TYPE
        SYNTAX INTEGER
        {
            uneq(0),
            unsp(1),
            tugs(2),
            tulock(3),
            asyn(4),
            develop(5),
            a140(18),
            atm(19),
            man(20),
            fddi(21),
            ppp(22),
            resvp1(23),
            laps(24),
            resvp2(25),
            enet(26),
            gfp(27),
            resv(207),
            resvn1(225),
            resvn2(252),
            test(254),
            ais(255)
        }
        MAX-ACCESS read-only
        STATUS current
        DESCRIPTION
            "This object indicates the value of the receivedC2 byte."
        ::= { optixSdhIfBoardVC4Entry 10 }

    -- 1.3.6.1.4.1.2011.2.25.4.10.39.1.3.1.11
    optixSdhIfBoardPassmode OBJECT-TYPE
        SYNTAX INTEGER
        {
            term(0),
            pass(1),
            auto(2)
        }
        MAX-ACCESS read-write
        STATUS current
        DESCRIPTION
            "This object indicates the overhead processing mode ."
        ::= { optixSdhIfBoardVC4Entry 11 }

    -- 1.3.6.1.4.1.2011.2.25.4.10.39.1.3.1.12
    optixSdhIfBoardSRJ1Mask OBJECT-TYPE
        SYNTAX OCTET STRING (SIZE(0..64))
        MAX-ACCESS read-write
        STATUS current
        DESCRIPTION
            "This object indicates the Mask of J1 byte to be transmitted."
        ::= { optixSdhIfBoardVC4Entry 12 }

    -- 1.3.6.1.4.1.2011.2.25.4.10.39.1.3.1.13
    optixSdhIfBoardSTJ1Mask OBJECT-TYPE
        SYNTAX OCTET STRING
        MAX-ACCESS read-write
        STATUS current
        DESCRIPTION
            "This object indicates the Mask of J1 byte to be transmitted."
        ::= { optixSdhIfBoardVC4Entry 13 }

    -- 1.3.6.1.4.1.2011.2.25.4.10.39.1.4
    optixSdhIfBoardAlmClkswTable OBJECT-TYPE
        SYNTAX SEQUENCE OF OptixSdhIfBoardAlmClkswEntry
        MAX-ACCESS not-accessible
        STATUS current
        DESCRIPTION
            "This table describes configurations ofalarm management of the SDH If board."
        ::= { optixIfBoardGroup 4 }

    -- 1.3.6.1.4.1.2011.2.25.4.10.39.1.4.1
    optixSdhIfBoardAlmClkswEntry OBJECT-TYPE
        SYNTAX OptixSdhIfBoardAlmClkswEntry
        MAX-ACCESS not-accessible
        STATUS current
        DESCRIPTION
            "This entry describes configurations ofalarm management of the SDH If board."
        INDEX{ optixLogBoardId,optixLogSubCardId,optixPortId,optixSdhIfBoardAlmId }
        ::= { optixSdhIfBoardAlmClkswTable 1 }

    OptixSdhIfBoardAlmClkswEntry ::=
        SEQUENCE {
            optixSdhIfBoardAlmId
                INTEGER,
            optixSdhIfBoardClkswEnable
                INTEGER
        }

    -- 1.3.6.1.4.1.2011.2.25.4.10.39.1.4.1.1
    optixSdhIfBoardAlmId OBJECT-TYPE
        SYNTAX INTEGER
        {
            msais(33),
            b2exc(35)
        }
        MAX-ACCESS not-accessible
        STATUS current
        DESCRIPTION
            "This object indicates the alarm ID."
        ::= { optixSdhIfBoardAlmClkswEntry 1 }

    -- 1.3.6.1.4.1.2011.2.25.4.10.39.1.4.1.2
    optixSdhIfBoardClkswEnable OBJECT-TYPE
        SYNTAX INTEGER
        {
            disable(0),
            enable(1)
        }
        MAX-ACCESS read-write
        STATUS current
        DESCRIPTION
            "This object indicates the enable status of the clock switching."
        ::= { optixSdhIfBoardAlmClkswEntry 2 }

    -- 1.3.6.1.4.1.2011.2.25.4.10.39.1.5
    optixSdhIfBoardB1B2B3ThTable OBJECT-TYPE
        SYNTAX SEQUENCE OF OptixSdhIfBoardB1B2B3ThEntry
        MAX-ACCESS not-accessible
        STATUS current
        DESCRIPTION
            "This table describes the configurations of bit error threshold or deterioration threshold."
        ::= { optixIfBoardGroup 5 }

    -- 1.3.6.1.4.1.2011.2.25.4.10.39.1.5.1
    optixSdhIfBoardB1B2B3ThEntry OBJECT-TYPE
        SYNTAX OptixSdhIfBoardB1B2B3ThEntry
        MAX-ACCESS not-accessible
        STATUS current
        DESCRIPTION
            "This entry describes the configurations of the bit error threshold or deterioration threshold."
        INDEX{ optixLogBoardId,optixLogSubCardId,optixPortId,optixSdhIfBoardThType }
        ::= { optixSdhIfBoardB1B2B3ThTable 1 }

    OptixSdhIfBoardB1B2B3ThEntry ::=
        SEQUENCE {
            optixSdhIfBoardThType
                Unsigned32,
            optixSdhIfBoardExecTh
                Unsigned32,
            optixSdhIfBoardSdTh
                Unsigned32
        }

    -- 1.3.6.1.4.1.2011.2.25.4.10.39.1.5.1.1
    optixSdhIfBoardThType OBJECT-TYPE
        SYNTAX Unsigned32
        MAX-ACCESS not-accessible
        STATUS current
        DESCRIPTION
            "This object indicates the threshold type."
        ::= { optixSdhIfBoardB1B2B3ThEntry 1 }

    -- 1.3.6.1.4.1.2011.2.25.4.10.39.1.5.1.2
    optixSdhIfBoardExecTh OBJECT-TYPE
        SYNTAX Unsigned32
        MAX-ACCESS read-write
        STATUS current
        DESCRIPTION
            "This object indicates the level of performance threshold-crossing."
        ::= { optixSdhIfBoardB1B2B3ThEntry 2 }

    -- 1.3.6.1.4.1.2011.2.25.4.10.39.1.5.1.3
    optixSdhIfBoardSdTh OBJECT-TYPE
        SYNTAX Unsigned32
        MAX-ACCESS read-write
        STATUS current
        DESCRIPTION
            "This object indicates the level of performance deterioration."
        ::= { optixSdhIfBoardB1B2B3ThEntry 3 }

END
