-- OPTIX-TUNNEL-APS-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-TUNNEL-APS-MIB DEFINITIONS ::= BEGIN
    IMPORTS
        OBJECT-GROUP,MODULE-COMPLIANCE
            FROM SNMPv2-CONF
        MODULE-IDENTITY,OBJECT-TYPE,Unsigned32,Integer32,IpAddress,NOTIFICATION-TYPE
            FROM SNMPv2-SMI
        RowStatus
            FROM SNMPv2-TC
        optixProvisionPtn
            FROM OPTIX-OID-MIB
        ;

    optixTunnelApsMod MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage theMPLStunnel APS. The MPLS tunnel is protected so the services carried through the tunnel are protected. When the working MPLS tunnel is faulty, services are switched to the protection MPLS tunnel. The PTN equipment supports the 1+1 MPLS tunnel APS and 1:1 MPLS tunnel APS."
        REVISION "201204170000Z"
        DESCRIPTION
            "Initial version of this MIB module"
        ::={ optixProvisionPtn 8 }

    -- 1.3.6.1.4.1.2011.2.25.4.50.8.1
    optixTunnelApsObject OBJECT IDENTIFIER ::= { optixTunnelApsMod 1 }

    -- 1.3.6.1.4.1.2011.2.25.4.50.8.1.1
    optixTunnelApsTable OBJECT-TYPE
        SYNTAX SEQUENCE OF OptixTunnelApsEntry
        MAX-ACCESS not-accessible
        STATUS current
        DESCRIPTION
            "This table implements the configurations and status management ofthe tunnel APS. These configurations include APS protection members, the enable status, revertive mode, single-ended or dual-ended, recovery time, delay time, and APS switching status."
        ::= { optixTunnelApsObject 1 }

    -- 1.3.6.1.4.1.2011.2.25.4.50.8.1.1.1
    optixTunnelApsEntry OBJECT-TYPE
        SYNTAX OptixTunnelApsEntry
        MAX-ACCESS not-accessible
        STATUS current
        DESCRIPTION
            "This entry indicates the PW APSconfiguration table."
        INDEX{ optixTunnelApsId }
        ::= { optixTunnelApsTable 1 }

    OptixTunnelApsEntry ::=
        SEQUENCE {
            optixTunnelApsId
                Unsigned32,
            optixTunnelApsTnlType
                INTEGER,
            optixTunnelApsType
                INTEGER,
            optixTunnelApsSwitchMode
                INTEGER,
            optixTunnelApsRevertiveMode
                INTEGER,
            optixTunnelApsRevertiveTime
                Unsigned32,
            optixTunnelApsHoldoffTime
                Unsigned32,
            optixTunnelApsWorkOutTnlIndex
                Unsigned32,
            optixTunnelApsWorkInTnlIndex
                Unsigned32,
            optixTunnelApsProtectOutTnlIndex
                Unsigned32,
            optixTunnelApsProtectInTnlIndex
                Unsigned32,
            optixTunnelApsEnable
                INTEGER,
            optixTunnelApsBdiEnable
                INTEGER,
            optixTunnelApsGroupState
                INTEGER,
            optixTunnelApsProtoolState
                INTEGER,
            optixTunnelApsWorkState
                INTEGER,
            optixTunnelApsProtectState
                INTEGER,
            optixTunnelApsExcSwitch
                INTEGER,
            optixTunnelApsRowStatus
                RowStatus
        }

    -- 1.3.6.1.4.1.2011.2.25.4.50.8.1.1.1.1
    optixTunnelApsId OBJECT-TYPE
        SYNTAX Unsigned32
        MAX-ACCESS not-accessible
        STATUS current
        DESCRIPTION
            "This object indicates the APS protection group ID."
        ::= { optixTunnelApsEntry 1 }

    -- 1.3.6.1.4.1.2011.2.25.4.50.8.1.1.1.2
    optixTunnelApsTnlType OBJECT-TYPE
        SYNTAX INTEGER
        {
            p2p(1),
            p2mp(2)
        }
        MAX-ACCESS read-create
        STATUS current
        DESCRIPTION
            "This object indicates the APS protectiontunnel type. 1: p2p 2: p2mp"
        DEFVAL{ 1 }
        ::= { optixTunnelApsEntry 2 }

    -- 1.3.6.1.4.1.2011.2.25.4.50.8.1.1.1.3
    optixTunnelApsType OBJECT-TYPE
        SYNTAX INTEGER
        {
            snmp1j1(0),
            snmp1p1(1)
        }
        MAX-ACCESS read-create
        STATUS current
        DESCRIPTION
            "This object indicates the APS protection group type. 0: 1 + 1 1: 1:1"
        DEFVAL{ 0 }
        ::= { optixTunnelApsEntry 3 }

    -- 1.3.6.1.4.1.2011.2.25.4.50.8.1.1.1.4
    optixTunnelApsSwitchMode OBJECT-TYPE
        SYNTAX INTEGER
        {
            uni(0),
            bi(1)
        }
        MAX-ACCESS read-create
        STATUS current
        DESCRIPTION
            "This object indicates the switching mode of the APS protection group. 0: uni 1: bi"
        DEFVAL{ 0 }
        ::= { optixTunnelApsEntry 4 }

    -- 1.3.6.1.4.1.2011.2.25.4.50.8.1.1.1.5
    optixTunnelApsRevertiveMode OBJECT-TYPE
        SYNTAX INTEGER
        {
            norevertive(0),
            revertive(1)
        }
        MAX-ACCESS read-create
        STATUS current
        DESCRIPTION
            "This object indicates the revertive mode of the APS protection group. 0: no-revertive 1: revertive"
        DEFVAL{ 0 }
        ::= { optixTunnelApsEntry 5 }

    -- 1.3.6.1.4.1.2011.2.25.4.50.8.1.1.1.6
    optixTunnelApsRevertiveTime OBJECT-TYPE
        SYNTAX Unsigned32(0..12)
        MAX-ACCESS read-create
        STATUS current
        DESCRIPTION
            "This object indicates the recovery time of the APS protection group. Unit: min"
        DEFVAL{ 0 }
        ::= { optixTunnelApsEntry 6 }

    -- 1.3.6.1.4.1.2011.2.25.4.50.8.1.1.1.7
    optixTunnelApsHoldoffTime OBJECT-TYPE
        SYNTAX Unsigned32(0..100)
        MAX-ACCESS read-create
        STATUS current
        DESCRIPTION
            "This object indicates the switching delay time of the APS protection group. Unit: 100 ms"
        DEFVAL{ 0 }
        ::= { optixTunnelApsEntry 7 }

    -- 1.3.6.1.4.1.2011.2.25.4.50.8.1.1.1.8
    optixTunnelApsWorkOutTnlIndex OBJECT-TYPE
        SYNTAX Unsigned32
        MAX-ACCESS read-create
        STATUS current
        DESCRIPTION
            "This object indicates the working output APS tunnel index."
        DEFVAL{ 0 }
        ::= { optixTunnelApsEntry 8 }

    -- 1.3.6.1.4.1.2011.2.25.4.50.8.1.1.1.9
    optixTunnelApsWorkInTnlIndex OBJECT-TYPE
        SYNTAX Unsigned32
        MAX-ACCESS read-create
        STATUS current
        DESCRIPTION
            "This object indicates the working input APS tunnel index."
        DEFVAL{ 0 }
        ::= { optixTunnelApsEntry 9 }

    -- 1.3.6.1.4.1.2011.2.25.4.50.8.1.1.1.10
    optixTunnelApsProtectOutTnlIndex OBJECT-TYPE
        SYNTAX Unsigned32
        MAX-ACCESS read-create
        STATUS current
        DESCRIPTION
            "This object indicates the protection output APS tunnel index."
        DEFVAL{ 0 }
        ::= { optixTunnelApsEntry 10 }

    -- 1.3.6.1.4.1.2011.2.25.4.50.8.1.1.1.11
    optixTunnelApsProtectInTnlIndex OBJECT-TYPE
        SYNTAX Unsigned32
        MAX-ACCESS read-create
        STATUS current
        DESCRIPTION
            "This object indicates the protection input APS tunnel index."
        DEFVAL{ 0 }
        ::= { optixTunnelApsEntry 11 }

    -- 1.3.6.1.4.1.2011.2.25.4.50.8.1.1.1.12
    optixTunnelApsEnable OBJECT-TYPE
        SYNTAX INTEGER
        {
            disable(0),
            enable(1)
        }
        MAX-ACCESS read-create
        STATUS current
        DESCRIPTION
            "This object indicates the enable status of the APS protection protocol. 1: enable 0: disable"
        DEFVAL{ 1 }
        ::= { optixTunnelApsEntry 12 }

    -- 1.3.6.1.4.1.2011.2.25.4.50.8.1.1.1.13
    optixTunnelApsBdiEnable OBJECT-TYPE
        SYNTAX INTEGER
        {
            disable(0),
            enable(1)
        }
        MAX-ACCESS read-create
        STATUS current
        DESCRIPTION
            "This object indicates the enable status of the APS protection group BDI. 1: enable 0: disable"
        DEFVAL{ 0 }
        ::= { optixTunnelApsEntry 13 }

    -- 1.3.6.1.4.1.2011.2.25.4.50.8.1.1.1.14
    optixTunnelApsGroupState OBJECT-TYPE
        SYNTAX INTEGER
        {
            inprotect(0),
            inwork(1)
        }
        MAX-ACCESS read-only
        STATUS current
        DESCRIPTION
            "This object indicates the switching mode of the APS protection group. 1: in-work 0: in-protect"
        ::= { optixTunnelApsEntry 14 }

    -- 1.3.6.1.4.1.2011.2.25.4.50.8.1.1.1.15
    optixTunnelApsProtoolState OBJECT-TYPE
        SYNTAX INTEGER
        {
            nrw(0),
            nrp(1),
            lo(2),
            fs(3),
            sfw(4),
            sfp(5),
            sdp(6),
            sdw(7),
            msw(8),
            msp(9),
            wtr(10),
            dnr(11),
            exerw(12),
            exerp(13),
            rrw(14),
            rrp(15)
        }
        MAX-ACCESS read-only
        STATUS current
        DESCRIPTION
            "This object indicates the status of the APS protection protocol."
        ::= { optixTunnelApsEntry 15 }

    -- 1.3.6.1.4.1.2011.2.25.4.50.8.1.1.1.16
    optixTunnelApsWorkState OBJECT-TYPE
        SYNTAX INTEGER
        {
            invalid(0),
            valid(1)
        }
        MAX-ACCESS read-only
        STATUS current
        DESCRIPTION
            "This object indicates the working channel status of the APS protection group. 1: valid 0: invalid"
        ::= { optixTunnelApsEntry 16 }

    -- 1.3.6.1.4.1.2011.2.25.4.50.8.1.1.1.17
    optixTunnelApsProtectState OBJECT-TYPE
        SYNTAX INTEGER
        {
            invalid(0),
            valid(1)
        }
        MAX-ACCESS read-only
        STATUS current
        DESCRIPTION
            "This object indicates the protection channel status of the APS protection group. 1: valid 0: invalid"
        ::= { optixTunnelApsEntry 17 }

    -- 1.3.6.1.4.1.2011.2.25.4.50.8.1.1.1.18
    optixTunnelApsExcSwitch OBJECT-TYPE
        SYNTAX INTEGER
        {
            clear(0),
            lock(1),
            force(2),
            manualtowork(3),
            manualtoprotect(4),
            exercise(5)
        }
        MAX-ACCESS read-create
        STATUS current
        DESCRIPTION
            "This object indicates that the tunnel APS protection switching is to be triggered."
        ::= { optixTunnelApsEntry 18 }

    -- 1.3.6.1.4.1.2011.2.25.4.50.8.1.1.1.255
    optixTunnelApsRowStatus OBJECT-TYPE
        SYNTAX RowStatus
        MAX-ACCESS read-create
        STATUS current
        DESCRIPTION
            "This object indicates the row status. 1: active4: createAndGo6: destroy"
        ::= { optixTunnelApsEntry 255 }

    -- 1.3.6.1.4.1.2011.2.25.4.50.8.2
    optixTunnelApsTrap OBJECT IDENTIFIER ::= { optixTunnelApsMod 2 }

    -- 1.3.6.1.4.1.2011.2.25.4.50.8.2.1
    optixTunnelApsTrapMember OBJECT IDENTIFIER ::= { optixTunnelApsTrap 1 }

    -- 1.3.6.1.4.1.2011.2.25.4.50.8.2.1.1
    optixTunnelApsTrapGrouppId OBJECT-TYPE
        SYNTAX Unsigned32
        MAX-ACCESS accessible-for-notify
        STATUS current
        DESCRIPTION
            "This object indicates the APS protection group ID."
        ::= { optixTunnelApsTrapMember 1 }

    -- 1.3.6.1.4.1.2011.2.25.4.50.8.2.1.2
    optixTunnelApsTrapGroupState OBJECT-TYPE
        SYNTAX INTEGER
        {
            inprotect(0),
            inwork(1)
        }
        MAX-ACCESS accessible-for-notify
        STATUS current
        DESCRIPTION
            "This object indicates the switching status of the APS protection group. 1: in-work 0: in-protect"
        ::= { optixTunnelApsTrapMember 2 }

    -- 1.3.6.1.4.1.2011.2.25.4.50.8.2.1.3
    optixTunnelApsTrapProtoolState OBJECT-TYPE
        SYNTAX INTEGER
        {
            nrw(0),
            nrp(1),
            lo(2),
            fs(3),
            sfw(4),
            sfp(5),
            sdp(6),
            sdw(7),
            msw(8),
            msp(9),
            wtr(10),
            dnr(11),
            exerw(12),
            exerp(13),
            rrw(14),
            rrp(15)
        }
        MAX-ACCESS accessible-for-notify
        STATUS current
        DESCRIPTION
            "This object indicates the status of the APS protection protocol. 0: nrw, 1: nrp, 2: lo, 3: fs, 4: sfw, 5: sfp, 6: sdp, 7: sdw, 8: msw, 9: msp, 10: wtr, 22: dnr, 12: exerw, 13: exerp, 14: rrw, 15: rrp"
        ::= { optixTunnelApsTrapMember 3 }

    -- 1.3.6.1.4.1.2011.2.25.4.50.8.2.1.4
    optixTunnelApsTrapWorkState OBJECT-TYPE
        SYNTAX INTEGER
        {
            invalid(0),
            valid(1)
        }
        MAX-ACCESS accessible-for-notify
        STATUS current
        DESCRIPTION
            "This object indicates the working channel status of the APS protection group. 1: valid 0: invalid"
        ::= { optixTunnelApsTrapMember 4 }

    -- 1.3.6.1.4.1.2011.2.25.4.50.8.2.1.5
    optixTunnelApsTrapProtectState OBJECT-TYPE
        SYNTAX INTEGER
        {
            invalid(0),
            valid(1)
        }
        MAX-ACCESS accessible-for-notify
        STATUS current
        DESCRIPTION
            "This object indicates the protection channel status of the APS protection group. 1: valid 0: invalid"
        ::= { optixTunnelApsTrapMember 5 }

    -- 1.3.6.1.4.1.2011.2.25.4.50.8.2.2
    optixTunnelApsTrapReport OBJECT IDENTIFIER ::= { optixTunnelApsTrap 2 }

    -- 1.3.6.1.4.1.2011.2.25.4.50.8.2.2.1
    optixTunnelApsSwitchTrap NOTIFICATION-TYPE
        OBJECTS{ optixTunnelApsTrapGrouppId,optixTunnelApsTrapGroupState,optixTunnelApsTrapProtoolState,optixTunnelApsTrapWorkState,optixTunnelApsTrapProtectState }
        STATUS current
        DESCRIPTION
            "This object is used to reporttunnel APS status change events. When the APS protection switching occurs, the status change event must be reported."
        ::= { optixTunnelApsTrapReport 1 }

END
