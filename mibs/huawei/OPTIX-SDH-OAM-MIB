-- OPTIX-SDH-OAM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-OAM-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        optixPortId
            FROM OPTIX-PORT-MANAGE-MIB
        optixSdhXcLevel
            FROM OPTIX-SDH-XC-MIB
        optixSdhLP,optixSdhHP
            FROM OPTIX-SDH-LINEBOARD-MIB
        RowStatus
            FROM SNMPv2-TC
        ;

    optixSdhOam MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describesOAM configurations."
        REVISION "201204200000Z"
        DESCRIPTION
            "The initial revision of this MIB module1."
        ::={ optixProvisionSdh 42 }

    -- 1.3.6.1.4.1.2011.2.25.4.10.42.1
    optixSdhOamGroup OBJECT IDENTIFIER ::= { optixSdhOam 1 }

    -- 1.3.6.1.4.1.2011.2.25.4.10.42.1.1
    optixLoopTable OBJECT-TYPE
        SYNTAX SEQUENCE OF OptixLoopEntry
        MAX-ACCESS not-accessible
        STATUS current
        DESCRIPTION
            "This table describes the basic port loopback configurations."
        ::= { optixSdhOamGroup 1 }

    -- 1.3.6.1.4.1.2011.2.25.4.10.42.1.1.1
    optixLoopEntry OBJECT-TYPE
        SYNTAX OptixLoopEntry
        MAX-ACCESS not-accessible
        STATUS current
        DESCRIPTION
            "Thisentry describes the basic port loopback configurations."
        INDEX{ optixLogBoardId,optixLogSubCardId,optixPortId }
        ::= { optixLoopTable 1 }

    OptixLoopEntry ::=
        SEQUENCE {
            optixLoopMode
                INTEGER
        }

    -- 1.3.6.1.4.1.2011.2.25.4.10.42.1.1.1.1
    optixLoopMode OBJECT-TYPE
        SYNTAX INTEGER
        {
            noloop(0),
            inloop(1),
            outloop(2)
        }
        MAX-ACCESS read-write
        STATUS current
        DESCRIPTION
            "This object indicates the loopback mode of theport. 0: noloop, 1: inloop, 2: outloop"
        ::= { optixLoopEntry 1 }

    -- 1.3.6.1.4.1.2011.2.25.4.10.42.1.2
    optixVC4LoopTable OBJECT-TYPE
        SYNTAX SEQUENCE OF OptixVC4LoopEntry
        MAX-ACCESS not-accessible
        STATUS current
        DESCRIPTION
            "This table describes the basic loopback configurations of the higher order path."
        ::= { optixSdhOamGroup 2 }

    -- 1.3.6.1.4.1.2011.2.25.4.10.42.1.2.1
    optixVC4LoopEntry OBJECT-TYPE
        SYNTAX OptixVC4LoopEntry
        MAX-ACCESS not-accessible
        STATUS current
        DESCRIPTION
            "Thisentry describes the basic loopback configurations of the higher order path."
        INDEX{ optixLogBoardId,optixLogSubCardId,optixPortId,optixSdhHP }
        ::= { optixVC4LoopTable 1 }

    OptixVC4LoopEntry ::=
        SEQUENCE {
            optixVC4LoopMode
                INTEGER
        }

    -- 1.3.6.1.4.1.2011.2.25.4.10.42.1.2.1.1
    optixVC4LoopMode OBJECT-TYPE
        SYNTAX INTEGER
        {
            noloop(0),
            inloop(1),
            outloop(2)
        }
        MAX-ACCESS read-write
        STATUS current
        DESCRIPTION
            "This object indicates the loopback mode of the higher order path. 0: noloop, 1: inloop, 2: outloop"
        ::= { optixVC4LoopEntry 1 }

    -- 1.3.6.1.4.1.2011.2.25.4.10.42.1.3
    optixOamLineFindTable OBJECT-TYPE
        SYNTAX SEQUENCE OF OptixOamLineFindEntry
        MAX-ACCESS not-accessible
        STATUS current
        DESCRIPTION
            "This table describes the basic configurations of fiber-searching function at the OAM port."
        ::= { optixSdhOamGroup 3 }

    -- 1.3.6.1.4.1.2011.2.25.4.10.42.1.3.1
    optixOamLineFindEntry OBJECT-TYPE
        SYNTAX OptixOamLineFindEntry
        MAX-ACCESS not-accessible
        STATUS current
        DESCRIPTION
            "Thisentry describes the basic configurations of fiber-searching function at the OAM port."
        INDEX{ optixOamLineFindInNeId,optixOamLineFindInBid,optixOamLineFindInSubCardId,optixOamLineFindInPid }
        ::= { optixOamLineFindTable 1 }

    OptixOamLineFindEntry ::=
        SEQUENCE {
            optixOamLineFindInNeId
                Unsigned32,
            optixOamLineFindInBid
                Unsigned32,
            optixOamLineFindInSubCardId
                Unsigned32,
            optixOamLineFindInPid
                Unsigned32,
            optixOamLineFindOutNeId
                Unsigned32,
            optixOamLineFindOutBid
                Unsigned32,
            optixOamLineFindOutSubCardId
                Unsigned32,
            optixOamLineFindOutPid
                Unsigned32,
            optixOamLineFindRowStatus
                RowStatus
        }

    -- 1.3.6.1.4.1.2011.2.25.4.10.42.1.3.1.1
    optixOamLineFindInNeId OBJECT-TYPE
        SYNTAX Unsigned32
        MAX-ACCESS not-accessible
        STATUS current
        DESCRIPTION
            "This object indicates the NE ID input for the fiber-searching. This parameter can be set to 0, indicating all fiber connections on an NE. NE IDs are used with ASON equipment. Therefore, ASON equipment can query all the fiber connections on an NE."
        ::= { optixOamLineFindEntry 1 }

    -- 1.3.6.1.4.1.2011.2.25.4.10.42.1.3.1.2
    optixOamLineFindInBid OBJECT-TYPE
        SYNTAX Unsigned32
        MAX-ACCESS not-accessible
        STATUS current
        DESCRIPTION
            "This object indicates the slot ID input for thefiber-searching. This parameter can be set to 0. If the NE ID is 0, the value of this parameter must be 0. If the NE ID is not 0, the value 0 of this parameter indicates all boards on a specified NE."
        ::= { optixOamLineFindEntry 2 }

    -- 1.3.6.1.4.1.2011.2.25.4.10.42.1.3.1.3
    optixOamLineFindInSubCardId OBJECT-TYPE
        SYNTAX Unsigned32
        MAX-ACCESS not-accessible
        STATUS current
        DESCRIPTION
            "This object indicates the subboard ID input for the fiber-searching. The parameter takes a fixed value of 255."
        ::= { optixOamLineFindEntry 3 }

    -- 1.3.6.1.4.1.2011.2.25.4.10.42.1.3.1.4
    optixOamLineFindInPid OBJECT-TYPE
        SYNTAX Unsigned32
        MAX-ACCESS not-accessible
        STATUS current
        DESCRIPTION
            "This object indicates the port number input for the fiber-searching.This parameter can be set to 0. If the slot ID is 0, the value of this parameter must be 0. If the slot ID is not 0, the value 0 of this parameter indicates all ports on a specified NE."
        ::= { optixOamLineFindEntry 4 }

    -- 1.3.6.1.4.1.2011.2.25.4.10.42.1.3.1.5
    optixOamLineFindOutNeId OBJECT-TYPE
        SYNTAX Unsigned32
        MAX-ACCESS read-only
        STATUS current
        DESCRIPTION
            "This object indicates the NE ID output after thefiber-searching."
        ::= { optixOamLineFindEntry 5 }

    -- 1.3.6.1.4.1.2011.2.25.4.10.42.1.3.1.6
    optixOamLineFindOutBid OBJECT-TYPE
        SYNTAX Unsigned32
        MAX-ACCESS read-only
        STATUS current
        DESCRIPTION
            "This object indicates the slot ID output after thefiber-searching."
        ::= { optixOamLineFindEntry 6 }

    -- 1.3.6.1.4.1.2011.2.25.4.10.42.1.3.1.7
    optixOamLineFindOutSubCardId OBJECT-TYPE
        SYNTAX Unsigned32
        MAX-ACCESS read-only
        STATUS current
        DESCRIPTION
            "This object indicates the subboard IDoutput after thefiber-searching."
        ::= { optixOamLineFindEntry 7 }

    -- 1.3.6.1.4.1.2011.2.25.4.10.42.1.3.1.8
    optixOamLineFindOutPid OBJECT-TYPE
        SYNTAX Unsigned32
        MAX-ACCESS read-only
        STATUS current
        DESCRIPTION
            "This object indicates the port numberoutput after thefiber-searching."
        ::= { optixOamLineFindEntry 8 }

    -- 1.3.6.1.4.1.2011.2.25.4.10.42.1.3.1.255
    optixOamLineFindRowStatus OBJECT-TYPE
        SYNTAX RowStatus
        MAX-ACCESS read-create
        STATUS current
        DESCRIPTION
            "This object indicates the row the basic configurations of fiber-searching function at the OAM port."
        ::= { optixOamLineFindEntry 255 }

    -- 1.3.6.1.4.1.2011.2.25.4.10.42.1.4
    optixSdhAlm2AisTable OBJECT-TYPE
        SYNTAX SEQUENCE OF OptixSdhAlm2AisEntry
        MAX-ACCESS not-accessible
        STATUS current
        DESCRIPTION
            "This table describes configurations of alarm management of the SDH board."
        ::= { optixSdhOamGroup 4 }

    -- 1.3.6.1.4.1.2011.2.25.4.10.42.1.4.1
    optixSdhAlm2AisEntry OBJECT-TYPE
        SYNTAX OptixSdhAlm2AisEntry
        MAX-ACCESS not-accessible
        STATUS current
        DESCRIPTION
            "This entry describes configurations of alarm management of the SDH board."
        INDEX{ optixLogBoardId,optixLogSubCardId,optixPortId,optixSdhAlmId }
        ::= { optixSdhAlm2AisTable 1 }

    OptixSdhAlm2AisEntry ::=
        SEQUENCE {
            optixSdhAlmId
                INTEGER,
            optixSdhAlm2AisEnable
                INTEGER
        }

    -- 1.3.6.1.4.1.2011.2.25.4.10.42.1.4.1.1
    optixSdhAlmId OBJECT-TYPE
        SYNTAX INTEGER
        {
            none(0),
            rlos(1),
            roof(5),
            rlof(8),
            b1exc(12),
            msais(33),
            msrdi(34),
            b2exc(35),
            b2sd(36),
            aulop(66),
            b3sd(70),
            b3exc(71),
            auais(72),
            hpuneq(75),
            hptim(76),
            hpslm(77),
            hplom(81),
            j0mm(87),
            lpuneq(90),
            lptim(91),
            lpslm(92),
            talos(107),
            plos(134),
            b1sd(175),
            bipsd(182),
            bipexc(183),
            linkerr(261),
            tcltc(352),
            tcuneq(353),
            tcincais(354),
            tctim(357),
            lpslmvc12(63594),
            lptimvc12(63596),
            lpuneqvc12(63598)
        }
        MAX-ACCESS not-accessible
        STATUS current
        DESCRIPTION
            "This object indicates the alarm ID. 0: none, 1: rlos, 5: roof, 8: rlof, 12: b1exc, 33: msais, 34: msrdi, 35: b2exc, 36: b2sd, 66: aulop, 70: b3sd, 71: b3exc, 72: auais, 75: hpuneq, 76: hptim, 77: hpslm, 81: hplom, 87: j0mm, 90: lpuneq, 91: lptim, 92: lpslm, 107: talos, 134: plos, 175: b1sd, 182: bipsd, 183: bipexc, 261: linkerr, 352: tcltc, 353: tcuneq, 354: tcincais, 357: tctim, 63594: lpslmvc12, 63596: lptimvc12, 63598: lpuneqvc12"
        ::= { optixSdhAlm2AisEntry 1 }

    -- 1.3.6.1.4.1.2011.2.25.4.10.42.1.4.1.2
    optixSdhAlm2AisEnable OBJECT-TYPE
        SYNTAX INTEGER
        {
            disable(0),
            enable(1)
        }
        MAX-ACCESS read-write
        STATUS current
        DESCRIPTION
            "This object indicates the enable status of port alarm insert. 0: disable, 1: enable"
        ::= { optixSdhAlm2AisEntry 2 }

    -- 1.3.6.1.4.1.2011.2.25.4.10.42.1.5
    optixSdhJ1C2MonitorTable OBJECT-TYPE
        SYNTAX SEQUENCE OF OptixSdhJ1C2MonitorEntry
        MAX-ACCESS not-accessible
        STATUS current
        DESCRIPTION
            "This table describes configurations of J1C2 monitor management of the SDH board."
        ::= { optixSdhOamGroup 5 }

    -- 1.3.6.1.4.1.2011.2.25.4.10.42.1.5.1
    optixSdhJ1C2MonitorEntry OBJECT-TYPE
        SYNTAX OptixSdhJ1C2MonitorEntry
        MAX-ACCESS not-accessible
        STATUS current
        DESCRIPTION
            "This entry describes configurations of J1C2 monitor management of the SDH board."
        INDEX{ optixLogBoardId,optixLogSubCardId,optixPortId }
        ::= { optixSdhJ1C2MonitorTable 1 }

    OptixSdhJ1C2MonitorEntry ::=
        SEQUENCE {
            optixSdhJ1C2MonitorEnable
                INTEGER
        }

    -- 1.3.6.1.4.1.2011.2.25.4.10.42.1.5.1.1
    optixSdhJ1C2MonitorEnable OBJECT-TYPE
        SYNTAX INTEGER
        {
            disable(0),
            enable(1)
        }
        MAX-ACCESS read-write
        STATUS current
        DESCRIPTION
            "This object indicates the enable of J1C2 byte to be monitored. 0: disable, 1: enable"
        ::= { optixSdhJ1C2MonitorEntry 1 }

    -- 1.3.6.1.4.1.2011.2.25.4.10.42.1.6
    optixSdhHsutTable OBJECT-TYPE
        SYNTAX SEQUENCE OF OptixSdhHsutEntry
        MAX-ACCESS not-accessible
        STATUS current
        DESCRIPTION
            "This table describes the unload path management for the SDH board."
        ::= { optixSdhOamGroup 6 }

    -- 1.3.6.1.4.1.2011.2.25.4.10.42.1.6.1
    optixSdhHsutEntry OBJECT-TYPE
        SYNTAX OptixSdhHsutEntry
        MAX-ACCESS not-accessible
        STATUS current
        DESCRIPTION
            "This entry describes the unload path management for the SDH board."
        INDEX{ optixLogBoardId,optixLogSubCardId,optixPortId,optixSdhHsutAu4ID }
        ::= { optixSdhHsutTable 1 }

    OptixSdhHsutEntry ::=
        SEQUENCE {
            optixSdhHsutAu4ID
                Unsigned32,
            optixSdhHsutEnable
                INTEGER
        }

    -- 1.3.6.1.4.1.2011.2.25.4.10.42.1.6.1.1
    optixSdhHsutAu4ID OBJECT-TYPE
        SYNTAX Unsigned32
        MAX-ACCESS not-accessible
        STATUS current
        DESCRIPTION
            "This object indicates the Au4ID of SDH board."
        ::= { optixSdhHsutEntry 1 }

    -- 1.3.6.1.4.1.2011.2.25.4.10.42.1.6.1.2
    optixSdhHsutEnable OBJECT-TYPE
        SYNTAX INTEGER
        {
            disable(0),
            enable(1)
        }
        MAX-ACCESS read-write
        STATUS current
        DESCRIPTION
            "This object indicates the enable state of unload path for SDH board. 0: disable, 1: enable"
        ::= { optixSdhHsutEntry 2 }

    -- 1.3.6.1.4.1.2011.2.25.4.10.42.1.7
    optixSdhBoardTohTable OBJECT-TYPE
        SYNTAX SEQUENCE OF OptixSdhBoardTohEntry
        MAX-ACCESS not-accessible
        STATUS current
        DESCRIPTION
            "This table describes the enable status of send overhead byte management for the SDH board."
        ::= { optixSdhOamGroup 7 }

    -- 1.3.6.1.4.1.2011.2.25.4.10.42.1.7.1
    optixSdhBoardTohEntry OBJECT-TYPE
        SYNTAX OptixSdhBoardTohEntry
        MAX-ACCESS not-accessible
        STATUS current
        DESCRIPTION
            "Thisentry describes the enable status of send overhead byte management for the SDH board."
        INDEX{ optixLogBoardId }
        ::= { optixSdhBoardTohTable 1 }

    OptixSdhBoardTohEntry ::=
        SEQUENCE {
            optixSdhBoardTohEnable
                INTEGER
        }

    -- 1.3.6.1.4.1.2011.2.25.4.10.42.1.7.1.1
    optixSdhBoardTohEnable OBJECT-TYPE
        SYNTAX INTEGER
        {
            disable(0),
            enable(1)
        }
        MAX-ACCESS read-write
        STATUS current
        DESCRIPTION
            "This object indicates the enabling status of sending overhead byte for the SDH board. 1/0 means respectively to enable/disable setting the sending overhead byte by the sending buffer of RAM"
        ::= { optixSdhBoardTohEntry 1 }

    -- 1.3.6.1.4.1.2011.2.25.4.10.42.1.8
    optixE1SrvModTable OBJECT-TYPE
        SYNTAX SEQUENCE OF OptixE1SrvModEntry
        MAX-ACCESS not-accessible
        STATUS current
        DESCRIPTION
            "This table describes the server mode for the E1 port."
        ::= { optixSdhOamGroup 8 }

    -- 1.3.6.1.4.1.2011.2.25.4.10.42.1.8.1
    optixE1SrvModEntry OBJECT-TYPE
        SYNTAX OptixE1SrvModEntry
        MAX-ACCESS not-accessible
        STATUS current
        DESCRIPTION
            "This entry describes the server mode for the E1 port."
        INDEX{ optixLogBoardId,optixLogSubCardId,optixPortId }
        ::= { optixE1SrvModTable 1 }

    OptixE1SrvModEntry ::=
        SEQUENCE {
            optixE1SrvMod
                INTEGER
        }

    -- 1.3.6.1.4.1.2011.2.25.4.10.42.1.8.1.1
    optixE1SrvMod OBJECT-TYPE
        SYNTAX INTEGER
        {
            pdh(0),
            ces(1)
        }
        MAX-ACCESS read-write
        STATUS current
        DESCRIPTION
            "This object indicates the server mode for the E1 port."
        ::= { optixE1SrvModEntry 1 }

    -- 1.3.6.1.4.1.2011.2.25.4.10.42.1.9
    optixSTM1SrvModTable OBJECT-TYPE
        SYNTAX SEQUENCE OF OptixSTM1SrvModEntry
        MAX-ACCESS not-accessible
        STATUS current
        DESCRIPTION
            "This table describes the server mode for the STM-1 port."
        ::= { optixSdhOamGroup 9 }

    -- 1.3.6.1.4.1.2011.2.25.4.10.42.1.9.1
    optixSTM1SrvModEntry OBJECT-TYPE
        SYNTAX OptixSTM1SrvModEntry
        MAX-ACCESS not-accessible
        STATUS current
        DESCRIPTION
            "This Entry describes the server mode for the STM-1 port."
        INDEX{ optixLogBoardId,optixLogSubCardId,optixPortId,optixSdhHP,optixSdhLP }
        ::= { optixSTM1SrvModTable 1 }

    OptixSTM1SrvModEntry ::=
        SEQUENCE {
            optixSTM1SrvMod
                INTEGER
        }

    -- 1.3.6.1.4.1.2011.2.25.4.10.42.1.9.1.1
    optixSTM1SrvMod OBJECT-TYPE
        SYNTAX INTEGER
        {
            tdm(0),
            ces(1)
        }
        MAX-ACCESS read-write
        STATUS current
        DESCRIPTION
            "This object indicates the server mode for the STM-1 port. 0: PDH, 1: CES"
        DEFVAL{ tdm }
        ::= { optixSTM1SrvModEntry 1 }

END
