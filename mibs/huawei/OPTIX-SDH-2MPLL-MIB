-- OPTIX-SDH-2MPLL-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-SDH-2MPLL-MIB DEFINITIONS ::= BEGIN
    IMPORTS
        optixProvisionSdh
            FROM OPTIX-OID-MIB
        OBJECT-GROUP,MODULE-COMPLIANCE
            FROM SNMPv2-CONF
        Unsigned32,OBJECT-TYPE,MODULE-IDENTITY
            FROM SNMPv2-SMI
        optixLogBoardId
            FROM OPTIX-BOARD-MANAGE-MIB
        ;

    optixSdh2MPll MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations of 2M phase-locked source management."
        REVISION "201204200000Z"
        DESCRIPTION
            "The initial revision of this MIB module1."
        ::={ optixProvisionSdh 38 }

    -- 1.3.6.1.4.1.2011.2.25.4.10.38.1
    optixSdh2MPllGroup OBJECT IDENTIFIER ::= { optixSdh2MPll 1 }

    -- 1.3.6.1.4.1.2011.2.25.4.10.38.1.1
    optixSdh2MPllTable OBJECT-TYPE
        SYNTAX SEQUENCE OF OptixSdh2MPllEntry
        MAX-ACCESS not-accessible
        STATUS current
        DESCRIPTION
            "This table describes the 2M phase-locked source configurations"
        ::= { optixSdh2MPllGroup 1 }

    -- 1.3.6.1.4.1.2011.2.25.4.10.38.1.1.1
    optixSdh2MPllEntry OBJECT-TYPE
        SYNTAX OptixSdh2MPllEntry
        MAX-ACCESS not-accessible
        STATUS current
        DESCRIPTION
            "This entry describes the 2M phase-locked source configurations"
        INDEX{ optixLogBoardId,optixSdh2MSynClassTable }
        ::= { optixSdh2MPllTable 1 }

    OptixSdh2MPllEntry ::=
        SEQUENCE {
            optixSdh2MSynClassTable
                INTEGER,
            optixSdh2MPllSwitchState
                INTEGER,
            optixSdh2MPllCurrentSyn
                OCTET STRING,
            optixSdh2MPllSynLosAction
                Unsigned32,
            optixSdh2MPllSynExist
                OCTET STRING,
            optixSdh2MPllSynId
                OCTET STRING,
            optixSdh2MPllSynCurSynS1Value
                INTEGER
        }

    -- 1.3.6.1.4.1.2011.2.25.4.10.38.1.1.1.1
    optixSdh2MSynClassTable OBJECT-TYPE
        SYNTAX INTEGER
        {
            synFir2mTbl(1),
            synSec2mTbl(2)
        }
        MAX-ACCESS not-accessible
        STATUS current
        DESCRIPTION
            "This parameter indicates the priority table of the 2M phase-locked source. 1: synFir2mTbl 2: synSec2mTbl"
        ::= { optixSdh2MPllEntry 1 }

    -- 1.3.6.1.4.1.2011.2.25.4.10.38.1.1.1.2
    optixSdh2MPllSwitchState OBJECT-TYPE
        SYNTAX INTEGER
        {
            synAuto(0),
            synMan(1),
            synForce(2)
        }
        MAX-ACCESS read-write
        STATUS current
        DESCRIPTION
            "This parameter indicates the switching mode of the 2M phase-locked source. 0: synAuto 1: synMan 2: synForce"
        ::= { optixSdh2MPllEntry 2 }

    -- 1.3.6.1.4.1.2011.2.25.4.10.38.1.1.1.3
    optixSdh2MPllCurrentSyn OBJECT-TYPE
        SYNTAX OCTET STRING (SIZE(0..255))
        MAX-ACCESS read-write
        STATUS current
        DESCRIPTION
            "This parameter indicates the current tracing source of the 2M phase-locked source."
        ::= { optixSdh2MPllEntry 3 }

    -- 1.3.6.1.4.1.2011.2.25.4.10.38.1.1.1.4
    optixSdh2MPllSynLosAction OBJECT-TYPE
        SYNTAX Unsigned32
        MAX-ACCESS read-write
        STATUS current
        DESCRIPTION
            "This parameter indicates the action when the 2M phase-locked source is invalid."
        ::= { optixSdh2MPllEntry 4 }

    -- 1.3.6.1.4.1.2011.2.25.4.10.38.1.1.1.5
    optixSdh2MPllSynExist OBJECT-TYPE
        SYNTAX OCTET STRING(SIZE(0..255))
        MAX-ACCESS read-only
        STATUS current
        DESCRIPTION
            "This parameter indicates the clock source whose clock status exists in the 2M phase-locked source priority table."
        ::= { optixSdh2MPllEntry 5 }

    -- 1.3.6.1.4.1.2011.2.25.4.10.38.1.1.1.6
    optixSdh2MPllSynId OBJECT-TYPE
        SYNTAX OCTET STRING(SIZE(0..255))
        MAX-ACCESS read-write
        STATUS current
        DESCRIPTION
            "This parameter indicates the clock source ID of the 2M phase-locked source."
        ::= { optixSdh2MPllEntry 6 }

    -- 1.3.6.1.4.1.2011.2.25.4.10.38.1.1.1.7
    optixSdh2MPllSynCurSynS1Value OBJECT-TYPE
        SYNTAX INTEGER
        {
            qlUnknown(0),
            qlPrc(2),
            qlSsua(4),
            qlSsub(8),
            qlSec(11),
            qlDnu(15)
        }
        MAX-ACCESS read-only
        STATUS current
        DESCRIPTION
            "This parameter specifies the synchronous S1 value of the 2M phase-locked source."
        ::= { optixSdh2MPllEntry 7 }

    -- 1.3.6.1.4.1.2011.2.25.4.10.38.1.2
    optixSdh2MPllSynS1Table OBJECT-TYPE
        SYNTAX SEQUENCE OF OptixSdh2MPllSynS1Entry
        MAX-ACCESS not-accessible
        STATUS current
        DESCRIPTION
            "This table contains the S1 byte configuration of the 2M phase-locked source."
        ::= { optixSdh2MPllGroup 2 }

    -- 1.3.6.1.4.1.2011.2.25.4.10.38.1.2.1
    optixSdh2MPllSynS1Entry OBJECT-TYPE
        SYNTAX OptixSdh2MPllSynS1Entry
        MAX-ACCESS not-accessible
        STATUS current
        DESCRIPTION
            "This entry contains the S1 byte configuration of the 2M phase-locked source."
        INDEX{ optixLogBoardId,optixSdh2MSynClassTable,optixSdh2MPllS1SynId }
        ::= { optixSdh2MPllSynS1Table 1 }

    OptixSdh2MPllSynS1Entry ::=
        SEQUENCE {
            optixSdh2MPllS1SynId
                Unsigned32,
            optixSdh2MPllS1Value
                INTEGER
        }

    -- 1.3.6.1.4.1.2011.2.25.4.10.38.1.2.1.1
    optixSdh2MPllS1SynId OBJECT-TYPE
        SYNTAX Unsigned32
        MAX-ACCESS not-accessible
        STATUS current
        DESCRIPTION
            "This parameter specifies the clock source ID of the 2M phase-locked source."
        ::= { optixSdh2MPllSynS1Entry 1 }

    -- 1.3.6.1.4.1.2011.2.25.4.10.38.1.2.1.2
    optixSdh2MPllS1Value OBJECT-TYPE
        SYNTAX INTEGER
        {
            qlUnknown(0),
            qlPrc(2),
            qlSsua(4),
            qlSsub(8),
            qlSec(11),
            qlDnu(15)
        }
        MAX-ACCESS read-only
        STATUS current
        DESCRIPTION
            "This parameter specifies all synchronous S1 byte values of the 2M phase-locked source."
        ::= { optixSdh2MPllSynS1Entry 2 }

END
