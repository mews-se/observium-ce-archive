-- OPTIX-PKT-SSM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-SSM-MIB DEFINITIONS ::= BEGIN
    IMPORTS
        optixProvisionPtn
            FROM OPTIX-OID-MIB
        OBJECT-GROUP,NOTIFICATION-GROUP
            FROM SNMPv2-CONF
        Unsigned32,OBJECT-TYPE,MODULE-IDENTITY
            FROM SNMPv2-SMI
        ;

    optixPktSsm MODULE-IDENTITY
        LAST-UPDATED "201603251505Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes configurations of SSM protocol management."
        REVISION "201603251505Z"
        DESCRIPTION
            "The initial revision of this MIB module1."
        ::={ optixProvisionPtn 37 }

    -- 1.3.6.1.4.1.2011.2.25.4.50.37.1
    optixPktSsmGroup OBJECT IDENTIFIER ::= { optixPktSsm 1 }

    -- 1.3.6.1.4.1.2011.2.25.4.50.37.1.1
    optixPktSsmS1ModeTable OBJECT-TYPE
        SYNTAX SEQUENCE OF OptixPktSsmS1ModeEntry
        MAX-ACCESS not-accessible
        STATUS current
        DESCRIPTION
            "This table describes the basic configurations of SSM protocol S1 mode management."
        ::= { optixPktSsmGroup 1 }

    -- 1.3.6.1.4.1.2011.2.25.4.50.37.1.1.1
    optixPktSsmS1ModeEntry OBJECT-TYPE
        SYNTAX OptixPktSsmS1ModeEntry
        MAX-ACCESS not-accessible
        STATUS current
        DESCRIPTION
            "This entry describes the basic configurations of SSM protocol S1 mode management."
        INDEX{ optixPktSsmS1BoardId }
        ::= { optixPktSsmS1ModeTable 1 }

    OptixPktSsmS1ModeEntry ::=
        SEQUENCE {
            optixPktSsmS1BoardId
                Unsigned32,
            optixPktSsmS1Mode
                INTEGER
        }

    -- 1.3.6.1.4.1.2011.2.25.4.50.37.1.1.1.1
    optixPktSsmS1BoardId OBJECT-TYPE
        SYNTAX Unsigned32
        MAX-ACCESS not-accessible
        STATUS current
        DESCRIPTION
            "This object indicates the board ID for SSM protocol working mode."
        ::= { optixPktSsmS1ModeEntry 1 }

    -- 1.3.6.1.4.1.2011.2.25.4.50.37.1.1.1.2
    optixPktSsmS1Mode OBJECT-TYPE
        SYNTAX INTEGER
        {
            disables1(0),
            expands1(1),
            standards1(2)
        }
        MAX-ACCESS read-write
        STATUS current
        DESCRIPTION
            "This object indicates the working mode of the SSM protocol. 0: disables1, 1: expands1, 2: standards1, 3: asonssm"
        ::= { optixPktSsmS1ModeEntry 2 }

END
