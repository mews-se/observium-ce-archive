-- OPTIX-GLOBAL-PM-DATA-RTN-MIB
-- MIB generated by ExcelToMIB tool 1.0
-- 
-- =================================================================
--  Copyright (C) 2010 by HUAWEI TECHNOLOGIES. All rights reserved
--  
--  Description:This MIB describes the Performance interface of Huawei microwave transmit
--  Reference:
--  Version: V1.00
--  History:
--     <author>,<date>,<contents>
-- =================================================================

OPTIX-GLOBAL-PM-DATA-RTN-MIB DEFINITIONS ::= BEGIN
    IMPORTS
        ObjType,DataPmEventType,ValidflagType
            FROM OPTIX-GLOBAL-TC-MIB
        optixCommon,rtn
            FROM OPTIX-OID-MIB
        OBJECT-GROUP,MODULE-COMPLIANCE
            FROM SNMPv2-CONF
        Unsigned32,OBJECT-TYPE,MODULE-IDENTITY,Counter64
            FROM SNMPv2-SMI
        DateAndTime,DisplayString
            FROM SNMPv2-TC
        optixCommonGlobal
            FROM OPTIX-OID-MIB;
    
    
    rtnData MODULE-IDENTITY
        LAST-UPDATED "200805240500Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Description."
        REVISION "200805240500Z"
        DESCRIPTION
            "The initial revision of this MIB module."
        ::={ rtn 20 }
--
-- Node definitions
    -- 1.3.6.1.4.1.2011.2.25.3.70.20.40
    tunnel OBJECT IDENTIFIER ::= { rtnData 40 }

    -- 1.3.6.1.4.1.2011.2.25.3.70.20.40.100
    tunnelPmCurTable OBJECT-TYPE
        SYNTAX SEQUENCE OF TunnelPmCurEntry
        MAX-ACCESS not-accessible
        STATUS current
        DESCRIPTION
            "tunnelDataPm30sCur."
        ::= { tunnel 100 }

    -- 1.3.6.1.4.1.2011.2.25.3.70.20.40.100.1
    tunnelPmCurEntry OBJECT-TYPE
        SYNTAX TunnelPmCurEntry
        MAX-ACCESS not-accessible
        STATUS current
        DESCRIPTION
            "tunnelPmCur."
        INDEX{ tunnelPmCurEid,tunnelPmCurParaLen, tunnelPmCurPara }
        ::= { tunnelPmCurTable 1 }

    TunnelPmCurEntry ::=
        SEQUENCE {
            tunnelPmCurEid
                DataPmEventType,
            tunnelPmCurParaLen
                Unsigned32,
            tunnelPmCurPara
                OCTET STRING,
            tunnelPmCurMonValue
                Counter64,
            tunnelPmCurDatetime
                DateAndTime
        }

    -- 1.3.6.1.4.1.2011.2.25.3.70.20.40.100.1.1
    tunnelPmCurEid OBJECT-TYPE
        SYNTAX DataPmEventType
        MAX-ACCESS read-only
        STATUS current
        DESCRIPTION
            "DataPmEid."
        ::= { tunnelPmCurEntry 1 }

    -- 1.3.6.1.4.1.2011.2.25.3.70.20.40.100.1.2
    tunnelPmCurParaLen OBJECT-TYPE
        SYNTAX Unsigned32
        MAX-ACCESS read-only
        STATUS current
        DESCRIPTION
            "ParaLen."
        ::= { tunnelPmCurEntry 2 }

    -- 1.3.6.1.4.1.2011.2.25.3.70.20.40.100.1.3
    tunnelPmCurPara OBJECT-TYPE
        SYNTAX OCTET STRING
        MAX-ACCESS read-only
        STATUS current
        DESCRIPTION
            "para"
        ::= { tunnelPmCurEntry 3 }

    -- 1.3.6.1.4.1.2011.2.25.3.70.20.40.100.1.4
    tunnelPmCurMonValue OBJECT-TYPE
        SYNTAX Counter64
        MAX-ACCESS read-only
        STATUS current
        DESCRIPTION
            "DataPmMonValue."
        ::= { tunnelPmCurEntry 4 }

    -- 1.3.6.1.4.1.2011.2.25.3.70.20.40.100.1.5
    tunnelPmCurDatetime OBJECT-TYPE
        SYNTAX DateAndTime
        MAX-ACCESS read-only
        STATUS current
        DESCRIPTION
            "Start Time."
        ::= { tunnelPmCurEntry 5 }

    -- 1.3.6.1.4.1.2011.2.25.3.70.20.40.110
    tunnelPm30sHisTable OBJECT-TYPE
        SYNTAX SEQUENCE OF TunnelPm30sHisEntry
        MAX-ACCESS not-accessible
        STATUS current
        DESCRIPTION
            "tunnelDataPm30sHis."
        ::= { tunnel 110 }

    -- 1.3.6.1.4.1.2011.2.25.3.70.20.40.110.1
    tunnelPm30sHisEntry OBJECT-TYPE
        SYNTAX TunnelPm30sHisEntry
        MAX-ACCESS not-accessible
        STATUS current
        DESCRIPTION
            "tunnelDataPm30sHis."
        INDEX{ tunnelPm30sHisEid,tunnelPm30sHisParaLen,tunnelPm30sHisPara,tunnelPm30sHisStartTime,tunnelPm30sHisEndTime }
        ::= { tunnelPm30sHisTable 1 }

    TunnelPm30sHisEntry ::=
        SEQUENCE {
            tunnelPm30sHisEid
                DataPmEventType,
            tunnelPm30sHisParaLen
                Unsigned32,
            tunnelPm30sHisPara
                OCTET STRING,
            tunnelPm30sHisMonValue
                Counter64,
            tunnelPm30sHisStartTime
                DateAndTime,
            tunnelPm30sHisEndTime
                DateAndTime,
            tunnelPm30sHisVldty
                ValidflagType
        }

    -- 1.3.6.1.4.1.2011.2.25.3.70.20.40.110.1.1
    tunnelPm30sHisEid OBJECT-TYPE
        SYNTAX DataPmEventType
        MAX-ACCESS read-only
        STATUS current
        DESCRIPTION
            "DataPmEid."
        ::= { tunnelPm30sHisEntry 1 }

    -- 1.3.6.1.4.1.2011.2.25.3.70.20.40.110.1.2
    tunnelPm30sHisParaLen OBJECT-TYPE
        SYNTAX Unsigned32
        MAX-ACCESS read-only
        STATUS current
        DESCRIPTION
            "ParaLen."
        ::= { tunnelPm30sHisEntry 2 }

    -- 1.3.6.1.4.1.2011.2.25.3.70.20.40.110.1.3
    tunnelPm30sHisPara OBJECT-TYPE
        SYNTAX OCTET STRING(SIZE (0..100))
        MAX-ACCESS read-only
        STATUS current
        DESCRIPTION
            "para"
        ::= { tunnelPm30sHisEntry 3 }

    -- 1.3.6.1.4.1.2011.2.25.3.70.20.40.110.1.4
    tunnelPm30sHisMonValue OBJECT-TYPE
        SYNTAX Counter64
        MAX-ACCESS read-only
        STATUS current
        DESCRIPTION
            "DataPmMonValue."
        ::= { tunnelPm30sHisEntry 4 }

    -- 1.3.6.1.4.1.2011.2.25.3.70.20.40.110.1.5
    tunnelPm30sHisStartTime OBJECT-TYPE
        SYNTAX DateAndTime
        MAX-ACCESS read-only
        STATUS current
        DESCRIPTION
            "Start Time."
        ::= { tunnelPm30sHisEntry 5 }

    -- 1.3.6.1.4.1.2011.2.25.3.70.20.40.110.1.6
    tunnelPm30sHisEndTime OBJECT-TYPE
        SYNTAX DateAndTime
        MAX-ACCESS read-only
        STATUS current
        DESCRIPTION
            "End Time."
        ::= { tunnelPm30sHisEntry 6 }

    -- 1.3.6.1.4.1.2011.2.25.3.70.20.40.110.1.7
    tunnelPm30sHisVldty OBJECT-TYPE
        SYNTAX ValidflagType
        MAX-ACCESS read-only
        STATUS current
        DESCRIPTION
            "Validity."
        ::= { tunnelPm30sHisEntry 7 }

    -- 1.3.6.1.4.1.2011.2.25.3.70.20.40.120
    tunnelPm30mHisTable OBJECT-TYPE
        SYNTAX SEQUENCE OF TunnelPm30mHisEntry
        MAX-ACCESS not-accessible
        STATUS current
        DESCRIPTION
            "tunnelPm30mHis."
        ::= { tunnel 120 }

    -- 1.3.6.1.4.1.2011.2.25.3.70.20.40.120.1
    tunnelPm30mHisEntry OBJECT-TYPE
        SYNTAX TunnelPm30mHisEntry
        MAX-ACCESS not-accessible
        STATUS current
        DESCRIPTION
            "tunnelPm30mHis."
        INDEX{ tunnelPm30mHisEid,tunnelPm30mHisParaLen,tunnelPm30mHisPara,tunnelPm30mHisStartTime,tunnelPm30mHisEndTime }
        ::= { tunnelPm30mHisTable 1 }

    TunnelPm30mHisEntry ::=
        SEQUENCE {
            tunnelPm30mHisEid
                DataPmEventType,
            tunnelPm30mHisParaLen
                Unsigned32,
            tunnelPm30mHisPara
                OCTET STRING,
            tunnelPm30mHisMonValue
                Counter64,
            tunnelPm30mHisStartTime
                DateAndTime,
            tunnelPm30mHisEndTime
                DateAndTime,
            tunnelPm30mHisVldty
                ValidflagType
        }

    -- 1.3.6.1.4.1.2011.2.25.3.70.20.40.120.1.1
    tunnelPm30mHisEid OBJECT-TYPE
        SYNTAX DataPmEventType
        MAX-ACCESS read-only
        STATUS current
        DESCRIPTION
            "DataPmEid."
        ::= { tunnelPm30mHisEntry 1 }

    -- 1.3.6.1.4.1.2011.2.25.3.70.20.40.120.1.2
    tunnelPm30mHisParaLen OBJECT-TYPE
        SYNTAX Unsigned32
        MAX-ACCESS read-only
        STATUS current
        DESCRIPTION
            "ParaLen."
        ::= { tunnelPm30mHisEntry 2 }

    -- 1.3.6.1.4.1.2011.2.25.3.70.20.40.120.1.3
    tunnelPm30mHisPara OBJECT-TYPE
        SYNTAX OCTET STRING(SIZE (0..100))
        MAX-ACCESS read-only
        STATUS current
        DESCRIPTION
            "para"
        ::= { tunnelPm30mHisEntry 3 }

    -- 1.3.6.1.4.1.2011.2.25.3.70.20.40.120.1.4
    tunnelPm30mHisMonValue OBJECT-TYPE
        SYNTAX Counter64
        MAX-ACCESS read-only
        STATUS current
        DESCRIPTION
            "DataPmMonValue."
        ::= { tunnelPm30mHisEntry 4 }

    -- 1.3.6.1.4.1.2011.2.25.3.70.20.40.120.1.5
    tunnelPm30mHisStartTime OBJECT-TYPE
        SYNTAX DateAndTime
        MAX-ACCESS read-only
        STATUS current
        DESCRIPTION
            "Start Time."
        ::= { tunnelPm30mHisEntry 5 }

    -- 1.3.6.1.4.1.2011.2.25.3.70.20.40.120.1.6
    tunnelPm30mHisEndTime OBJECT-TYPE
        SYNTAX DateAndTime
        MAX-ACCESS read-only
        STATUS current
        DESCRIPTION
            "End Time."
        ::= { tunnelPm30mHisEntry 6 }

    -- 1.3.6.1.4.1.2011.2.25.3.70.20.40.120.1.7
    tunnelPm30mHisVldty OBJECT-TYPE
        SYNTAX ValidflagType
        MAX-ACCESS read-only
        STATUS current
        DESCRIPTION
            "Validity."
        ::= { tunnelPm30mHisEntry 7 }

    -- 1.3.6.1.4.1.2011.2.25.3.70.20.40.130
    tunnelPmvar1HisTable OBJECT-TYPE
        SYNTAX SEQUENCE OF TunnelPmvar1HisEntry
        MAX-ACCESS not-accessible
        STATUS current
        DESCRIPTION
            "tunnelPmvar1His."
        ::= { tunnel 130 }

    -- 1.3.6.1.4.1.2011.2.25.3.70.20.40.130.1
    tunnelPmvar1HisEntry OBJECT-TYPE
        SYNTAX TunnelPmvar1HisEntry
        MAX-ACCESS not-accessible
        STATUS current
        DESCRIPTION
            "tunnelPmvar1His."
        INDEX{ tunnelPmvar1HisEid,tunnelPmvar1HisParaLen,tunnelPmvar1HisPara,tunnelPmvar1HisStartTime,tunnelPmvar1HisEndTime }
        ::= { tunnelPmvar1HisTable 1 }

    TunnelPmvar1HisEntry ::=
        SEQUENCE {
            tunnelPmvar1HisEid
                DataPmEventType,
            tunnelPmvar1HisParaLen
                Unsigned32,
            tunnelPmvar1HisPara
                OCTET STRING,
            tunnelPmvar1HisMonValue
                Counter64,
            tunnelPmvar1HisStartTime
                DateAndTime,
            tunnelPmvar1HisEndTime
                DateAndTime,
            tunnelPmvar1HisVldty
                ValidflagType
        }

    -- 1.3.6.1.4.1.2011.2.25.3.70.20.40.130.1.1
    tunnelPmvar1HisEid OBJECT-TYPE
        SYNTAX DataPmEventType
        MAX-ACCESS read-only
        STATUS current
        DESCRIPTION
            "DataPmEid."
        ::= { tunnelPmvar1HisEntry 1 }

    -- 1.3.6.1.4.1.2011.2.25.3.70.20.40.130.1.2
    tunnelPmvar1HisParaLen OBJECT-TYPE
        SYNTAX Unsigned32
        MAX-ACCESS read-only
        STATUS current
        DESCRIPTION
            "ParaLen."
        ::= { tunnelPmvar1HisEntry 2 }

    -- 1.3.6.1.4.1.2011.2.25.3.70.20.40.130.1.3
    tunnelPmvar1HisPara OBJECT-TYPE
        SYNTAX OCTET STRING (SIZE (0..100))
        MAX-ACCESS read-only
        STATUS current
        DESCRIPTION
            "para"
        ::= { tunnelPmvar1HisEntry 3 }

    -- 1.3.6.1.4.1.2011.2.25.3.70.20.40.130.1.4
    tunnelPmvar1HisMonValue OBJECT-TYPE
        SYNTAX Counter64
        MAX-ACCESS read-only
        STATUS current
        DESCRIPTION
            "DataPmMonValue."
        ::= { tunnelPmvar1HisEntry 4 }

    -- 1.3.6.1.4.1.2011.2.25.3.70.20.40.130.1.5
    tunnelPmvar1HisStartTime OBJECT-TYPE
        SYNTAX DateAndTime
        MAX-ACCESS read-only
        STATUS current
        DESCRIPTION
            "Start Time."
        ::= { tunnelPmvar1HisEntry 5 }

    -- 1.3.6.1.4.1.2011.2.25.3.70.20.40.130.1.6
    tunnelPmvar1HisEndTime OBJECT-TYPE
        SYNTAX DateAndTime
        MAX-ACCESS read-only
        STATUS current
        DESCRIPTION
            "End Time."
        ::= { tunnelPmvar1HisEntry 6 }

    -- 1.3.6.1.4.1.2011.2.25.3.70.20.40.130.1.7
    tunnelPmvar1HisVldty OBJECT-TYPE
        SYNTAX ValidflagType
        MAX-ACCESS read-only
        STATUS current
        DESCRIPTION
            "Validity."
        ::= { tunnelPmvar1HisEntry 7 }

    -- 1.3.6.1.4.1.2011.2.25.3.70.20.40.140
    tunnelPmvar2HisTable OBJECT-TYPE
        SYNTAX SEQUENCE OF TunnelPmvar2HisEntry
        MAX-ACCESS not-accessible
        STATUS current
        DESCRIPTION
            "tunnelPmvar2His."
        ::= { tunnel 140 }

    -- 1.3.6.1.4.1.2011.2.25.3.70.20.40.140.1
    tunnelPmvar2HisEntry OBJECT-TYPE
        SYNTAX TunnelPmvar2HisEntry
        MAX-ACCESS not-accessible
        STATUS current
        DESCRIPTION
            "tunnelPmvar2His."
        INDEX{ tunnelPmvar2HisEid,tunnelPmvar2HisParaLen,tunnelPmvar2HisPara,tunnelPmvar2HisStartTime,tunnelPmvar2HisEndTime }
        ::= { tunnelPmvar2HisTable 1 }

    TunnelPmvar2HisEntry ::=
        SEQUENCE {
            tunnelPmvar2HisEid
                DataPmEventType,
            tunnelPmvar2HisParaLen
                Unsigned32,
            tunnelPmvar2HisPara
                OCTET STRING,
            tunnelPmvar2HisMonValue
                Counter64,
            tunnelPmvar2HisStartTime
                DateAndTime,
            tunnelPmvar2HisEndTime
                DateAndTime,
            tunnelPmvar2HisVldty
                ValidflagType
        }

    -- 1.3.6.1.4.1.2011.2.25.3.70.20.40.140.1.1
    tunnelPmvar2HisEid OBJECT-TYPE
        SYNTAX DataPmEventType
        MAX-ACCESS read-only
        STATUS current
        DESCRIPTION
            "DataPmEid."
        ::= { tunnelPmvar2HisEntry 1 }

    -- 1.3.6.1.4.1.2011.2.25.3.70.20.40.140.1.2
    tunnelPmvar2HisParaLen OBJECT-TYPE
        SYNTAX Unsigned32
        MAX-ACCESS read-only
        STATUS current
        DESCRIPTION
            "ParaLen."
        ::= { tunnelPmvar2HisEntry 2 }

    -- 1.3.6.1.4.1.2011.2.25.3.70.20.40.140.1.3
    tunnelPmvar2HisPara OBJECT-TYPE
        SYNTAX OCTET STRING(SIZE (0..100))
        MAX-ACCESS read-only
        STATUS current
        DESCRIPTION
            "para"
        ::= { tunnelPmvar2HisEntry 3 }

    -- 1.3.6.1.4.1.2011.2.25.3.70.20.40.140.1.4
    tunnelPmvar2HisMonValue OBJECT-TYPE
        SYNTAX Counter64
        MAX-ACCESS read-only
        STATUS current
        DESCRIPTION
            "DataPmMonValue."
        ::= { tunnelPmvar2HisEntry 4 }

    -- 1.3.6.1.4.1.2011.2.25.3.70.20.40.140.1.5
    tunnelPmvar2HisStartTime OBJECT-TYPE
        SYNTAX DateAndTime
        MAX-ACCESS read-only
        STATUS current
        DESCRIPTION
            "Start Time."
        ::= { tunnelPmvar2HisEntry 5 }

    -- 1.3.6.1.4.1.2011.2.25.3.70.20.40.140.1.6
    tunnelPmvar2HisEndTime OBJECT-TYPE
        SYNTAX DateAndTime
        MAX-ACCESS read-only
        STATUS current
        DESCRIPTION
            "End Time."
        ::= { tunnelPmvar2HisEntry 6 }

    -- 1.3.6.1.4.1.2011.2.25.3.70.20.40.140.1.7
    tunnelPmvar2HisVldty OBJECT-TYPE
        SYNTAX ValidflagType
        MAX-ACCESS read-only
        STATUS current
        DESCRIPTION
            "Validity."
        ::= { tunnelPmvar2HisEntry 7 }

    -- 1.3.6.1.4.1.2011.2.25.3.70.20.42
    pwofatm OBJECT IDENTIFIER ::= { rtnData 42 }

    -- 1.3.6.1.4.1.2011.2.25.3.70.20.42.100
    pwofatmPmCurTable OBJECT-TYPE
        SYNTAX SEQUENCE OF PwofatmPmCurEntry
        MAX-ACCESS not-accessible
        STATUS current
        DESCRIPTION
            "pwofatmDataPm30sCur."
        ::= { pwofatm 100 }

    -- 1.3.6.1.4.1.2011.2.25.3.70.20.42.100.1
    pwofatmPmCurEntry OBJECT-TYPE
        SYNTAX PwofatmPmCurEntry
        MAX-ACCESS not-accessible
        STATUS current
        DESCRIPTION
            "pwofatmPmCur."
        INDEX{ pwofatmPmCurEid,pwofatmPmCurParaLen, pwofatmPmCurPara }
        ::= { pwofatmPmCurTable 1 }

    PwofatmPmCurEntry ::=
        SEQUENCE {
            pwofatmPmCurEid
                DataPmEventType,
            pwofatmPmCurParaLen
                Unsigned32,
            pwofatmPmCurPara
                OCTET STRING,
            pwofatmPmCurMonValue
                Counter64,
            pwofatmPmCurDatetime
                DateAndTime
        }

    -- 1.3.6.1.4.1.2011.2.25.3.70.20.42.100.1.1
    pwofatmPmCurEid OBJECT-TYPE
        SYNTAX DataPmEventType
        MAX-ACCESS read-only
        STATUS current
        DESCRIPTION
            "DataPmEid."
        ::= { pwofatmPmCurEntry 1 }

    -- 1.3.6.1.4.1.2011.2.25.3.70.20.42.100.1.2
    pwofatmPmCurParaLen OBJECT-TYPE
        SYNTAX Unsigned32
        MAX-ACCESS read-only
        STATUS current
        DESCRIPTION
            "ParaLen."
        ::= { pwofatmPmCurEntry 2 }

    -- 1.3.6.1.4.1.2011.2.25.3.70.20.42.100.1.3
    pwofatmPmCurPara OBJECT-TYPE
        SYNTAX OCTET STRING
        MAX-ACCESS read-only
        STATUS current
        DESCRIPTION
            "para"
        ::= { pwofatmPmCurEntry 3 }

    -- 1.3.6.1.4.1.2011.2.25.3.70.20.42.100.1.4
    pwofatmPmCurMonValue OBJECT-TYPE
        SYNTAX Counter64
        MAX-ACCESS read-only
        STATUS current
        DESCRIPTION
            "DataPmMonValue."
        ::= { pwofatmPmCurEntry 4 }

    -- 1.3.6.1.4.1.2011.2.25.3.70.20.42.100.1.5
    pwofatmPmCurDatetime OBJECT-TYPE
        SYNTAX DateAndTime
        MAX-ACCESS read-only
        STATUS current
        DESCRIPTION
            "Start Time."
        ::= { pwofatmPmCurEntry 5 }

    -- 1.3.6.1.4.1.2011.2.25.3.70.20.42.110
    pwofatmPm30sHisTable OBJECT-TYPE
        SYNTAX SEQUENCE OF PwofatmPm30sHisEntry
        MAX-ACCESS not-accessible
        STATUS current
        DESCRIPTION
            "pwofatmDataPm30sHis."
        ::= { pwofatm 110 }

    -- 1.3.6.1.4.1.2011.2.25.3.70.20.42.110.1
    pwofatmPm30sHisEntry OBJECT-TYPE
        SYNTAX PwofatmPm30sHisEntry
        MAX-ACCESS not-accessible
        STATUS current
        DESCRIPTION
            "pwofatmDataPm30sHis."
        INDEX{ pwofatmPm30sHisEid,pwofatmPm30sHisParaLen,pwofatmPm30sHisPara,pwofatmPm30sHisStartTime,pwofatmPm30sHisEndTime }
        ::= { pwofatmPm30sHisTable 1 }

    PwofatmPm30sHisEntry ::=
        SEQUENCE {
            pwofatmPm30sHisEid
                DataPmEventType,
            pwofatmPm30sHisParaLen
                Unsigned32,
            pwofatmPm30sHisPara
                OCTET STRING,
            pwofatmPm30sHisMonValue
                Counter64,
            pwofatmPm30sHisStartTime
                DateAndTime,
            pwofatmPm30sHisEndTime
                DateAndTime,
            pwofatmPm30sHisVldty
                ValidflagType
        }

    -- 1.3.6.1.4.1.2011.2.25.3.70.20.42.110.1.1
    pwofatmPm30sHisEid OBJECT-TYPE
        SYNTAX DataPmEventType
        MAX-ACCESS read-only
        STATUS current
        DESCRIPTION
            "DataPmEid."
        ::= { pwofatmPm30sHisEntry 1 }

    -- 1.3.6.1.4.1.2011.2.25.3.70.20.42.110.1.2
    pwofatmPm30sHisParaLen OBJECT-TYPE
        SYNTAX Unsigned32
        MAX-ACCESS read-only
        STATUS current
        DESCRIPTION
            "ParaLen."
        ::= { pwofatmPm30sHisEntry 2 }

    -- 1.3.6.1.4.1.2011.2.25.3.70.20.42.110.1.3
    pwofatmPm30sHisPara OBJECT-TYPE
        SYNTAX OCTET STRING(SIZE (0..100))
        MAX-ACCESS read-only
        STATUS current
        DESCRIPTION
            "para"
        ::= { pwofatmPm30sHisEntry 3 }

    -- 1.3.6.1.4.1.2011.2.25.3.70.20.42.110.1.4
    pwofatmPm30sHisMonValue OBJECT-TYPE
        SYNTAX Counter64
        MAX-ACCESS read-only
        STATUS current
        DESCRIPTION
            "DataPmMonValue."
        ::= { pwofatmPm30sHisEntry 4 }

    -- 1.3.6.1.4.1.2011.2.25.3.70.20.42.110.1.5
    pwofatmPm30sHisStartTime OBJECT-TYPE
        SYNTAX DateAndTime
        MAX-ACCESS read-only
        STATUS current
        DESCRIPTION
            "Start Time."
        ::= { pwofatmPm30sHisEntry 5 }

    -- 1.3.6.1.4.1.2011.2.25.3.70.20.42.110.1.6
    pwofatmPm30sHisEndTime OBJECT-TYPE
        SYNTAX DateAndTime
        MAX-ACCESS read-only
        STATUS current
        DESCRIPTION
            "End Time."
        ::= { pwofatmPm30sHisEntry 6 }

    -- 1.3.6.1.4.1.2011.2.25.3.70.20.42.110.1.7
    pwofatmPm30sHisVldty OBJECT-TYPE
        SYNTAX ValidflagType
        MAX-ACCESS read-only
        STATUS current
        DESCRIPTION
            "Validity."
        ::= { pwofatmPm30sHisEntry 7 }

    -- 1.3.6.1.4.1.2011.2.25.3.70.20.42.120
    pwofatmPm30mHisTable OBJECT-TYPE
        SYNTAX SEQUENCE OF PwofatmPm30mHisEntry
        MAX-ACCESS not-accessible
        STATUS current
        DESCRIPTION
            "pwofatmPm30mHis."
        ::= { pwofatm 120 }

    -- 1.3.6.1.4.1.2011.2.25.3.70.20.42.120.1
    pwofatmPm30mHisEntry OBJECT-TYPE
        SYNTAX PwofatmPm30mHisEntry
        MAX-ACCESS not-accessible
        STATUS current
        DESCRIPTION
            "pwofatmPm30mHis."
        INDEX{ pwofatmPm30mHisEid,pwofatmPm30mHisParaLen,pwofatmPm30mHisPara,pwofatmPm30mHisStartTime,pwofatmPm30mHisEndTime }
        ::= { pwofatmPm30mHisTable 1 }

    PwofatmPm30mHisEntry ::=
        SEQUENCE {
            pwofatmPm30mHisEid
                DataPmEventType,
            pwofatmPm30mHisParaLen
                Unsigned32,
            pwofatmPm30mHisPara
                OCTET STRING,
            pwofatmPm30mHisMonValue
                Counter64,
            pwofatmPm30mHisStartTime
                DateAndTime,
            pwofatmPm30mHisEndTime
                DateAndTime,
            pwofatmPm30mHisVldty
                ValidflagType
        }

    -- 1.3.6.1.4.1.2011.2.25.3.70.20.42.120.1.1
    pwofatmPm30mHisEid OBJECT-TYPE
        SYNTAX DataPmEventType
        MAX-ACCESS read-only
        STATUS current
        DESCRIPTION
            "DataPmEid."
        ::= { pwofatmPm30mHisEntry 1 }

    -- 1.3.6.1.4.1.2011.2.25.3.70.20.42.120.1.2
    pwofatmPm30mHisParaLen OBJECT-TYPE
        SYNTAX Unsigned32
        MAX-ACCESS read-only
        STATUS current
        DESCRIPTION
            "ParaLen."
        ::= { pwofatmPm30mHisEntry 2 }

    -- 1.3.6.1.4.1.2011.2.25.3.70.20.42.120.1.3
    pwofatmPm30mHisPara OBJECT-TYPE
        SYNTAX OCTET STRING(SIZE (0..100))
        MAX-ACCESS read-only
        STATUS current
        DESCRIPTION
            "para"
        ::= { pwofatmPm30mHisEntry 3 }

    -- 1.3.6.1.4.1.2011.2.25.3.70.20.42.120.1.4
    pwofatmPm30mHisMonValue OBJECT-TYPE
        SYNTAX Counter64
        MAX-ACCESS read-only
        STATUS current
        DESCRIPTION
            "DataPmMonValue."
        ::= { pwofatmPm30mHisEntry 4 }

    -- 1.3.6.1.4.1.2011.2.25.3.70.20.42.120.1.5
    pwofatmPm30mHisStartTime OBJECT-TYPE
        SYNTAX DateAndTime
        MAX-ACCESS read-only
        STATUS current
        DESCRIPTION
            "Start Time."
        ::= { pwofatmPm30mHisEntry 5 }

    -- 1.3.6.1.4.1.2011.2.25.3.70.20.42.120.1.6
    pwofatmPm30mHisEndTime OBJECT-TYPE
        SYNTAX DateAndTime
        MAX-ACCESS read-only
        STATUS current
        DESCRIPTION
            "End Time."
        ::= { pwofatmPm30mHisEntry 6 }

    -- 1.3.6.1.4.1.2011.2.25.3.70.20.42.120.1.7
    pwofatmPm30mHisVldty OBJECT-TYPE
        SYNTAX ValidflagType
        MAX-ACCESS read-only
        STATUS current
        DESCRIPTION
            "Validity."
        ::= { pwofatmPm30mHisEntry 7 }

    -- 1.3.6.1.4.1.2011.2.25.3.70.20.42.130
    pwofatmPmvar1HisTable OBJECT-TYPE
        SYNTAX SEQUENCE OF PwofatmPmvar1HisEntry
        MAX-ACCESS not-accessible
        STATUS current
        DESCRIPTION
            "pwofatmPmvar1His."
        ::= { pwofatm 130 }

    -- 1.3.6.1.4.1.2011.2.25.3.70.20.42.130.1
    pwofatmPmvar1HisEntry OBJECT-TYPE
        SYNTAX PwofatmPmvar1HisEntry
        MAX-ACCESS not-accessible
        STATUS current
        DESCRIPTION
            "pwofatmPmvar1His."
        INDEX{ pwofatmPmvar1HisEid,pwofatmPmvar1HisParaLen,pwofatmPmvar1HisPara,pwofatmPmvar1HisStartTime,pwofatmPmvar1HisEndTime }
        ::= { pwofatmPmvar1HisTable 1 }

    PwofatmPmvar1HisEntry ::=
        SEQUENCE {
            pwofatmPmvar1HisEid
                DataPmEventType,
            pwofatmPmvar1HisParaLen
                Unsigned32,
            pwofatmPmvar1HisPara
                OCTET STRING,
            pwofatmPmvar1HisMonValue
                Counter64,
            pwofatmPmvar1HisStartTime
                DateAndTime,
            pwofatmPmvar1HisEndTime
                DateAndTime,
            pwofatmPmvar1HisVldty
                ValidflagType
        }

    -- 1.3.6.1.4.1.2011.2.25.3.70.20.42.130.1.1
    pwofatmPmvar1HisEid OBJECT-TYPE
        SYNTAX DataPmEventType
        MAX-ACCESS read-only
        STATUS current
        DESCRIPTION
            "DataPmEid."
        ::= { pwofatmPmvar1HisEntry 1 }

    -- 1.3.6.1.4.1.2011.2.25.3.70.20.42.130.1.2
    pwofatmPmvar1HisParaLen OBJECT-TYPE
        SYNTAX Unsigned32
        MAX-ACCESS read-only
        STATUS current
        DESCRIPTION
            "ParaLen."
        ::= { pwofatmPmvar1HisEntry 2 }

    -- 1.3.6.1.4.1.2011.2.25.3.70.20.42.130.1.3
    pwofatmPmvar1HisPara OBJECT-TYPE
        SYNTAX OCTET STRING (SIZE (0..100))
        MAX-ACCESS read-only
        STATUS current
        DESCRIPTION
            "para"
        ::= { pwofatmPmvar1HisEntry 3 }

    -- 1.3.6.1.4.1.2011.2.25.3.70.20.42.130.1.4
    pwofatmPmvar1HisMonValue OBJECT-TYPE
        SYNTAX Counter64
        MAX-ACCESS read-only
        STATUS current
        DESCRIPTION
            "DataPmMonValue."
        ::= { pwofatmPmvar1HisEntry 4 }

    -- 1.3.6.1.4.1.2011.2.25.3.70.20.42.130.1.5
    pwofatmPmvar1HisStartTime OBJECT-TYPE
        SYNTAX DateAndTime
        MAX-ACCESS read-only
        STATUS current
        DESCRIPTION
            "Start Time."
        ::= { pwofatmPmvar1HisEntry 5 }

    -- 1.3.6.1.4.1.2011.2.25.3.70.20.42.130.1.6
    pwofatmPmvar1HisEndTime OBJECT-TYPE
        SYNTAX DateAndTime
        MAX-ACCESS read-only
        STATUS current
        DESCRIPTION
            "End Time."
        ::= { pwofatmPmvar1HisEntry 6 }

    -- 1.3.6.1.4.1.2011.2.25.3.70.20.42.130.1.7
    pwofatmPmvar1HisVldty OBJECT-TYPE
        SYNTAX ValidflagType
        MAX-ACCESS read-only
        STATUS current
        DESCRIPTION
            "Validity."
        ::= { pwofatmPmvar1HisEntry 7 }

    -- 1.3.6.1.4.1.2011.2.25.3.70.20.42.140
    pwofatmPmvar2HisTable OBJECT-TYPE
        SYNTAX SEQUENCE OF PwofatmPmvar2HisEntry
        MAX-ACCESS not-accessible
        STATUS current
        DESCRIPTION
            "pwofatmPmvar2His."
        ::= { pwofatm 140 }

    -- 1.3.6.1.4.1.2011.2.25.3.70.20.42.140.1
    pwofatmPmvar2HisEntry OBJECT-TYPE
        SYNTAX PwofatmPmvar2HisEntry
        MAX-ACCESS not-accessible
        STATUS current
        DESCRIPTION
            "pwofatmPmvar2His."
        INDEX{ pwofatmPmvar2HisEid,pwofatmPmvar2HisParaLen,pwofatmPmvar2HisPara,pwofatmPmvar2HisStartTime,pwofatmPmvar2HisEndTime }
        ::= { pwofatmPmvar2HisTable 1 }

    PwofatmPmvar2HisEntry ::=
        SEQUENCE {
            pwofatmPmvar2HisEid
                DataPmEventType,
            pwofatmPmvar2HisParaLen
                Unsigned32,
            pwofatmPmvar2HisPara
                OCTET STRING,
            pwofatmPmvar2HisMonValue
                Counter64,
            pwofatmPmvar2HisStartTime
                DateAndTime,
            pwofatmPmvar2HisEndTime
                DateAndTime,
            pwofatmPmvar2HisVldty
                ValidflagType
        }

    -- 1.3.6.1.4.1.2011.2.25.3.70.20.42.140.1.1
    pwofatmPmvar2HisEid OBJECT-TYPE
        SYNTAX DataPmEventType
        MAX-ACCESS read-only
        STATUS current
        DESCRIPTION
            "DataPmEid."
        ::= { pwofatmPmvar2HisEntry 1 }

    -- 1.3.6.1.4.1.2011.2.25.3.70.20.42.140.1.2
    pwofatmPmvar2HisParaLen OBJECT-TYPE
        SYNTAX Unsigned32
        MAX-ACCESS read-only
        STATUS current
        DESCRIPTION
            "ParaLen."
        ::= { pwofatmPmvar2HisEntry 2 }

    -- 1.3.6.1.4.1.2011.2.25.3.70.20.42.140.1.3
    pwofatmPmvar2HisPara OBJECT-TYPE
        SYNTAX OCTET STRING(SIZE (0..100))
        MAX-ACCESS read-only
        STATUS current
        DESCRIPTION
            "para"
        ::= { pwofatmPmvar2HisEntry 3 }

    -- 1.3.6.1.4.1.2011.2.25.3.70.20.42.140.1.4
    pwofatmPmvar2HisMonValue OBJECT-TYPE
        SYNTAX Counter64
        MAX-ACCESS read-only
        STATUS current
        DESCRIPTION
            "DataPmMonValue."
        ::= { pwofatmPmvar2HisEntry 4 }

    -- 1.3.6.1.4.1.2011.2.25.3.70.20.42.140.1.5
    pwofatmPmvar2HisStartTime OBJECT-TYPE
        SYNTAX DateAndTime
        MAX-ACCESS read-only
        STATUS current
        DESCRIPTION
            "Start Time."
        ::= { pwofatmPmvar2HisEntry 5 }

    -- 1.3.6.1.4.1.2011.2.25.3.70.20.42.140.1.6
    pwofatmPmvar2HisEndTime OBJECT-TYPE
        SYNTAX DateAndTime
        MAX-ACCESS read-only
        STATUS current
        DESCRIPTION
            "End Time."
        ::= { pwofatmPmvar2HisEntry 6 }

    -- 1.3.6.1.4.1.2011.2.25.3.70.20.42.140.1.7
    pwofatmPmvar2HisVldty OBJECT-TYPE
        SYNTAX ValidflagType
        MAX-ACCESS read-only
        STATUS current
        DESCRIPTION
            "Validity."
        ::= { pwofatmPmvar2HisEntry 7 }

    -- 1.3.6.1.4.1.2011.2.25.3.70.20.43
    pwofces OBJECT IDENTIFIER ::= { rtnData 43 }

    -- 1.3.6.1.4.1.2011.2.25.3.70.20.43.100
    pwofcesPmCurTable OBJECT-TYPE
        SYNTAX SEQUENCE OF PwofcesPmCurEntry
        MAX-ACCESS not-accessible
        STATUS current
        DESCRIPTION
            "pwofcesDataPm30sCur."
        ::= { pwofces 100 }

    -- 1.3.6.1.4.1.2011.2.25.3.70.20.43.100.1
    pwofcesPmCurEntry OBJECT-TYPE
        SYNTAX PwofcesPmCurEntry
        MAX-ACCESS not-accessible
        STATUS current
        DESCRIPTION
            "pwofcesPmCur."
        INDEX{ pwofcesPmCurEid,pwofcesPmCurParaLen, pwofcesPmCurPara }
        ::= { pwofcesPmCurTable 1 }

    PwofcesPmCurEntry ::=
        SEQUENCE {
            pwofcesPmCurEid
                DataPmEventType,
            pwofcesPmCurParaLen
                Unsigned32,
            pwofcesPmCurPara
                OCTET STRING,
            pwofcesPmCurMonValue
                Counter64,
            pwofcesPmCurDatetime
                DateAndTime
        }

    -- 1.3.6.1.4.1.2011.2.25.3.70.20.43.100.1.1
    pwofcesPmCurEid OBJECT-TYPE
        SYNTAX DataPmEventType
        MAX-ACCESS read-only
        STATUS current
        DESCRIPTION
            "DataPmEid."
        ::= { pwofcesPmCurEntry 1 }

    -- 1.3.6.1.4.1.2011.2.25.3.70.20.43.100.1.2
    pwofcesPmCurParaLen OBJECT-TYPE
        SYNTAX Unsigned32
        MAX-ACCESS read-only
        STATUS current
        DESCRIPTION
            "ParaLen."
        ::= { pwofcesPmCurEntry 2 }

    -- 1.3.6.1.4.1.2011.2.25.3.70.20.43.100.1.3
    pwofcesPmCurPara OBJECT-TYPE
        SYNTAX OCTET STRING
        MAX-ACCESS read-only
        STATUS current
        DESCRIPTION
            "para"
        ::= { pwofcesPmCurEntry 3 }

    -- 1.3.6.1.4.1.2011.2.25.3.70.20.43.100.1.4
    pwofcesPmCurMonValue OBJECT-TYPE
        SYNTAX Counter64
        MAX-ACCESS read-only
        STATUS current
        DESCRIPTION
            "DataPmMonValue."
        ::= { pwofcesPmCurEntry 4 }

    -- 1.3.6.1.4.1.2011.2.25.3.70.20.43.100.1.5
    pwofcesPmCurDatetime OBJECT-TYPE
        SYNTAX DateAndTime
        MAX-ACCESS read-only
        STATUS current
        DESCRIPTION
            "Start Time."
        ::= { pwofcesPmCurEntry 5 }

    -- 1.3.6.1.4.1.2011.2.25.3.70.20.43.110
    pwofcesPm30sHisTable OBJECT-TYPE
        SYNTAX SEQUENCE OF PwofcesPm30sHisEntry
        MAX-ACCESS not-accessible
        STATUS current
        DESCRIPTION
            "pwofcesDataPm30sHis."
        ::= { pwofces 110 }

    -- 1.3.6.1.4.1.2011.2.25.3.70.20.43.110.1
    pwofcesPm30sHisEntry OBJECT-TYPE
        SYNTAX PwofcesPm30sHisEntry
        MAX-ACCESS not-accessible
        STATUS current
        DESCRIPTION
            "pwofcesDataPm30sHis."
        INDEX{ pwofcesPm30sHisEid,pwofcesPm30sHisParaLen,pwofcesPm30sHisPara,pwofcesPm30sHisStartTime,pwofcesPm30sHisEndTime }
        ::= { pwofcesPm30sHisTable 1 }

    PwofcesPm30sHisEntry ::=
        SEQUENCE {
            pwofcesPm30sHisEid
                DataPmEventType,
            pwofcesPm30sHisParaLen
                Unsigned32,
            pwofcesPm30sHisPara
                OCTET STRING,
            pwofcesPm30sHisMonValue
                Counter64,
            pwofcesPm30sHisStartTime
                DateAndTime,
            pwofcesPm30sHisEndTime
                DateAndTime,
            pwofcesPm30sHisVldty
                ValidflagType
        }

    -- 1.3.6.1.4.1.2011.2.25.3.70.20.43.110.1.1
    pwofcesPm30sHisEid OBJECT-TYPE
        SYNTAX DataPmEventType
        MAX-ACCESS read-only
        STATUS current
        DESCRIPTION
            "DataPmEid."
        ::= { pwofcesPm30sHisEntry 1 }

    -- 1.3.6.1.4.1.2011.2.25.3.70.20.43.110.1.2
    pwofcesPm30sHisParaLen OBJECT-TYPE
        SYNTAX Unsigned32
        MAX-ACCESS read-only
        STATUS current
        DESCRIPTION
            "ParaLen."
        ::= { pwofcesPm30sHisEntry 2 }

    -- 1.3.6.1.4.1.2011.2.25.3.70.20.43.110.1.3
    pwofcesPm30sHisPara OBJECT-TYPE
        SYNTAX OCTET STRING(SIZE (0..100))
        MAX-ACCESS read-only
        STATUS current
        DESCRIPTION
            "para"
        ::= { pwofcesPm30sHisEntry 3 }

    -- 1.3.6.1.4.1.2011.2.25.3.70.20.43.110.1.4
    pwofcesPm30sHisMonValue OBJECT-TYPE
        SYNTAX Counter64
        MAX-ACCESS read-only
        STATUS current
        DESCRIPTION
            "DataPmMonValue."
        ::= { pwofcesPm30sHisEntry 4 }

    -- 1.3.6.1.4.1.2011.2.25.3.70.20.43.110.1.5
    pwofcesPm30sHisStartTime OBJECT-TYPE
        SYNTAX DateAndTime
        MAX-ACCESS read-only
        STATUS current
        DESCRIPTION
            "Start Time."
        ::= { pwofcesPm30sHisEntry 5 }

    -- 1.3.6.1.4.1.2011.2.25.3.70.20.43.110.1.6
    pwofcesPm30sHisEndTime OBJECT-TYPE
        SYNTAX DateAndTime
        MAX-ACCESS read-only
        STATUS current
        DESCRIPTION
            "End Time."
        ::= { pwofcesPm30sHisEntry 6 }

    -- 1.3.6.1.4.1.2011.2.25.3.70.20.43.110.1.7
    pwofcesPm30sHisVldty OBJECT-TYPE
        SYNTAX ValidflagType
        MAX-ACCESS read-only
        STATUS current
        DESCRIPTION
            "Validity."
        ::= { pwofcesPm30sHisEntry 7 }

    -- 1.3.6.1.4.1.2011.2.25.3.70.20.43.120
    pwofcesPm30mHisTable OBJECT-TYPE
        SYNTAX SEQUENCE OF PwofcesPm30mHisEntry
        MAX-ACCESS not-accessible
        STATUS current
        DESCRIPTION
            "pwofcesPm30mHis."
        ::= { pwofces 120 }

    -- 1.3.6.1.4.1.2011.2.25.3.70.20.43.120.1
    pwofcesPm30mHisEntry OBJECT-TYPE
        SYNTAX PwofcesPm30mHisEntry
        MAX-ACCESS not-accessible
        STATUS current
        DESCRIPTION
            "pwofcesPm30mHis."
        INDEX{ pwofcesPm30mHisEid,pwofcesPm30mHisParaLen,pwofcesPm30mHisPara,pwofcesPm30mHisStartTime,pwofcesPm30mHisEndTime }
        ::= { pwofcesPm30mHisTable 1 }

    PwofcesPm30mHisEntry ::=
        SEQUENCE {
            pwofcesPm30mHisEid
                DataPmEventType,
            pwofcesPm30mHisParaLen
                Unsigned32,
            pwofcesPm30mHisPara
                OCTET STRING,
            pwofcesPm30mHisMonValue
                Counter64,
            pwofcesPm30mHisStartTime
                DateAndTime,
            pwofcesPm30mHisEndTime
                DateAndTime,
            pwofcesPm30mHisVldty
                ValidflagType
        }

    -- 1.3.6.1.4.1.2011.2.25.3.70.20.43.120.1.1
    pwofcesPm30mHisEid OBJECT-TYPE
        SYNTAX DataPmEventType
        MAX-ACCESS read-only
        STATUS current
        DESCRIPTION
            "DataPmEid."
        ::= { pwofcesPm30mHisEntry 1 }

    -- 1.3.6.1.4.1.2011.2.25.3.70.20.43.120.1.2
    pwofcesPm30mHisParaLen OBJECT-TYPE
        SYNTAX Unsigned32
        MAX-ACCESS read-only
        STATUS current
        DESCRIPTION
            "ParaLen."
        ::= { pwofcesPm30mHisEntry 2 }

    -- 1.3.6.1.4.1.2011.2.25.3.70.20.43.120.1.3
    pwofcesPm30mHisPara OBJECT-TYPE
        SYNTAX OCTET STRING(SIZE (0..100))
        MAX-ACCESS read-only
        STATUS current
        DESCRIPTION
            "para"
        ::= { pwofcesPm30mHisEntry 3 }

    -- 1.3.6.1.4.1.2011.2.25.3.70.20.43.120.1.4
    pwofcesPm30mHisMonValue OBJECT-TYPE
        SYNTAX Counter64
        MAX-ACCESS read-only
        STATUS current
        DESCRIPTION
            "DataPmMonValue."
        ::= { pwofcesPm30mHisEntry 4 }

    -- 1.3.6.1.4.1.2011.2.25.3.70.20.43.120.1.5
    pwofcesPm30mHisStartTime OBJECT-TYPE
        SYNTAX DateAndTime
        MAX-ACCESS read-only
        STATUS current
        DESCRIPTION
            "Start Time."
        ::= { pwofcesPm30mHisEntry 5 }

    -- 1.3.6.1.4.1.2011.2.25.3.70.20.43.120.1.6
    pwofcesPm30mHisEndTime OBJECT-TYPE
        SYNTAX DateAndTime
        MAX-ACCESS read-only
        STATUS current
        DESCRIPTION
            "End Time."
        ::= { pwofcesPm30mHisEntry 6 }

    -- 1.3.6.1.4.1.2011.2.25.3.70.20.43.120.1.7
    pwofcesPm30mHisVldty OBJECT-TYPE
        SYNTAX ValidflagType
        MAX-ACCESS read-only
        STATUS current
        DESCRIPTION
            "Validity."
        ::= { pwofcesPm30mHisEntry 7 }

    -- 1.3.6.1.4.1.2011.2.25.3.70.20.43.130
    pwofcesPmvar1HisTable OBJECT-TYPE
        SYNTAX SEQUENCE OF PwofcesPmvar1HisEntry
        MAX-ACCESS not-accessible
        STATUS current
        DESCRIPTION
            "pwofcesPmvar1His."
        ::= { pwofces 130 }

    -- 1.3.6.1.4.1.2011.2.25.3.70.20.43.130.1
    pwofcesPmvar1HisEntry OBJECT-TYPE
        SYNTAX PwofcesPmvar1HisEntry
        MAX-ACCESS not-accessible
        STATUS current
        DESCRIPTION
            "pwofcesPmvar1His."
        INDEX{ pwofcesPmvar1HisEid,pwofcesPmvar1HisParaLen,pwofcesPmvar1HisPara,pwofcesPmvar1HisStartTime,pwofcesPmvar1HisEndTime }
        ::= { pwofcesPmvar1HisTable 1 }

    PwofcesPmvar1HisEntry ::=
        SEQUENCE {
            pwofcesPmvar1HisEid
                DataPmEventType,
            pwofcesPmvar1HisParaLen
                Unsigned32,
            pwofcesPmvar1HisPara
                OCTET STRING,
            pwofcesPmvar1HisMonValue
                Counter64,
            pwofcesPmvar1HisStartTime
                DateAndTime,
            pwofcesPmvar1HisEndTime
                DateAndTime,
            pwofcesPmvar1HisVldty
                ValidflagType
        }

    -- 1.3.6.1.4.1.2011.2.25.3.70.20.43.130.1.1
    pwofcesPmvar1HisEid OBJECT-TYPE
        SYNTAX DataPmEventType
        MAX-ACCESS read-only
        STATUS current
        DESCRIPTION
            "DataPmEid."
        ::= { pwofcesPmvar1HisEntry 1 }

    -- 1.3.6.1.4.1.2011.2.25.3.70.20.43.130.1.2
    pwofcesPmvar1HisParaLen OBJECT-TYPE
        SYNTAX Unsigned32
        MAX-ACCESS read-only
        STATUS current
        DESCRIPTION
            "ParaLen."
        ::= { pwofcesPmvar1HisEntry 2 }

    -- 1.3.6.1.4.1.2011.2.25.3.70.20.43.130.1.3
    pwofcesPmvar1HisPara OBJECT-TYPE
        SYNTAX OCTET STRING (SIZE (0..100))
        MAX-ACCESS read-only
        STATUS current
        DESCRIPTION
            "para"
        ::= { pwofcesPmvar1HisEntry 3 }

    -- 1.3.6.1.4.1.2011.2.25.3.70.20.43.130.1.4
    pwofcesPmvar1HisMonValue OBJECT-TYPE
        SYNTAX Counter64
        MAX-ACCESS read-only
        STATUS current
        DESCRIPTION
            "DataPmMonValue."
        ::= { pwofcesPmvar1HisEntry 4 }

    -- 1.3.6.1.4.1.2011.2.25.3.70.20.43.130.1.5
    pwofcesPmvar1HisStartTime OBJECT-TYPE
        SYNTAX DateAndTime
        MAX-ACCESS read-only
        STATUS current
        DESCRIPTION
            "Start Time."
        ::= { pwofcesPmvar1HisEntry 5 }

    -- 1.3.6.1.4.1.2011.2.25.3.70.20.43.130.1.6
    pwofcesPmvar1HisEndTime OBJECT-TYPE
        SYNTAX DateAndTime
        MAX-ACCESS read-only
        STATUS current
        DESCRIPTION
            "End Time."
        ::= { pwofcesPmvar1HisEntry 6 }

    -- 1.3.6.1.4.1.2011.2.25.3.70.20.43.130.1.7
    pwofcesPmvar1HisVldty OBJECT-TYPE
        SYNTAX ValidflagType
        MAX-ACCESS read-only
        STATUS current
        DESCRIPTION
            "Validity."
        ::= { pwofcesPmvar1HisEntry 7 }

    -- 1.3.6.1.4.1.2011.2.25.3.70.20.43.140
    pwofcesPmvar2HisTable OBJECT-TYPE
        SYNTAX SEQUENCE OF PwofcesPmvar2HisEntry
        MAX-ACCESS not-accessible
        STATUS current
        DESCRIPTION
            "pwofcesPmvar2His."
        ::= { pwofces 140 }

    -- 1.3.6.1.4.1.2011.2.25.3.70.20.43.140.1
    pwofcesPmvar2HisEntry OBJECT-TYPE
        SYNTAX PwofcesPmvar2HisEntry
        MAX-ACCESS not-accessible
        STATUS current
        DESCRIPTION
            "pwofcesPmvar2His."
        INDEX{ pwofcesPmvar2HisEid,pwofcesPmvar2HisParaLen,pwofcesPmvar2HisPara,pwofcesPmvar2HisStartTime,pwofcesPmvar2HisEndTime }
        ::= { pwofcesPmvar2HisTable 1 }

    PwofcesPmvar2HisEntry ::=
        SEQUENCE {
            pwofcesPmvar2HisEid
                DataPmEventType,
            pwofcesPmvar2HisParaLen
                Unsigned32,
            pwofcesPmvar2HisPara
                OCTET STRING,
            pwofcesPmvar2HisMonValue
                Counter64,
            pwofcesPmvar2HisStartTime
                DateAndTime,
            pwofcesPmvar2HisEndTime
                DateAndTime,
            pwofcesPmvar2HisVldty
                ValidflagType
        }

    -- 1.3.6.1.4.1.2011.2.25.3.70.20.43.140.1.1
    pwofcesPmvar2HisEid OBJECT-TYPE
        SYNTAX DataPmEventType
        MAX-ACCESS read-only
        STATUS current
        DESCRIPTION
            "DataPmEid."
        ::= { pwofcesPmvar2HisEntry 1 }

    -- 1.3.6.1.4.1.2011.2.25.3.70.20.43.140.1.2
    pwofcesPmvar2HisParaLen OBJECT-TYPE
        SYNTAX Unsigned32
        MAX-ACCESS read-only
        STATUS current
        DESCRIPTION
            "ParaLen."
        ::= { pwofcesPmvar2HisEntry 2 }

    -- 1.3.6.1.4.1.2011.2.25.3.70.20.43.140.1.3
    pwofcesPmvar2HisPara OBJECT-TYPE
        SYNTAX OCTET STRING(SIZE (0..100))
        MAX-ACCESS read-only
        STATUS current
        DESCRIPTION
            "para"
        ::= { pwofcesPmvar2HisEntry 3 }

    -- 1.3.6.1.4.1.2011.2.25.3.70.20.43.140.1.4
    pwofcesPmvar2HisMonValue OBJECT-TYPE
        SYNTAX Counter64
        MAX-ACCESS read-only
        STATUS current
        DESCRIPTION
            "DataPmMonValue."
        ::= { pwofcesPmvar2HisEntry 4 }

    -- 1.3.6.1.4.1.2011.2.25.3.70.20.43.140.1.5
    pwofcesPmvar2HisStartTime OBJECT-TYPE
        SYNTAX DateAndTime
        MAX-ACCESS read-only
        STATUS current
        DESCRIPTION
            "Start Time."
        ::= { pwofcesPmvar2HisEntry 5 }

    -- 1.3.6.1.4.1.2011.2.25.3.70.20.43.140.1.6
    pwofcesPmvar2HisEndTime OBJECT-TYPE
        SYNTAX DateAndTime
        MAX-ACCESS read-only
        STATUS current
        DESCRIPTION
            "End Time."
        ::= { pwofcesPmvar2HisEntry 6 }

    -- 1.3.6.1.4.1.2011.2.25.3.70.20.43.140.1.7
    pwofcesPmvar2HisVldty OBJECT-TYPE
        SYNTAX ValidflagType
        MAX-ACCESS read-only
        STATUS current
        DESCRIPTION
            "Validity."
        ::= { pwofcesPmvar2HisEntry 7 }

    -- 1.3.6.1.4.1.2011.2.25.3.70.20.44
    pwofl2vpn OBJECT IDENTIFIER ::= { rtnData 44 }

    -- 1.3.6.1.4.1.2011.2.25.3.70.20.44.100
    pwofl2vpnPmCurTable OBJECT-TYPE
        SYNTAX SEQUENCE OF Pwofl2vpnPmCurEntry
        MAX-ACCESS not-accessible
        STATUS current
        DESCRIPTION
            "pwofl2vpnDataPm30sCur."
        ::= { pwofl2vpn 100 }

    -- 1.3.6.1.4.1.2011.2.25.3.70.20.44.100.1
    pwofl2vpnPmCurEntry OBJECT-TYPE
        SYNTAX Pwofl2vpnPmCurEntry
        MAX-ACCESS not-accessible
        STATUS current
        DESCRIPTION
            "pwofl2vpnPmCur."
        INDEX{ pwofl2vpnPmCurEid,pwofl2vpnPmCurParaLen, pwofl2vpnPmCurPara }
        ::= { pwofl2vpnPmCurTable 1 }

    Pwofl2vpnPmCurEntry ::=
        SEQUENCE {
            pwofl2vpnPmCurEid
                DataPmEventType,
            pwofl2vpnPmCurParaLen
                Unsigned32,
            pwofl2vpnPmCurPara
                OCTET STRING,
            pwofl2vpnPmCurMonValue
                Counter64,
            pwofl2vpnPmCurDatetime
                DateAndTime
        }

    -- 1.3.6.1.4.1.2011.2.25.3.70.20.44.100.1.1
    pwofl2vpnPmCurEid OBJECT-TYPE
        SYNTAX DataPmEventType
        MAX-ACCESS read-only
        STATUS current
        DESCRIPTION
            "DataPmEid."
        ::= { pwofl2vpnPmCurEntry 1 }

    -- 1.3.6.1.4.1.2011.2.25.3.70.20.44.100.1.2
    pwofl2vpnPmCurParaLen OBJECT-TYPE
        SYNTAX Unsigned32
        MAX-ACCESS read-only
        STATUS current
        DESCRIPTION
            "ParaLen."
        ::= { pwofl2vpnPmCurEntry 2 }

    -- 1.3.6.1.4.1.2011.2.25.3.70.20.44.100.1.3
    pwofl2vpnPmCurPara OBJECT-TYPE
        SYNTAX OCTET STRING
        MAX-ACCESS read-only
        STATUS current
        DESCRIPTION
            "para"
        ::= { pwofl2vpnPmCurEntry 3 }

    -- 1.3.6.1.4.1.2011.2.25.3.70.20.44.100.1.4
    pwofl2vpnPmCurMonValue OBJECT-TYPE
        SYNTAX Counter64
        MAX-ACCESS read-only
        STATUS current
        DESCRIPTION
            "DataPmMonValue."
        ::= { pwofl2vpnPmCurEntry 4 }

    -- 1.3.6.1.4.1.2011.2.25.3.70.20.44.100.1.5
    pwofl2vpnPmCurDatetime OBJECT-TYPE
        SYNTAX DateAndTime
        MAX-ACCESS read-only
        STATUS current
        DESCRIPTION
            "Start Time."
        ::= { pwofl2vpnPmCurEntry 5 }

    -- 1.3.6.1.4.1.2011.2.25.3.70.20.44.110
    pwofl2vpnPm30sHisTable OBJECT-TYPE
        SYNTAX SEQUENCE OF Pwofl2vpnPm30sHisEntry
        MAX-ACCESS not-accessible
        STATUS current
        DESCRIPTION
            "pwofl2vpnDataPm30sHis."
        ::= { pwofl2vpn 110 }

    -- 1.3.6.1.4.1.2011.2.25.3.70.20.44.110.1
    pwofl2vpnPm30sHisEntry OBJECT-TYPE
        SYNTAX Pwofl2vpnPm30sHisEntry
        MAX-ACCESS not-accessible
        STATUS current
        DESCRIPTION
            "pwofl2vpnDataPm30sHis."
        INDEX{ pwofl2vpnPm30sHisEid,pwofl2vpnPm30sHisParaLen,pwofl2vpnPm30sHisPara,pwofl2vpnPm30sHisStartTime,pwofl2vpnPm30sHisEndTime }
        ::= { pwofl2vpnPm30sHisTable 1 }

    Pwofl2vpnPm30sHisEntry ::=
        SEQUENCE {
            pwofl2vpnPm30sHisEid
                DataPmEventType,
            pwofl2vpnPm30sHisParaLen
                Unsigned32,
            pwofl2vpnPm30sHisPara
                OCTET STRING,
            pwofl2vpnPm30sHisMonValue
                Counter64,
            pwofl2vpnPm30sHisStartTime
                DateAndTime,
            pwofl2vpnPm30sHisEndTime
                DateAndTime,
            pwofl2vpnPm30sHisVldty
                ValidflagType
        }

    -- 1.3.6.1.4.1.2011.2.25.3.70.20.44.110.1.1
    pwofl2vpnPm30sHisEid OBJECT-TYPE
        SYNTAX DataPmEventType
        MAX-ACCESS read-only
        STATUS current
        DESCRIPTION
            "DataPmEid."
        ::= { pwofl2vpnPm30sHisEntry 1 }

    -- 1.3.6.1.4.1.2011.2.25.3.70.20.44.110.1.2
    pwofl2vpnPm30sHisParaLen OBJECT-TYPE
        SYNTAX Unsigned32
        MAX-ACCESS read-only
        STATUS current
        DESCRIPTION
            "ParaLen."
        ::= { pwofl2vpnPm30sHisEntry 2 }

    -- 1.3.6.1.4.1.2011.2.25.3.70.20.44.110.1.3
    pwofl2vpnPm30sHisPara OBJECT-TYPE
        SYNTAX OCTET STRING(SIZE (0..100))
        MAX-ACCESS read-only
        STATUS current
        DESCRIPTION
            "para"
        ::= { pwofl2vpnPm30sHisEntry 3 }

    -- 1.3.6.1.4.1.2011.2.25.3.70.20.44.110.1.4
    pwofl2vpnPm30sHisMonValue OBJECT-TYPE
        SYNTAX Counter64
        MAX-ACCESS read-only
        STATUS current
        DESCRIPTION
            "DataPmMonValue."
        ::= { pwofl2vpnPm30sHisEntry 4 }

    -- 1.3.6.1.4.1.2011.2.25.3.70.20.44.110.1.5
    pwofl2vpnPm30sHisStartTime OBJECT-TYPE
        SYNTAX DateAndTime
        MAX-ACCESS read-only
        STATUS current
        DESCRIPTION
            "Start Time."
        ::= { pwofl2vpnPm30sHisEntry 5 }

    -- 1.3.6.1.4.1.2011.2.25.3.70.20.44.110.1.6
    pwofl2vpnPm30sHisEndTime OBJECT-TYPE
        SYNTAX DateAndTime
        MAX-ACCESS read-only
        STATUS current
        DESCRIPTION
            "End Time."
        ::= { pwofl2vpnPm30sHisEntry 6 }

    -- 1.3.6.1.4.1.2011.2.25.3.70.20.44.110.1.7
    pwofl2vpnPm30sHisVldty OBJECT-TYPE
        SYNTAX ValidflagType
        MAX-ACCESS read-only
        STATUS current
        DESCRIPTION
            "Validity."
        ::= { pwofl2vpnPm30sHisEntry 7 }

    -- 1.3.6.1.4.1.2011.2.25.3.70.20.44.120
    pwofl2vpnPm30mHisTable OBJECT-TYPE
        SYNTAX SEQUENCE OF Pwofl2vpnPm30mHisEntry
        MAX-ACCESS not-accessible
        STATUS current
        DESCRIPTION
            "pwofl2vpnPm30mHis."
        ::= { pwofl2vpn 120 }

    -- 1.3.6.1.4.1.2011.2.25.3.70.20.44.120.1
    pwofl2vpnPm30mHisEntry OBJECT-TYPE
        SYNTAX Pwofl2vpnPm30mHisEntry
        MAX-ACCESS not-accessible
        STATUS current
        DESCRIPTION
            "pwofl2vpnPm30mHis."
        INDEX{ pwofl2vpnPm30mHisEid,pwofl2vpnPm30mHisParaLen,pwofl2vpnPm30mHisPara,pwofl2vpnPm30mHisStartTime,pwofl2vpnPm30mHisEndTime }
        ::= { pwofl2vpnPm30mHisTable 1 }

    Pwofl2vpnPm30mHisEntry ::=
        SEQUENCE {
            pwofl2vpnPm30mHisEid
                DataPmEventType,
            pwofl2vpnPm30mHisParaLen
                Unsigned32,
            pwofl2vpnPm30mHisPara
                OCTET STRING,
            pwofl2vpnPm30mHisMonValue
                Counter64,
            pwofl2vpnPm30mHisStartTime
                DateAndTime,
            pwofl2vpnPm30mHisEndTime
                DateAndTime,
            pwofl2vpnPm30mHisVldty
                ValidflagType
        }

    -- 1.3.6.1.4.1.2011.2.25.3.70.20.44.120.1.1
    pwofl2vpnPm30mHisEid OBJECT-TYPE
        SYNTAX DataPmEventType
        MAX-ACCESS read-only
        STATUS current
        DESCRIPTION
            "DataPmEid."
        ::= { pwofl2vpnPm30mHisEntry 1 }

    -- 1.3.6.1.4.1.2011.2.25.3.70.20.44.120.1.2
    pwofl2vpnPm30mHisParaLen OBJECT-TYPE
        SYNTAX Unsigned32
        MAX-ACCESS read-only
        STATUS current
        DESCRIPTION
            "ParaLen."
        ::= { pwofl2vpnPm30mHisEntry 2 }

    -- 1.3.6.1.4.1.2011.2.25.3.70.20.44.120.1.3
    pwofl2vpnPm30mHisPara OBJECT-TYPE
        SYNTAX OCTET STRING(SIZE (0..100))
        MAX-ACCESS read-only
        STATUS current
        DESCRIPTION
            "para"
        ::= { pwofl2vpnPm30mHisEntry 3 }

    -- 1.3.6.1.4.1.2011.2.25.3.70.20.44.120.1.4
    pwofl2vpnPm30mHisMonValue OBJECT-TYPE
        SYNTAX Counter64
        MAX-ACCESS read-only
        STATUS current
        DESCRIPTION
            "DataPmMonValue."
        ::= { pwofl2vpnPm30mHisEntry 4 }

    -- 1.3.6.1.4.1.2011.2.25.3.70.20.44.120.1.5
    pwofl2vpnPm30mHisStartTime OBJECT-TYPE
        SYNTAX DateAndTime
        MAX-ACCESS read-only
        STATUS current
        DESCRIPTION
            "Start Time."
        ::= { pwofl2vpnPm30mHisEntry 5 }

    -- 1.3.6.1.4.1.2011.2.25.3.70.20.44.120.1.6
    pwofl2vpnPm30mHisEndTime OBJECT-TYPE
        SYNTAX DateAndTime
        MAX-ACCESS read-only
        STATUS current
        DESCRIPTION
            "End Time."
        ::= { pwofl2vpnPm30mHisEntry 6 }

    -- 1.3.6.1.4.1.2011.2.25.3.70.20.44.120.1.7
    pwofl2vpnPm30mHisVldty OBJECT-TYPE
        SYNTAX ValidflagType
        MAX-ACCESS read-only
        STATUS current
        DESCRIPTION
            "Validity."
        ::= { pwofl2vpnPm30mHisEntry 7 }

    -- 1.3.6.1.4.1.2011.2.25.3.70.20.44.130
    pwofl2vpnPmvar1HisTable OBJECT-TYPE
        SYNTAX SEQUENCE OF Pwofl2vpnPmvar1HisEntry
        MAX-ACCESS not-accessible
        STATUS current
        DESCRIPTION
            "pwofl2vpnPmvar1His."
        ::= { pwofl2vpn 130 }

    -- 1.3.6.1.4.1.2011.2.25.3.70.20.44.130.1
    pwofl2vpnPmvar1HisEntry OBJECT-TYPE
        SYNTAX Pwofl2vpnPmvar1HisEntry
        MAX-ACCESS not-accessible
        STATUS current
        DESCRIPTION
            "pwofl2vpnPmvar1His."
        INDEX{ pwofl2vpnPmvar1HisEid,pwofl2vpnPmvar1HisParaLen,pwofl2vpnPmvar1HisPara,pwofl2vpnPmvar1HisStartTime,pwofl2vpnPmvar1HisEndTime }
        ::= { pwofl2vpnPmvar1HisTable 1 }

    Pwofl2vpnPmvar1HisEntry ::=
        SEQUENCE {
            pwofl2vpnPmvar1HisEid
                DataPmEventType,
            pwofl2vpnPmvar1HisParaLen
                Unsigned32,
            pwofl2vpnPmvar1HisPara
                OCTET STRING,
            pwofl2vpnPmvar1HisMonValue
                Counter64,
            pwofl2vpnPmvar1HisStartTime
                DateAndTime,
            pwofl2vpnPmvar1HisEndTime
                DateAndTime,
            pwofl2vpnPmvar1HisVldty
                ValidflagType
        }

    -- 1.3.6.1.4.1.2011.2.25.3.70.20.44.130.1.1
    pwofl2vpnPmvar1HisEid OBJECT-TYPE
        SYNTAX DataPmEventType
        MAX-ACCESS read-only
        STATUS current
        DESCRIPTION
            "DataPmEid."
        ::= { pwofl2vpnPmvar1HisEntry 1 }

    -- 1.3.6.1.4.1.2011.2.25.3.70.20.44.130.1.2
    pwofl2vpnPmvar1HisParaLen OBJECT-TYPE
        SYNTAX Unsigned32
        MAX-ACCESS read-only
        STATUS current
        DESCRIPTION
            "ParaLen."
        ::= { pwofl2vpnPmvar1HisEntry 2 }

    -- 1.3.6.1.4.1.2011.2.25.3.70.20.44.130.1.3
    pwofl2vpnPmvar1HisPara OBJECT-TYPE
        SYNTAX OCTET STRING (SIZE (0..100))
        MAX-ACCESS read-only
        STATUS current
        DESCRIPTION
            "para"
        ::= { pwofl2vpnPmvar1HisEntry 3 }

    -- 1.3.6.1.4.1.2011.2.25.3.70.20.44.130.1.4
    pwofl2vpnPmvar1HisMonValue OBJECT-TYPE
        SYNTAX Counter64
        MAX-ACCESS read-only
        STATUS current
        DESCRIPTION
            "DataPmMonValue."
        ::= { pwofl2vpnPmvar1HisEntry 4 }

    -- 1.3.6.1.4.1.2011.2.25.3.70.20.44.130.1.5
    pwofl2vpnPmvar1HisStartTime OBJECT-TYPE
        SYNTAX DateAndTime
        MAX-ACCESS read-only
        STATUS current
        DESCRIPTION
            "Start Time."
        ::= { pwofl2vpnPmvar1HisEntry 5 }

    -- 1.3.6.1.4.1.2011.2.25.3.70.20.44.130.1.6
    pwofl2vpnPmvar1HisEndTime OBJECT-TYPE
        SYNTAX DateAndTime
        MAX-ACCESS read-only
        STATUS current
        DESCRIPTION
            "End Time."
        ::= { pwofl2vpnPmvar1HisEntry 6 }

    -- 1.3.6.1.4.1.2011.2.25.3.70.20.44.130.1.7
    pwofl2vpnPmvar1HisVldty OBJECT-TYPE
        SYNTAX ValidflagType
        MAX-ACCESS read-only
        STATUS current
        DESCRIPTION
            "Validity."
        ::= { pwofl2vpnPmvar1HisEntry 7 }

    -- 1.3.6.1.4.1.2011.2.25.3.70.20.44.140
    pwofl2vpnPmvar2HisTable OBJECT-TYPE
        SYNTAX SEQUENCE OF Pwofl2vpnPmvar2HisEntry
        MAX-ACCESS not-accessible
        STATUS current
        DESCRIPTION
            "pwofl2vpnPmvar2His."
        ::= { pwofl2vpn 140 }

    -- 1.3.6.1.4.1.2011.2.25.3.70.20.44.140.1
    pwofl2vpnPmvar2HisEntry OBJECT-TYPE
        SYNTAX Pwofl2vpnPmvar2HisEntry
        MAX-ACCESS not-accessible
        STATUS current
        DESCRIPTION
            "pwofl2vpnPmvar2His."
        INDEX{ pwofl2vpnPmvar2HisEid,pwofl2vpnPmvar2HisParaLen,pwofl2vpnPmvar2HisPara,pwofl2vpnPmvar2HisStartTime,pwofl2vpnPmvar2HisEndTime }
        ::= { pwofl2vpnPmvar2HisTable 1 }

    Pwofl2vpnPmvar2HisEntry ::=
        SEQUENCE {
            pwofl2vpnPmvar2HisEid
                DataPmEventType,
            pwofl2vpnPmvar2HisParaLen
                Unsigned32,
            pwofl2vpnPmvar2HisPara
                OCTET STRING,
            pwofl2vpnPmvar2HisMonValue
                Counter64,
            pwofl2vpnPmvar2HisStartTime
                DateAndTime,
            pwofl2vpnPmvar2HisEndTime
                DateAndTime,
            pwofl2vpnPmvar2HisVldty
                ValidflagType
        }

    -- 1.3.6.1.4.1.2011.2.25.3.70.20.44.140.1.1
    pwofl2vpnPmvar2HisEid OBJECT-TYPE
        SYNTAX DataPmEventType
        MAX-ACCESS read-only
        STATUS current
        DESCRIPTION
            "DataPmEid."
        ::= { pwofl2vpnPmvar2HisEntry 1 }

    -- 1.3.6.1.4.1.2011.2.25.3.70.20.44.140.1.2
    pwofl2vpnPmvar2HisParaLen OBJECT-TYPE
        SYNTAX Unsigned32
        MAX-ACCESS read-only
        STATUS current
        DESCRIPTION
            "ParaLen."
        ::= { pwofl2vpnPmvar2HisEntry 2 }

    -- 1.3.6.1.4.1.2011.2.25.3.70.20.44.140.1.3
    pwofl2vpnPmvar2HisPara OBJECT-TYPE
        SYNTAX OCTET STRING(SIZE (0..100))
        MAX-ACCESS read-only
        STATUS current
        DESCRIPTION
            "para"
        ::= { pwofl2vpnPmvar2HisEntry 3 }

    -- 1.3.6.1.4.1.2011.2.25.3.70.20.44.140.1.4
    pwofl2vpnPmvar2HisMonValue OBJECT-TYPE
        SYNTAX Counter64
        MAX-ACCESS read-only
        STATUS current
        DESCRIPTION
            "DataPmMonValue."
        ::= { pwofl2vpnPmvar2HisEntry 4 }

    -- 1.3.6.1.4.1.2011.2.25.3.70.20.44.140.1.5
    pwofl2vpnPmvar2HisStartTime OBJECT-TYPE
        SYNTAX DateAndTime
        MAX-ACCESS read-only
        STATUS current
        DESCRIPTION
            "Start Time."
        ::= { pwofl2vpnPmvar2HisEntry 5 }

    -- 1.3.6.1.4.1.2011.2.25.3.70.20.44.140.1.6
    pwofl2vpnPmvar2HisEndTime OBJECT-TYPE
        SYNTAX DateAndTime
        MAX-ACCESS read-only
        STATUS current
        DESCRIPTION
            "End Time."
        ::= { pwofl2vpnPmvar2HisEntry 6 }

    -- 1.3.6.1.4.1.2011.2.25.3.70.20.44.140.1.7
    pwofl2vpnPmvar2HisVldty OBJECT-TYPE
        SYNTAX ValidflagType
        MAX-ACCESS read-only
        STATUS current
        DESCRIPTION
            "Validity."
        ::= { pwofl2vpnPmvar2HisEntry 7 }

    -- 1.3.6.1.4.1.2011.2.25.3.70.20.45
    atmconnection OBJECT IDENTIFIER ::= { rtnData 45 }

    -- 1.3.6.1.4.1.2011.2.25.3.70.20.45.100
    atmconnectionPmCurTable OBJECT-TYPE
        SYNTAX SEQUENCE OF AtmconnectionPmCurEntry
        MAX-ACCESS not-accessible
        STATUS current
        DESCRIPTION
            "atmconnectionDataPm30sCur."
        ::= { atmconnection 100 }

    -- 1.3.6.1.4.1.2011.2.25.3.70.20.45.100.1
    atmconnectionPmCurEntry OBJECT-TYPE
        SYNTAX AtmconnectionPmCurEntry
        MAX-ACCESS not-accessible
        STATUS current
        DESCRIPTION
            "atmconnectionPmCur."
        INDEX{ atmconnectionPmCurEid,atmconnectionPmCurParaLen, atmconnectionPmCurPara }
        ::= { atmconnectionPmCurTable 1 }

    AtmconnectionPmCurEntry ::=
        SEQUENCE {
            atmconnectionPmCurEid
                DataPmEventType,
            atmconnectionPmCurParaLen
                Unsigned32,
            atmconnectionPmCurPara
                OCTET STRING,
            atmconnectionPmCurMonValue
                Counter64,
            atmconnectionPmCurDatetime
                DateAndTime
        }

    -- 1.3.6.1.4.1.2011.2.25.3.70.20.45.100.1.1
    atmconnectionPmCurEid OBJECT-TYPE
        SYNTAX DataPmEventType
        MAX-ACCESS read-only
        STATUS current
        DESCRIPTION
            "DataPmEid."
        ::= { atmconnectionPmCurEntry 1 }

    -- 1.3.6.1.4.1.2011.2.25.3.70.20.45.100.1.2
    atmconnectionPmCurParaLen OBJECT-TYPE
        SYNTAX Unsigned32
        MAX-ACCESS read-only
        STATUS current
        DESCRIPTION
            "ParaLen."
        ::= { atmconnectionPmCurEntry 2 }

    -- 1.3.6.1.4.1.2011.2.25.3.70.20.45.100.1.3
    atmconnectionPmCurPara OBJECT-TYPE
        SYNTAX OCTET STRING
        MAX-ACCESS read-only
        STATUS current
        DESCRIPTION
            "para"
        ::= { atmconnectionPmCurEntry 3 }

    -- 1.3.6.1.4.1.2011.2.25.3.70.20.45.100.1.4
    atmconnectionPmCurMonValue OBJECT-TYPE
        SYNTAX Counter64
        MAX-ACCESS read-only
        STATUS current
        DESCRIPTION
            "DataPmMonValue."
        ::= { atmconnectionPmCurEntry 4 }

    -- 1.3.6.1.4.1.2011.2.25.3.70.20.45.100.1.5
    atmconnectionPmCurDatetime OBJECT-TYPE
        SYNTAX DateAndTime
        MAX-ACCESS read-only
        STATUS current
        DESCRIPTION
            "Start Time."
        ::= { atmconnectionPmCurEntry 5 }

    -- 1.3.6.1.4.1.2011.2.25.3.70.20.45.110
    atmconnectionPm30sHisTable OBJECT-TYPE
        SYNTAX SEQUENCE OF AtmconnectionPm30sHisEntry
        MAX-ACCESS not-accessible
        STATUS current
        DESCRIPTION
            "atmconnectionDataPm30sHis."
        ::= { atmconnection 110 }

    -- 1.3.6.1.4.1.2011.2.25.3.70.20.45.110.1
    atmconnectionPm30sHisEntry OBJECT-TYPE
        SYNTAX AtmconnectionPm30sHisEntry
        MAX-ACCESS not-accessible
        STATUS current
        DESCRIPTION
            "atmconnectionDataPm30sHis."
        INDEX{ atmconnectionPm30sHisEid,atmconnectionPm30sHisParaLen,atmconnectionPm30sHisPara,atmconnectionPm30sHisStartTime,atmconnectionPm30sHisEndTime }
        ::= { atmconnectionPm30sHisTable 1 }

    AtmconnectionPm30sHisEntry ::=
        SEQUENCE {
            atmconnectionPm30sHisEid
                DataPmEventType,
            atmconnectionPm30sHisParaLen
                Unsigned32,
            atmconnectionPm30sHisPara
                OCTET STRING,
            atmconnectionPm30sHisMonValue
                Counter64,
            atmconnectionPm30sHisStartTime
                DateAndTime,
            atmconnectionPm30sHisEndTime
                DateAndTime,
            atmconnectionPm30sHisVldty
                ValidflagType
        }

    -- 1.3.6.1.4.1.2011.2.25.3.70.20.45.110.1.1
    atmconnectionPm30sHisEid OBJECT-TYPE
        SYNTAX DataPmEventType
        MAX-ACCESS read-only
        STATUS current
        DESCRIPTION
            "DataPmEid."
        ::= { atmconnectionPm30sHisEntry 1 }

    -- 1.3.6.1.4.1.2011.2.25.3.70.20.45.110.1.2
    atmconnectionPm30sHisParaLen OBJECT-TYPE
        SYNTAX Unsigned32
        MAX-ACCESS read-only
        STATUS current
        DESCRIPTION
            "ParaLen."
        ::= { atmconnectionPm30sHisEntry 2 }

    -- 1.3.6.1.4.1.2011.2.25.3.70.20.45.110.1.3
    atmconnectionPm30sHisPara OBJECT-TYPE
        SYNTAX OCTET STRING(SIZE (0..100))
        MAX-ACCESS read-only
        STATUS current
        DESCRIPTION
            "para"
        ::= { atmconnectionPm30sHisEntry 3 }

    -- 1.3.6.1.4.1.2011.2.25.3.70.20.45.110.1.4
    atmconnectionPm30sHisMonValue OBJECT-TYPE
        SYNTAX Counter64
        MAX-ACCESS read-only
        STATUS current
        DESCRIPTION
            "DataPmMonValue."
        ::= { atmconnectionPm30sHisEntry 4 }

    -- 1.3.6.1.4.1.2011.2.25.3.70.20.45.110.1.5
    atmconnectionPm30sHisStartTime OBJECT-TYPE
        SYNTAX DateAndTime
        MAX-ACCESS read-only
        STATUS current
        DESCRIPTION
            "Start Time."
        ::= { atmconnectionPm30sHisEntry 5 }

    -- 1.3.6.1.4.1.2011.2.25.3.70.20.45.110.1.6
    atmconnectionPm30sHisEndTime OBJECT-TYPE
        SYNTAX DateAndTime
        MAX-ACCESS read-only
        STATUS current
        DESCRIPTION
            "End Time."
        ::= { atmconnectionPm30sHisEntry 6 }

    -- 1.3.6.1.4.1.2011.2.25.3.70.20.45.110.1.7
    atmconnectionPm30sHisVldty OBJECT-TYPE
        SYNTAX ValidflagType
        MAX-ACCESS read-only
        STATUS current
        DESCRIPTION
            "Validity."
        ::= { atmconnectionPm30sHisEntry 7 }

    -- 1.3.6.1.4.1.2011.2.25.3.70.20.45.120
    atmconnectionPm30mHisTable OBJECT-TYPE
        SYNTAX SEQUENCE OF AtmconnectionPm30mHisEntry
        MAX-ACCESS not-accessible
        STATUS current
        DESCRIPTION
            "atmconnectionPm30mHis."
        ::= { atmconnection 120 }

    -- 1.3.6.1.4.1.2011.2.25.3.70.20.45.120.1
    atmconnectionPm30mHisEntry OBJECT-TYPE
        SYNTAX AtmconnectionPm30mHisEntry
        MAX-ACCESS not-accessible
        STATUS current
        DESCRIPTION
            "atmconnectionPm30mHis."
        INDEX{ atmconnectionPm30mHisEid,atmconnectionPm30mHisParaLen,atmconnectionPm30mHisPara,atmconnectionPm30mHisStartTime,atmconnectionPm30mHisEndTime }
        ::= { atmconnectionPm30mHisTable 1 }

    AtmconnectionPm30mHisEntry ::=
        SEQUENCE {
            atmconnectionPm30mHisEid
                DataPmEventType,
            atmconnectionPm30mHisParaLen
                Unsigned32,
            atmconnectionPm30mHisPara
                OCTET STRING,
            atmconnectionPm30mHisMonValue
                Counter64,
            atmconnectionPm30mHisStartTime
                DateAndTime,
            atmconnectionPm30mHisEndTime
                DateAndTime,
            atmconnectionPm30mHisVldty
                ValidflagType
        }

    -- 1.3.6.1.4.1.2011.2.25.3.70.20.45.120.1.1
    atmconnectionPm30mHisEid OBJECT-TYPE
        SYNTAX DataPmEventType
        MAX-ACCESS read-only
        STATUS current
        DESCRIPTION
            "DataPmEid."
        ::= { atmconnectionPm30mHisEntry 1 }

    -- 1.3.6.1.4.1.2011.2.25.3.70.20.45.120.1.2
    atmconnectionPm30mHisParaLen OBJECT-TYPE
        SYNTAX Unsigned32
        MAX-ACCESS read-only
        STATUS current
        DESCRIPTION
            "ParaLen."
        ::= { atmconnectionPm30mHisEntry 2 }

    -- 1.3.6.1.4.1.2011.2.25.3.70.20.45.120.1.3
    atmconnectionPm30mHisPara OBJECT-TYPE
        SYNTAX OCTET STRING(SIZE (0..100))
        MAX-ACCESS read-only
        STATUS current
        DESCRIPTION
            "para"
        ::= { atmconnectionPm30mHisEntry 3 }

    -- 1.3.6.1.4.1.2011.2.25.3.70.20.45.120.1.4
    atmconnectionPm30mHisMonValue OBJECT-TYPE
        SYNTAX Counter64
        MAX-ACCESS read-only
        STATUS current
        DESCRIPTION
            "DataPmMonValue."
        ::= { atmconnectionPm30mHisEntry 4 }

    -- 1.3.6.1.4.1.2011.2.25.3.70.20.45.120.1.5
    atmconnectionPm30mHisStartTime OBJECT-TYPE
        SYNTAX DateAndTime
        MAX-ACCESS read-only
        STATUS current
        DESCRIPTION
            "Start Time."
        ::= { atmconnectionPm30mHisEntry 5 }

    -- 1.3.6.1.4.1.2011.2.25.3.70.20.45.120.1.6
    atmconnectionPm30mHisEndTime OBJECT-TYPE
        SYNTAX DateAndTime
        MAX-ACCESS read-only
        STATUS current
        DESCRIPTION
            "End Time."
        ::= { atmconnectionPm30mHisEntry 6 }

    -- 1.3.6.1.4.1.2011.2.25.3.70.20.45.120.1.7
    atmconnectionPm30mHisVldty OBJECT-TYPE
        SYNTAX ValidflagType
        MAX-ACCESS read-only
        STATUS current
        DESCRIPTION
            "Validity."
        ::= { atmconnectionPm30mHisEntry 7 }

    -- 1.3.6.1.4.1.2011.2.25.3.70.20.45.130
    atmconnectionPmvar1HisTable OBJECT-TYPE
        SYNTAX SEQUENCE OF AtmconnectionPmvar1HisEntry
        MAX-ACCESS not-accessible
        STATUS current
        DESCRIPTION
            "atmconnectionPmvar1His."
        ::= { atmconnection 130 }

    -- 1.3.6.1.4.1.2011.2.25.3.70.20.45.130.1
    atmconnectionPmvar1HisEntry OBJECT-TYPE
        SYNTAX AtmconnectionPmvar1HisEntry
        MAX-ACCESS not-accessible
        STATUS current
        DESCRIPTION
            "atmconnectionPmvar1His."
        INDEX{ atmconnectionPmvar1HisEid,atmconnectionPmvar1HisParaLen,atmconnectionPmvar1HisPara,atmconnectionPmvar1HisStartTime,atmconnectionPmvar1HisEndTime }
        ::= { atmconnectionPmvar1HisTable 1 }

    AtmconnectionPmvar1HisEntry ::=
        SEQUENCE {
            atmconnectionPmvar1HisEid
                DataPmEventType,
            atmconnectionPmvar1HisParaLen
                Unsigned32,
            atmconnectionPmvar1HisPara
                OCTET STRING,
            atmconnectionPmvar1HisMonValue
                Counter64,
            atmconnectionPmvar1HisStartTime
                DateAndTime,
            atmconnectionPmvar1HisEndTime
                DateAndTime,
            atmconnectionPmvar1HisVldty
                ValidflagType
        }

    -- 1.3.6.1.4.1.2011.2.25.3.70.20.45.130.1.1
    atmconnectionPmvar1HisEid OBJECT-TYPE
        SYNTAX DataPmEventType
        MAX-ACCESS read-only
        STATUS current
        DESCRIPTION
            "DataPmEid."
        ::= { atmconnectionPmvar1HisEntry 1 }

    -- 1.3.6.1.4.1.2011.2.25.3.70.20.45.130.1.2
    atmconnectionPmvar1HisParaLen OBJECT-TYPE
        SYNTAX Unsigned32
        MAX-ACCESS read-only
        STATUS current
        DESCRIPTION
            "ParaLen."
        ::= { atmconnectionPmvar1HisEntry 2 }

    -- 1.3.6.1.4.1.2011.2.25.3.70.20.45.130.1.3
    atmconnectionPmvar1HisPara OBJECT-TYPE
        SYNTAX OCTET STRING (SIZE (0..100))
        MAX-ACCESS read-only
        STATUS current
        DESCRIPTION
            "para"
        ::= { atmconnectionPmvar1HisEntry 3 }

    -- 1.3.6.1.4.1.2011.2.25.3.70.20.45.130.1.4
    atmconnectionPmvar1HisMonValue OBJECT-TYPE
        SYNTAX Counter64
        MAX-ACCESS read-only
        STATUS current
        DESCRIPTION
            "DataPmMonValue."
        ::= { atmconnectionPmvar1HisEntry 4 }

    -- 1.3.6.1.4.1.2011.2.25.3.70.20.45.130.1.5
    atmconnectionPmvar1HisStartTime OBJECT-TYPE
        SYNTAX DateAndTime
        MAX-ACCESS read-only
        STATUS current
        DESCRIPTION
            "Start Time."
        ::= { atmconnectionPmvar1HisEntry 5 }

    -- 1.3.6.1.4.1.2011.2.25.3.70.20.45.130.1.6
    atmconnectionPmvar1HisEndTime OBJECT-TYPE
        SYNTAX DateAndTime
        MAX-ACCESS read-only
        STATUS current
        DESCRIPTION
            "End Time."
        ::= { atmconnectionPmvar1HisEntry 6 }

    -- 1.3.6.1.4.1.2011.2.25.3.70.20.45.130.1.7
    atmconnectionPmvar1HisVldty OBJECT-TYPE
        SYNTAX ValidflagType
        MAX-ACCESS read-only
        STATUS current
        DESCRIPTION
            "Validity."
        ::= { atmconnectionPmvar1HisEntry 7 }

    -- 1.3.6.1.4.1.2011.2.25.3.70.20.45.140
    atmconnectionPmvar2HisTable OBJECT-TYPE
        SYNTAX SEQUENCE OF AtmconnectionPmvar2HisEntry
        MAX-ACCESS not-accessible
        STATUS current
        DESCRIPTION
            "atmconnectionPmvar2His."
        ::= { atmconnection 140 }

    -- 1.3.6.1.4.1.2011.2.25.3.70.20.45.140.1
    atmconnectionPmvar2HisEntry OBJECT-TYPE
        SYNTAX AtmconnectionPmvar2HisEntry
        MAX-ACCESS not-accessible
        STATUS current
        DESCRIPTION
            "atmconnectionPmvar2His."
        INDEX{ atmconnectionPmvar2HisEid,atmconnectionPmvar2HisParaLen,atmconnectionPmvar2HisPara,atmconnectionPmvar2HisStartTime,atmconnectionPmvar2HisEndTime }
        ::= { atmconnectionPmvar2HisTable 1 }

    AtmconnectionPmvar2HisEntry ::=
        SEQUENCE {
            atmconnectionPmvar2HisEid
                DataPmEventType,
            atmconnectionPmvar2HisParaLen
                Unsigned32,
            atmconnectionPmvar2HisPara
                OCTET STRING,
            atmconnectionPmvar2HisMonValue
                Counter64,
            atmconnectionPmvar2HisStartTime
                DateAndTime,
            atmconnectionPmvar2HisEndTime
                DateAndTime,
            atmconnectionPmvar2HisVldty
                ValidflagType
        }

    -- 1.3.6.1.4.1.2011.2.25.3.70.20.45.140.1.1
    atmconnectionPmvar2HisEid OBJECT-TYPE
        SYNTAX DataPmEventType
        MAX-ACCESS read-only
        STATUS current
        DESCRIPTION
            "DataPmEid."
        ::= { atmconnectionPmvar2HisEntry 1 }

    -- 1.3.6.1.4.1.2011.2.25.3.70.20.45.140.1.2
    atmconnectionPmvar2HisParaLen OBJECT-TYPE
        SYNTAX Unsigned32
        MAX-ACCESS read-only
        STATUS current
        DESCRIPTION
            "ParaLen."
        ::= { atmconnectionPmvar2HisEntry 2 }

    -- 1.3.6.1.4.1.2011.2.25.3.70.20.45.140.1.3
    atmconnectionPmvar2HisPara OBJECT-TYPE
        SYNTAX OCTET STRING(SIZE (0..100))
        MAX-ACCESS read-only
        STATUS current
        DESCRIPTION
            "para"
        ::= { atmconnectionPmvar2HisEntry 3 }

    -- 1.3.6.1.4.1.2011.2.25.3.70.20.45.140.1.4
    atmconnectionPmvar2HisMonValue OBJECT-TYPE
        SYNTAX Counter64
        MAX-ACCESS read-only
        STATUS current
        DESCRIPTION
            "DataPmMonValue."
        ::= { atmconnectionPmvar2HisEntry 4 }

    -- 1.3.6.1.4.1.2011.2.25.3.70.20.45.140.1.5
    atmconnectionPmvar2HisStartTime OBJECT-TYPE
        SYNTAX DateAndTime
        MAX-ACCESS read-only
        STATUS current
        DESCRIPTION
            "Start Time."
        ::= { atmconnectionPmvar2HisEntry 5 }

    -- 1.3.6.1.4.1.2011.2.25.3.70.20.45.140.1.6
    atmconnectionPmvar2HisEndTime OBJECT-TYPE
        SYNTAX DateAndTime
        MAX-ACCESS read-only
        STATUS current
        DESCRIPTION
            "End Time."
        ::= { atmconnectionPmvar2HisEntry 6 }

    -- 1.3.6.1.4.1.2011.2.25.3.70.20.45.140.1.7
    atmconnectionPmvar2HisVldty OBJECT-TYPE
        SYNTAX ValidflagType
        MAX-ACCESS read-only
        STATUS current
        DESCRIPTION
            "Validity."
        ::= { atmconnectionPmvar2HisEntry 7 }

    -- 1.3.6.1.4.1.2011.2.25.3.70.20.48
    vuniofl2vpn OBJECT IDENTIFIER ::= { rtnData 48 }

    -- 1.3.6.1.4.1.2011.2.25.3.70.20.48.100
    vuniofl2vpnPmCurTable OBJECT-TYPE
        SYNTAX SEQUENCE OF Vuniofl2vpnPmCurEntry
        MAX-ACCESS not-accessible
        STATUS current
        DESCRIPTION
            "vuniofl2vpnDataPm30sCur."
        ::= { vuniofl2vpn 100 }

    -- 1.3.6.1.4.1.2011.2.25.3.70.20.48.100.1
    vuniofl2vpnPmCurEntry OBJECT-TYPE
        SYNTAX Vuniofl2vpnPmCurEntry
        MAX-ACCESS not-accessible
        STATUS current
        DESCRIPTION
            "vuniofl2vpnPmCur."
        INDEX{ vuniofl2vpnPmCurEid,vuniofl2vpnPmCurParaLen, vuniofl2vpnPmCurPara }
        ::= { vuniofl2vpnPmCurTable 1 }

    Vuniofl2vpnPmCurEntry ::=
        SEQUENCE {
            vuniofl2vpnPmCurEid
                DataPmEventType,
            vuniofl2vpnPmCurParaLen
                Unsigned32,
            vuniofl2vpnPmCurPara
                OCTET STRING,
            vuniofl2vpnPmCurMonValue
                Counter64,
            vuniofl2vpnPmCurDatetime
                DateAndTime
        }

    -- 1.3.6.1.4.1.2011.2.25.3.70.20.48.100.1.1
    vuniofl2vpnPmCurEid OBJECT-TYPE
        SYNTAX DataPmEventType
        MAX-ACCESS read-only
        STATUS current
        DESCRIPTION
            "DataPmEid."
        ::= { vuniofl2vpnPmCurEntry 1 }

    -- 1.3.6.1.4.1.2011.2.25.3.70.20.48.100.1.2
    vuniofl2vpnPmCurParaLen OBJECT-TYPE
        SYNTAX Unsigned32
        MAX-ACCESS read-only
        STATUS current
        DESCRIPTION
            "ParaLen."
        ::= { vuniofl2vpnPmCurEntry 2 }

    -- 1.3.6.1.4.1.2011.2.25.3.70.20.48.100.1.3
    vuniofl2vpnPmCurPara OBJECT-TYPE
        SYNTAX OCTET STRING
        MAX-ACCESS read-only
        STATUS current
        DESCRIPTION
            "para"
        ::= { vuniofl2vpnPmCurEntry 3 }

    -- 1.3.6.1.4.1.2011.2.25.3.70.20.48.100.1.4
    vuniofl2vpnPmCurMonValue OBJECT-TYPE
        SYNTAX Counter64
        MAX-ACCESS read-only
        STATUS current
        DESCRIPTION
            "DataPmMonValue."
        ::= { vuniofl2vpnPmCurEntry 4 }

    -- 1.3.6.1.4.1.2011.2.25.3.70.20.48.100.1.5
    vuniofl2vpnPmCurDatetime OBJECT-TYPE
        SYNTAX DateAndTime
        MAX-ACCESS read-only
        STATUS current
        DESCRIPTION
            "Start Time."
        ::= { vuniofl2vpnPmCurEntry 5 }

    -- 1.3.6.1.4.1.2011.2.25.3.70.20.48.110
    vuniofl2vpnPm30sHisTable OBJECT-TYPE
        SYNTAX SEQUENCE OF Vuniofl2vpnPm30sHisEntry
        MAX-ACCESS not-accessible
        STATUS current
        DESCRIPTION
            "vuniofl2vpnDataPm30sHis."
        ::= { vuniofl2vpn 110 }

    -- 1.3.6.1.4.1.2011.2.25.3.70.20.48.110.1
    vuniofl2vpnPm30sHisEntry OBJECT-TYPE
        SYNTAX Vuniofl2vpnPm30sHisEntry
        MAX-ACCESS not-accessible
        STATUS current
        DESCRIPTION
            "vuniofl2vpnDataPm30sHis."
        INDEX{ vuniofl2vpnPm30sHisEid,vuniofl2vpnPm30sHisParaLen,vuniofl2vpnPm30sHisPara,vuniofl2vpnPm30sHisStartTime,vuniofl2vpnPm30sHisEndTime }
        ::= { vuniofl2vpnPm30sHisTable 1 }

    Vuniofl2vpnPm30sHisEntry ::=
        SEQUENCE {
            vuniofl2vpnPm30sHisEid
                DataPmEventType,
            vuniofl2vpnPm30sHisParaLen
                Unsigned32,
            vuniofl2vpnPm30sHisPara
                OCTET STRING,
            vuniofl2vpnPm30sHisMonValue
                Counter64,
            vuniofl2vpnPm30sHisStartTime
                DateAndTime,
            vuniofl2vpnPm30sHisEndTime
                DateAndTime,
            vuniofl2vpnPm30sHisVldty
                ValidflagType
        }

    -- 1.3.6.1.4.1.2011.2.25.3.70.20.48.110.1.1
    vuniofl2vpnPm30sHisEid OBJECT-TYPE
        SYNTAX DataPmEventType
        MAX-ACCESS read-only
        STATUS current
        DESCRIPTION
            "DataPmEid."
        ::= { vuniofl2vpnPm30sHisEntry 1 }

    -- 1.3.6.1.4.1.2011.2.25.3.70.20.48.110.1.2
    vuniofl2vpnPm30sHisParaLen OBJECT-TYPE
        SYNTAX Unsigned32
        MAX-ACCESS read-only
        STATUS current
        DESCRIPTION
            "ParaLen."
        ::= { vuniofl2vpnPm30sHisEntry 2 }

    -- 1.3.6.1.4.1.2011.2.25.3.70.20.48.110.1.3
    vuniofl2vpnPm30sHisPara OBJECT-TYPE
        SYNTAX OCTET STRING(SIZE (0..100))
        MAX-ACCESS read-only
        STATUS current
        DESCRIPTION
            "para"
        ::= { vuniofl2vpnPm30sHisEntry 3 }

    -- 1.3.6.1.4.1.2011.2.25.3.70.20.48.110.1.4
    vuniofl2vpnPm30sHisMonValue OBJECT-TYPE
        SYNTAX Counter64
        MAX-ACCESS read-only
        STATUS current
        DESCRIPTION
            "DataPmMonValue."
        ::= { vuniofl2vpnPm30sHisEntry 4 }

    -- 1.3.6.1.4.1.2011.2.25.3.70.20.48.110.1.5
    vuniofl2vpnPm30sHisStartTime OBJECT-TYPE
        SYNTAX DateAndTime
        MAX-ACCESS read-only
        STATUS current
        DESCRIPTION
            "Start Time."
        ::= { vuniofl2vpnPm30sHisEntry 5 }

    -- 1.3.6.1.4.1.2011.2.25.3.70.20.48.110.1.6
    vuniofl2vpnPm30sHisEndTime OBJECT-TYPE
        SYNTAX DateAndTime
        MAX-ACCESS read-only
        STATUS current
        DESCRIPTION
            "End Time."
        ::= { vuniofl2vpnPm30sHisEntry 6 }

    -- 1.3.6.1.4.1.2011.2.25.3.70.20.48.110.1.7
    vuniofl2vpnPm30sHisVldty OBJECT-TYPE
        SYNTAX ValidflagType
        MAX-ACCESS read-only
        STATUS current
        DESCRIPTION
            "Validity."
        ::= { vuniofl2vpnPm30sHisEntry 7 }

    -- 1.3.6.1.4.1.2011.2.25.3.70.20.48.120
    vuniofl2vpnPm30mHisTable OBJECT-TYPE
        SYNTAX SEQUENCE OF Vuniofl2vpnPm30mHisEntry
        MAX-ACCESS not-accessible
        STATUS current
        DESCRIPTION
            "vuniofl2vpnPm30mHis."
        ::= { vuniofl2vpn 120 }

    -- 1.3.6.1.4.1.2011.2.25.3.70.20.48.120.1
    vuniofl2vpnPm30mHisEntry OBJECT-TYPE
        SYNTAX Vuniofl2vpnPm30mHisEntry
        MAX-ACCESS not-accessible
        STATUS current
        DESCRIPTION
            "vuniofl2vpnPm30mHis."
        INDEX{ vuniofl2vpnPm30mHisEid,vuniofl2vpnPm30mHisParaLen,vuniofl2vpnPm30mHisPara,vuniofl2vpnPm30mHisStartTime,vuniofl2vpnPm30mHisEndTime }
        ::= { vuniofl2vpnPm30mHisTable 1 }

    Vuniofl2vpnPm30mHisEntry ::=
        SEQUENCE {
            vuniofl2vpnPm30mHisEid
                DataPmEventType,
            vuniofl2vpnPm30mHisParaLen
                Unsigned32,
            vuniofl2vpnPm30mHisPara
                OCTET STRING,
            vuniofl2vpnPm30mHisMonValue
                Counter64,
            vuniofl2vpnPm30mHisStartTime
                DateAndTime,
            vuniofl2vpnPm30mHisEndTime
                DateAndTime,
            vuniofl2vpnPm30mHisVldty
                ValidflagType
        }

    -- 1.3.6.1.4.1.2011.2.25.3.70.20.48.120.1.1
    vuniofl2vpnPm30mHisEid OBJECT-TYPE
        SYNTAX DataPmEventType
        MAX-ACCESS read-only
        STATUS current
        DESCRIPTION
            "DataPmEid."
        ::= { vuniofl2vpnPm30mHisEntry 1 }

    -- 1.3.6.1.4.1.2011.2.25.3.70.20.48.120.1.2
    vuniofl2vpnPm30mHisParaLen OBJECT-TYPE
        SYNTAX Unsigned32
        MAX-ACCESS read-only
        STATUS current
        DESCRIPTION
            "ParaLen."
        ::= { vuniofl2vpnPm30mHisEntry 2 }

    -- 1.3.6.1.4.1.2011.2.25.3.70.20.48.120.1.3
    vuniofl2vpnPm30mHisPara OBJECT-TYPE
        SYNTAX OCTET STRING(SIZE (0..100))
        MAX-ACCESS read-only
        STATUS current
        DESCRIPTION
            "para"
        ::= { vuniofl2vpnPm30mHisEntry 3 }

    -- 1.3.6.1.4.1.2011.2.25.3.70.20.48.120.1.4
    vuniofl2vpnPm30mHisMonValue OBJECT-TYPE
        SYNTAX Counter64
        MAX-ACCESS read-only
        STATUS current
        DESCRIPTION
            "DataPmMonValue."
        ::= { vuniofl2vpnPm30mHisEntry 4 }

    -- 1.3.6.1.4.1.2011.2.25.3.70.20.48.120.1.5
    vuniofl2vpnPm30mHisStartTime OBJECT-TYPE
        SYNTAX DateAndTime
        MAX-ACCESS read-only
        STATUS current
        DESCRIPTION
            "Start Time."
        ::= { vuniofl2vpnPm30mHisEntry 5 }

    -- 1.3.6.1.4.1.2011.2.25.3.70.20.48.120.1.6
    vuniofl2vpnPm30mHisEndTime OBJECT-TYPE
        SYNTAX DateAndTime
        MAX-ACCESS read-only
        STATUS current
        DESCRIPTION
            "End Time."
        ::= { vuniofl2vpnPm30mHisEntry 6 }

    -- 1.3.6.1.4.1.2011.2.25.3.70.20.48.120.1.7
    vuniofl2vpnPm30mHisVldty OBJECT-TYPE
        SYNTAX ValidflagType
        MAX-ACCESS read-only
        STATUS current
        DESCRIPTION
            "Validity."
        ::= { vuniofl2vpnPm30mHisEntry 7 }

    -- 1.3.6.1.4.1.2011.2.25.3.70.20.48.130
    vuniofl2vpnPmvar1HisTable OBJECT-TYPE
        SYNTAX SEQUENCE OF Vuniofl2vpnPmvar1HisEntry
        MAX-ACCESS not-accessible
        STATUS current
        DESCRIPTION
            "vuniofl2vpnPmvar1His."
        ::= { vuniofl2vpn 130 }

    -- 1.3.6.1.4.1.2011.2.25.3.70.20.48.130.1
    vuniofl2vpnPmvar1HisEntry OBJECT-TYPE
        SYNTAX Vuniofl2vpnPmvar1HisEntry
        MAX-ACCESS not-accessible
        STATUS current
        DESCRIPTION
            "vuniofl2vpnPmvar1His."
        INDEX{ vuniofl2vpnPmvar1HisEid,vuniofl2vpnPmvar1HisParaLen,vuniofl2vpnPmvar1HisPara,vuniofl2vpnPmvar1HisStartTime,vuniofl2vpnPmvar1HisEndTime }
        ::= { vuniofl2vpnPmvar1HisTable 1 }

    Vuniofl2vpnPmvar1HisEntry ::=
        SEQUENCE {
            vuniofl2vpnPmvar1HisEid
                DataPmEventType,
            vuniofl2vpnPmvar1HisParaLen
                Unsigned32,
            vuniofl2vpnPmvar1HisPara
                OCTET STRING,
            vuniofl2vpnPmvar1HisMonValue
                Counter64,
            vuniofl2vpnPmvar1HisStartTime
                DateAndTime,
            vuniofl2vpnPmvar1HisEndTime
                DateAndTime,
            vuniofl2vpnPmvar1HisVldty
                ValidflagType
        }

    -- 1.3.6.1.4.1.2011.2.25.3.70.20.48.130.1.1
    vuniofl2vpnPmvar1HisEid OBJECT-TYPE
        SYNTAX DataPmEventType
        MAX-ACCESS read-only
        STATUS current
        DESCRIPTION
            "DataPmEid."
        ::= { vuniofl2vpnPmvar1HisEntry 1 }

    -- 1.3.6.1.4.1.2011.2.25.3.70.20.48.130.1.2
    vuniofl2vpnPmvar1HisParaLen OBJECT-TYPE
        SYNTAX Unsigned32
        MAX-ACCESS read-only
        STATUS current
        DESCRIPTION
            "ParaLen."
        ::= { vuniofl2vpnPmvar1HisEntry 2 }

    -- 1.3.6.1.4.1.2011.2.25.3.70.20.48.130.1.3
    vuniofl2vpnPmvar1HisPara OBJECT-TYPE
        SYNTAX OCTET STRING (SIZE (0..100))
        MAX-ACCESS read-only
        STATUS current
        DESCRIPTION
            "para"
        ::= { vuniofl2vpnPmvar1HisEntry 3 }

    -- 1.3.6.1.4.1.2011.2.25.3.70.20.48.130.1.4
    vuniofl2vpnPmvar1HisMonValue OBJECT-TYPE
        SYNTAX Counter64
        MAX-ACCESS read-only
        STATUS current
        DESCRIPTION
            "DataPmMonValue."
        ::= { vuniofl2vpnPmvar1HisEntry 4 }

    -- 1.3.6.1.4.1.2011.2.25.3.70.20.48.130.1.5
    vuniofl2vpnPmvar1HisStartTime OBJECT-TYPE
        SYNTAX DateAndTime
        MAX-ACCESS read-only
        STATUS current
        DESCRIPTION
            "Start Time."
        ::= { vuniofl2vpnPmvar1HisEntry 5 }

    -- 1.3.6.1.4.1.2011.2.25.3.70.20.48.130.1.6
    vuniofl2vpnPmvar1HisEndTime OBJECT-TYPE
        SYNTAX DateAndTime
        MAX-ACCESS read-only
        STATUS current
        DESCRIPTION
            "End Time."
        ::= { vuniofl2vpnPmvar1HisEntry 6 }

    -- 1.3.6.1.4.1.2011.2.25.3.70.20.48.130.1.7
    vuniofl2vpnPmvar1HisVldty OBJECT-TYPE
        SYNTAX ValidflagType
        MAX-ACCESS read-only
        STATUS current
        DESCRIPTION
            "Validity."
        ::= { vuniofl2vpnPmvar1HisEntry 7 }

    -- 1.3.6.1.4.1.2011.2.25.3.70.20.48.140
    vuniofl2vpnPmvar2HisTable OBJECT-TYPE
        SYNTAX SEQUENCE OF Vuniofl2vpnPmvar2HisEntry
        MAX-ACCESS not-accessible
        STATUS current
        DESCRIPTION
            "vuniofl2vpnPmvar2His."
        ::= { vuniofl2vpn 140 }

    -- 1.3.6.1.4.1.2011.2.25.3.70.20.48.140.1
    vuniofl2vpnPmvar2HisEntry OBJECT-TYPE
        SYNTAX Vuniofl2vpnPmvar2HisEntry
        MAX-ACCESS not-accessible
        STATUS current
        DESCRIPTION
            "vuniofl2vpnPmvar2His."
        INDEX{ vuniofl2vpnPmvar2HisEid,vuniofl2vpnPmvar2HisParaLen,vuniofl2vpnPmvar2HisPara,vuniofl2vpnPmvar2HisStartTime,vuniofl2vpnPmvar2HisEndTime }
        ::= { vuniofl2vpnPmvar2HisTable 1 }

    Vuniofl2vpnPmvar2HisEntry ::=
        SEQUENCE {
            vuniofl2vpnPmvar2HisEid
                DataPmEventType,
            vuniofl2vpnPmvar2HisParaLen
                Unsigned32,
            vuniofl2vpnPmvar2HisPara
                OCTET STRING,
            vuniofl2vpnPmvar2HisMonValue
                Counter64,
            vuniofl2vpnPmvar2HisStartTime
                DateAndTime,
            vuniofl2vpnPmvar2HisEndTime
                DateAndTime,
            vuniofl2vpnPmvar2HisVldty
                ValidflagType
        }

    -- 1.3.6.1.4.1.2011.2.25.3.70.20.48.140.1.1
    vuniofl2vpnPmvar2HisEid OBJECT-TYPE
        SYNTAX DataPmEventType
        MAX-ACCESS read-only
        STATUS current
        DESCRIPTION
            "DataPmEid."
        ::= { vuniofl2vpnPmvar2HisEntry 1 }

    -- 1.3.6.1.4.1.2011.2.25.3.70.20.48.140.1.2
    vuniofl2vpnPmvar2HisParaLen OBJECT-TYPE
        SYNTAX Unsigned32
        MAX-ACCESS read-only
        STATUS current
        DESCRIPTION
            "ParaLen."
        ::= { vuniofl2vpnPmvar2HisEntry 2 }

    -- 1.3.6.1.4.1.2011.2.25.3.70.20.48.140.1.3
    vuniofl2vpnPmvar2HisPara OBJECT-TYPE
        SYNTAX OCTET STRING(SIZE (0..100))
        MAX-ACCESS read-only
        STATUS current
        DESCRIPTION
            "para"
        ::= { vuniofl2vpnPmvar2HisEntry 3 }

    -- 1.3.6.1.4.1.2011.2.25.3.70.20.48.140.1.4
    vuniofl2vpnPmvar2HisMonValue OBJECT-TYPE
        SYNTAX Counter64
        MAX-ACCESS read-only
        STATUS current
        DESCRIPTION
            "DataPmMonValue."
        ::= { vuniofl2vpnPmvar2HisEntry 4 }

    -- 1.3.6.1.4.1.2011.2.25.3.70.20.48.140.1.5
    vuniofl2vpnPmvar2HisStartTime OBJECT-TYPE
        SYNTAX DateAndTime
        MAX-ACCESS read-only
        STATUS current
        DESCRIPTION
            "Start Time."
        ::= { vuniofl2vpnPmvar2HisEntry 5 }

    -- 1.3.6.1.4.1.2011.2.25.3.70.20.48.140.1.6
    vuniofl2vpnPmvar2HisEndTime OBJECT-TYPE
        SYNTAX DateAndTime
        MAX-ACCESS read-only
        STATUS current
        DESCRIPTION
            "End Time."
        ::= { vuniofl2vpnPmvar2HisEntry 6 }

    -- 1.3.6.1.4.1.2011.2.25.3.70.20.48.140.1.7
    vuniofl2vpnPmvar2HisVldty OBJECT-TYPE
        SYNTAX ValidflagType
        MAX-ACCESS read-only
        STATUS current
        DESCRIPTION
            "Validity."
        ::= { vuniofl2vpnPmvar2HisEntry 7 }

    -- 1.3.6.1.4.1.2011.2.25.3.70.20.50
    classifier OBJECT IDENTIFIER ::= { rtnData 50 }

    -- 1.3.6.1.4.1.2011.2.25.3.70.20.50.100
    classifierPmCurTable OBJECT-TYPE
        SYNTAX SEQUENCE OF ClassifierPmCurEntry
        MAX-ACCESS not-accessible
        STATUS current
        DESCRIPTION
            "classifierDataPm30sCur."
        ::= { classifier 100 }

    -- 1.3.6.1.4.1.2011.2.25.3.70.20.50.100.1
    classifierPmCurEntry OBJECT-TYPE
        SYNTAX ClassifierPmCurEntry
        MAX-ACCESS not-accessible
        STATUS current
        DESCRIPTION
            "classifierPmCur."
        INDEX{ classifierPmCurEid,classifierPmCurParaLen,classifierPmCurPara }
        ::= { classifierPmCurTable 1 }

    ClassifierPmCurEntry ::=
        SEQUENCE {
            classifierPmCurEid
                DataPmEventType,
            classifierPmCurParaLen
                Unsigned32,
            classifierPmCurPara
                OCTET STRING,
            classifierPmCurMonValue
                Counter64,
            classifierPmCurDatetime
                DateAndTime
        }

    -- 1.3.6.1.4.1.2011.2.25.3.70.20.50.100.1.1
    classifierPmCurEid OBJECT-TYPE
        SYNTAX DataPmEventType
        MAX-ACCESS read-only
        STATUS current
        DESCRIPTION
            "DataPmEid."
        ::= { classifierPmCurEntry 1 }

    -- 1.3.6.1.4.1.2011.2.25.3.70.20.50.100.1.2
    classifierPmCurParaLen OBJECT-TYPE
        SYNTAX Unsigned32
        MAX-ACCESS read-only
        STATUS current
        DESCRIPTION
            "ParaLen."
        ::= { classifierPmCurEntry 2 }

    -- 1.3.6.1.4.1.2011.2.25.3.70.20.50.100.1.3
    classifierPmCurPara OBJECT-TYPE
        SYNTAX OCTET STRING
        MAX-ACCESS read-only
        STATUS current
        DESCRIPTION
            "para"
        ::= { classifierPmCurEntry 3 }

    -- 1.3.6.1.4.1.2011.2.25.3.70.20.50.100.1.4
    classifierPmCurMonValue OBJECT-TYPE
        SYNTAX Counter64
        MAX-ACCESS read-only
        STATUS current
        DESCRIPTION
            "DataPmMonValue."
        ::= { classifierPmCurEntry 4 }

    -- 1.3.6.1.4.1.2011.2.25.3.70.20.50.100.1.5
    classifierPmCurDatetime OBJECT-TYPE
        SYNTAX DateAndTime
        MAX-ACCESS read-only
        STATUS current
        DESCRIPTION
            "Start Time."
        ::= { classifierPmCurEntry 5 }

    -- 1.3.6.1.4.1.2011.2.25.3.70.20.50.110
    classifierPm30sHisTable OBJECT-TYPE
        SYNTAX SEQUENCE OF ClassifierPm30sHisEntry
        MAX-ACCESS not-accessible
        STATUS current
        DESCRIPTION
            "classifierDataPm30sHis."
        ::= { classifier 110 }

    -- 1.3.6.1.4.1.2011.2.25.3.70.20.50.110.1
    classifierPm30sHisEntry OBJECT-TYPE
        SYNTAX ClassifierPm30sHisEntry
        MAX-ACCESS not-accessible
        STATUS current
        DESCRIPTION
            "classifierDataPm30sHis."
        INDEX{ classifierPm30sHisEid,classifierPm30sHisParaLen,classifierPm30sHisPara,classifierPm30sHisStartTime,classifierPm30sHisEndTime }
        ::= { classifierPm30sHisTable 1 }

    ClassifierPm30sHisEntry ::=
        SEQUENCE {
            classifierPm30sHisEid
                DataPmEventType,
            classifierPm30sHisParaLen
                Unsigned32,
            classifierPm30sHisPara
                OCTET STRING,
            classifierPm30sHisMonValue
                Counter64,
            classifierPm30sHisStartTime
                DateAndTime,
            classifierPm30sHisEndTime
                DateAndTime,
            classifierPm30sHisVldty
                ValidflagType
        }

    -- 1.3.6.1.4.1.2011.2.25.3.70.20.50.110.1.1
    classifierPm30sHisEid OBJECT-TYPE
        SYNTAX DataPmEventType
        MAX-ACCESS read-only
        STATUS current
        DESCRIPTION
            "DataPmEid."
        ::= { classifierPm30sHisEntry 1 }

    -- 1.3.6.1.4.1.2011.2.25.3.70.20.50.110.1.2
    classifierPm30sHisParaLen OBJECT-TYPE
        SYNTAX Unsigned32
        MAX-ACCESS read-only
        STATUS current
        DESCRIPTION
            "ParaLen."
        ::= { classifierPm30sHisEntry 2 }

    -- 1.3.6.1.4.1.2011.2.25.3.70.20.50.110.1.3
    classifierPm30sHisPara OBJECT-TYPE
        SYNTAX OCTET STRING(SIZE (0..100))
        MAX-ACCESS read-only
        STATUS current
        DESCRIPTION
            "para"
        ::= { classifierPm30sHisEntry 3 }

    -- 1.3.6.1.4.1.2011.2.25.3.70.20.50.110.1.4
    classifierPm30sHisMonValue OBJECT-TYPE
        SYNTAX Counter64
        MAX-ACCESS read-only
        STATUS current
        DESCRIPTION
            "DataPmMonValue."
        ::= { classifierPm30sHisEntry 4 }

    -- 1.3.6.1.4.1.2011.2.25.3.70.20.50.110.1.5
    classifierPm30sHisStartTime OBJECT-TYPE
        SYNTAX DateAndTime
        MAX-ACCESS read-only
        STATUS current
        DESCRIPTION
            "Start Time."
        ::= { classifierPm30sHisEntry 5 }

    -- 1.3.6.1.4.1.2011.2.25.3.70.20.50.110.1.6
    classifierPm30sHisEndTime OBJECT-TYPE
        SYNTAX DateAndTime
        MAX-ACCESS read-only
        STATUS current
        DESCRIPTION
            "End Time."
        ::= { classifierPm30sHisEntry 6 }

    -- 1.3.6.1.4.1.2011.2.25.3.70.20.50.110.1.7
    classifierPm30sHisVldty OBJECT-TYPE
        SYNTAX ValidflagType
        MAX-ACCESS read-only
        STATUS current
        DESCRIPTION
            "Validity."
        ::= { classifierPm30sHisEntry 7 }

    -- 1.3.6.1.4.1.2011.2.25.3.70.20.50.120
    classifierPm30mHisTable OBJECT-TYPE
        SYNTAX SEQUENCE OF ClassifierPm30mHisEntry
        MAX-ACCESS not-accessible
        STATUS current
        DESCRIPTION
            "classifierPm30mHis."
        ::= { classifier 120 }

    -- 1.3.6.1.4.1.2011.2.25.3.70.20.50.120.1
    classifierPm30mHisEntry OBJECT-TYPE
        SYNTAX ClassifierPm30mHisEntry
        MAX-ACCESS not-accessible
        STATUS current
        DESCRIPTION
            "classifierPm30mHis."
        INDEX{ classifierPm30mHisEid,classifierPm30mHisParaLen,classifierPm30mHisPara,classifierPm30mHisStartTime,classifierPm30mHisEndTime }
        ::= { classifierPm30mHisTable 1 }

    ClassifierPm30mHisEntry ::=
        SEQUENCE {
            classifierPm30mHisEid
                DataPmEventType,
            classifierPm30mHisParaLen
                Unsigned32,
            classifierPm30mHisPara
                OCTET STRING,
            classifierPm30mHisMonValue
                Counter64,
            classifierPm30mHisStartTime
                DateAndTime,
            classifierPm30mHisEndTime
                DateAndTime,
            classifierPm30mHisVldty
                ValidflagType
        }

    -- 1.3.6.1.4.1.2011.2.25.3.70.20.50.120.1.1
    classifierPm30mHisEid OBJECT-TYPE
        SYNTAX DataPmEventType
        MAX-ACCESS read-only
        STATUS current
        DESCRIPTION
            "DataPmEid."
        ::= { classifierPm30mHisEntry 1 }

    -- 1.3.6.1.4.1.2011.2.25.3.70.20.50.120.1.2
    classifierPm30mHisParaLen OBJECT-TYPE
        SYNTAX Unsigned32
        MAX-ACCESS read-only
        STATUS current
        DESCRIPTION
            "ParaLen."
        ::= { classifierPm30mHisEntry 2 }

    -- 1.3.6.1.4.1.2011.2.25.3.70.20.50.120.1.3
    classifierPm30mHisPara OBJECT-TYPE
        SYNTAX OCTET STRING(SIZE (0..100))
        MAX-ACCESS read-only
        STATUS current
        DESCRIPTION
            "para"
        ::= { classifierPm30mHisEntry 3 }

    -- 1.3.6.1.4.1.2011.2.25.3.70.20.50.120.1.4
    classifierPm30mHisMonValue OBJECT-TYPE
        SYNTAX Counter64
        MAX-ACCESS read-only
        STATUS current
        DESCRIPTION
            "DataPmMonValue."
        ::= { classifierPm30mHisEntry 4 }

    -- 1.3.6.1.4.1.2011.2.25.3.70.20.50.120.1.5
    classifierPm30mHisStartTime OBJECT-TYPE
        SYNTAX DateAndTime
        MAX-ACCESS read-only
        STATUS current
        DESCRIPTION
            "Start Time."
        ::= { classifierPm30mHisEntry 5 }

    -- 1.3.6.1.4.1.2011.2.25.3.70.20.50.120.1.6
    classifierPm30mHisEndTime OBJECT-TYPE
        SYNTAX DateAndTime
        MAX-ACCESS read-only
        STATUS current
        DESCRIPTION
            "End Time."
        ::= { classifierPm30mHisEntry 6 }

    -- 1.3.6.1.4.1.2011.2.25.3.70.20.50.120.1.7
    classifierPm30mHisVldty OBJECT-TYPE
        SYNTAX ValidflagType
        MAX-ACCESS read-only
        STATUS current
        DESCRIPTION
            "Validity."
        ::= { classifierPm30mHisEntry 7 }

    -- 1.3.6.1.4.1.2011.2.25.3.70.20.50.130
    classifierPmvar1HisTable OBJECT-TYPE
        SYNTAX SEQUENCE OF ClassifierPmvar1HisEntry
        MAX-ACCESS not-accessible
        STATUS current
        DESCRIPTION
            "classifierPmvar1His."
        ::= { classifier 130 }

    -- 1.3.6.1.4.1.2011.2.25.3.70.20.50.130.1
    classifierPmvar1HisEntry OBJECT-TYPE
        SYNTAX ClassifierPmvar1HisEntry
        MAX-ACCESS not-accessible
        STATUS current
        DESCRIPTION
            "classifierPmvar1His."
        INDEX{ classifierPmvar1HisEid,classifierPmvar1HisParaLen,classifierPmvar1HisPara,classifierPmvar1HisStartTime,classifierPmvar1HisEndTime }
        ::= { classifierPmvar1HisTable 1 }

    ClassifierPmvar1HisEntry ::=
        SEQUENCE {
            classifierPmvar1HisEid
                DataPmEventType,
            classifierPmvar1HisParaLen
                Unsigned32,
            classifierPmvar1HisPara
                OCTET STRING,
            classifierPmvar1HisMonValue
                Counter64,
            classifierPmvar1HisStartTime
                DateAndTime,
            classifierPmvar1HisEndTime
                DateAndTime,
            classifierPmvar1HisVldty
                ValidflagType
        }

    -- 1.3.6.1.4.1.2011.2.25.3.70.20.50.130.1.1
    classifierPmvar1HisEid OBJECT-TYPE
        SYNTAX DataPmEventType
        MAX-ACCESS read-only
        STATUS current
        DESCRIPTION
            "DataPmEid."
        ::= { classifierPmvar1HisEntry 1 }

    -- 1.3.6.1.4.1.2011.2.25.3.70.20.50.130.1.2
    classifierPmvar1HisParaLen OBJECT-TYPE
        SYNTAX Unsigned32
        MAX-ACCESS read-only
        STATUS current
        DESCRIPTION
            "ParaLen."
        ::= { classifierPmvar1HisEntry 2 }

    -- 1.3.6.1.4.1.2011.2.25.3.70.20.50.130.1.3
    classifierPmvar1HisPara OBJECT-TYPE
        SYNTAX OCTET STRING (SIZE (0..100))
        MAX-ACCESS read-only
        STATUS current
        DESCRIPTION
            "para"
        ::= { classifierPmvar1HisEntry 3 }

    -- 1.3.6.1.4.1.2011.2.25.3.70.20.50.130.1.4
    classifierPmvar1HisMonValue OBJECT-TYPE
        SYNTAX Counter64
        MAX-ACCESS read-only
        STATUS current
        DESCRIPTION
            "DataPmMonValue."
        ::= { classifierPmvar1HisEntry 4 }

    -- 1.3.6.1.4.1.2011.2.25.3.70.20.50.130.1.5
    classifierPmvar1HisStartTime OBJECT-TYPE
        SYNTAX DateAndTime
        MAX-ACCESS read-only
        STATUS current
        DESCRIPTION
            "Start Time."
        ::= { classifierPmvar1HisEntry 5 }

    -- 1.3.6.1.4.1.2011.2.25.3.70.20.50.130.1.6
    classifierPmvar1HisEndTime OBJECT-TYPE
        SYNTAX DateAndTime
        MAX-ACCESS read-only
        STATUS current
        DESCRIPTION
            "End Time."
        ::= { classifierPmvar1HisEntry 6 }

    -- 1.3.6.1.4.1.2011.2.25.3.70.20.50.130.1.7
    classifierPmvar1HisVldty OBJECT-TYPE
        SYNTAX ValidflagType
        MAX-ACCESS read-only
        STATUS current
        DESCRIPTION
            "Validity."
        ::= { classifierPmvar1HisEntry 7 }

    -- 1.3.6.1.4.1.2011.2.25.3.70.20.50.140
    classifierPmvar2HisTable OBJECT-TYPE
        SYNTAX SEQUENCE OF ClassifierPmvar2HisEntry
        MAX-ACCESS not-accessible
        STATUS current
        DESCRIPTION
            "classifierPmvar2His."
        ::= { classifier 140 }

    -- 1.3.6.1.4.1.2011.2.25.3.70.20.50.140.1
    classifierPmvar2HisEntry OBJECT-TYPE
        SYNTAX ClassifierPmvar2HisEntry
        MAX-ACCESS not-accessible
        STATUS current
        DESCRIPTION
            "classifierPmvar2His."
        INDEX{ classifierPmvar2HisEid,classifierPmvar2HisParaLen,classifierPmvar2HisPara,classifierPmvar2HisStartTime,classifierPmvar2HisEndTime }
        ::= { classifierPmvar2HisTable 1 }

    ClassifierPmvar2HisEntry ::=
        SEQUENCE {
            classifierPmvar2HisEid
                DataPmEventType,
            classifierPmvar2HisParaLen
                Unsigned32,
            classifierPmvar2HisPara
                OCTET STRING,
            classifierPmvar2HisMonValue
                Counter64,
            classifierPmvar2HisStartTime
                DateAndTime,
            classifierPmvar2HisEndTime
                DateAndTime,
            classifierPmvar2HisVldty
                ValidflagType
        }

    -- 1.3.6.1.4.1.2011.2.25.3.70.20.50.140.1.1
    classifierPmvar2HisEid OBJECT-TYPE
        SYNTAX DataPmEventType
        MAX-ACCESS read-only
        STATUS current
        DESCRIPTION
            "DataPmEid."
        ::= { classifierPmvar2HisEntry 1 }

    -- 1.3.6.1.4.1.2011.2.25.3.70.20.50.140.1.2
    classifierPmvar2HisParaLen OBJECT-TYPE
        SYNTAX Unsigned32
        MAX-ACCESS read-only
        STATUS current
        DESCRIPTION
            "ParaLen."
        ::= { classifierPmvar2HisEntry 2 }

    -- 1.3.6.1.4.1.2011.2.25.3.70.20.50.140.1.3
    classifierPmvar2HisPara OBJECT-TYPE
        SYNTAX OCTET STRING(SIZE (0..100))
        MAX-ACCESS read-only
        STATUS current
        DESCRIPTION
            "para"
        ::= { classifierPmvar2HisEntry 3 }

    -- 1.3.6.1.4.1.2011.2.25.3.70.20.50.140.1.4
    classifierPmvar2HisMonValue OBJECT-TYPE
        SYNTAX Counter64
        MAX-ACCESS read-only
        STATUS current
        DESCRIPTION
            "DataPmMonValue."
        ::= { classifierPmvar2HisEntry 4 }

    -- 1.3.6.1.4.1.2011.2.25.3.70.20.50.140.1.5
    classifierPmvar2HisStartTime OBJECT-TYPE
        SYNTAX DateAndTime
        MAX-ACCESS read-only
        STATUS current
        DESCRIPTION
            "Start Time."
        ::= { classifierPmvar2HisEntry 5 }

    -- 1.3.6.1.4.1.2011.2.25.3.70.20.50.140.1.6
    classifierPmvar2HisEndTime OBJECT-TYPE
        SYNTAX DateAndTime
        MAX-ACCESS read-only
        STATUS current
        DESCRIPTION
            "End Time."
        ::= { classifierPmvar2HisEntry 6 }

    -- 1.3.6.1.4.1.2011.2.25.3.70.20.50.140.1.7
    classifierPmvar2HisVldty OBJECT-TYPE
        SYNTAX ValidflagType
        MAX-ACCESS read-only
        STATUS current
        DESCRIPTION
            "Validity."
        ::= { classifierPmvar2HisEntry 7 }

    -- 1.3.6.1.4.1.2011.2.25.3.70.20.51
    mlppp OBJECT IDENTIFIER ::= { rtnData 51 }

    -- 1.3.6.1.4.1.2011.2.25.3.70.20.51.100
    mlpppPmCurTable OBJECT-TYPE
        SYNTAX SEQUENCE OF MlpppPmCurEntry
        MAX-ACCESS not-accessible
        STATUS current
        DESCRIPTION
            "mlpppDataPm30sCur."
        ::= { mlppp 100 }

    -- 1.3.6.1.4.1.2011.2.25.3.70.20.51.100.1
    mlpppPmCurEntry OBJECT-TYPE
        SYNTAX MlpppPmCurEntry
        MAX-ACCESS not-accessible
        STATUS current
        DESCRIPTION
            "mlpppPmCur."
        INDEX{ mlpppPmCurEid,mlpppPmCurPara }
        ::= { mlpppPmCurTable 1 }

    MlpppPmCurEntry ::=
        SEQUENCE {
            mlpppPmCurEid
                DataPmEventType,
            mlpppPmCurParaLen
                Unsigned32,
            mlpppPmCurPara
                OCTET STRING,
            mlpppPmCurMonValue
                Counter64,
            mlpppPmCurDatetime
                DateAndTime
        }

    -- 1.3.6.1.4.1.2011.2.25.3.70.20.51.100.1.1
    mlpppPmCurEid OBJECT-TYPE
        SYNTAX DataPmEventType
        MAX-ACCESS read-only
        STATUS current
        DESCRIPTION
            "DataPmEid."
        ::= { mlpppPmCurEntry 1 }

    -- 1.3.6.1.4.1.2011.2.25.3.70.20.51.100.1.2
    mlpppPmCurParaLen OBJECT-TYPE
        SYNTAX Unsigned32
        MAX-ACCESS read-only
        STATUS current
        DESCRIPTION
            "ParaLen."
        ::= { mlpppPmCurEntry 2 }

    -- 1.3.6.1.4.1.2011.2.25.3.70.20.51.100.1.3
    mlpppPmCurPara OBJECT-TYPE
        SYNTAX OCTET STRING
        MAX-ACCESS read-only
        STATUS current
        DESCRIPTION
            "para"
        ::= { mlpppPmCurEntry 3 }

    -- 1.3.6.1.4.1.2011.2.25.3.70.20.51.100.1.4
    mlpppPmCurMonValue OBJECT-TYPE
        SYNTAX Counter64
        MAX-ACCESS read-only
        STATUS current
        DESCRIPTION
            "DataPmMonValue."
        ::= { mlpppPmCurEntry 4 }

    -- 1.3.6.1.4.1.2011.2.25.3.70.20.51.100.1.5
    mlpppPmCurDatetime OBJECT-TYPE
        SYNTAX DateAndTime
        MAX-ACCESS read-only
        STATUS current
        DESCRIPTION
            "Start Time."
        ::= { mlpppPmCurEntry 5 }

    -- 1.3.6.1.4.1.2011.2.25.3.70.20.51.110
    mlpppPm30sHisTable OBJECT-TYPE
        SYNTAX SEQUENCE OF MlpppPm30sHisEntry
        MAX-ACCESS not-accessible
        STATUS current
        DESCRIPTION
            "mlpppDataPm30sHis."
        ::= { mlppp 110 }

    -- 1.3.6.1.4.1.2011.2.25.3.70.20.51.110.1
    mlpppPm30sHisEntry OBJECT-TYPE
        SYNTAX MlpppPm30sHisEntry
        MAX-ACCESS not-accessible
        STATUS current
        DESCRIPTION
            "mlpppDataPm30sHis."
        INDEX{ mlpppPm30sHisEid,mlpppPm30sHisParaLen,mlpppPm30sHisPara,mlpppPm30sHisStartTime,mlpppPm30sHisEndTime }
        ::= { mlpppPm30sHisTable 1 }

    MlpppPm30sHisEntry ::=
        SEQUENCE {
            mlpppPm30sHisEid
                DataPmEventType,
            mlpppPm30sHisParaLen
                Unsigned32,
            mlpppPm30sHisPara
                OCTET STRING,
            mlpppPm30sHisMonValue
                Counter64,
            mlpppPm30sHisStartTime
                DateAndTime,
            mlpppPm30sHisEndTime
                DateAndTime,
            mlpppPm30sHisVldty
                ValidflagType
        }

    -- 1.3.6.1.4.1.2011.2.25.3.70.20.51.110.1.1
    mlpppPm30sHisEid OBJECT-TYPE
        SYNTAX DataPmEventType
        MAX-ACCESS read-only
        STATUS current
        DESCRIPTION
            "DataPmEid."
        ::= { mlpppPm30sHisEntry 1 }

    -- 1.3.6.1.4.1.2011.2.25.3.70.20.51.110.1.2
    mlpppPm30sHisParaLen OBJECT-TYPE
        SYNTAX Unsigned32
        MAX-ACCESS read-only
        STATUS current
        DESCRIPTION
            "ParaLen."
        ::= { mlpppPm30sHisEntry 2 }

    -- 1.3.6.1.4.1.2011.2.25.3.70.20.51.110.1.3
    mlpppPm30sHisPara OBJECT-TYPE
        SYNTAX OCTET STRING(SIZE (0..100))
        MAX-ACCESS read-only
        STATUS current
        DESCRIPTION
            "para"
        ::= { mlpppPm30sHisEntry 3 }

    -- 1.3.6.1.4.1.2011.2.25.3.70.20.51.110.1.4
    mlpppPm30sHisMonValue OBJECT-TYPE
        SYNTAX Counter64
        MAX-ACCESS read-only
        STATUS current
        DESCRIPTION
            "DataPmMonValue."
        ::= { mlpppPm30sHisEntry 4 }

    -- 1.3.6.1.4.1.2011.2.25.3.70.20.51.110.1.5
    mlpppPm30sHisStartTime OBJECT-TYPE
        SYNTAX DateAndTime
        MAX-ACCESS read-only
        STATUS current
        DESCRIPTION
            "Start Time."
        ::= { mlpppPm30sHisEntry 5 }

    -- 1.3.6.1.4.1.2011.2.25.3.70.20.51.110.1.6
    mlpppPm30sHisEndTime OBJECT-TYPE
        SYNTAX DateAndTime
        MAX-ACCESS read-only
        STATUS current
        DESCRIPTION
            "End Time."
        ::= { mlpppPm30sHisEntry 6 }

    -- 1.3.6.1.4.1.2011.2.25.3.70.20.51.110.1.7
    mlpppPm30sHisVldty OBJECT-TYPE
        SYNTAX ValidflagType
        MAX-ACCESS read-only
        STATUS current
        DESCRIPTION
            "Validity."
        ::= { mlpppPm30sHisEntry 7 }

    -- 1.3.6.1.4.1.2011.2.25.3.70.20.51.120
    mlpppPm30mHisTable OBJECT-TYPE
        SYNTAX SEQUENCE OF MlpppPm30mHisEntry
        MAX-ACCESS not-accessible
        STATUS current
        DESCRIPTION
            "mlpppPm30mHis."
        ::= { mlppp 120 }

    -- 1.3.6.1.4.1.2011.2.25.3.70.20.51.120.1
    mlpppPm30mHisEntry OBJECT-TYPE
        SYNTAX MlpppPm30mHisEntry
        MAX-ACCESS not-accessible
        STATUS current
        DESCRIPTION
            "mlpppPm30mHis."
        INDEX{ mlpppPm30mHisEid,mlpppPm30mHisParaLen,mlpppPm30mHisPara,mlpppPm30mHisStartTime,mlpppPm30mHisEndTime }
        ::= { mlpppPm30mHisTable 1 }

    MlpppPm30mHisEntry ::=
        SEQUENCE {
            mlpppPm30mHisEid
                DataPmEventType,
            mlpppPm30mHisParaLen
                Unsigned32,
            mlpppPm30mHisPara
                OCTET STRING,
            mlpppPm30mHisMonValue
                Counter64,
            mlpppPm30mHisStartTime
                DateAndTime,
            mlpppPm30mHisEndTime
                DateAndTime,
            mlpppPm30mHisVldty
                ValidflagType
        }

    -- 1.3.6.1.4.1.2011.2.25.3.70.20.51.120.1.1
    mlpppPm30mHisEid OBJECT-TYPE
        SYNTAX DataPmEventType
        MAX-ACCESS read-only
        STATUS current
        DESCRIPTION
            "DataPmEid."
        ::= { mlpppPm30mHisEntry 1 }

    -- 1.3.6.1.4.1.2011.2.25.3.70.20.51.120.1.2
    mlpppPm30mHisParaLen OBJECT-TYPE
        SYNTAX Unsigned32
        MAX-ACCESS read-only
        STATUS current
        DESCRIPTION
            "ParaLen."
        ::= { mlpppPm30mHisEntry 2 }

    -- 1.3.6.1.4.1.2011.2.25.3.70.20.51.120.1.3
    mlpppPm30mHisPara OBJECT-TYPE
        SYNTAX OCTET STRING(SIZE (0..100))
        MAX-ACCESS read-only
        STATUS current
        DESCRIPTION
            "para"
        ::= { mlpppPm30mHisEntry 3 }

    -- 1.3.6.1.4.1.2011.2.25.3.70.20.51.120.1.4
    mlpppPm30mHisMonValue OBJECT-TYPE
        SYNTAX Counter64
        MAX-ACCESS read-only
        STATUS current
        DESCRIPTION
            "DataPmMonValue."
        ::= { mlpppPm30mHisEntry 4 }

    -- 1.3.6.1.4.1.2011.2.25.3.70.20.51.120.1.5
    mlpppPm30mHisStartTime OBJECT-TYPE
        SYNTAX DateAndTime
        MAX-ACCESS read-only
        STATUS current
        DESCRIPTION
            "Start Time."
        ::= { mlpppPm30mHisEntry 5 }

    -- 1.3.6.1.4.1.2011.2.25.3.70.20.51.120.1.6
    mlpppPm30mHisEndTime OBJECT-TYPE
        SYNTAX DateAndTime
        MAX-ACCESS read-only
        STATUS current
        DESCRIPTION
            "End Time."
        ::= { mlpppPm30mHisEntry 6 }

    -- 1.3.6.1.4.1.2011.2.25.3.70.20.51.120.1.7
    mlpppPm30mHisVldty OBJECT-TYPE
        SYNTAX ValidflagType
        MAX-ACCESS read-only
        STATUS current
        DESCRIPTION
            "Validity."
        ::= { mlpppPm30mHisEntry 7 }

    -- 1.3.6.1.4.1.2011.2.25.3.70.20.51.130
    mlpppPmvar1HisTable OBJECT-TYPE
        SYNTAX SEQUENCE OF MlpppPmvar1HisEntry
        MAX-ACCESS not-accessible
        STATUS current
        DESCRIPTION
            "mlpppPmvar1His."
        ::= { mlppp 130 }

    -- 1.3.6.1.4.1.2011.2.25.3.70.20.51.130.1
    mlpppPmvar1HisEntry OBJECT-TYPE
        SYNTAX MlpppPmvar1HisEntry
        MAX-ACCESS not-accessible
        STATUS current
        DESCRIPTION
            "mlpppPmvar1His."
        INDEX{ mlpppPmvar1HisEid,mlpppPmvar1HisParaLen,mlpppPmvar1HisPara,mlpppPmvar1HisStartTime,mlpppPmvar1HisEndTime }
        ::= { mlpppPmvar1HisTable 1 }

    MlpppPmvar1HisEntry ::=
        SEQUENCE {
            mlpppPmvar1HisEid
                DataPmEventType,
            mlpppPmvar1HisParaLen
                Unsigned32,
            mlpppPmvar1HisPara
                OCTET STRING,
            mlpppPmvar1HisMonValue
                Counter64,
            mlpppPmvar1HisStartTime
                DateAndTime,
            mlpppPmvar1HisEndTime
                DateAndTime,
            mlpppPmvar1HisVldty
                ValidflagType
        }

    -- 1.3.6.1.4.1.2011.2.25.3.70.20.51.130.1.1
    mlpppPmvar1HisEid OBJECT-TYPE
        SYNTAX DataPmEventType
        MAX-ACCESS read-only
        STATUS current
        DESCRIPTION
            "DataPmEid."
        ::= { mlpppPmvar1HisEntry 1 }

    -- 1.3.6.1.4.1.2011.2.25.3.70.20.51.130.1.2
    mlpppPmvar1HisParaLen OBJECT-TYPE
        SYNTAX Unsigned32
        MAX-ACCESS read-only
        STATUS current
        DESCRIPTION
            "ParaLen."
        ::= { mlpppPmvar1HisEntry 2 }

    -- 1.3.6.1.4.1.2011.2.25.3.70.20.51.130.1.3
    mlpppPmvar1HisPara OBJECT-TYPE
        SYNTAX OCTET STRING (SIZE (0..100))
        MAX-ACCESS read-only
        STATUS current
        DESCRIPTION
            "para"
        ::= { mlpppPmvar1HisEntry 3 }

    -- 1.3.6.1.4.1.2011.2.25.3.70.20.51.130.1.4
    mlpppPmvar1HisMonValue OBJECT-TYPE
        SYNTAX Counter64
        MAX-ACCESS read-only
        STATUS current
        DESCRIPTION
            "DataPmMonValue."
        ::= { mlpppPmvar1HisEntry 4 }

    -- 1.3.6.1.4.1.2011.2.25.3.70.20.51.130.1.5
    mlpppPmvar1HisStartTime OBJECT-TYPE
        SYNTAX DateAndTime
        MAX-ACCESS read-only
        STATUS current
        DESCRIPTION
            "Start Time."
        ::= { mlpppPmvar1HisEntry 5 }

    -- 1.3.6.1.4.1.2011.2.25.3.70.20.51.130.1.6
    mlpppPmvar1HisEndTime OBJECT-TYPE
        SYNTAX DateAndTime
        MAX-ACCESS read-only
        STATUS current
        DESCRIPTION
            "End Time."
        ::= { mlpppPmvar1HisEntry 6 }

    -- 1.3.6.1.4.1.2011.2.25.3.70.20.51.130.1.7
    mlpppPmvar1HisVldty OBJECT-TYPE
        SYNTAX ValidflagType
        MAX-ACCESS read-only
        STATUS current
        DESCRIPTION
            "Validity."
        ::= { mlpppPmvar1HisEntry 7 }

    -- 1.3.6.1.4.1.2011.2.25.3.70.20.51.140
    mlpppPmvar2HisTable OBJECT-TYPE
        SYNTAX SEQUENCE OF MlpppPmvar2HisEntry
        MAX-ACCESS not-accessible
        STATUS current
        DESCRIPTION
            "mlpppPmvar2His."
        ::= { mlppp 140 }

    -- 1.3.6.1.4.1.2011.2.25.3.70.20.51.140.1
    mlpppPmvar2HisEntry OBJECT-TYPE
        SYNTAX MlpppPmvar2HisEntry
        MAX-ACCESS not-accessible
        STATUS current
        DESCRIPTION
            "mlpppPmvar2His."
        INDEX{ mlpppPmvar2HisEid,mlpppPmvar2HisParaLen,mlpppPmvar2HisPara,mlpppPmvar2HisStartTime,mlpppPmvar2HisEndTime }
        ::= { mlpppPmvar2HisTable 1 }

    MlpppPmvar2HisEntry ::=
        SEQUENCE {
            mlpppPmvar2HisEid
                DataPmEventType,
            mlpppPmvar2HisParaLen
                Unsigned32,
            mlpppPmvar2HisPara
                OCTET STRING,
            mlpppPmvar2HisMonValue
                Counter64,
            mlpppPmvar2HisStartTime
                DateAndTime,
            mlpppPmvar2HisEndTime
                DateAndTime,
            mlpppPmvar2HisVldty
                ValidflagType
        }

    -- 1.3.6.1.4.1.2011.2.25.3.70.20.51.140.1.1
    mlpppPmvar2HisEid OBJECT-TYPE
        SYNTAX DataPmEventType
        MAX-ACCESS read-only
        STATUS current
        DESCRIPTION
            "DataPmEid."
        ::= { mlpppPmvar2HisEntry 1 }

    -- 1.3.6.1.4.1.2011.2.25.3.70.20.51.140.1.2
    mlpppPmvar2HisParaLen OBJECT-TYPE
        SYNTAX Unsigned32
        MAX-ACCESS read-only
        STATUS current
        DESCRIPTION
            "ParaLen."
        ::= { mlpppPmvar2HisEntry 2 }

    -- 1.3.6.1.4.1.2011.2.25.3.70.20.51.140.1.3
    mlpppPmvar2HisPara OBJECT-TYPE
        SYNTAX OCTET STRING(SIZE (0..100))
        MAX-ACCESS read-only
        STATUS current
        DESCRIPTION
            "para"
        ::= { mlpppPmvar2HisEntry 3 }

    -- 1.3.6.1.4.1.2011.2.25.3.70.20.51.140.1.4
    mlpppPmvar2HisMonValue OBJECT-TYPE
        SYNTAX Counter64
        MAX-ACCESS read-only
        STATUS current
        DESCRIPTION
            "DataPmMonValue."
        ::= { mlpppPmvar2HisEntry 4 }

    -- 1.3.6.1.4.1.2011.2.25.3.70.20.51.140.1.5
    mlpppPmvar2HisStartTime OBJECT-TYPE
        SYNTAX DateAndTime
        MAX-ACCESS read-only
        STATUS current
        DESCRIPTION
            "Start Time."
        ::= { mlpppPmvar2HisEntry 5 }

    -- 1.3.6.1.4.1.2011.2.25.3.70.20.51.140.1.6
    mlpppPmvar2HisEndTime OBJECT-TYPE
        SYNTAX DateAndTime
        MAX-ACCESS read-only
        STATUS current
        DESCRIPTION
            "End Time."
        ::= { mlpppPmvar2HisEntry 6 }

    -- 1.3.6.1.4.1.2011.2.25.3.70.20.51.140.1.7
    mlpppPmvar2HisVldty OBJECT-TYPE
        SYNTAX ValidflagType
        MAX-ACCESS read-only
        STATUS current
        DESCRIPTION
            "Validity."
        ::= { mlpppPmvar2HisEntry 7 }

    -- 1.3.6.1.4.1.2011.2.25.3.70.20.55
    lag OBJECT IDENTIFIER ::= { rtnData 55 }

    -- 1.3.6.1.4.1.2011.2.25.3.70.20.55.100
    lagPmCurTable OBJECT-TYPE
        SYNTAX SEQUENCE OF LagPmCurEntry
        MAX-ACCESS not-accessible
        STATUS current
        DESCRIPTION
            "lagDataPm30sCur."
        ::= { lag 100 }

    -- 1.3.6.1.4.1.2011.2.25.3.70.20.55.100.1
    lagPmCurEntry OBJECT-TYPE
        SYNTAX LagPmCurEntry
        MAX-ACCESS not-accessible
        STATUS current
        DESCRIPTION
            "lagPmCur."
        INDEX{ lagPmCurEid,lagPmCurParaLen,lagPmCurPara }
        ::= { lagPmCurTable 1 }

    LagPmCurEntry ::=
        SEQUENCE {
            lagPmCurEid
                DataPmEventType,
            lagPmCurParaLen
                Unsigned32,
            lagPmCurPara
                OCTET STRING,
            lagPmCurMonValue
                Counter64,
            lagPmCurDatetime
                DateAndTime
        }

    -- 1.3.6.1.4.1.2011.2.25.3.70.20.55.100.1.1
    lagPmCurEid OBJECT-TYPE
        SYNTAX DataPmEventType
        MAX-ACCESS read-only
        STATUS current
        DESCRIPTION
            "DataPmEid."
        ::= { lagPmCurEntry 1 }

    -- 1.3.6.1.4.1.2011.2.25.3.70.20.55.100.1.2
    lagPmCurParaLen OBJECT-TYPE
        SYNTAX Unsigned32
        MAX-ACCESS read-only
        STATUS current
        DESCRIPTION
            "ParaLen."
        ::= { lagPmCurEntry 2 }

    -- 1.3.6.1.4.1.2011.2.25.3.70.20.55.100.1.3
    lagPmCurPara OBJECT-TYPE
        SYNTAX OCTET STRING
        MAX-ACCESS read-only
        STATUS current
        DESCRIPTION
            "para"
        ::= { lagPmCurEntry 3 }

    -- 1.3.6.1.4.1.2011.2.25.3.70.20.55.100.1.4
    lagPmCurMonValue OBJECT-TYPE
        SYNTAX Counter64
        MAX-ACCESS read-only
        STATUS current
        DESCRIPTION
            "DataPmMonValue."
        ::= { lagPmCurEntry 4 }

    -- 1.3.6.1.4.1.2011.2.25.3.70.20.55.100.1.5
    lagPmCurDatetime OBJECT-TYPE
        SYNTAX DateAndTime
        MAX-ACCESS read-only
        STATUS current
        DESCRIPTION
            "Start Time."
        ::= { lagPmCurEntry 5 }

    -- 1.3.6.1.4.1.2011.2.25.3.70.20.55.110
    lagPm30sHisTable OBJECT-TYPE
        SYNTAX SEQUENCE OF LagPm30sHisEntry
        MAX-ACCESS not-accessible
        STATUS current
        DESCRIPTION
            "lagDataPm30sHis."
        ::= { lag 110 }

    -- 1.3.6.1.4.1.2011.2.25.3.70.20.55.110.1
    lagPm30sHisEntry OBJECT-TYPE
        SYNTAX LagPm30sHisEntry
        MAX-ACCESS not-accessible
        STATUS current
        DESCRIPTION
            "lagDataPm30sHis."
        INDEX{ lagPm30sHisEid,lagPm30sHisParaLen,lagPm30sHisPara,lagPm30sHisStartTime,lagPm30sHisEndTime }
        ::= { lagPm30sHisTable 1 }

    LagPm30sHisEntry ::=
        SEQUENCE {
            lagPm30sHisEid
                DataPmEventType,
            lagPm30sHisParaLen
                Unsigned32,
            lagPm30sHisPara
                OCTET STRING,
            lagPm30sHisMonValue
                Counter64,
            lagPm30sHisStartTime
                DateAndTime,
            lagPm30sHisEndTime
                DateAndTime,
            lagPm30sHisVldty
                ValidflagType
        }

    -- 1.3.6.1.4.1.2011.2.25.3.70.20.55.110.1.1
    lagPm30sHisEid OBJECT-TYPE
        SYNTAX DataPmEventType
        MAX-ACCESS read-only
        STATUS current
        DESCRIPTION
            "DataPmEid."
        ::= { lagPm30sHisEntry 1 }

    -- 1.3.6.1.4.1.2011.2.25.3.70.20.55.110.1.2
    lagPm30sHisParaLen OBJECT-TYPE
        SYNTAX Unsigned32
        MAX-ACCESS read-only
        STATUS current
        DESCRIPTION
            "ParaLen."
        ::= { lagPm30sHisEntry 2 }

    -- 1.3.6.1.4.1.2011.2.25.3.70.20.55.110.1.3
    lagPm30sHisPara OBJECT-TYPE
        SYNTAX OCTET STRING(SIZE (0..100))
        MAX-ACCESS read-only
        STATUS current
        DESCRIPTION
            "para"
        ::= { lagPm30sHisEntry 3 }

    -- 1.3.6.1.4.1.2011.2.25.3.70.20.55.110.1.4
    lagPm30sHisMonValue OBJECT-TYPE
        SYNTAX Counter64
        MAX-ACCESS read-only
        STATUS current
        DESCRIPTION
            "DataPmMonValue."
        ::= { lagPm30sHisEntry 4 }

    -- 1.3.6.1.4.1.2011.2.25.3.70.20.55.110.1.5
    lagPm30sHisStartTime OBJECT-TYPE
        SYNTAX DateAndTime
        MAX-ACCESS read-only
        STATUS current
        DESCRIPTION
            "Start Time."
        ::= { lagPm30sHisEntry 5 }

    -- 1.3.6.1.4.1.2011.2.25.3.70.20.55.110.1.6
    lagPm30sHisEndTime OBJECT-TYPE
        SYNTAX DateAndTime
        MAX-ACCESS read-only
        STATUS current
        DESCRIPTION
            "End Time."
        ::= { lagPm30sHisEntry 6 }

    -- 1.3.6.1.4.1.2011.2.25.3.70.20.55.110.1.7
    lagPm30sHisVldty OBJECT-TYPE
        SYNTAX ValidflagType
        MAX-ACCESS read-only
        STATUS current
        DESCRIPTION
            "Validity."
        ::= { lagPm30sHisEntry 7 }

    -- 1.3.6.1.4.1.2011.2.25.3.70.20.55.120
    lagPm30mHisTable OBJECT-TYPE
        SYNTAX SEQUENCE OF LagPm30mHisEntry
        MAX-ACCESS not-accessible
        STATUS current
        DESCRIPTION
            "lagPm30mHis."
        ::= { lag 120 }

    -- 1.3.6.1.4.1.2011.2.25.3.70.20.55.120.1
    lagPm30mHisEntry OBJECT-TYPE
        SYNTAX LagPm30mHisEntry
        MAX-ACCESS not-accessible
        STATUS current
        DESCRIPTION
            "lagPm30mHis."
        INDEX{ lagPm30mHisEid,lagPm30mHisParaLen,lagPm30mHisPara,lagPm30mHisStartTime,lagPm30mHisEndTime }
        ::= { lagPm30mHisTable 1 }

    LagPm30mHisEntry ::=
        SEQUENCE {
            lagPm30mHisEid
                DataPmEventType,
            lagPm30mHisParaLen
                Unsigned32,
            lagPm30mHisPara
                OCTET STRING,
            lagPm30mHisMonValue
                Counter64,
            lagPm30mHisStartTime
                DateAndTime,
            lagPm30mHisEndTime
                DateAndTime,
            lagPm30mHisVldty
                ValidflagType
        }

    -- 1.3.6.1.4.1.2011.2.25.3.70.20.55.120.1.1
    lagPm30mHisEid OBJECT-TYPE
        SYNTAX DataPmEventType
        MAX-ACCESS read-only
        STATUS current
        DESCRIPTION
            "DataPmEid."
        ::= { lagPm30mHisEntry 1 }

    -- 1.3.6.1.4.1.2011.2.25.3.70.20.55.120.1.2
    lagPm30mHisParaLen OBJECT-TYPE
        SYNTAX Unsigned32
        MAX-ACCESS read-only
        STATUS current
        DESCRIPTION
            "ParaLen."
        ::= { lagPm30mHisEntry 2 }

    -- 1.3.6.1.4.1.2011.2.25.3.70.20.55.120.1.3
    lagPm30mHisPara OBJECT-TYPE
        SYNTAX OCTET STRING(SIZE (0..100))
        MAX-ACCESS read-only
        STATUS current
        DESCRIPTION
            "para"
        ::= { lagPm30mHisEntry 3 }

    -- 1.3.6.1.4.1.2011.2.25.3.70.20.55.120.1.4
    lagPm30mHisMonValue OBJECT-TYPE
        SYNTAX Counter64
        MAX-ACCESS read-only
        STATUS current
        DESCRIPTION
            "DataPmMonValue."
        ::= { lagPm30mHisEntry 4 }

    -- 1.3.6.1.4.1.2011.2.25.3.70.20.55.120.1.5
    lagPm30mHisStartTime OBJECT-TYPE
        SYNTAX DateAndTime
        MAX-ACCESS read-only
        STATUS current
        DESCRIPTION
            "Start Time."
        ::= { lagPm30mHisEntry 5 }

    -- 1.3.6.1.4.1.2011.2.25.3.70.20.55.120.1.6
    lagPm30mHisEndTime OBJECT-TYPE
        SYNTAX DateAndTime
        MAX-ACCESS read-only
        STATUS current
        DESCRIPTION
            "End Time."
        ::= { lagPm30mHisEntry 6 }

    -- 1.3.6.1.4.1.2011.2.25.3.70.20.55.120.1.7
    lagPm30mHisVldty OBJECT-TYPE
        SYNTAX ValidflagType
        MAX-ACCESS read-only
        STATUS current
        DESCRIPTION
            "Validity."
        ::= { lagPm30mHisEntry 7 }

    -- 1.3.6.1.4.1.2011.2.25.3.70.20.55.130
    lagPmvar1HisTable OBJECT-TYPE
        SYNTAX SEQUENCE OF LagPmvar1HisEntry
        MAX-ACCESS not-accessible
        STATUS current
        DESCRIPTION
            "lagPmvar1His."
        ::= { lag 130 }

    -- 1.3.6.1.4.1.2011.2.25.3.70.20.55.130.1
    lagPmvar1HisEntry OBJECT-TYPE
        SYNTAX LagPmvar1HisEntry
        MAX-ACCESS not-accessible
        STATUS current
        DESCRIPTION
            "lagPmvar1His."
        INDEX{ lagPmvar1HisEid,lagPmvar1HisParaLen,lagPmvar1HisPara,lagPmvar1HisStartTime,lagPmvar1HisEndTime }
        ::= { lagPmvar1HisTable 1 }

    LagPmvar1HisEntry ::=
        SEQUENCE {
            lagPmvar1HisEid
                DataPmEventType,
            lagPmvar1HisParaLen
                Unsigned32,
            lagPmvar1HisPara
                OCTET STRING,
            lagPmvar1HisMonValue
                Counter64,
            lagPmvar1HisStartTime
                DateAndTime,
            lagPmvar1HisEndTime
                DateAndTime,
            lagPmvar1HisVldty
                ValidflagType
        }

    -- 1.3.6.1.4.1.2011.2.25.3.70.20.55.130.1.1
    lagPmvar1HisEid OBJECT-TYPE
        SYNTAX DataPmEventType
        MAX-ACCESS read-only
        STATUS current
        DESCRIPTION
            "DataPmEid."
        ::= { lagPmvar1HisEntry 1 }

    -- 1.3.6.1.4.1.2011.2.25.3.70.20.55.130.1.2
    lagPmvar1HisParaLen OBJECT-TYPE
        SYNTAX Unsigned32
        MAX-ACCESS read-only
        STATUS current
        DESCRIPTION
            "ParaLen."
        ::= { lagPmvar1HisEntry 2 }

    -- 1.3.6.1.4.1.2011.2.25.3.70.20.55.130.1.3
    lagPmvar1HisPara OBJECT-TYPE
        SYNTAX OCTET STRING (SIZE (0..100))
        MAX-ACCESS read-only
        STATUS current
        DESCRIPTION
            "para"
        ::= { lagPmvar1HisEntry 3 }

    -- 1.3.6.1.4.1.2011.2.25.3.70.20.55.130.1.4
    lagPmvar1HisMonValue OBJECT-TYPE
        SYNTAX Counter64
        MAX-ACCESS read-only
        STATUS current
        DESCRIPTION
            "DataPmMonValue."
        ::= { lagPmvar1HisEntry 4 }

    -- 1.3.6.1.4.1.2011.2.25.3.70.20.55.130.1.5
    lagPmvar1HisStartTime OBJECT-TYPE
        SYNTAX DateAndTime
        MAX-ACCESS read-only
        STATUS current
        DESCRIPTION
            "Start Time."
        ::= { lagPmvar1HisEntry 5 }

    -- 1.3.6.1.4.1.2011.2.25.3.70.20.55.130.1.6
    lagPmvar1HisEndTime OBJECT-TYPE
        SYNTAX DateAndTime
        MAX-ACCESS read-only
        STATUS current
        DESCRIPTION
            "End Time."
        ::= { lagPmvar1HisEntry 6 }

    -- 1.3.6.1.4.1.2011.2.25.3.70.20.55.130.1.7
    lagPmvar1HisVldty OBJECT-TYPE
        SYNTAX ValidflagType
        MAX-ACCESS read-only
        STATUS current
        DESCRIPTION
            "Validity."
        ::= { lagPmvar1HisEntry 7 }

    -- 1.3.6.1.4.1.2011.2.25.3.70.20.55.140
    lagPmvar2HisTable OBJECT-TYPE
        SYNTAX SEQUENCE OF LagPmvar2HisEntry
        MAX-ACCESS not-accessible
        STATUS current
        DESCRIPTION
            "lagPmvar2His."
        ::= { lag 140 }

    -- 1.3.6.1.4.1.2011.2.25.3.70.20.55.140.1
    lagPmvar2HisEntry OBJECT-TYPE
        SYNTAX LagPmvar2HisEntry
        MAX-ACCESS not-accessible
        STATUS current
        DESCRIPTION
            "lagPmvar2His."
        INDEX{ lagPmvar2HisEid,lagPmvar2HisParaLen,lagPmvar2HisPara,lagPmvar2HisStartTime,lagPmvar2HisEndTime }
        ::= { lagPmvar2HisTable 1 }

    LagPmvar2HisEntry ::=
        SEQUENCE {
            lagPmvar2HisEid
                DataPmEventType,
            lagPmvar2HisParaLen
                Unsigned32,
            lagPmvar2HisPara
                OCTET STRING,
            lagPmvar2HisMonValue
                Counter64,
            lagPmvar2HisStartTime
                DateAndTime,
            lagPmvar2HisEndTime
                DateAndTime,
            lagPmvar2HisVldty
                ValidflagType
        }

    -- 1.3.6.1.4.1.2011.2.25.3.70.20.55.140.1.1
    lagPmvar2HisEid OBJECT-TYPE
        SYNTAX DataPmEventType
        MAX-ACCESS read-only
        STATUS current
        DESCRIPTION
            "DataPmEid."
        ::= { lagPmvar2HisEntry 1 }

    -- 1.3.6.1.4.1.2011.2.25.3.70.20.55.140.1.2
    lagPmvar2HisParaLen OBJECT-TYPE
        SYNTAX Unsigned32
        MAX-ACCESS read-only
        STATUS current
        DESCRIPTION
            "ParaLen."
        ::= { lagPmvar2HisEntry 2 }

    -- 1.3.6.1.4.1.2011.2.25.3.70.20.55.140.1.3
    lagPmvar2HisPara OBJECT-TYPE
        SYNTAX OCTET STRING(SIZE (0..100))
        MAX-ACCESS read-only
        STATUS current
        DESCRIPTION
            "para"
        ::= { lagPmvar2HisEntry 3 }

    -- 1.3.6.1.4.1.2011.2.25.3.70.20.55.140.1.4
    lagPmvar2HisMonValue OBJECT-TYPE
        SYNTAX Counter64
        MAX-ACCESS read-only
        STATUS current
        DESCRIPTION
            "DataPmMonValue."
        ::= { lagPmvar2HisEntry 4 }

    -- 1.3.6.1.4.1.2011.2.25.3.70.20.55.140.1.5
    lagPmvar2HisStartTime OBJECT-TYPE
        SYNTAX DateAndTime
        MAX-ACCESS read-only
        STATUS current
        DESCRIPTION
            "Start Time."
        ::= { lagPmvar2HisEntry 5 }

    -- 1.3.6.1.4.1.2011.2.25.3.70.20.55.140.1.6
    lagPmvar2HisEndTime OBJECT-TYPE
        SYNTAX DateAndTime
        MAX-ACCESS read-only
        STATUS current
        DESCRIPTION
            "End Time."
        ::= { lagPmvar2HisEntry 6 }

    -- 1.3.6.1.4.1.2011.2.25.3.70.20.55.140.1.7
    lagPmvar2HisVldty OBJECT-TYPE
        SYNTAX ValidflagType
        MAX-ACCESS read-only
        STATUS current
        DESCRIPTION
            "Validity."
        ::= { lagPmvar2HisEntry 7 }

    -- 1.3.6.1.4.1.2011.2.25.3.70.20.59
    mepperf OBJECT IDENTIFIER ::= { rtnData 59 }

    -- 1.3.6.1.4.1.2011.2.25.3.70.20.59.100
    mepperfPmCurTable OBJECT-TYPE
        SYNTAX SEQUENCE OF MepperfPmCurEntry
        MAX-ACCESS not-accessible
        STATUS current
        DESCRIPTION
            "mepperfDataPm30sCur."
        ::= { mepperf 100 }

    -- 1.3.6.1.4.1.2011.2.25.3.70.20.59.100.1
    mepperfPmCurEntry OBJECT-TYPE
        SYNTAX MepperfPmCurEntry
        MAX-ACCESS not-accessible
        STATUS current
        DESCRIPTION
            "mepperfPmCur."
        INDEX{ mepperfPmCurEid,mepperfPmCurParaLen, mepperfPmCurPara }
        ::= { mepperfPmCurTable 1 }

    MepperfPmCurEntry ::=
        SEQUENCE {
            mepperfPmCurEid
                DataPmEventType,
            mepperfPmCurParaLen
                Unsigned32,
            mepperfPmCurPara
                OCTET STRING,
            mepperfPmCurMonValue
                Counter64,
            mepperfPmCurDatetime
                DateAndTime
        }

    -- 1.3.6.1.4.1.2011.2.25.3.70.20.59.100.1.1
    mepperfPmCurEid OBJECT-TYPE
        SYNTAX DataPmEventType
        MAX-ACCESS read-only
        STATUS current
        DESCRIPTION
            "DataPmEid."
        ::= { mepperfPmCurEntry 1 }

    -- 1.3.6.1.4.1.2011.2.25.3.70.20.59.100.1.2
    mepperfPmCurParaLen OBJECT-TYPE
        SYNTAX Unsigned32
        MAX-ACCESS read-only
        STATUS current
        DESCRIPTION
            "ParaLen."
        ::= { mepperfPmCurEntry 2 }

    -- 1.3.6.1.4.1.2011.2.25.3.70.20.59.100.1.3
    mepperfPmCurPara OBJECT-TYPE
        SYNTAX OCTET STRING
        MAX-ACCESS read-only
        STATUS current
        DESCRIPTION
            "para"
        ::= { mepperfPmCurEntry 3 }

    -- 1.3.6.1.4.1.2011.2.25.3.70.20.59.100.1.4
    mepperfPmCurMonValue OBJECT-TYPE
        SYNTAX Counter64
        MAX-ACCESS read-only
        STATUS current
        DESCRIPTION
            "DataPmMonValue."
        ::= { mepperfPmCurEntry 4 }

    -- 1.3.6.1.4.1.2011.2.25.3.70.20.59.100.1.5
    mepperfPmCurDatetime OBJECT-TYPE
        SYNTAX DateAndTime
        MAX-ACCESS read-only
        STATUS current
        DESCRIPTION
            "Start Time."
        ::= { mepperfPmCurEntry 5 }

    -- 1.3.6.1.4.1.2011.2.25.3.70.20.59.110
    mepperfPm30sHisTable OBJECT-TYPE
        SYNTAX SEQUENCE OF MepperfPm30sHisEntry
        MAX-ACCESS not-accessible
        STATUS current
        DESCRIPTION
            "mepperfDataPm30sHis."
        ::= { mepperf 110 }

    -- 1.3.6.1.4.1.2011.2.25.3.70.20.59.110.1
    mepperfPm30sHisEntry OBJECT-TYPE
        SYNTAX MepperfPm30sHisEntry
        MAX-ACCESS not-accessible
        STATUS current
        DESCRIPTION
            "mepperfDataPm30sHis."
        INDEX{ mepperfPm30sHisEid,mepperfPm30sHisParaLen,mepperfPm30sHisPara,mepperfPm30sHisStartTime,mepperfPm30sHisEndTime }
        ::= { mepperfPm30sHisTable 1 }

    MepperfPm30sHisEntry ::=
        SEQUENCE {
            mepperfPm30sHisEid
                DataPmEventType,
            mepperfPm30sHisParaLen
                Unsigned32,
            mepperfPm30sHisPara
                OCTET STRING,
            mepperfPm30sHisMonValue
                Counter64,
            mepperfPm30sHisStartTime
                DateAndTime,
            mepperfPm30sHisEndTime
                DateAndTime,
            mepperfPm30sHisVldty
                ValidflagType
        }

    -- 1.3.6.1.4.1.2011.2.25.3.70.20.59.110.1.1
    mepperfPm30sHisEid OBJECT-TYPE
        SYNTAX DataPmEventType
        MAX-ACCESS read-only
        STATUS current
        DESCRIPTION
            "DataPmEid."
        ::= { mepperfPm30sHisEntry 1 }

    -- 1.3.6.1.4.1.2011.2.25.3.70.20.59.110.1.2
    mepperfPm30sHisParaLen OBJECT-TYPE
        SYNTAX Unsigned32
        MAX-ACCESS read-only
        STATUS current
        DESCRIPTION
            "ParaLen."
        ::= { mepperfPm30sHisEntry 2 }

    -- 1.3.6.1.4.1.2011.2.25.3.70.20.59.110.1.3
    mepperfPm30sHisPara OBJECT-TYPE
        SYNTAX OCTET STRING(SIZE (0..100))
        MAX-ACCESS read-only
        STATUS current
        DESCRIPTION
            "para"
        ::= { mepperfPm30sHisEntry 3 }

    -- 1.3.6.1.4.1.2011.2.25.3.70.20.59.110.1.4
    mepperfPm30sHisMonValue OBJECT-TYPE
        SYNTAX Counter64
        MAX-ACCESS read-only
        STATUS current
        DESCRIPTION
            "DataPmMonValue."
        ::= { mepperfPm30sHisEntry 4 }

    -- 1.3.6.1.4.1.2011.2.25.3.70.20.59.110.1.5
    mepperfPm30sHisStartTime OBJECT-TYPE
        SYNTAX DateAndTime
        MAX-ACCESS read-only
        STATUS current
        DESCRIPTION
            "Start Time."
        ::= { mepperfPm30sHisEntry 5 }

    -- 1.3.6.1.4.1.2011.2.25.3.70.20.59.110.1.6
    mepperfPm30sHisEndTime OBJECT-TYPE
        SYNTAX DateAndTime
        MAX-ACCESS read-only
        STATUS current
        DESCRIPTION
            "End Time."
        ::= { mepperfPm30sHisEntry 6 }

    -- 1.3.6.1.4.1.2011.2.25.3.70.20.59.110.1.7
    mepperfPm30sHisVldty OBJECT-TYPE
        SYNTAX ValidflagType
        MAX-ACCESS read-only
        STATUS current
        DESCRIPTION
            "Validity."
        ::= { mepperfPm30sHisEntry 7 }

    -- 1.3.6.1.4.1.2011.2.25.3.70.20.59.120
    mepperfPm30mHisTable OBJECT-TYPE
        SYNTAX SEQUENCE OF MepperfPm30mHisEntry
        MAX-ACCESS not-accessible
        STATUS current
        DESCRIPTION
            "mepperfPm30mHis."
        ::= { mepperf 120 }

    -- 1.3.6.1.4.1.2011.2.25.3.70.20.59.120.1
    mepperfPm30mHisEntry OBJECT-TYPE
        SYNTAX MepperfPm30mHisEntry
        MAX-ACCESS not-accessible
        STATUS current
        DESCRIPTION
            "mepperfPm30mHis."
        INDEX{ mepperfPm30mHisEid,mepperfPm30mHisParaLen,mepperfPm30mHisPara,mepperfPm30mHisStartTime,mepperfPm30mHisEndTime }
        ::= { mepperfPm30mHisTable 1 }

    MepperfPm30mHisEntry ::=
        SEQUENCE {
            mepperfPm30mHisEid
                DataPmEventType,
            mepperfPm30mHisParaLen
                Unsigned32,
            mepperfPm30mHisPara
                OCTET STRING,
            mepperfPm30mHisMonValue
                Counter64,
            mepperfPm30mHisStartTime
                DateAndTime,
            mepperfPm30mHisEndTime
                DateAndTime,
            mepperfPm30mHisVldty
                ValidflagType
        }

    -- 1.3.6.1.4.1.2011.2.25.3.70.20.59.120.1.1
    mepperfPm30mHisEid OBJECT-TYPE
        SYNTAX DataPmEventType
        MAX-ACCESS read-only
        STATUS current
        DESCRIPTION
            "DataPmEid."
        ::= { mepperfPm30mHisEntry 1 }

    -- 1.3.6.1.4.1.2011.2.25.3.70.20.59.120.1.2
    mepperfPm30mHisParaLen OBJECT-TYPE
        SYNTAX Unsigned32
        MAX-ACCESS read-only
        STATUS current
        DESCRIPTION
            "ParaLen."
        ::= { mepperfPm30mHisEntry 2 }

    -- 1.3.6.1.4.1.2011.2.25.3.70.20.59.120.1.3
    mepperfPm30mHisPara OBJECT-TYPE
        SYNTAX OCTET STRING(SIZE (0..100))
        MAX-ACCESS read-only
        STATUS current
        DESCRIPTION
            "para"
        ::= { mepperfPm30mHisEntry 3 }

    -- 1.3.6.1.4.1.2011.2.25.3.70.20.59.120.1.4
    mepperfPm30mHisMonValue OBJECT-TYPE
        SYNTAX Counter64
        MAX-ACCESS read-only
        STATUS current
        DESCRIPTION
            "DataPmMonValue."
        ::= { mepperfPm30mHisEntry 4 }

    -- 1.3.6.1.4.1.2011.2.25.3.70.20.59.120.1.5
    mepperfPm30mHisStartTime OBJECT-TYPE
        SYNTAX DateAndTime
        MAX-ACCESS read-only
        STATUS current
        DESCRIPTION
            "Start Time."
        ::= { mepperfPm30mHisEntry 5 }

    -- 1.3.6.1.4.1.2011.2.25.3.70.20.59.120.1.6
    mepperfPm30mHisEndTime OBJECT-TYPE
        SYNTAX DateAndTime
        MAX-ACCESS read-only
        STATUS current
        DESCRIPTION
            "End Time."
        ::= { mepperfPm30mHisEntry 6 }

    -- 1.3.6.1.4.1.2011.2.25.3.70.20.59.120.1.7
    mepperfPm30mHisVldty OBJECT-TYPE
        SYNTAX ValidflagType
        MAX-ACCESS read-only
        STATUS current
        DESCRIPTION
            "Validity."
        ::= { mepperfPm30mHisEntry 7 }

    -- 1.3.6.1.4.1.2011.2.25.3.70.20.59.130
    mepperfPmvar1HisTable OBJECT-TYPE
        SYNTAX SEQUENCE OF MepperfPmvar1HisEntry
        MAX-ACCESS not-accessible
        STATUS current
        DESCRIPTION
            "mepperfPmvar1His."
        ::= { mepperf 130 }

    -- 1.3.6.1.4.1.2011.2.25.3.70.20.59.130.1
    mepperfPmvar1HisEntry OBJECT-TYPE
        SYNTAX MepperfPmvar1HisEntry
        MAX-ACCESS not-accessible
        STATUS current
        DESCRIPTION
            "mepperfPmvar1His."
        INDEX{ mepperfPmvar1HisEid,mepperfPmvar1HisParaLen,mepperfPmvar1HisPara,mepperfPmvar1HisStartTime,mepperfPmvar1HisEndTime }
        ::= { mepperfPmvar1HisTable 1 }

    MepperfPmvar1HisEntry ::=
        SEQUENCE {
            mepperfPmvar1HisEid
                DataPmEventType,
            mepperfPmvar1HisParaLen
                Unsigned32,
            mepperfPmvar1HisPara
                OCTET STRING,
            mepperfPmvar1HisMonValue
                Counter64,
            mepperfPmvar1HisStartTime
                DateAndTime,
            mepperfPmvar1HisEndTime
                DateAndTime,
            mepperfPmvar1HisVldty
                ValidflagType
        }

    -- 1.3.6.1.4.1.2011.2.25.3.70.20.59.130.1.1
    mepperfPmvar1HisEid OBJECT-TYPE
        SYNTAX DataPmEventType
        MAX-ACCESS read-only
        STATUS current
        DESCRIPTION
            "DataPmEid."
        ::= { mepperfPmvar1HisEntry 1 }

    -- 1.3.6.1.4.1.2011.2.25.3.70.20.59.130.1.2
    mepperfPmvar1HisParaLen OBJECT-TYPE
        SYNTAX Unsigned32
        MAX-ACCESS read-only
        STATUS current
        DESCRIPTION
            "ParaLen."
        ::= { mepperfPmvar1HisEntry 2 }

    -- 1.3.6.1.4.1.2011.2.25.3.70.20.59.130.1.3
    mepperfPmvar1HisPara OBJECT-TYPE
        SYNTAX OCTET STRING (SIZE (0..100))
        MAX-ACCESS read-only
        STATUS current
        DESCRIPTION
            "para"
        ::= { mepperfPmvar1HisEntry 3 }

    -- 1.3.6.1.4.1.2011.2.25.3.70.20.59.130.1.4
    mepperfPmvar1HisMonValue OBJECT-TYPE
        SYNTAX Counter64
        MAX-ACCESS read-only
        STATUS current
        DESCRIPTION
            "DataPmMonValue."
        ::= { mepperfPmvar1HisEntry 4 }

    -- 1.3.6.1.4.1.2011.2.25.3.70.20.59.130.1.5
    mepperfPmvar1HisStartTime OBJECT-TYPE
        SYNTAX DateAndTime
        MAX-ACCESS read-only
        STATUS current
        DESCRIPTION
            "Start Time."
        ::= { mepperfPmvar1HisEntry 5 }

    -- 1.3.6.1.4.1.2011.2.25.3.70.20.59.130.1.6
    mepperfPmvar1HisEndTime OBJECT-TYPE
        SYNTAX DateAndTime
        MAX-ACCESS read-only
        STATUS current
        DESCRIPTION
            "End Time."
        ::= { mepperfPmvar1HisEntry 6 }

    -- 1.3.6.1.4.1.2011.2.25.3.70.20.59.130.1.7
    mepperfPmvar1HisVldty OBJECT-TYPE
        SYNTAX ValidflagType
        MAX-ACCESS read-only
        STATUS current
        DESCRIPTION
            "Validity."
        ::= { mepperfPmvar1HisEntry 7 }

    -- 1.3.6.1.4.1.2011.2.25.3.70.20.59.140
    mepperfPmvar2HisTable OBJECT-TYPE
        SYNTAX SEQUENCE OF MepperfPmvar2HisEntry
        MAX-ACCESS not-accessible
        STATUS current
        DESCRIPTION
            "mepperfPmvar2His."
        ::= { mepperf 140 }

    -- 1.3.6.1.4.1.2011.2.25.3.70.20.59.140.1
    mepperfPmvar2HisEntry OBJECT-TYPE
        SYNTAX MepperfPmvar2HisEntry
        MAX-ACCESS not-accessible
        STATUS current
        DESCRIPTION
            "mepperfPmvar2His."
        INDEX{ mepperfPmvar2HisEid,mepperfPmvar2HisParaLen,mepperfPmvar2HisPara,mepperfPmvar2HisStartTime,mepperfPmvar2HisEndTime }
        ::= { mepperfPmvar2HisTable 1 }

    MepperfPmvar2HisEntry ::=
        SEQUENCE {
            mepperfPmvar2HisEid
                DataPmEventType,
            mepperfPmvar2HisParaLen
                Unsigned32,
            mepperfPmvar2HisPara
                OCTET STRING,
            mepperfPmvar2HisMonValue
                Counter64,
            mepperfPmvar2HisStartTime
                DateAndTime,
            mepperfPmvar2HisEndTime
                DateAndTime,
            mepperfPmvar2HisVldty
                ValidflagType
        }

    -- 1.3.6.1.4.1.2011.2.25.3.70.20.59.140.1.1
    mepperfPmvar2HisEid OBJECT-TYPE
        SYNTAX DataPmEventType
        MAX-ACCESS read-only
        STATUS current
        DESCRIPTION
            "DataPmEid."
        ::= { mepperfPmvar2HisEntry 1 }

    -- 1.3.6.1.4.1.2011.2.25.3.70.20.59.140.1.2
    mepperfPmvar2HisParaLen OBJECT-TYPE
        SYNTAX Unsigned32
        MAX-ACCESS read-only
        STATUS current
        DESCRIPTION
            "ParaLen."
        ::= { mepperfPmvar2HisEntry 2 }

    -- 1.3.6.1.4.1.2011.2.25.3.70.20.59.140.1.3
    mepperfPmvar2HisPara OBJECT-TYPE
        SYNTAX OCTET STRING(SIZE (0..100))
        MAX-ACCESS read-only
        STATUS current
        DESCRIPTION
            "para"
        ::= { mepperfPmvar2HisEntry 3 }

    -- 1.3.6.1.4.1.2011.2.25.3.70.20.59.140.1.4
    mepperfPmvar2HisMonValue OBJECT-TYPE
        SYNTAX Counter64
        MAX-ACCESS read-only
        STATUS current
        DESCRIPTION
            "DataPmMonValue."
        ::= { mepperfPmvar2HisEntry 4 }

    -- 1.3.6.1.4.1.2011.2.25.3.70.20.59.140.1.5
    mepperfPmvar2HisStartTime OBJECT-TYPE
        SYNTAX DateAndTime
        MAX-ACCESS read-only
        STATUS current
        DESCRIPTION
            "Start Time."
        ::= { mepperfPmvar2HisEntry 5 }

    -- 1.3.6.1.4.1.2011.2.25.3.70.20.59.140.1.6
    mepperfPmvar2HisEndTime OBJECT-TYPE
        SYNTAX DateAndTime
        MAX-ACCESS read-only
        STATUS current
        DESCRIPTION
            "End Time."
        ::= { mepperfPmvar2HisEntry 6 }

    -- 1.3.6.1.4.1.2011.2.25.3.70.20.59.140.1.7
    mepperfPmvar2HisVldty OBJECT-TYPE
        SYNTAX ValidflagType
        MAX-ACCESS read-only
        STATUS current
        DESCRIPTION
            "Validity."
        ::= { mepperfPmvar2HisEntry 7 }

    -- 1.3.6.1.4.1.2011.2.25.3.70.20.102
    ethPort OBJECT IDENTIFIER ::= { rtnData 102 }

    -- 1.3.6.1.4.1.2011.2.25.3.70.20.102.100
    ethPortPmCurTable OBJECT-TYPE
        SYNTAX SEQUENCE OF EthPortPmCurEntry
        MAX-ACCESS not-accessible
        STATUS current
        DESCRIPTION
            "ethPortDataPm30sCur."
        ::= { ethPort 100 }

    -- 1.3.6.1.4.1.2011.2.25.3.70.20.102.100.1
    ethPortPmCurEntry OBJECT-TYPE
        SYNTAX EthPortPmCurEntry
        MAX-ACCESS not-accessible
        STATUS current
        DESCRIPTION
            "ethPortPmCur."
        INDEX{ ethPortPmCurEid,ethPortPmCurParaLen, ethPortPmCurPara }
        ::= { ethPortPmCurTable 1 }

    EthPortPmCurEntry ::=
        SEQUENCE {
            ethPortPmCurEid
                DataPmEventType,
            ethPortPmCurParaLen
                Unsigned32,
            ethPortPmCurPara
                OCTET STRING,
            ethPortPmCurMonValue
                Counter64,
            ethPortPmCurDatetime
                DateAndTime
        }

    -- 1.3.6.1.4.1.2011.2.25.3.70.20.102.100.1.1
    ethPortPmCurEid OBJECT-TYPE
        SYNTAX DataPmEventType
        MAX-ACCESS read-only
        STATUS current
        DESCRIPTION
            "DataPmEid."
        ::= { ethPortPmCurEntry 1 }

    -- 1.3.6.1.4.1.2011.2.25.3.70.20.102.100.1.2
    ethPortPmCurParaLen OBJECT-TYPE
        SYNTAX Unsigned32
        MAX-ACCESS read-only
        STATUS current
        DESCRIPTION
            "ParaLen."
        ::= { ethPortPmCurEntry 2 }

    -- 1.3.6.1.4.1.2011.2.25.3.70.20.102.100.1.3
    ethPortPmCurPara OBJECT-TYPE
        SYNTAX OCTET STRING
        MAX-ACCESS read-only
        STATUS current
        DESCRIPTION
            "para"
        ::= { ethPortPmCurEntry 3 }

    -- 1.3.6.1.4.1.2011.2.25.3.70.20.102.100.1.4
    ethPortPmCurMonValue OBJECT-TYPE
        SYNTAX Counter64
        MAX-ACCESS read-only
        STATUS current
        DESCRIPTION
            "DataPmMonValue."
        ::= { ethPortPmCurEntry 4 }

    -- 1.3.6.1.4.1.2011.2.25.3.70.20.102.100.1.5
    ethPortPmCurDatetime OBJECT-TYPE
        SYNTAX DateAndTime
        MAX-ACCESS read-only
        STATUS current
        DESCRIPTION
            "Start Time."
        ::= { ethPortPmCurEntry 5 }

    -- 1.3.6.1.4.1.2011.2.25.3.70.20.102.110
    ethPortPm30sHisTable OBJECT-TYPE
        SYNTAX SEQUENCE OF EthPortPm30sHisEntry
        MAX-ACCESS not-accessible
        STATUS current
        DESCRIPTION
            "ethPortDataPm30sHis."
        ::= { ethPort 110 }

    -- 1.3.6.1.4.1.2011.2.25.3.70.20.102.110.1
    ethPortPm30sHisEntry OBJECT-TYPE
        SYNTAX EthPortPm30sHisEntry
        MAX-ACCESS not-accessible
        STATUS current
        DESCRIPTION
            "ethPortDataPm30sHis."
        INDEX{ ethPortPm30sHisEid,ethPortPm30sHisParaLen,ethPortPm30sHisPara,ethPortPm30sHisStartTime,ethPortPm30sHisEndTime }
        ::= { ethPortPm30sHisTable 1 }

    EthPortPm30sHisEntry ::=
        SEQUENCE {
            ethPortPm30sHisEid
                DataPmEventType,
            ethPortPm30sHisParaLen
                Unsigned32,
            ethPortPm30sHisPara
                OCTET STRING,
            ethPortPm30sHisMonValue
                Counter64,
            ethPortPm30sHisStartTime
                DateAndTime,
            ethPortPm30sHisEndTime
                DateAndTime,
            ethPortPm30sHisVldty
                ValidflagType
        }

    -- 1.3.6.1.4.1.2011.2.25.3.70.20.102.110.1.1
    ethPortPm30sHisEid OBJECT-TYPE
        SYNTAX DataPmEventType
        MAX-ACCESS read-only
        STATUS current
        DESCRIPTION
            "DataPmEid."
        ::= { ethPortPm30sHisEntry 1 }

    -- 1.3.6.1.4.1.2011.2.25.3.70.20.102.110.1.2
    ethPortPm30sHisParaLen OBJECT-TYPE
        SYNTAX Unsigned32
        MAX-ACCESS read-only
        STATUS current
        DESCRIPTION
            "ParaLen."
        ::= { ethPortPm30sHisEntry 2 }

    -- 1.3.6.1.4.1.2011.2.25.3.70.20.102.110.1.3
    ethPortPm30sHisPara OBJECT-TYPE
        SYNTAX OCTET STRING(SIZE (0..100))
        MAX-ACCESS read-only
        STATUS current
        DESCRIPTION
            "para"
        ::= { ethPortPm30sHisEntry 3 }

    -- 1.3.6.1.4.1.2011.2.25.3.70.20.102.110.1.4
    ethPortPm30sHisMonValue OBJECT-TYPE
        SYNTAX Counter64
        MAX-ACCESS read-only
        STATUS current
        DESCRIPTION
            "DataPmMonValue."
        ::= { ethPortPm30sHisEntry 4 }

    -- 1.3.6.1.4.1.2011.2.25.3.70.20.102.110.1.5
    ethPortPm30sHisStartTime OBJECT-TYPE
        SYNTAX DateAndTime
        MAX-ACCESS read-only
        STATUS current
        DESCRIPTION
            "Start Time."
        ::= { ethPortPm30sHisEntry 5 }

    -- 1.3.6.1.4.1.2011.2.25.3.70.20.102.110.1.6
    ethPortPm30sHisEndTime OBJECT-TYPE
        SYNTAX DateAndTime
        MAX-ACCESS read-only
        STATUS current
        DESCRIPTION
            "End Time."
        ::= { ethPortPm30sHisEntry 6 }

    -- 1.3.6.1.4.1.2011.2.25.3.70.20.102.110.1.7
    ethPortPm30sHisVldty OBJECT-TYPE
        SYNTAX ValidflagType
        MAX-ACCESS read-only
        STATUS current
        DESCRIPTION
            "Validity."
        ::= { ethPortPm30sHisEntry 7 }

    -- 1.3.6.1.4.1.2011.2.25.3.70.20.102.120
    ethPortPm30mHisTable OBJECT-TYPE
        SYNTAX SEQUENCE OF EthPortPm30mHisEntry
        MAX-ACCESS not-accessible
        STATUS current
        DESCRIPTION
            "ethPortPm30mHis."
        ::= { ethPort 120 }

    -- 1.3.6.1.4.1.2011.2.25.3.70.20.102.120.1
    ethPortPm30mHisEntry OBJECT-TYPE
        SYNTAX EthPortPm30mHisEntry
        MAX-ACCESS not-accessible
        STATUS current
        DESCRIPTION
            "ethPortPm30mHis."
        INDEX{ ethPortPm30mHisEid,ethPortPm30mHisParaLen,ethPortPm30mHisPara,ethPortPm30mHisStartTime,ethPortPm30mHisEndTime }
        ::= { ethPortPm30mHisTable 1 }

    EthPortPm30mHisEntry ::=
        SEQUENCE {
            ethPortPm30mHisEid
                DataPmEventType,
            ethPortPm30mHisParaLen
                Unsigned32,
            ethPortPm30mHisPara
                OCTET STRING,
            ethPortPm30mHisMonValue
                Counter64,
            ethPortPm30mHisStartTime
                DateAndTime,
            ethPortPm30mHisEndTime
                DateAndTime,
            ethPortPm30mHisVldty
                ValidflagType
        }

    -- 1.3.6.1.4.1.2011.2.25.3.70.20.102.120.1.1
    ethPortPm30mHisEid OBJECT-TYPE
        SYNTAX DataPmEventType
        MAX-ACCESS read-only
        STATUS current
        DESCRIPTION
            "DataPmEid."
        ::= { ethPortPm30mHisEntry 1 }

    -- 1.3.6.1.4.1.2011.2.25.3.70.20.102.120.1.2
    ethPortPm30mHisParaLen OBJECT-TYPE
        SYNTAX Unsigned32
        MAX-ACCESS read-only
        STATUS current
        DESCRIPTION
            "ParaLen."
        ::= { ethPortPm30mHisEntry 2 }

    -- 1.3.6.1.4.1.2011.2.25.3.70.20.102.120.1.3
    ethPortPm30mHisPara OBJECT-TYPE
        SYNTAX OCTET STRING(SIZE (0..100))
        MAX-ACCESS read-only
        STATUS current
        DESCRIPTION
            "para"
        ::= { ethPortPm30mHisEntry 3 }

    -- 1.3.6.1.4.1.2011.2.25.3.70.20.102.120.1.4
    ethPortPm30mHisMonValue OBJECT-TYPE
        SYNTAX Counter64
        MAX-ACCESS read-only
        STATUS current
        DESCRIPTION
            "DataPmMonValue."
        ::= { ethPortPm30mHisEntry 4 }

    -- 1.3.6.1.4.1.2011.2.25.3.70.20.102.120.1.5
    ethPortPm30mHisStartTime OBJECT-TYPE
        SYNTAX DateAndTime
        MAX-ACCESS read-only
        STATUS current
        DESCRIPTION
            "Start Time."
        ::= { ethPortPm30mHisEntry 5 }

    -- 1.3.6.1.4.1.2011.2.25.3.70.20.102.120.1.6
    ethPortPm30mHisEndTime OBJECT-TYPE
        SYNTAX DateAndTime
        MAX-ACCESS read-only
        STATUS current
        DESCRIPTION
            "End Time."
        ::= { ethPortPm30mHisEntry 6 }

    -- 1.3.6.1.4.1.2011.2.25.3.70.20.102.120.1.7
    ethPortPm30mHisVldty OBJECT-TYPE
        SYNTAX ValidflagType
        MAX-ACCESS read-only
        STATUS current
        DESCRIPTION
            "Validity."
        ::= { ethPortPm30mHisEntry 7 }

    -- 1.3.6.1.4.1.2011.2.25.3.70.20.102.130
    ethPortPmvar1HisTable OBJECT-TYPE
        SYNTAX SEQUENCE OF EthPortPmvar1HisEntry
        MAX-ACCESS not-accessible
        STATUS current
        DESCRIPTION
            "ethPortPmvar1His."
        ::= { ethPort 130 }

    -- 1.3.6.1.4.1.2011.2.25.3.70.20.102.130.1
    ethPortPmvar1HisEntry OBJECT-TYPE
        SYNTAX EthPortPmvar1HisEntry
        MAX-ACCESS not-accessible
        STATUS current
        DESCRIPTION
            "ethPortPmvar1His."
        INDEX{ ethPortPmvar1HisEid,ethPortPmvar1HisParaLen,ethPortPmvar1HisPara,ethPortPmvar1HisStartTime,ethPortPmvar1HisEndTime }
        ::= { ethPortPmvar1HisTable 1 }

    EthPortPmvar1HisEntry ::=
        SEQUENCE {
            ethPortPmvar1HisEid
                DataPmEventType,
            ethPortPmvar1HisParaLen
                Unsigned32,
            ethPortPmvar1HisPara
                OCTET STRING,
            ethPortPmvar1HisMonValue
                Counter64,
            ethPortPmvar1HisStartTime
                DateAndTime,
            ethPortPmvar1HisEndTime
                DateAndTime,
            ethPortPmvar1HisVldty
                ValidflagType
        }

    -- 1.3.6.1.4.1.2011.2.25.3.70.20.102.130.1.1
    ethPortPmvar1HisEid OBJECT-TYPE
        SYNTAX DataPmEventType
        MAX-ACCESS read-only
        STATUS current
        DESCRIPTION
            "DataPmEid."
        ::= { ethPortPmvar1HisEntry 1 }

    -- 1.3.6.1.4.1.2011.2.25.3.70.20.102.130.1.2
    ethPortPmvar1HisParaLen OBJECT-TYPE
        SYNTAX Unsigned32
        MAX-ACCESS read-only
        STATUS current
        DESCRIPTION
            "ParaLen."
        ::= { ethPortPmvar1HisEntry 2 }

    -- 1.3.6.1.4.1.2011.2.25.3.70.20.102.130.1.3
    ethPortPmvar1HisPara OBJECT-TYPE
        SYNTAX OCTET STRING (SIZE (0..100))
        MAX-ACCESS read-only
        STATUS current
        DESCRIPTION
            "para"
        ::= { ethPortPmvar1HisEntry 3 }

    -- 1.3.6.1.4.1.2011.2.25.3.70.20.102.130.1.4
    ethPortPmvar1HisMonValue OBJECT-TYPE
        SYNTAX Counter64
        MAX-ACCESS read-only
        STATUS current
        DESCRIPTION
            "DataPmMonValue."
        ::= { ethPortPmvar1HisEntry 4 }

    -- 1.3.6.1.4.1.2011.2.25.3.70.20.102.130.1.5
    ethPortPmvar1HisStartTime OBJECT-TYPE
        SYNTAX DateAndTime
        MAX-ACCESS read-only
        STATUS current
        DESCRIPTION
            "Start Time."
        ::= { ethPortPmvar1HisEntry 5 }

    -- 1.3.6.1.4.1.2011.2.25.3.70.20.102.130.1.6
    ethPortPmvar1HisEndTime OBJECT-TYPE
        SYNTAX DateAndTime
        MAX-ACCESS read-only
        STATUS current
        DESCRIPTION
            "End Time."
        ::= { ethPortPmvar1HisEntry 6 }

    -- 1.3.6.1.4.1.2011.2.25.3.70.20.102.130.1.7
    ethPortPmvar1HisVldty OBJECT-TYPE
        SYNTAX ValidflagType
        MAX-ACCESS read-only
        STATUS current
        DESCRIPTION
            "Validity."
        ::= { ethPortPmvar1HisEntry 7 }

    -- 1.3.6.1.4.1.2011.2.25.3.70.20.102.140
    ethPortPmvar2HisTable OBJECT-TYPE
        SYNTAX SEQUENCE OF EthPortPmvar2HisEntry
        MAX-ACCESS not-accessible
        STATUS current
        DESCRIPTION
            "ethPortPmvar2His."
        ::= { ethPort 140 }

    -- 1.3.6.1.4.1.2011.2.25.3.70.20.102.140.1
    ethPortPmvar2HisEntry OBJECT-TYPE
        SYNTAX EthPortPmvar2HisEntry
        MAX-ACCESS not-accessible
        STATUS current
        DESCRIPTION
            "ethPortPmvar2His."
        INDEX{ ethPortPmvar2HisEid,ethPortPmvar2HisParaLen,ethPortPmvar2HisPara,ethPortPmvar2HisStartTime,ethPortPmvar2HisEndTime }
        ::= { ethPortPmvar2HisTable 1 }

    EthPortPmvar2HisEntry ::=
        SEQUENCE {
            ethPortPmvar2HisEid
                DataPmEventType,
            ethPortPmvar2HisParaLen
                Unsigned32,
            ethPortPmvar2HisPara
                OCTET STRING,
            ethPortPmvar2HisMonValue
                Counter64,
            ethPortPmvar2HisStartTime
                DateAndTime,
            ethPortPmvar2HisEndTime
                DateAndTime,
            ethPortPmvar2HisVldty
                ValidflagType
        }

    -- 1.3.6.1.4.1.2011.2.25.3.70.20.102.140.1.1
    ethPortPmvar2HisEid OBJECT-TYPE
        SYNTAX DataPmEventType
        MAX-ACCESS read-only
        STATUS current
        DESCRIPTION
            "DataPmEid."
        ::= { ethPortPmvar2HisEntry 1 }

    -- 1.3.6.1.4.1.2011.2.25.3.70.20.102.140.1.2
    ethPortPmvar2HisParaLen OBJECT-TYPE
        SYNTAX Unsigned32
        MAX-ACCESS read-only
        STATUS current
        DESCRIPTION
            "ParaLen."
        ::= { ethPortPmvar2HisEntry 2 }

    -- 1.3.6.1.4.1.2011.2.25.3.70.20.102.140.1.3
    ethPortPmvar2HisPara OBJECT-TYPE
        SYNTAX OCTET STRING(SIZE (0..100))
        MAX-ACCESS read-only
        STATUS current
        DESCRIPTION
            "para"
        ::= { ethPortPmvar2HisEntry 3 }

    -- 1.3.6.1.4.1.2011.2.25.3.70.20.102.140.1.4
    ethPortPmvar2HisMonValue OBJECT-TYPE
        SYNTAX Counter64
        MAX-ACCESS read-only
        STATUS current
        DESCRIPTION
            "DataPmMonValue."
        ::= { ethPortPmvar2HisEntry 4 }

    -- 1.3.6.1.4.1.2011.2.25.3.70.20.102.140.1.5
    ethPortPmvar2HisStartTime OBJECT-TYPE
        SYNTAX DateAndTime
        MAX-ACCESS read-only
        STATUS current
        DESCRIPTION
            "Start Time."
        ::= { ethPortPmvar2HisEntry 5 }

    -- 1.3.6.1.4.1.2011.2.25.3.70.20.102.140.1.6
    ethPortPmvar2HisEndTime OBJECT-TYPE
        SYNTAX DateAndTime
        MAX-ACCESS read-only
        STATUS current
        DESCRIPTION
            "End Time."
        ::= { ethPortPmvar2HisEntry 6 }

    -- 1.3.6.1.4.1.2011.2.25.3.70.20.102.140.1.7
    ethPortPmvar2HisVldty OBJECT-TYPE
        SYNTAX ValidflagType
        MAX-ACCESS read-only
        STATUS current
        DESCRIPTION
            "Validity."
        ::= { ethPortPmvar2HisEntry 7 }

    -- 1.3.6.1.4.1.2011.2.25.3.70.20.104
    atmport OBJECT IDENTIFIER ::= { rtnData 104 }

    -- 1.3.6.1.4.1.2011.2.25.3.70.20.104.100
    atmportPmCurTable OBJECT-TYPE
        SYNTAX SEQUENCE OF AtmportPmCurEntry
        MAX-ACCESS not-accessible
        STATUS current
        DESCRIPTION
            "atmportDataPm30sCur."
        ::= { atmport 100 }

    -- 1.3.6.1.4.1.2011.2.25.3.70.20.104.100.1
    atmportPmCurEntry OBJECT-TYPE
        SYNTAX AtmportPmCurEntry
        MAX-ACCESS not-accessible
        STATUS current
        DESCRIPTION
            "atmportPmCur."
        INDEX{ atmportPmCurEid,atmportPmCurParaLen,atmportPmCurPara }
        ::= { atmportPmCurTable 1 }

    AtmportPmCurEntry ::=
        SEQUENCE {
            atmportPmCurEid
                DataPmEventType,
            atmportPmCurParaLen
                Unsigned32,
            atmportPmCurPara
                OCTET STRING,
            atmportPmCurMonValue
                Counter64,
            atmportPmCurDatetime
                DateAndTime
        }

    -- 1.3.6.1.4.1.2011.2.25.3.70.20.104.100.1.1
    atmportPmCurEid OBJECT-TYPE
        SYNTAX DataPmEventType
        MAX-ACCESS read-only
        STATUS current
        DESCRIPTION
            "DataPmEid."
        ::= { atmportPmCurEntry 1 }

    -- 1.3.6.1.4.1.2011.2.25.3.70.20.104.100.1.2
    atmportPmCurParaLen OBJECT-TYPE
        SYNTAX Unsigned32
        MAX-ACCESS read-only
        STATUS current
        DESCRIPTION
            "ParaLen."
        ::= { atmportPmCurEntry 2 }

    -- 1.3.6.1.4.1.2011.2.25.3.70.20.104.100.1.3
    atmportPmCurPara OBJECT-TYPE
        SYNTAX OCTET STRING
        MAX-ACCESS read-only
        STATUS current
        DESCRIPTION
            "para"
        ::= { atmportPmCurEntry 3 }

    -- 1.3.6.1.4.1.2011.2.25.3.70.20.104.100.1.4
    atmportPmCurMonValue OBJECT-TYPE
        SYNTAX Counter64
        MAX-ACCESS read-only
        STATUS current
        DESCRIPTION
            "DataPmMonValue."
        ::= { atmportPmCurEntry 4 }

    -- 1.3.6.1.4.1.2011.2.25.3.70.20.104.100.1.5
    atmportPmCurDatetime OBJECT-TYPE
        SYNTAX DateAndTime
        MAX-ACCESS read-only
        STATUS current
        DESCRIPTION
            "Start Time."
        ::= { atmportPmCurEntry 5 }

    -- 1.3.6.1.4.1.2011.2.25.3.70.20.104.110
    atmportPm30sHisTable OBJECT-TYPE
        SYNTAX SEQUENCE OF AtmportPm30sHisEntry
        MAX-ACCESS not-accessible
        STATUS current
        DESCRIPTION
            "atmportDataPm30sHis."
        ::= { atmport 110 }

    -- 1.3.6.1.4.1.2011.2.25.3.70.20.104.110.1
    atmportPm30sHisEntry OBJECT-TYPE
        SYNTAX AtmportPm30sHisEntry
        MAX-ACCESS not-accessible
        STATUS current
        DESCRIPTION
            "atmportDataPm30sHis."
        INDEX{ atmportPm30sHisEid,atmportPm30sHisParaLen,atmportPm30sHisPara,atmportPm30sHisStartTime,atmportPm30sHisEndTime }
        ::= { atmportPm30sHisTable 1 }

    AtmportPm30sHisEntry ::=
        SEQUENCE {
            atmportPm30sHisEid
                DataPmEventType,
            atmportPm30sHisParaLen
                Unsigned32,
            atmportPm30sHisPara
                OCTET STRING,
            atmportPm30sHisMonValue
                Counter64,
            atmportPm30sHisStartTime
                DateAndTime,
            atmportPm30sHisEndTime
                DateAndTime,
            atmportPm30sHisVldty
                ValidflagType
        }

    -- 1.3.6.1.4.1.2011.2.25.3.70.20.104.110.1.1
    atmportPm30sHisEid OBJECT-TYPE
        SYNTAX DataPmEventType
        MAX-ACCESS read-only
        STATUS current
        DESCRIPTION
            "DataPmEid."
        ::= { atmportPm30sHisEntry 1 }

    -- 1.3.6.1.4.1.2011.2.25.3.70.20.104.110.1.2
    atmportPm30sHisParaLen OBJECT-TYPE
        SYNTAX Unsigned32
        MAX-ACCESS read-only
        STATUS current
        DESCRIPTION
            "ParaLen."
        ::= { atmportPm30sHisEntry 2 }

    -- 1.3.6.1.4.1.2011.2.25.3.70.20.104.110.1.3
    atmportPm30sHisPara OBJECT-TYPE
        SYNTAX OCTET STRING(SIZE (0..100))
        MAX-ACCESS read-only
        STATUS current
        DESCRIPTION
            "para"
        ::= { atmportPm30sHisEntry 3 }

    -- 1.3.6.1.4.1.2011.2.25.3.70.20.104.110.1.4
    atmportPm30sHisMonValue OBJECT-TYPE
        SYNTAX Counter64
        MAX-ACCESS read-only
        STATUS current
        DESCRIPTION
            "DataPmMonValue."
        ::= { atmportPm30sHisEntry 4 }

    -- 1.3.6.1.4.1.2011.2.25.3.70.20.104.110.1.5
    atmportPm30sHisStartTime OBJECT-TYPE
        SYNTAX DateAndTime
        MAX-ACCESS read-only
        STATUS current
        DESCRIPTION
            "Start Time."
        ::= { atmportPm30sHisEntry 5 }

    -- 1.3.6.1.4.1.2011.2.25.3.70.20.104.110.1.6
    atmportPm30sHisEndTime OBJECT-TYPE
        SYNTAX DateAndTime
        MAX-ACCESS read-only
        STATUS current
        DESCRIPTION
            "End Time."
        ::= { atmportPm30sHisEntry 6 }

    -- 1.3.6.1.4.1.2011.2.25.3.70.20.104.110.1.7
    atmportPm30sHisVldty OBJECT-TYPE
        SYNTAX ValidflagType
        MAX-ACCESS read-only
        STATUS current
        DESCRIPTION
            "Validity."
        ::= { atmportPm30sHisEntry 7 }

    -- 1.3.6.1.4.1.2011.2.25.3.70.20.104.120
    atmportPm30mHisTable OBJECT-TYPE
        SYNTAX SEQUENCE OF AtmportPm30mHisEntry
        MAX-ACCESS not-accessible
        STATUS current
        DESCRIPTION
            "atmportPm30mHis."
        ::= { atmport 120 }

    -- 1.3.6.1.4.1.2011.2.25.3.70.20.104.120.1
    atmportPm30mHisEntry OBJECT-TYPE
        SYNTAX AtmportPm30mHisEntry
        MAX-ACCESS not-accessible
        STATUS current
        DESCRIPTION
            "atmportPm30mHis."
        INDEX{ atmportPm30mHisEid,atmportPm30mHisParaLen,atmportPm30mHisPara,atmportPm30mHisStartTime,atmportPm30mHisEndTime }
        ::= { atmportPm30mHisTable 1 }

    AtmportPm30mHisEntry ::=
        SEQUENCE {
            atmportPm30mHisEid
                DataPmEventType,
            atmportPm30mHisParaLen
                Unsigned32,
            atmportPm30mHisPara
                OCTET STRING,
            atmportPm30mHisMonValue
                Counter64,
            atmportPm30mHisStartTime
                DateAndTime,
            atmportPm30mHisEndTime
                DateAndTime,
            atmportPm30mHisVldty
                ValidflagType
        }

    -- 1.3.6.1.4.1.2011.2.25.3.70.20.104.120.1.1
    atmportPm30mHisEid OBJECT-TYPE
        SYNTAX DataPmEventType
        MAX-ACCESS read-only
        STATUS current
        DESCRIPTION
            "DataPmEid."
        ::= { atmportPm30mHisEntry 1 }

    -- 1.3.6.1.4.1.2011.2.25.3.70.20.104.120.1.2
    atmportPm30mHisParaLen OBJECT-TYPE
        SYNTAX Unsigned32
        MAX-ACCESS read-only
        STATUS current
        DESCRIPTION
            "ParaLen."
        ::= { atmportPm30mHisEntry 2 }

    -- 1.3.6.1.4.1.2011.2.25.3.70.20.104.120.1.3
    atmportPm30mHisPara OBJECT-TYPE
        SYNTAX OCTET STRING(SIZE (0..100))
        MAX-ACCESS read-only
        STATUS current
        DESCRIPTION
            "para"
        ::= { atmportPm30mHisEntry 3 }

    -- 1.3.6.1.4.1.2011.2.25.3.70.20.104.120.1.4
    atmportPm30mHisMonValue OBJECT-TYPE
        SYNTAX Counter64
        MAX-ACCESS read-only
        STATUS current
        DESCRIPTION
            "DataPmMonValue."
        ::= { atmportPm30mHisEntry 4 }

    -- 1.3.6.1.4.1.2011.2.25.3.70.20.104.120.1.5
    atmportPm30mHisStartTime OBJECT-TYPE
        SYNTAX DateAndTime
        MAX-ACCESS read-only
        STATUS current
        DESCRIPTION
            "Start Time."
        ::= { atmportPm30mHisEntry 5 }

    -- 1.3.6.1.4.1.2011.2.25.3.70.20.104.120.1.6
    atmportPm30mHisEndTime OBJECT-TYPE
        SYNTAX DateAndTime
        MAX-ACCESS read-only
        STATUS current
        DESCRIPTION
            "End Time."
        ::= { atmportPm30mHisEntry 6 }

    -- 1.3.6.1.4.1.2011.2.25.3.70.20.104.120.1.7
    atmportPm30mHisVldty OBJECT-TYPE
        SYNTAX ValidflagType
        MAX-ACCESS read-only
        STATUS current
        DESCRIPTION
            "Validity."
        ::= { atmportPm30mHisEntry 7 }

    -- 1.3.6.1.4.1.2011.2.25.3.70.20.104.130
    atmportPmvar1HisTable OBJECT-TYPE
        SYNTAX SEQUENCE OF AtmportPmvar1HisEntry
        MAX-ACCESS not-accessible
        STATUS current
        DESCRIPTION
            "atmportPmvar1His."
        ::= { atmport 130 }

    -- 1.3.6.1.4.1.2011.2.25.3.70.20.104.130.1
    atmportPmvar1HisEntry OBJECT-TYPE
        SYNTAX AtmportPmvar1HisEntry
        MAX-ACCESS not-accessible
        STATUS current
        DESCRIPTION
            "atmportPmvar1His."
        INDEX{ atmportPmvar1HisEid,atmportPmvar1HisParaLen,atmportPmvar1HisPara,atmportPmvar1HisStartTime,atmportPmvar1HisEndTime }
        ::= { atmportPmvar1HisTable 1 }

    AtmportPmvar1HisEntry ::=
        SEQUENCE {
            atmportPmvar1HisEid
                DataPmEventType,
            atmportPmvar1HisParaLen
                Unsigned32,
            atmportPmvar1HisPara
                OCTET STRING,
            atmportPmvar1HisMonValue
                Counter64,
            atmportPmvar1HisStartTime
                DateAndTime,
            atmportPmvar1HisEndTime
                DateAndTime,
            atmportPmvar1HisVldty
                ValidflagType
        }

    -- 1.3.6.1.4.1.2011.2.25.3.70.20.104.130.1.1
    atmportPmvar1HisEid OBJECT-TYPE
        SYNTAX DataPmEventType
        MAX-ACCESS read-only
        STATUS current
        DESCRIPTION
            "DataPmEid."
        ::= { atmportPmvar1HisEntry 1 }

    -- 1.3.6.1.4.1.2011.2.25.3.70.20.104.130.1.2
    atmportPmvar1HisParaLen OBJECT-TYPE
        SYNTAX Unsigned32
        MAX-ACCESS read-only
        STATUS current
        DESCRIPTION
            "ParaLen."
        ::= { atmportPmvar1HisEntry 2 }

    -- 1.3.6.1.4.1.2011.2.25.3.70.20.104.130.1.3
    atmportPmvar1HisPara OBJECT-TYPE
        SYNTAX OCTET STRING (SIZE (0..100))
        MAX-ACCESS read-only
        STATUS current
        DESCRIPTION
            "para"
        ::= { atmportPmvar1HisEntry 3 }

    -- 1.3.6.1.4.1.2011.2.25.3.70.20.104.130.1.4
    atmportPmvar1HisMonValue OBJECT-TYPE
        SYNTAX Counter64
        MAX-ACCESS read-only
        STATUS current
        DESCRIPTION
            "DataPmMonValue."
        ::= { atmportPmvar1HisEntry 4 }

    -- 1.3.6.1.4.1.2011.2.25.3.70.20.104.130.1.5
    atmportPmvar1HisStartTime OBJECT-TYPE
        SYNTAX DateAndTime
        MAX-ACCESS read-only
        STATUS current
        DESCRIPTION
            "Start Time."
        ::= { atmportPmvar1HisEntry 5 }

    -- 1.3.6.1.4.1.2011.2.25.3.70.20.104.130.1.6
    atmportPmvar1HisEndTime OBJECT-TYPE
        SYNTAX DateAndTime
        MAX-ACCESS read-only
        STATUS current
        DESCRIPTION
            "End Time."
        ::= { atmportPmvar1HisEntry 6 }

    -- 1.3.6.1.4.1.2011.2.25.3.70.20.104.130.1.7
    atmportPmvar1HisVldty OBJECT-TYPE
        SYNTAX ValidflagType
        MAX-ACCESS read-only
        STATUS current
        DESCRIPTION
            "Validity."
        ::= { atmportPmvar1HisEntry 7 }

    -- 1.3.6.1.4.1.2011.2.25.3.70.20.104.140
    atmportPmvar2HisTable OBJECT-TYPE
        SYNTAX SEQUENCE OF AtmportPmvar2HisEntry
        MAX-ACCESS not-accessible
        STATUS current
        DESCRIPTION
            "atmportPmvar2His."
        ::= { atmport 140 }

    -- 1.3.6.1.4.1.2011.2.25.3.70.20.104.140.1
    atmportPmvar2HisEntry OBJECT-TYPE
        SYNTAX AtmportPmvar2HisEntry
        MAX-ACCESS not-accessible
        STATUS current
        DESCRIPTION
            "atmportPmvar2His."
        INDEX{ atmportPmvar2HisEid,atmportPmvar2HisParaLen,atmportPmvar2HisPara,atmportPmvar2HisStartTime,atmportPmvar2HisEndTime }
        ::= { atmportPmvar2HisTable 1 }

    AtmportPmvar2HisEntry ::=
        SEQUENCE {
            atmportPmvar2HisEid
                DataPmEventType,
            atmportPmvar2HisParaLen
                Unsigned32,
            atmportPmvar2HisPara
                OCTET STRING,
            atmportPmvar2HisMonValue
                Counter64,
            atmportPmvar2HisStartTime
                DateAndTime,
            atmportPmvar2HisEndTime
                DateAndTime,
            atmportPmvar2HisVldty
                ValidflagType
        }

    -- 1.3.6.1.4.1.2011.2.25.3.70.20.104.140.1.1
    atmportPmvar2HisEid OBJECT-TYPE
        SYNTAX DataPmEventType
        MAX-ACCESS read-only
        STATUS current
        DESCRIPTION
            "DataPmEid."
        ::= { atmportPmvar2HisEntry 1 }

    -- 1.3.6.1.4.1.2011.2.25.3.70.20.104.140.1.2
    atmportPmvar2HisParaLen OBJECT-TYPE
        SYNTAX Unsigned32
        MAX-ACCESS read-only
        STATUS current
        DESCRIPTION
            "ParaLen."
        ::= { atmportPmvar2HisEntry 2 }

    -- 1.3.6.1.4.1.2011.2.25.3.70.20.104.140.1.3
    atmportPmvar2HisPara OBJECT-TYPE
        SYNTAX OCTET STRING(SIZE (0..100))
        MAX-ACCESS read-only
        STATUS current
        DESCRIPTION
            "para"
        ::= { atmportPmvar2HisEntry 3 }

    -- 1.3.6.1.4.1.2011.2.25.3.70.20.104.140.1.4
    atmportPmvar2HisMonValue OBJECT-TYPE
        SYNTAX Counter64
        MAX-ACCESS read-only
        STATUS current
        DESCRIPTION
            "DataPmMonValue."
        ::= { atmportPmvar2HisEntry 4 }

    -- 1.3.6.1.4.1.2011.2.25.3.70.20.104.140.1.5
    atmportPmvar2HisStartTime OBJECT-TYPE
        SYNTAX DateAndTime
        MAX-ACCESS read-only
        STATUS current
        DESCRIPTION
            "Start Time."
        ::= { atmportPmvar2HisEntry 5 }

    -- 1.3.6.1.4.1.2011.2.25.3.70.20.104.140.1.6
    atmportPmvar2HisEndTime OBJECT-TYPE
        SYNTAX DateAndTime
        MAX-ACCESS read-only
        STATUS current
        DESCRIPTION
            "End Time."
        ::= { atmportPmvar2HisEntry 6 }

    -- 1.3.6.1.4.1.2011.2.25.3.70.20.104.140.1.7
    atmportPmvar2HisVldty OBJECT-TYPE
        SYNTAX ValidflagType
        MAX-ACCESS read-only
        STATUS current
        DESCRIPTION
            "Validity."
        ::= { atmportPmvar2HisEntry 7 }

    -- 1.3.6.1.4.1.2011.2.25.3.70.20.105
    atmtrunk OBJECT IDENTIFIER ::= { rtnData 105 }

    -- 1.3.6.1.4.1.2011.2.25.3.70.20.105.100
    atmtrunkPmCurTable OBJECT-TYPE
        SYNTAX SEQUENCE OF AtmtrunkPmCurEntry
        MAX-ACCESS not-accessible
        STATUS current
        DESCRIPTION
            "atmtrunkDataPm30sCur."
        ::= { atmtrunk 100 }

    -- 1.3.6.1.4.1.2011.2.25.3.70.20.105.100.1
    atmtrunkPmCurEntry OBJECT-TYPE
        SYNTAX AtmtrunkPmCurEntry
        MAX-ACCESS not-accessible
        STATUS current
        DESCRIPTION
            "atmtrunkPmCur."
        INDEX{ atmtrunkPmCurEid,atmtrunkPmCurParaLen, atmtrunkPmCurPara }
        ::= { atmtrunkPmCurTable 1 }

    AtmtrunkPmCurEntry ::=
        SEQUENCE {
            atmtrunkPmCurEid
                DataPmEventType,
            atmtrunkPmCurParaLen
                Unsigned32,
            atmtrunkPmCurPara
                OCTET STRING,
            atmtrunkPmCurMonValue
                Counter64,
            atmtrunkPmCurDatetime
                DateAndTime
        }

    -- 1.3.6.1.4.1.2011.2.25.3.70.20.105.100.1.1
    atmtrunkPmCurEid OBJECT-TYPE
        SYNTAX DataPmEventType
        MAX-ACCESS read-only
        STATUS current
        DESCRIPTION
            "DataPmEid."
        ::= { atmtrunkPmCurEntry 1 }

    -- 1.3.6.1.4.1.2011.2.25.3.70.20.105.100.1.2
    atmtrunkPmCurParaLen OBJECT-TYPE
        SYNTAX Unsigned32
        MAX-ACCESS read-only
        STATUS current
        DESCRIPTION
            "ParaLen."
        ::= { atmtrunkPmCurEntry 2 }

    -- 1.3.6.1.4.1.2011.2.25.3.70.20.105.100.1.3
    atmtrunkPmCurPara OBJECT-TYPE
        SYNTAX OCTET STRING
        MAX-ACCESS read-only
        STATUS current
        DESCRIPTION
            "para"
        ::= { atmtrunkPmCurEntry 3 }

    -- 1.3.6.1.4.1.2011.2.25.3.70.20.105.100.1.4
    atmtrunkPmCurMonValue OBJECT-TYPE
        SYNTAX Counter64
        MAX-ACCESS read-only
        STATUS current
        DESCRIPTION
            "DataPmMonValue."
        ::= { atmtrunkPmCurEntry 4 }

    -- 1.3.6.1.4.1.2011.2.25.3.70.20.105.100.1.5
    atmtrunkPmCurDatetime OBJECT-TYPE
        SYNTAX DateAndTime
        MAX-ACCESS read-only
        STATUS current
        DESCRIPTION
            "Start Time."
        ::= { atmtrunkPmCurEntry 5 }

    -- 1.3.6.1.4.1.2011.2.25.3.70.20.105.110
    atmtrunkPm30sHisTable OBJECT-TYPE
        SYNTAX SEQUENCE OF AtmtrunkPm30sHisEntry
        MAX-ACCESS not-accessible
        STATUS current
        DESCRIPTION
            "atmtrunkDataPm30sHis."
        ::= { atmtrunk 110 }

    -- 1.3.6.1.4.1.2011.2.25.3.70.20.105.110.1
    atmtrunkPm30sHisEntry OBJECT-TYPE
        SYNTAX AtmtrunkPm30sHisEntry
        MAX-ACCESS not-accessible
        STATUS current
        DESCRIPTION
            "atmtrunkDataPm30sHis."
        INDEX{ atmtrunkPm30sHisEid,atmtrunkPm30sHisParaLen,atmtrunkPm30sHisPara,atmtrunkPm30sHisStartTime,atmtrunkPm30sHisEndTime }
        ::= { atmtrunkPm30sHisTable 1 }

    AtmtrunkPm30sHisEntry ::=
        SEQUENCE {
            atmtrunkPm30sHisEid
                DataPmEventType,
            atmtrunkPm30sHisParaLen
                Unsigned32,
            atmtrunkPm30sHisPara
                OCTET STRING,
            atmtrunkPm30sHisMonValue
                Counter64,
            atmtrunkPm30sHisStartTime
                DateAndTime,
            atmtrunkPm30sHisEndTime
                DateAndTime,
            atmtrunkPm30sHisVldty
                ValidflagType
        }

    -- 1.3.6.1.4.1.2011.2.25.3.70.20.105.110.1.1
    atmtrunkPm30sHisEid OBJECT-TYPE
        SYNTAX DataPmEventType
        MAX-ACCESS read-only
        STATUS current
        DESCRIPTION
            "DataPmEid."
        ::= { atmtrunkPm30sHisEntry 1 }

    -- 1.3.6.1.4.1.2011.2.25.3.70.20.105.110.1.2
    atmtrunkPm30sHisParaLen OBJECT-TYPE
        SYNTAX Unsigned32
        MAX-ACCESS read-only
        STATUS current
        DESCRIPTION
            "ParaLen."
        ::= { atmtrunkPm30sHisEntry 2 }

    -- 1.3.6.1.4.1.2011.2.25.3.70.20.105.110.1.3
    atmtrunkPm30sHisPara OBJECT-TYPE
        SYNTAX OCTET STRING(SIZE (0..100))
        MAX-ACCESS read-only
        STATUS current
        DESCRIPTION
            "para"
        ::= { atmtrunkPm30sHisEntry 3 }

    -- 1.3.6.1.4.1.2011.2.25.3.70.20.105.110.1.4
    atmtrunkPm30sHisMonValue OBJECT-TYPE
        SYNTAX Counter64
        MAX-ACCESS read-only
        STATUS current
        DESCRIPTION
            "DataPmMonValue."
        ::= { atmtrunkPm30sHisEntry 4 }

    -- 1.3.6.1.4.1.2011.2.25.3.70.20.105.110.1.5
    atmtrunkPm30sHisStartTime OBJECT-TYPE
        SYNTAX DateAndTime
        MAX-ACCESS read-only
        STATUS current
        DESCRIPTION
            "Start Time."
        ::= { atmtrunkPm30sHisEntry 5 }

    -- 1.3.6.1.4.1.2011.2.25.3.70.20.105.110.1.6
    atmtrunkPm30sHisEndTime OBJECT-TYPE
        SYNTAX DateAndTime
        MAX-ACCESS read-only
        STATUS current
        DESCRIPTION
            "End Time."
        ::= { atmtrunkPm30sHisEntry 6 }

    -- 1.3.6.1.4.1.2011.2.25.3.70.20.105.110.1.7
    atmtrunkPm30sHisVldty OBJECT-TYPE
        SYNTAX ValidflagType
        MAX-ACCESS read-only
        STATUS current
        DESCRIPTION
            "Validity."
        ::= { atmtrunkPm30sHisEntry 7 }

    -- 1.3.6.1.4.1.2011.2.25.3.70.20.105.120
    atmtrunkPm30mHisTable OBJECT-TYPE
        SYNTAX SEQUENCE OF AtmtrunkPm30mHisEntry
        MAX-ACCESS not-accessible
        STATUS current
        DESCRIPTION
            "atmtrunkPm30mHis."
        ::= { atmtrunk 120 }

    -- 1.3.6.1.4.1.2011.2.25.3.70.20.105.120.1
    atmtrunkPm30mHisEntry OBJECT-TYPE
        SYNTAX AtmtrunkPm30mHisEntry
        MAX-ACCESS not-accessible
        STATUS current
        DESCRIPTION
            "atmtrunkPm30mHis."
        INDEX{ atmtrunkPm30mHisEid,atmtrunkPm30mHisParaLen,atmtrunkPm30mHisPara,atmtrunkPm30mHisStartTime,atmtrunkPm30mHisEndTime }
        ::= { atmtrunkPm30mHisTable 1 }

    AtmtrunkPm30mHisEntry ::=
        SEQUENCE {
            atmtrunkPm30mHisEid
                DataPmEventType,
            atmtrunkPm30mHisParaLen
                Unsigned32,
            atmtrunkPm30mHisPara
                OCTET STRING,
            atmtrunkPm30mHisMonValue
                Counter64,
            atmtrunkPm30mHisStartTime
                DateAndTime,
            atmtrunkPm30mHisEndTime
                DateAndTime,
            atmtrunkPm30mHisVldty
                ValidflagType
        }

    -- 1.3.6.1.4.1.2011.2.25.3.70.20.105.120.1.1
    atmtrunkPm30mHisEid OBJECT-TYPE
        SYNTAX DataPmEventType
        MAX-ACCESS read-only
        STATUS current
        DESCRIPTION
            "DataPmEid."
        ::= { atmtrunkPm30mHisEntry 1 }

    -- 1.3.6.1.4.1.2011.2.25.3.70.20.105.120.1.2
    atmtrunkPm30mHisParaLen OBJECT-TYPE
        SYNTAX Unsigned32
        MAX-ACCESS read-only
        STATUS current
        DESCRIPTION
            "ParaLen."
        ::= { atmtrunkPm30mHisEntry 2 }

    -- 1.3.6.1.4.1.2011.2.25.3.70.20.105.120.1.3
    atmtrunkPm30mHisPara OBJECT-TYPE
        SYNTAX OCTET STRING(SIZE (0..100))
        MAX-ACCESS read-only
        STATUS current
        DESCRIPTION
            "para"
        ::= { atmtrunkPm30mHisEntry 3 }

    -- 1.3.6.1.4.1.2011.2.25.3.70.20.105.120.1.4
    atmtrunkPm30mHisMonValue OBJECT-TYPE
        SYNTAX Counter64
        MAX-ACCESS read-only
        STATUS current
        DESCRIPTION
            "DataPmMonValue."
        ::= { atmtrunkPm30mHisEntry 4 }

    -- 1.3.6.1.4.1.2011.2.25.3.70.20.105.120.1.5
    atmtrunkPm30mHisStartTime OBJECT-TYPE
        SYNTAX DateAndTime
        MAX-ACCESS read-only
        STATUS current
        DESCRIPTION
            "Start Time."
        ::= { atmtrunkPm30mHisEntry 5 }

    -- 1.3.6.1.4.1.2011.2.25.3.70.20.105.120.1.6
    atmtrunkPm30mHisEndTime OBJECT-TYPE
        SYNTAX DateAndTime
        MAX-ACCESS read-only
        STATUS current
        DESCRIPTION
            "End Time."
        ::= { atmtrunkPm30mHisEntry 6 }

    -- 1.3.6.1.4.1.2011.2.25.3.70.20.105.120.1.7
    atmtrunkPm30mHisVldty OBJECT-TYPE
        SYNTAX ValidflagType
        MAX-ACCESS read-only
        STATUS current
        DESCRIPTION
            "Validity."
        ::= { atmtrunkPm30mHisEntry 7 }

    -- 1.3.6.1.4.1.2011.2.25.3.70.20.105.130
    atmtrunkPmvar1HisTable OBJECT-TYPE
        SYNTAX SEQUENCE OF AtmtrunkPmvar1HisEntry
        MAX-ACCESS not-accessible
        STATUS current
        DESCRIPTION
            "atmtrunkPmvar1His."
        ::= { atmtrunk 130 }

    -- 1.3.6.1.4.1.2011.2.25.3.70.20.105.130.1
    atmtrunkPmvar1HisEntry OBJECT-TYPE
        SYNTAX AtmtrunkPmvar1HisEntry
        MAX-ACCESS not-accessible
        STATUS current
        DESCRIPTION
            "atmtrunkPmvar1His."
        INDEX{ atmtrunkPmvar1HisEid,atmtrunkPmvar1HisParaLen,atmtrunkPmvar1HisPara,atmtrunkPmvar1HisStartTime,atmtrunkPmvar1HisEndTime }
        ::= { atmtrunkPmvar1HisTable 1 }

    AtmtrunkPmvar1HisEntry ::=
        SEQUENCE {
            atmtrunkPmvar1HisEid
                DataPmEventType,
            atmtrunkPmvar1HisParaLen
                Unsigned32,
            atmtrunkPmvar1HisPara
                OCTET STRING,
            atmtrunkPmvar1HisMonValue
                Counter64,
            atmtrunkPmvar1HisStartTime
                DateAndTime,
            atmtrunkPmvar1HisEndTime
                DateAndTime,
            atmtrunkPmvar1HisVldty
                ValidflagType
        }

    -- 1.3.6.1.4.1.2011.2.25.3.70.20.105.130.1.1
    atmtrunkPmvar1HisEid OBJECT-TYPE
        SYNTAX DataPmEventType
        MAX-ACCESS read-only
        STATUS current
        DESCRIPTION
            "DataPmEid."
        ::= { atmtrunkPmvar1HisEntry 1 }

    -- 1.3.6.1.4.1.2011.2.25.3.70.20.105.130.1.2
    atmtrunkPmvar1HisParaLen OBJECT-TYPE
        SYNTAX Unsigned32
        MAX-ACCESS read-only
        STATUS current
        DESCRIPTION
            "ParaLen."
        ::= { atmtrunkPmvar1HisEntry 2 }

    -- 1.3.6.1.4.1.2011.2.25.3.70.20.105.130.1.3
    atmtrunkPmvar1HisPara OBJECT-TYPE
        SYNTAX OCTET STRING (SIZE (0..100))
        MAX-ACCESS read-only
        STATUS current
        DESCRIPTION
            "para"
        ::= { atmtrunkPmvar1HisEntry 3 }

    -- 1.3.6.1.4.1.2011.2.25.3.70.20.105.130.1.4
    atmtrunkPmvar1HisMonValue OBJECT-TYPE
        SYNTAX Counter64
        MAX-ACCESS read-only
        STATUS current
        DESCRIPTION
            "DataPmMonValue."
        ::= { atmtrunkPmvar1HisEntry 4 }

    -- 1.3.6.1.4.1.2011.2.25.3.70.20.105.130.1.5
    atmtrunkPmvar1HisStartTime OBJECT-TYPE
        SYNTAX DateAndTime
        MAX-ACCESS read-only
        STATUS current
        DESCRIPTION
            "Start Time."
        ::= { atmtrunkPmvar1HisEntry 5 }

    -- 1.3.6.1.4.1.2011.2.25.3.70.20.105.130.1.6
    atmtrunkPmvar1HisEndTime OBJECT-TYPE
        SYNTAX DateAndTime
        MAX-ACCESS read-only
        STATUS current
        DESCRIPTION
            "End Time."
        ::= { atmtrunkPmvar1HisEntry 6 }

    -- 1.3.6.1.4.1.2011.2.25.3.70.20.105.130.1.7
    atmtrunkPmvar1HisVldty OBJECT-TYPE
        SYNTAX ValidflagType
        MAX-ACCESS read-only
        STATUS current
        DESCRIPTION
            "Validity."
        ::= { atmtrunkPmvar1HisEntry 7 }

    -- 1.3.6.1.4.1.2011.2.25.3.70.20.105.140
    atmtrunkPmvar2HisTable OBJECT-TYPE
        SYNTAX SEQUENCE OF AtmtrunkPmvar2HisEntry
        MAX-ACCESS not-accessible
        STATUS current
        DESCRIPTION
            "atmtrunkPmvar2His."
        ::= { atmtrunk 140 }

    -- 1.3.6.1.4.1.2011.2.25.3.70.20.105.140.1
    atmtrunkPmvar2HisEntry OBJECT-TYPE
        SYNTAX AtmtrunkPmvar2HisEntry
        MAX-ACCESS not-accessible
        STATUS current
        DESCRIPTION
            "atmtrunkPmvar2His."
        INDEX{ atmtrunkPmvar2HisEid,atmtrunkPmvar2HisParaLen,atmtrunkPmvar2HisPara,atmtrunkPmvar2HisStartTime,atmtrunkPmvar2HisEndTime }
        ::= { atmtrunkPmvar2HisTable 1 }

    AtmtrunkPmvar2HisEntry ::=
        SEQUENCE {
            atmtrunkPmvar2HisEid
                DataPmEventType,
            atmtrunkPmvar2HisParaLen
                Unsigned32,
            atmtrunkPmvar2HisPara
                OCTET STRING,
            atmtrunkPmvar2HisMonValue
                Counter64,
            atmtrunkPmvar2HisStartTime
                DateAndTime,
            atmtrunkPmvar2HisEndTime
                DateAndTime,
            atmtrunkPmvar2HisVldty
                ValidflagType
        }

    -- 1.3.6.1.4.1.2011.2.25.3.70.20.105.140.1.1
    atmtrunkPmvar2HisEid OBJECT-TYPE
        SYNTAX DataPmEventType
        MAX-ACCESS read-only
        STATUS current
        DESCRIPTION
            "DataPmEid."
        ::= { atmtrunkPmvar2HisEntry 1 }

    -- 1.3.6.1.4.1.2011.2.25.3.70.20.105.140.1.2
    atmtrunkPmvar2HisParaLen OBJECT-TYPE
        SYNTAX Unsigned32
        MAX-ACCESS read-only
        STATUS current
        DESCRIPTION
            "ParaLen."
        ::= { atmtrunkPmvar2HisEntry 2 }

    -- 1.3.6.1.4.1.2011.2.25.3.70.20.105.140.1.3
    atmtrunkPmvar2HisPara OBJECT-TYPE
        SYNTAX OCTET STRING(SIZE (0..100))
        MAX-ACCESS read-only
        STATUS current
        DESCRIPTION
            "para"
        ::= { atmtrunkPmvar2HisEntry 3 }

    -- 1.3.6.1.4.1.2011.2.25.3.70.20.105.140.1.4
    atmtrunkPmvar2HisMonValue OBJECT-TYPE
        SYNTAX Counter64
        MAX-ACCESS read-only
        STATUS current
        DESCRIPTION
            "DataPmMonValue."
        ::= { atmtrunkPmvar2HisEntry 4 }

    -- 1.3.6.1.4.1.2011.2.25.3.70.20.105.140.1.5
    atmtrunkPmvar2HisStartTime OBJECT-TYPE
        SYNTAX DateAndTime
        MAX-ACCESS read-only
        STATUS current
        DESCRIPTION
            "Start Time."
        ::= { atmtrunkPmvar2HisEntry 5 }

    -- 1.3.6.1.4.1.2011.2.25.3.70.20.105.140.1.6
    atmtrunkPmvar2HisEndTime OBJECT-TYPE
        SYNTAX DateAndTime
        MAX-ACCESS read-only
        STATUS current
        DESCRIPTION
            "End Time."
        ::= { atmtrunkPmvar2HisEntry 6 }

    -- 1.3.6.1.4.1.2011.2.25.3.70.20.105.140.1.7
    atmtrunkPmvar2HisVldty OBJECT-TYPE
        SYNTAX ValidflagType
        MAX-ACCESS read-only
        STATUS current
        DESCRIPTION
            "Validity."
        ::= { atmtrunkPmvar2HisEntry 7 }

    -- 1.3.6.1.4.1.2011.2.25.3.70.20.107
    newportpri OBJECT IDENTIFIER ::= { rtnData 107 }

    -- 1.3.6.1.4.1.2011.2.25.3.70.20.107.100
    newportpriPmCurTable OBJECT-TYPE
        SYNTAX SEQUENCE OF NewportpriPmCurEntry
        MAX-ACCESS not-accessible
        STATUS current
        DESCRIPTION
            "newportpriDataPm30sCur."
        ::= { newportpri 100 }

    -- 1.3.6.1.4.1.2011.2.25.3.70.20.107.100.1
    newportpriPmCurEntry OBJECT-TYPE
        SYNTAX NewportpriPmCurEntry
        MAX-ACCESS not-accessible
        STATUS current
        DESCRIPTION
            "newportpriPmCur."
        INDEX{ newportpriPmCurEid,newportpriPmCurParaLen, newportpriPmCurPara }
        ::= { newportpriPmCurTable 1 }

    NewportpriPmCurEntry ::=
        SEQUENCE {
            newportpriPmCurEid
                DataPmEventType,
            newportpriPmCurParaLen
                Unsigned32,
            newportpriPmCurPara
                OCTET STRING,
            newportpriPmCurMonValue
                Counter64,
            newportpriPmCurDatetime
                DateAndTime
        }

    -- 1.3.6.1.4.1.2011.2.25.3.70.20.107.100.1.1
    newportpriPmCurEid OBJECT-TYPE
        SYNTAX DataPmEventType
        MAX-ACCESS read-only
        STATUS current
        DESCRIPTION
            "DataPmEid."
        ::= { newportpriPmCurEntry 1 }

    -- 1.3.6.1.4.1.2011.2.25.3.70.20.107.100.1.2
    newportpriPmCurParaLen OBJECT-TYPE
        SYNTAX Unsigned32
        MAX-ACCESS read-only
        STATUS current
        DESCRIPTION
            "ParaLen."
        ::= { newportpriPmCurEntry 2 }

    -- 1.3.6.1.4.1.2011.2.25.3.70.20.107.100.1.3
    newportpriPmCurPara OBJECT-TYPE
        SYNTAX OCTET STRING
        MAX-ACCESS read-only
        STATUS current
        DESCRIPTION
            "para"
        ::= { newportpriPmCurEntry 3 }

    -- 1.3.6.1.4.1.2011.2.25.3.70.20.107.100.1.4
    newportpriPmCurMonValue OBJECT-TYPE
        SYNTAX Counter64
        MAX-ACCESS read-only
        STATUS current
        DESCRIPTION
            "DataPmMonValue."
        ::= { newportpriPmCurEntry 4 }

    -- 1.3.6.1.4.1.2011.2.25.3.70.20.107.100.1.5
    newportpriPmCurDatetime OBJECT-TYPE
        SYNTAX DateAndTime
        MAX-ACCESS read-only
        STATUS current
        DESCRIPTION
            "Start Time."
        ::= { newportpriPmCurEntry 5 }

    -- 1.3.6.1.4.1.2011.2.25.3.70.20.107.110
    newportpriPm30sHisTable OBJECT-TYPE
        SYNTAX SEQUENCE OF NewportpriPm30sHisEntry
        MAX-ACCESS not-accessible
        STATUS current
        DESCRIPTION
            "newportpriDataPm30sHis."
        ::= { newportpri 110 }

    -- 1.3.6.1.4.1.2011.2.25.3.70.20.107.110.1
    newportpriPm30sHisEntry OBJECT-TYPE
        SYNTAX NewportpriPm30sHisEntry
        MAX-ACCESS not-accessible
        STATUS current
        DESCRIPTION
            "newportpriDataPm30sHis."
        INDEX{ newportpriPm30sHisEid,newportpriPm30sHisParaLen,newportpriPm30sHisPara,newportpriPm30sHisStartTime,newportpriPm30sHisEndTime }
        ::= { newportpriPm30sHisTable 1 }

    NewportpriPm30sHisEntry ::=
        SEQUENCE {
            newportpriPm30sHisEid
                DataPmEventType,
            newportpriPm30sHisParaLen
                Unsigned32,
            newportpriPm30sHisPara
                OCTET STRING,
            newportpriPm30sHisMonValue
                Counter64,
            newportpriPm30sHisStartTime
                DateAndTime,
            newportpriPm30sHisEndTime
                DateAndTime,
            newportpriPm30sHisVldty
                ValidflagType
        }

    -- 1.3.6.1.4.1.2011.2.25.3.70.20.107.110.1.1
    newportpriPm30sHisEid OBJECT-TYPE
        SYNTAX DataPmEventType
        MAX-ACCESS read-only
        STATUS current
        DESCRIPTION
            "DataPmEid."
        ::= { newportpriPm30sHisEntry 1 }

    -- 1.3.6.1.4.1.2011.2.25.3.70.20.107.110.1.2
    newportpriPm30sHisParaLen OBJECT-TYPE
        SYNTAX Unsigned32
        MAX-ACCESS read-only
        STATUS current
        DESCRIPTION
            "ParaLen."
        ::= { newportpriPm30sHisEntry 2 }

    -- 1.3.6.1.4.1.2011.2.25.3.70.20.107.110.1.3
    newportpriPm30sHisPara OBJECT-TYPE
        SYNTAX OCTET STRING(SIZE (0..100))
        MAX-ACCESS read-only
        STATUS current
        DESCRIPTION
            "para"
        ::= { newportpriPm30sHisEntry 3 }

    -- 1.3.6.1.4.1.2011.2.25.3.70.20.107.110.1.4
    newportpriPm30sHisMonValue OBJECT-TYPE
        SYNTAX Counter64
        MAX-ACCESS read-only
        STATUS current
        DESCRIPTION
            "DataPmMonValue."
        ::= { newportpriPm30sHisEntry 4 }

    -- 1.3.6.1.4.1.2011.2.25.3.70.20.107.110.1.5
    newportpriPm30sHisStartTime OBJECT-TYPE
        SYNTAX DateAndTime
        MAX-ACCESS read-only
        STATUS current
        DESCRIPTION
            "Start Time."
        ::= { newportpriPm30sHisEntry 5 }

    -- 1.3.6.1.4.1.2011.2.25.3.70.20.107.110.1.6
    newportpriPm30sHisEndTime OBJECT-TYPE
        SYNTAX DateAndTime
        MAX-ACCESS read-only
        STATUS current
        DESCRIPTION
            "End Time."
        ::= { newportpriPm30sHisEntry 6 }

    -- 1.3.6.1.4.1.2011.2.25.3.70.20.107.110.1.7
    newportpriPm30sHisVldty OBJECT-TYPE
        SYNTAX ValidflagType
        MAX-ACCESS read-only
        STATUS current
        DESCRIPTION
            "Validity."
        ::= { newportpriPm30sHisEntry 7 }

    -- 1.3.6.1.4.1.2011.2.25.3.70.20.107.120
    newportpriPm30mHisTable OBJECT-TYPE
        SYNTAX SEQUENCE OF NewportpriPm30mHisEntry
        MAX-ACCESS not-accessible
        STATUS current
        DESCRIPTION
            "newportpriPm30mHis."
        ::= { newportpri 120 }

    -- 1.3.6.1.4.1.2011.2.25.3.70.20.107.120.1
    newportpriPm30mHisEntry OBJECT-TYPE
        SYNTAX NewportpriPm30mHisEntry
        MAX-ACCESS not-accessible
        STATUS current
        DESCRIPTION
            "newportpriPm30mHis."
        INDEX{ newportpriPm30mHisEid,newportpriPm30mHisParaLen,newportpriPm30mHisPara,newportpriPm30mHisStartTime,newportpriPm30mHisEndTime }
        ::= { newportpriPm30mHisTable 1 }

    NewportpriPm30mHisEntry ::=
        SEQUENCE {
            newportpriPm30mHisEid
                DataPmEventType,
            newportpriPm30mHisParaLen
                Unsigned32,
            newportpriPm30mHisPara
                OCTET STRING,
            newportpriPm30mHisMonValue
                Counter64,
            newportpriPm30mHisStartTime
                DateAndTime,
            newportpriPm30mHisEndTime
                DateAndTime,
            newportpriPm30mHisVldty
                ValidflagType
        }

    -- 1.3.6.1.4.1.2011.2.25.3.70.20.107.120.1.1
    newportpriPm30mHisEid OBJECT-TYPE
        SYNTAX DataPmEventType
        MAX-ACCESS read-only
        STATUS current
        DESCRIPTION
            "DataPmEid."
        ::= { newportpriPm30mHisEntry 1 }

    -- 1.3.6.1.4.1.2011.2.25.3.70.20.107.120.1.2
    newportpriPm30mHisParaLen OBJECT-TYPE
        SYNTAX Unsigned32
        MAX-ACCESS read-only
        STATUS current
        DESCRIPTION
            "ParaLen."
        ::= { newportpriPm30mHisEntry 2 }

    -- 1.3.6.1.4.1.2011.2.25.3.70.20.107.120.1.3
    newportpriPm30mHisPara OBJECT-TYPE
        SYNTAX OCTET STRING(SIZE (0..100))
        MAX-ACCESS read-only
        STATUS current
        DESCRIPTION
            "para"
        ::= { newportpriPm30mHisEntry 3 }

    -- 1.3.6.1.4.1.2011.2.25.3.70.20.107.120.1.4
    newportpriPm30mHisMonValue OBJECT-TYPE
        SYNTAX Counter64
        MAX-ACCESS read-only
        STATUS current
        DESCRIPTION
            "DataPmMonValue."
        ::= { newportpriPm30mHisEntry 4 }

    -- 1.3.6.1.4.1.2011.2.25.3.70.20.107.120.1.5
    newportpriPm30mHisStartTime OBJECT-TYPE
        SYNTAX DateAndTime
        MAX-ACCESS read-only
        STATUS current
        DESCRIPTION
            "Start Time."
        ::= { newportpriPm30mHisEntry 5 }

    -- 1.3.6.1.4.1.2011.2.25.3.70.20.107.120.1.6
    newportpriPm30mHisEndTime OBJECT-TYPE
        SYNTAX DateAndTime
        MAX-ACCESS read-only
        STATUS current
        DESCRIPTION
            "End Time."
        ::= { newportpriPm30mHisEntry 6 }

    -- 1.3.6.1.4.1.2011.2.25.3.70.20.107.120.1.7
    newportpriPm30mHisVldty OBJECT-TYPE
        SYNTAX ValidflagType
        MAX-ACCESS read-only
        STATUS current
        DESCRIPTION
            "Validity."
        ::= { newportpriPm30mHisEntry 7 }

    -- 1.3.6.1.4.1.2011.2.25.3.70.20.107.130
    newportpriPmvar1HisTable OBJECT-TYPE
        SYNTAX SEQUENCE OF NewportpriPmvar1HisEntry
        MAX-ACCESS not-accessible
        STATUS current
        DESCRIPTION
            "newportpriPmvar1His."
        ::= { newportpri 130 }

    -- 1.3.6.1.4.1.2011.2.25.3.70.20.107.130.1
    newportpriPmvar1HisEntry OBJECT-TYPE
        SYNTAX NewportpriPmvar1HisEntry
        MAX-ACCESS not-accessible
        STATUS current
        DESCRIPTION
            "newportpriPmvar1His."
        INDEX{ newportpriPmvar1HisEid,newportpriPmvar1HisParaLen,newportpriPmvar1HisPara,newportpriPmvar1HisStartTime,newportpriPmvar1HisEndTime }
        ::= { newportpriPmvar1HisTable 1 }

    NewportpriPmvar1HisEntry ::=
        SEQUENCE {
            newportpriPmvar1HisEid
                DataPmEventType,
            newportpriPmvar1HisParaLen
                Unsigned32,
            newportpriPmvar1HisPara
                OCTET STRING,
            newportpriPmvar1HisMonValue
                Counter64,
            newportpriPmvar1HisStartTime
                DateAndTime,
            newportpriPmvar1HisEndTime
                DateAndTime,
            newportpriPmvar1HisVldty
                ValidflagType
        }

    -- 1.3.6.1.4.1.2011.2.25.3.70.20.107.130.1.1
    newportpriPmvar1HisEid OBJECT-TYPE
        SYNTAX DataPmEventType
        MAX-ACCESS read-only
        STATUS current
        DESCRIPTION
            "DataPmEid."
        ::= { newportpriPmvar1HisEntry 1 }

    -- 1.3.6.1.4.1.2011.2.25.3.70.20.107.130.1.2
    newportpriPmvar1HisParaLen OBJECT-TYPE
        SYNTAX Unsigned32
        MAX-ACCESS read-only
        STATUS current
        DESCRIPTION
            "ParaLen."
        ::= { newportpriPmvar1HisEntry 2 }

    -- 1.3.6.1.4.1.2011.2.25.3.70.20.107.130.1.3
    newportpriPmvar1HisPara OBJECT-TYPE
        SYNTAX OCTET STRING (SIZE (0..100))
        MAX-ACCESS read-only
        STATUS current
        DESCRIPTION
            "para"
        ::= { newportpriPmvar1HisEntry 3 }

    -- 1.3.6.1.4.1.2011.2.25.3.70.20.107.130.1.4
    newportpriPmvar1HisMonValue OBJECT-TYPE
        SYNTAX Counter64
        MAX-ACCESS read-only
        STATUS current
        DESCRIPTION
            "DataPmMonValue."
        ::= { newportpriPmvar1HisEntry 4 }

    -- 1.3.6.1.4.1.2011.2.25.3.70.20.107.130.1.5
    newportpriPmvar1HisStartTime OBJECT-TYPE
        SYNTAX DateAndTime
        MAX-ACCESS read-only
        STATUS current
        DESCRIPTION
            "Start Time."
        ::= { newportpriPmvar1HisEntry 5 }

    -- 1.3.6.1.4.1.2011.2.25.3.70.20.107.130.1.6
    newportpriPmvar1HisEndTime OBJECT-TYPE
        SYNTAX DateAndTime
        MAX-ACCESS read-only
        STATUS current
        DESCRIPTION
            "End Time."
        ::= { newportpriPmvar1HisEntry 6 }

    -- 1.3.6.1.4.1.2011.2.25.3.70.20.107.130.1.7
    newportpriPmvar1HisVldty OBJECT-TYPE
        SYNTAX ValidflagType
        MAX-ACCESS read-only
        STATUS current
        DESCRIPTION
            "Validity."
        ::= { newportpriPmvar1HisEntry 7 }

    -- 1.3.6.1.4.1.2011.2.25.3.70.20.107.140
    newportpriPmvar2HisTable OBJECT-TYPE
        SYNTAX SEQUENCE OF NewportpriPmvar2HisEntry
        MAX-ACCESS not-accessible
        STATUS current
        DESCRIPTION
            "newportpriPmvar2His."
        ::= { newportpri 140 }

    -- 1.3.6.1.4.1.2011.2.25.3.70.20.107.140.1
    newportpriPmvar2HisEntry OBJECT-TYPE
        SYNTAX NewportpriPmvar2HisEntry
        MAX-ACCESS not-accessible
        STATUS current
        DESCRIPTION
            "newportpriPmvar2His."
        INDEX{ newportpriPmvar2HisEid,newportpriPmvar2HisParaLen,newportpriPmvar2HisPara,newportpriPmvar2HisStartTime,newportpriPmvar2HisEndTime }
        ::= { newportpriPmvar2HisTable 1 }

    NewportpriPmvar2HisEntry ::=
        SEQUENCE {
            newportpriPmvar2HisEid
                DataPmEventType,
            newportpriPmvar2HisParaLen
                Unsigned32,
            newportpriPmvar2HisPara
                OCTET STRING,
            newportpriPmvar2HisMonValue
                Counter64,
            newportpriPmvar2HisStartTime
                DateAndTime,
            newportpriPmvar2HisEndTime
                DateAndTime,
            newportpriPmvar2HisVldty
                ValidflagType
        }

    -- 1.3.6.1.4.1.2011.2.25.3.70.20.107.140.1.1
    newportpriPmvar2HisEid OBJECT-TYPE
        SYNTAX DataPmEventType
        MAX-ACCESS read-only
        STATUS current
        DESCRIPTION
            "DataPmEid."
        ::= { newportpriPmvar2HisEntry 1 }

    -- 1.3.6.1.4.1.2011.2.25.3.70.20.107.140.1.2
    newportpriPmvar2HisParaLen OBJECT-TYPE
        SYNTAX Unsigned32
        MAX-ACCESS read-only
        STATUS current
        DESCRIPTION
            "ParaLen."
        ::= { newportpriPmvar2HisEntry 2 }

    -- 1.3.6.1.4.1.2011.2.25.3.70.20.107.140.1.3
    newportpriPmvar2HisPara OBJECT-TYPE
        SYNTAX OCTET STRING(SIZE (0..100))
        MAX-ACCESS read-only
        STATUS current
        DESCRIPTION
            "para"
        ::= { newportpriPmvar2HisEntry 3 }

    -- 1.3.6.1.4.1.2011.2.25.3.70.20.107.140.1.4
    newportpriPmvar2HisMonValue OBJECT-TYPE
        SYNTAX Counter64
        MAX-ACCESS read-only
        STATUS current
        DESCRIPTION
            "DataPmMonValue."
        ::= { newportpriPmvar2HisEntry 4 }

    -- 1.3.6.1.4.1.2011.2.25.3.70.20.107.140.1.5
    newportpriPmvar2HisStartTime OBJECT-TYPE
        SYNTAX DateAndTime
        MAX-ACCESS read-only
        STATUS current
        DESCRIPTION
            "Start Time."
        ::= { newportpriPmvar2HisEntry 5 }

    -- 1.3.6.1.4.1.2011.2.25.3.70.20.107.140.1.6
    newportpriPmvar2HisEndTime OBJECT-TYPE
        SYNTAX DateAndTime
        MAX-ACCESS read-only
        STATUS current
        DESCRIPTION
            "End Time."
        ::= { newportpriPmvar2HisEntry 6 }

    -- 1.3.6.1.4.1.2011.2.25.3.70.20.107.140.1.7
    newportpriPmvar2HisVldty OBJECT-TYPE
        SYNTAX ValidflagType
        MAX-ACCESS read-only
        STATUS current
        DESCRIPTION
            "Validity."
        ::= { newportpriPmvar2HisEntry 7 }

    -- 1.3.6.1.4.1.2011.2.25.3.70.20.108
    newe1port OBJECT IDENTIFIER ::= { rtnData 108 }

    -- 1.3.6.1.4.1.2011.2.25.3.70.20.108.100
    newe1portPmCurTable OBJECT-TYPE
        SYNTAX SEQUENCE OF Newe1portPmCurEntry
        MAX-ACCESS not-accessible
        STATUS current
        DESCRIPTION
            "newe1portDataPm30sCur."
        ::= { newe1port 100 }

    -- 1.3.6.1.4.1.2011.2.25.3.70.20.108.100.1
    newe1portPmCurEntry OBJECT-TYPE
        SYNTAX Newe1portPmCurEntry
        MAX-ACCESS not-accessible
        STATUS current
        DESCRIPTION
            "newe1portPmCur."
        INDEX{ newe1portPmCurEid,newe1portPmCurParaLen,newe1portPmCurPara }
        ::= { newe1portPmCurTable 1 }

    Newe1portPmCurEntry ::=
        SEQUENCE {
            newe1portPmCurEid
                DataPmEventType,
            newe1portPmCurParaLen
                Unsigned32,
            newe1portPmCurPara
                OCTET STRING,
            newe1portPmCurMonValue
                Counter64,
            newe1portPmCurDatetime
                DateAndTime
        }

    -- 1.3.6.1.4.1.2011.2.25.3.70.20.108.100.1.1
    newe1portPmCurEid OBJECT-TYPE
        SYNTAX DataPmEventType
        MAX-ACCESS read-only
        STATUS current
        DESCRIPTION
            "DataPmEid."
        ::= { newe1portPmCurEntry 1 }

    -- 1.3.6.1.4.1.2011.2.25.3.70.20.108.100.1.2
    newe1portPmCurParaLen OBJECT-TYPE
        SYNTAX Unsigned32
        MAX-ACCESS read-only
        STATUS current
        DESCRIPTION
            "ParaLen."
        ::= { newe1portPmCurEntry 2 }

    -- 1.3.6.1.4.1.2011.2.25.3.70.20.108.100.1.3
    newe1portPmCurPara OBJECT-TYPE
        SYNTAX OCTET STRING
        MAX-ACCESS read-only
        STATUS current
        DESCRIPTION
            "para"
        ::= { newe1portPmCurEntry 3 }

    -- 1.3.6.1.4.1.2011.2.25.3.70.20.108.100.1.4
    newe1portPmCurMonValue OBJECT-TYPE
        SYNTAX Counter64
        MAX-ACCESS read-only
        STATUS current
        DESCRIPTION
            "DataPmMonValue."
        ::= { newe1portPmCurEntry 4 }

    -- 1.3.6.1.4.1.2011.2.25.3.70.20.108.100.1.5
    newe1portPmCurDatetime OBJECT-TYPE
        SYNTAX DateAndTime
        MAX-ACCESS read-only
        STATUS current
        DESCRIPTION
            "Start Time."
        ::= { newe1portPmCurEntry 5 }

    -- 1.3.6.1.4.1.2011.2.25.3.70.20.108.110
    newe1portPm30sHisTable OBJECT-TYPE
        SYNTAX SEQUENCE OF Newe1portPm30sHisEntry
        MAX-ACCESS not-accessible
        STATUS current
        DESCRIPTION
            "newe1portDataPm30sHis."
        ::= { newe1port 110 }

    -- 1.3.6.1.4.1.2011.2.25.3.70.20.108.110.1
    newe1portPm30sHisEntry OBJECT-TYPE
        SYNTAX Newe1portPm30sHisEntry
        MAX-ACCESS not-accessible
        STATUS current
        DESCRIPTION
            "newe1portDataPm30sHis."
        INDEX{ newe1portPm30sHisEid,newe1portPm30sHisParaLen,newe1portPm30sHisPara,newe1portPm30sHisStartTime,newe1portPm30sHisEndTime }
        ::= { newe1portPm30sHisTable 1 }

    Newe1portPm30sHisEntry ::=
        SEQUENCE {
            newe1portPm30sHisEid
                DataPmEventType,
            newe1portPm30sHisParaLen
                Unsigned32,
            newe1portPm30sHisPara
                OCTET STRING,
            newe1portPm30sHisMonValue
                Counter64,
            newe1portPm30sHisStartTime
                DateAndTime,
            newe1portPm30sHisEndTime
                DateAndTime,
            newe1portPm30sHisVldty
                ValidflagType
        }

    -- 1.3.6.1.4.1.2011.2.25.3.70.20.108.110.1.1
    newe1portPm30sHisEid OBJECT-TYPE
        SYNTAX DataPmEventType
        MAX-ACCESS read-only
        STATUS current
        DESCRIPTION
            "DataPmEid."
        ::= { newe1portPm30sHisEntry 1 }

    -- 1.3.6.1.4.1.2011.2.25.3.70.20.108.110.1.2
    newe1portPm30sHisParaLen OBJECT-TYPE
        SYNTAX Unsigned32
        MAX-ACCESS read-only
        STATUS current
        DESCRIPTION
            "ParaLen."
        ::= { newe1portPm30sHisEntry 2 }

    -- 1.3.6.1.4.1.2011.2.25.3.70.20.108.110.1.3
    newe1portPm30sHisPara OBJECT-TYPE
        SYNTAX OCTET STRING(SIZE (0..100))
        MAX-ACCESS read-only
        STATUS current
        DESCRIPTION
            "para"
        ::= { newe1portPm30sHisEntry 3 }

    -- 1.3.6.1.4.1.2011.2.25.3.70.20.108.110.1.4
    newe1portPm30sHisMonValue OBJECT-TYPE
        SYNTAX Counter64
        MAX-ACCESS read-only
        STATUS current
        DESCRIPTION
            "DataPmMonValue."
        ::= { newe1portPm30sHisEntry 4 }

    -- 1.3.6.1.4.1.2011.2.25.3.70.20.108.110.1.5
    newe1portPm30sHisStartTime OBJECT-TYPE
        SYNTAX DateAndTime
        MAX-ACCESS read-only
        STATUS current
        DESCRIPTION
            "Start Time."
        ::= { newe1portPm30sHisEntry 5 }

    -- 1.3.6.1.4.1.2011.2.25.3.70.20.108.110.1.6
    newe1portPm30sHisEndTime OBJECT-TYPE
        SYNTAX DateAndTime
        MAX-ACCESS read-only
        STATUS current
        DESCRIPTION
            "End Time."
        ::= { newe1portPm30sHisEntry 6 }

    -- 1.3.6.1.4.1.2011.2.25.3.70.20.108.110.1.7
    newe1portPm30sHisVldty OBJECT-TYPE
        SYNTAX ValidflagType
        MAX-ACCESS read-only
        STATUS current
        DESCRIPTION
            "Validity."
        ::= { newe1portPm30sHisEntry 7 }

    -- 1.3.6.1.4.1.2011.2.25.3.70.20.108.120
    newe1portPm30mHisTable OBJECT-TYPE
        SYNTAX SEQUENCE OF Newe1portPm30mHisEntry
        MAX-ACCESS not-accessible
        STATUS current
        DESCRIPTION
            "newe1portPm30mHis."
        ::= { newe1port 120 }

    -- 1.3.6.1.4.1.2011.2.25.3.70.20.108.120.1
    newe1portPm30mHisEntry OBJECT-TYPE
        SYNTAX Newe1portPm30mHisEntry
        MAX-ACCESS not-accessible
        STATUS current
        DESCRIPTION
            "newe1portPm30mHis."
        INDEX{ newe1portPm30mHisEid,newe1portPm30mHisParaLen,newe1portPm30mHisPara,newe1portPm30mHisStartTime,newe1portPm30mHisEndTime }
        ::= { newe1portPm30mHisTable 1 }

    Newe1portPm30mHisEntry ::=
        SEQUENCE {
            newe1portPm30mHisEid
                DataPmEventType,
            newe1portPm30mHisParaLen
                Unsigned32,
            newe1portPm30mHisPara
                OCTET STRING,
            newe1portPm30mHisMonValue
                Counter64,
            newe1portPm30mHisStartTime
                DateAndTime,
            newe1portPm30mHisEndTime
                DateAndTime,
            newe1portPm30mHisVldty
                ValidflagType
        }

    -- 1.3.6.1.4.1.2011.2.25.3.70.20.108.120.1.1
    newe1portPm30mHisEid OBJECT-TYPE
        SYNTAX DataPmEventType
        MAX-ACCESS read-only
        STATUS current
        DESCRIPTION
            "DataPmEid."
        ::= { newe1portPm30mHisEntry 1 }

    -- 1.3.6.1.4.1.2011.2.25.3.70.20.108.120.1.2
    newe1portPm30mHisParaLen OBJECT-TYPE
        SYNTAX Unsigned32
        MAX-ACCESS read-only
        STATUS current
        DESCRIPTION
            "ParaLen."
        ::= { newe1portPm30mHisEntry 2 }

    -- 1.3.6.1.4.1.2011.2.25.3.70.20.108.120.1.3
    newe1portPm30mHisPara OBJECT-TYPE
        SYNTAX OCTET STRING(SIZE (0..100))
        MAX-ACCESS read-only
        STATUS current
        DESCRIPTION
            "para"
        ::= { newe1portPm30mHisEntry 3 }

    -- 1.3.6.1.4.1.2011.2.25.3.70.20.108.120.1.4
    newe1portPm30mHisMonValue OBJECT-TYPE
        SYNTAX Counter64
        MAX-ACCESS read-only
        STATUS current
        DESCRIPTION
            "DataPmMonValue."
        ::= { newe1portPm30mHisEntry 4 }

    -- 1.3.6.1.4.1.2011.2.25.3.70.20.108.120.1.5
    newe1portPm30mHisStartTime OBJECT-TYPE
        SYNTAX DateAndTime
        MAX-ACCESS read-only
        STATUS current
        DESCRIPTION
            "Start Time."
        ::= { newe1portPm30mHisEntry 5 }

    -- 1.3.6.1.4.1.2011.2.25.3.70.20.108.120.1.6
    newe1portPm30mHisEndTime OBJECT-TYPE
        SYNTAX DateAndTime
        MAX-ACCESS read-only
        STATUS current
        DESCRIPTION
            "End Time."
        ::= { newe1portPm30mHisEntry 6 }

    -- 1.3.6.1.4.1.2011.2.25.3.70.20.108.120.1.7
    newe1portPm30mHisVldty OBJECT-TYPE
        SYNTAX ValidflagType
        MAX-ACCESS read-only
        STATUS current
        DESCRIPTION
            "Validity."
        ::= { newe1portPm30mHisEntry 7 }

    -- 1.3.6.1.4.1.2011.2.25.3.70.20.108.130
    newe1portPmvar1HisTable OBJECT-TYPE
        SYNTAX SEQUENCE OF Newe1portPmvar1HisEntry
        MAX-ACCESS not-accessible
        STATUS current
        DESCRIPTION
            "newe1portPmvar1His."
        ::= { newe1port 130 }

    -- 1.3.6.1.4.1.2011.2.25.3.70.20.108.130.1
    newe1portPmvar1HisEntry OBJECT-TYPE
        SYNTAX Newe1portPmvar1HisEntry
        MAX-ACCESS not-accessible
        STATUS current
        DESCRIPTION
            "newe1portPmvar1His."
        INDEX{ newe1portPmvar1HisEid,newe1portPmvar1HisParaLen,newe1portPmvar1HisPara,newe1portPmvar1HisStartTime,newe1portPmvar1HisEndTime }
        ::= { newe1portPmvar1HisTable 1 }

    Newe1portPmvar1HisEntry ::=
        SEQUENCE {
            newe1portPmvar1HisEid
                DataPmEventType,
            newe1portPmvar1HisParaLen
                Unsigned32,
            newe1portPmvar1HisPara
                OCTET STRING,
            newe1portPmvar1HisMonValue
                Counter64,
            newe1portPmvar1HisStartTime
                DateAndTime,
            newe1portPmvar1HisEndTime
                DateAndTime,
            newe1portPmvar1HisVldty
                ValidflagType
        }

    -- 1.3.6.1.4.1.2011.2.25.3.70.20.108.130.1.1
    newe1portPmvar1HisEid OBJECT-TYPE
        SYNTAX DataPmEventType
        MAX-ACCESS read-only
        STATUS current
        DESCRIPTION
            "DataPmEid."
        ::= { newe1portPmvar1HisEntry 1 }

    -- 1.3.6.1.4.1.2011.2.25.3.70.20.108.130.1.2
    newe1portPmvar1HisParaLen OBJECT-TYPE
        SYNTAX Unsigned32
        MAX-ACCESS read-only
        STATUS current
        DESCRIPTION
            "ParaLen."
        ::= { newe1portPmvar1HisEntry 2 }

    -- 1.3.6.1.4.1.2011.2.25.3.70.20.108.130.1.3
    newe1portPmvar1HisPara OBJECT-TYPE
        SYNTAX OCTET STRING (SIZE (0..100))
        MAX-ACCESS read-only
        STATUS current
        DESCRIPTION
            "para"
        ::= { newe1portPmvar1HisEntry 3 }

    -- 1.3.6.1.4.1.2011.2.25.3.70.20.108.130.1.4
    newe1portPmvar1HisMonValue OBJECT-TYPE
        SYNTAX Counter64
        MAX-ACCESS read-only
        STATUS current
        DESCRIPTION
            "DataPmMonValue."
        ::= { newe1portPmvar1HisEntry 4 }

    -- 1.3.6.1.4.1.2011.2.25.3.70.20.108.130.1.5
    newe1portPmvar1HisStartTime OBJECT-TYPE
        SYNTAX DateAndTime
        MAX-ACCESS read-only
        STATUS current
        DESCRIPTION
            "Start Time."
        ::= { newe1portPmvar1HisEntry 5 }

    -- 1.3.6.1.4.1.2011.2.25.3.70.20.108.130.1.6
    newe1portPmvar1HisEndTime OBJECT-TYPE
        SYNTAX DateAndTime
        MAX-ACCESS read-only
        STATUS current
        DESCRIPTION
            "End Time."
        ::= { newe1portPmvar1HisEntry 6 }

    -- 1.3.6.1.4.1.2011.2.25.3.70.20.108.130.1.7
    newe1portPmvar1HisVldty OBJECT-TYPE
        SYNTAX ValidflagType
        MAX-ACCESS read-only
        STATUS current
        DESCRIPTION
            "Validity."
        ::= { newe1portPmvar1HisEntry 7 }

    -- 1.3.6.1.4.1.2011.2.25.3.70.20.108.140
    newe1portPmvar2HisTable OBJECT-TYPE
        SYNTAX SEQUENCE OF Newe1portPmvar2HisEntry
        MAX-ACCESS not-accessible
        STATUS current
        DESCRIPTION
            "newe1portPmvar2His."
        ::= { newe1port 140 }

    -- 1.3.6.1.4.1.2011.2.25.3.70.20.108.140.1
    newe1portPmvar2HisEntry OBJECT-TYPE
        SYNTAX Newe1portPmvar2HisEntry
        MAX-ACCESS not-accessible
        STATUS current
        DESCRIPTION
            "newe1portPmvar2His."
        INDEX{ newe1portPmvar2HisEid,newe1portPmvar2HisParaLen,newe1portPmvar2HisPara,newe1portPmvar2HisStartTime,newe1portPmvar2HisEndTime }
        ::= { newe1portPmvar2HisTable 1 }

    Newe1portPmvar2HisEntry ::=
        SEQUENCE {
            newe1portPmvar2HisEid
                DataPmEventType,
            newe1portPmvar2HisParaLen
                Unsigned32,
            newe1portPmvar2HisPara
                OCTET STRING,
            newe1portPmvar2HisMonValue
                Counter64,
            newe1portPmvar2HisStartTime
                DateAndTime,
            newe1portPmvar2HisEndTime
                DateAndTime,
            newe1portPmvar2HisVldty
                ValidflagType
        }

    -- 1.3.6.1.4.1.2011.2.25.3.70.20.108.140.1.1
    newe1portPmvar2HisEid OBJECT-TYPE
        SYNTAX DataPmEventType
        MAX-ACCESS read-only
        STATUS current
        DESCRIPTION
            "DataPmEid."
        ::= { newe1portPmvar2HisEntry 1 }

    -- 1.3.6.1.4.1.2011.2.25.3.70.20.108.140.1.2
    newe1portPmvar2HisParaLen OBJECT-TYPE
        SYNTAX Unsigned32
        MAX-ACCESS read-only
        STATUS current
        DESCRIPTION
            "ParaLen."
        ::= { newe1portPmvar2HisEntry 2 }

    -- 1.3.6.1.4.1.2011.2.25.3.70.20.108.140.1.3
    newe1portPmvar2HisPara OBJECT-TYPE
        SYNTAX OCTET STRING(SIZE (0..100))
        MAX-ACCESS read-only
        STATUS current
        DESCRIPTION
            "para"
        ::= { newe1portPmvar2HisEntry 3 }

    -- 1.3.6.1.4.1.2011.2.25.3.70.20.108.140.1.4
    newe1portPmvar2HisMonValue OBJECT-TYPE
        SYNTAX Counter64
        MAX-ACCESS read-only
        STATUS current
        DESCRIPTION
            "DataPmMonValue."
        ::= { newe1portPmvar2HisEntry 4 }

    -- 1.3.6.1.4.1.2011.2.25.3.70.20.108.140.1.5
    newe1portPmvar2HisStartTime OBJECT-TYPE
        SYNTAX DateAndTime
        MAX-ACCESS read-only
        STATUS current
        DESCRIPTION
            "Start Time."
        ::= { newe1portPmvar2HisEntry 5 }

    -- 1.3.6.1.4.1.2011.2.25.3.70.20.108.140.1.6
    newe1portPmvar2HisEndTime OBJECT-TYPE
        SYNTAX DateAndTime
        MAX-ACCESS read-only
        STATUS current
        DESCRIPTION
            "End Time."
        ::= { newe1portPmvar2HisEntry 6 }

    -- 1.3.6.1.4.1.2011.2.25.3.70.20.108.140.1.7
    newe1portPmvar2HisVldty OBJECT-TYPE
        SYNTAX ValidflagType
        MAX-ACCESS read-only
        STATUS current
        DESCRIPTION
            "Validity."
        ::= { newe1portPmvar2HisEntry 7 }

    -- 1.3.6.1.4.1.2011.2.25.3.70.20.114
    g1j1 OBJECT IDENTIFIER ::= { rtnData 114 }

    -- 1.3.6.1.4.1.2011.2.25.3.70.20.114.100
    g1j1PmCurTable OBJECT-TYPE
        SYNTAX SEQUENCE OF G1j1PmCurEntry
        MAX-ACCESS not-accessible
        STATUS current
        DESCRIPTION
            "g1j1DataPm30sCur."
        ::= { g1j1 100 }

    -- 1.3.6.1.4.1.2011.2.25.3.70.20.114.100.1
    g1j1PmCurEntry OBJECT-TYPE
        SYNTAX G1j1PmCurEntry
        MAX-ACCESS not-accessible
        STATUS current
        DESCRIPTION
            "g1j1PmCur."
        INDEX{ g1j1PmCurEid, g1j1PmCurParaLen, g1j1PmCurPara }
        ::= { g1j1PmCurTable 1 }

    G1j1PmCurEntry ::=
        SEQUENCE {
            g1j1PmCurEid
                DataPmEventType,
            g1j1PmCurParaLen
                Unsigned32,
            g1j1PmCurPara
                OCTET STRING,
            g1j1PmCurMonValue
                Counter64,
            g1j1PmCurDatetime
                DateAndTime
        }

    -- 1.3.6.1.4.1.2011.2.25.3.70.20.114.100.1.1
    g1j1PmCurEid OBJECT-TYPE
        SYNTAX DataPmEventType
        MAX-ACCESS read-only
        STATUS current
        DESCRIPTION
            "DataPmEid."
        ::= { g1j1PmCurEntry 1 }

    -- 1.3.6.1.4.1.2011.2.25.3.70.20.114.100.1.2
    g1j1PmCurParaLen OBJECT-TYPE
        SYNTAX Unsigned32
        MAX-ACCESS read-only
        STATUS current
        DESCRIPTION
            "ParaLen."
        ::= { g1j1PmCurEntry 2 }

    -- 1.3.6.1.4.1.2011.2.25.3.70.20.114.100.1.3
    g1j1PmCurPara OBJECT-TYPE
        SYNTAX OCTET STRING
        MAX-ACCESS read-only
        STATUS current
        DESCRIPTION
            "para"
        ::= { g1j1PmCurEntry 3 }

    -- 1.3.6.1.4.1.2011.2.25.3.70.20.114.100.1.4
    g1j1PmCurMonValue OBJECT-TYPE
        SYNTAX Counter64
        MAX-ACCESS read-only
        STATUS current
        DESCRIPTION
            "DataPmMonValue."
        ::= { g1j1PmCurEntry 4 }

    -- 1.3.6.1.4.1.2011.2.25.3.70.20.114.100.1.5
    g1j1PmCurDatetime OBJECT-TYPE
        SYNTAX DateAndTime
        MAX-ACCESS read-only
        STATUS current
        DESCRIPTION
            "Start Time."
        ::= { g1j1PmCurEntry 5 }

    -- 1.3.6.1.4.1.2011.2.25.3.70.20.114.110
    g1j1Pm30sHisTable OBJECT-TYPE
        SYNTAX SEQUENCE OF G1j1Pm30sHisEntry
        MAX-ACCESS not-accessible
        STATUS current
        DESCRIPTION
            "g1j1DataPm30sHis."
        ::= { g1j1 110 }

    -- 1.3.6.1.4.1.2011.2.25.3.70.20.114.110.1
    g1j1Pm30sHisEntry OBJECT-TYPE
        SYNTAX G1j1Pm30sHisEntry
        MAX-ACCESS not-accessible
        STATUS current
        DESCRIPTION
            "g1j1DataPm30sHis."
        INDEX{ g1j1Pm30sHisEid,g1j1Pm30sHisParaLen,g1j1Pm30sHisPara,g1j1Pm30sHisStartTime,g1j1Pm30sHisEndTime }
        ::= { g1j1Pm30sHisTable 1 }

    G1j1Pm30sHisEntry ::=
        SEQUENCE {
            g1j1Pm30sHisEid
                DataPmEventType,
            g1j1Pm30sHisParaLen
                Unsigned32,
            g1j1Pm30sHisPara
                OCTET STRING,
            g1j1Pm30sHisMonValue
                Counter64,
            g1j1Pm30sHisStartTime
                DateAndTime,
            g1j1Pm30sHisEndTime
                DateAndTime,
            g1j1Pm30sHisVldty
                ValidflagType
        }

    -- 1.3.6.1.4.1.2011.2.25.3.70.20.114.110.1.1
    g1j1Pm30sHisEid OBJECT-TYPE
        SYNTAX DataPmEventType
        MAX-ACCESS read-only
        STATUS current
        DESCRIPTION
            "DataPmEid."
        ::= { g1j1Pm30sHisEntry 1 }

    -- 1.3.6.1.4.1.2011.2.25.3.70.20.114.110.1.2
    g1j1Pm30sHisParaLen OBJECT-TYPE
        SYNTAX Unsigned32
        MAX-ACCESS read-only
        STATUS current
        DESCRIPTION
            "ParaLen."
        ::= { g1j1Pm30sHisEntry 2 }

    -- 1.3.6.1.4.1.2011.2.25.3.70.20.114.110.1.3
    g1j1Pm30sHisPara OBJECT-TYPE
        SYNTAX OCTET STRING(SIZE (0..100))
        MAX-ACCESS read-only
        STATUS current
        DESCRIPTION
            "para"
        ::= { g1j1Pm30sHisEntry 3 }

    -- 1.3.6.1.4.1.2011.2.25.3.70.20.114.110.1.4
    g1j1Pm30sHisMonValue OBJECT-TYPE
        SYNTAX Counter64
        MAX-ACCESS read-only
        STATUS current
        DESCRIPTION
            "DataPmMonValue."
        ::= { g1j1Pm30sHisEntry 4 }

    -- 1.3.6.1.4.1.2011.2.25.3.70.20.114.110.1.5
    g1j1Pm30sHisStartTime OBJECT-TYPE
        SYNTAX DateAndTime
        MAX-ACCESS read-only
        STATUS current
        DESCRIPTION
            "Start Time."
        ::= { g1j1Pm30sHisEntry 5 }

    -- 1.3.6.1.4.1.2011.2.25.3.70.20.114.110.1.6
    g1j1Pm30sHisEndTime OBJECT-TYPE
        SYNTAX DateAndTime
        MAX-ACCESS read-only
        STATUS current
        DESCRIPTION
            "End Time."
        ::= { g1j1Pm30sHisEntry 6 }

    -- 1.3.6.1.4.1.2011.2.25.3.70.20.114.110.1.7
    g1j1Pm30sHisVldty OBJECT-TYPE
        SYNTAX ValidflagType
        MAX-ACCESS read-only
        STATUS current
        DESCRIPTION
            "Validity."
        ::= { g1j1Pm30sHisEntry 7 }

    -- 1.3.6.1.4.1.2011.2.25.3.70.20.114.120
    g1j1Pm30mHisTable OBJECT-TYPE
        SYNTAX SEQUENCE OF G1j1Pm30mHisEntry
        MAX-ACCESS not-accessible
        STATUS current
        DESCRIPTION
            "g1j1Pm30mHis."
        ::= { g1j1 120 }

    -- 1.3.6.1.4.1.2011.2.25.3.70.20.114.120.1
    g1j1Pm30mHisEntry OBJECT-TYPE
        SYNTAX G1j1Pm30mHisEntry
        MAX-ACCESS not-accessible
        STATUS current
        DESCRIPTION
            "g1j1Pm30mHis."
        INDEX{ g1j1Pm30mHisEid,g1j1Pm30mHisParaLen,g1j1Pm30mHisPara,g1j1Pm30mHisStartTime,g1j1Pm30mHisEndTime }
        ::= { g1j1Pm30mHisTable 1 }

    G1j1Pm30mHisEntry ::=
        SEQUENCE {
            g1j1Pm30mHisEid
                DataPmEventType,
            g1j1Pm30mHisParaLen
                Unsigned32,
            g1j1Pm30mHisPara
                OCTET STRING,
            g1j1Pm30mHisMonValue
                Counter64,
            g1j1Pm30mHisStartTime
                DateAndTime,
            g1j1Pm30mHisEndTime
                DateAndTime,
            g1j1Pm30mHisVldty
                ValidflagType
        }

    -- 1.3.6.1.4.1.2011.2.25.3.70.20.114.120.1.1
    g1j1Pm30mHisEid OBJECT-TYPE
        SYNTAX DataPmEventType
        MAX-ACCESS read-only
        STATUS current
        DESCRIPTION
            "DataPmEid."
        ::= { g1j1Pm30mHisEntry 1 }

    -- 1.3.6.1.4.1.2011.2.25.3.70.20.114.120.1.2
    g1j1Pm30mHisParaLen OBJECT-TYPE
        SYNTAX Unsigned32
        MAX-ACCESS read-only
        STATUS current
        DESCRIPTION
            "ParaLen."
        ::= { g1j1Pm30mHisEntry 2 }

    -- 1.3.6.1.4.1.2011.2.25.3.70.20.114.120.1.3
    g1j1Pm30mHisPara OBJECT-TYPE
        SYNTAX OCTET STRING(SIZE (0..100))
        MAX-ACCESS read-only
        STATUS current
        DESCRIPTION
            "para"
        ::= { g1j1Pm30mHisEntry 3 }

    -- 1.3.6.1.4.1.2011.2.25.3.70.20.114.120.1.4
    g1j1Pm30mHisMonValue OBJECT-TYPE
        SYNTAX Counter64
        MAX-ACCESS read-only
        STATUS current
        DESCRIPTION
            "DataPmMonValue."
        ::= { g1j1Pm30mHisEntry 4 }

    -- 1.3.6.1.4.1.2011.2.25.3.70.20.114.120.1.5
    g1j1Pm30mHisStartTime OBJECT-TYPE
        SYNTAX DateAndTime
        MAX-ACCESS read-only
        STATUS current
        DESCRIPTION
            "Start Time."
        ::= { g1j1Pm30mHisEntry 5 }

    -- 1.3.6.1.4.1.2011.2.25.3.70.20.114.120.1.6
    g1j1Pm30mHisEndTime OBJECT-TYPE
        SYNTAX DateAndTime
        MAX-ACCESS read-only
        STATUS current
        DESCRIPTION
            "End Time."
        ::= { g1j1Pm30mHisEntry 6 }

    -- 1.3.6.1.4.1.2011.2.25.3.70.20.114.120.1.7
    g1j1Pm30mHisVldty OBJECT-TYPE
        SYNTAX ValidflagType
        MAX-ACCESS read-only
        STATUS current
        DESCRIPTION
            "Validity."
        ::= { g1j1Pm30mHisEntry 7 }

    -- 1.3.6.1.4.1.2011.2.25.3.70.20.114.130
    g1j1Pmvar1HisTable OBJECT-TYPE
        SYNTAX SEQUENCE OF G1j1Pmvar1HisEntry
        MAX-ACCESS not-accessible
        STATUS current
        DESCRIPTION
            "g1j1Pmvar1His."
        ::= { g1j1 130 }

    -- 1.3.6.1.4.1.2011.2.25.3.70.20.114.130.1
    g1j1Pmvar1HisEntry OBJECT-TYPE
        SYNTAX G1j1Pmvar1HisEntry
        MAX-ACCESS not-accessible
        STATUS current
        DESCRIPTION
            "g1j1Pmvar1His."
        INDEX{ g1j1Pmvar1HisEid,g1j1Pmvar1HisParaLen,g1j1Pmvar1HisPara,g1j1Pmvar1HisStartTime,g1j1Pmvar1HisEndTime }
        ::= { g1j1Pmvar1HisTable 1 }

    G1j1Pmvar1HisEntry ::=
        SEQUENCE {
            g1j1Pmvar1HisEid
                DataPmEventType,
            g1j1Pmvar1HisParaLen
                Unsigned32,
            g1j1Pmvar1HisPara
                OCTET STRING,
            g1j1Pmvar1HisMonValue
                Counter64,
            g1j1Pmvar1HisStartTime
                DateAndTime,
            g1j1Pmvar1HisEndTime
                DateAndTime,
            g1j1Pmvar1HisVldty
                ValidflagType
        }

    -- 1.3.6.1.4.1.2011.2.25.3.70.20.114.130.1.1
    g1j1Pmvar1HisEid OBJECT-TYPE
        SYNTAX DataPmEventType
        MAX-ACCESS read-only
        STATUS current
        DESCRIPTION
            "DataPmEid."
        ::= { g1j1Pmvar1HisEntry 1 }

    -- 1.3.6.1.4.1.2011.2.25.3.70.20.114.130.1.2
    g1j1Pmvar1HisParaLen OBJECT-TYPE
        SYNTAX Unsigned32
        MAX-ACCESS read-only
        STATUS current
        DESCRIPTION
            "ParaLen."
        ::= { g1j1Pmvar1HisEntry 2 }

    -- 1.3.6.1.4.1.2011.2.25.3.70.20.114.130.1.3
    g1j1Pmvar1HisPara OBJECT-TYPE
        SYNTAX OCTET STRING (SIZE (0..100))
        MAX-ACCESS read-only
        STATUS current
        DESCRIPTION
            "para"
        ::= { g1j1Pmvar1HisEntry 3 }

    -- 1.3.6.1.4.1.2011.2.25.3.70.20.114.130.1.4
    g1j1Pmvar1HisMonValue OBJECT-TYPE
        SYNTAX Counter64
        MAX-ACCESS read-only
        STATUS current
        DESCRIPTION
            "DataPmMonValue."
        ::= { g1j1Pmvar1HisEntry 4 }

    -- 1.3.6.1.4.1.2011.2.25.3.70.20.114.130.1.5
    g1j1Pmvar1HisStartTime OBJECT-TYPE
        SYNTAX DateAndTime
        MAX-ACCESS read-only
        STATUS current
        DESCRIPTION
            "Start Time."
        ::= { g1j1Pmvar1HisEntry 5 }

    -- 1.3.6.1.4.1.2011.2.25.3.70.20.114.130.1.6
    g1j1Pmvar1HisEndTime OBJECT-TYPE
        SYNTAX DateAndTime
        MAX-ACCESS read-only
        STATUS current
        DESCRIPTION
            "End Time."
        ::= { g1j1Pmvar1HisEntry 6 }

    -- 1.3.6.1.4.1.2011.2.25.3.70.20.114.130.1.7
    g1j1Pmvar1HisVldty OBJECT-TYPE
        SYNTAX ValidflagType
        MAX-ACCESS read-only
        STATUS current
        DESCRIPTION
            "Validity."
        ::= { g1j1Pmvar1HisEntry 7 }

    -- 1.3.6.1.4.1.2011.2.25.3.70.20.114.140
    g1j1Pmvar2HisTable OBJECT-TYPE
        SYNTAX SEQUENCE OF G1j1Pmvar2HisEntry
        MAX-ACCESS not-accessible
        STATUS current
        DESCRIPTION
            "g1j1Pmvar2His."
        ::= { g1j1 140 }

    -- 1.3.6.1.4.1.2011.2.25.3.70.20.114.140.1
    g1j1Pmvar2HisEntry OBJECT-TYPE
        SYNTAX G1j1Pmvar2HisEntry
        MAX-ACCESS not-accessible
        STATUS current
        DESCRIPTION
            "g1j1Pmvar2His."
        INDEX{ g1j1Pmvar2HisEid,g1j1Pmvar2HisParaLen,g1j1Pmvar2HisPara,g1j1Pmvar2HisStartTime,g1j1Pmvar2HisEndTime }
        ::= { g1j1Pmvar2HisTable 1 }

    G1j1Pmvar2HisEntry ::=
        SEQUENCE {
            g1j1Pmvar2HisEid
                DataPmEventType,
            g1j1Pmvar2HisParaLen
                Unsigned32,
            g1j1Pmvar2HisPara
                OCTET STRING,
            g1j1Pmvar2HisMonValue
                Counter64,
            g1j1Pmvar2HisStartTime
                DateAndTime,
            g1j1Pmvar2HisEndTime
                DateAndTime,
            g1j1Pmvar2HisVldty
                ValidflagType
        }

    -- 1.3.6.1.4.1.2011.2.25.3.70.20.114.140.1.1
    g1j1Pmvar2HisEid OBJECT-TYPE
        SYNTAX DataPmEventType
        MAX-ACCESS read-only
        STATUS current
        DESCRIPTION
            "DataPmEid."
        ::= { g1j1Pmvar2HisEntry 1 }

    -- 1.3.6.1.4.1.2011.2.25.3.70.20.114.140.1.2
    g1j1Pmvar2HisParaLen OBJECT-TYPE
        SYNTAX Unsigned32
        MAX-ACCESS read-only
        STATUS current
        DESCRIPTION
            "ParaLen."
        ::= { g1j1Pmvar2HisEntry 2 }

    -- 1.3.6.1.4.1.2011.2.25.3.70.20.114.140.1.3
    g1j1Pmvar2HisPara OBJECT-TYPE
        SYNTAX OCTET STRING(SIZE (0..100))
        MAX-ACCESS read-only
        STATUS current
        DESCRIPTION
            "para"
        ::= { g1j1Pmvar2HisEntry 3 }

    -- 1.3.6.1.4.1.2011.2.25.3.70.20.114.140.1.4
    g1j1Pmvar2HisMonValue OBJECT-TYPE
        SYNTAX Counter64
        MAX-ACCESS read-only
        STATUS current
        DESCRIPTION
            "DataPmMonValue."
        ::= { g1j1Pmvar2HisEntry 4 }

    -- 1.3.6.1.4.1.2011.2.25.3.70.20.114.140.1.5
    g1j1Pmvar2HisStartTime OBJECT-TYPE
        SYNTAX DateAndTime
        MAX-ACCESS read-only
        STATUS current
        DESCRIPTION
            "Start Time."
        ::= { g1j1Pmvar2HisEntry 5 }

    -- 1.3.6.1.4.1.2011.2.25.3.70.20.114.140.1.6
    g1j1Pmvar2HisEndTime OBJECT-TYPE
        SYNTAX DateAndTime
        MAX-ACCESS read-only
        STATUS current
        DESCRIPTION
            "End Time."
        ::= { g1j1Pmvar2HisEntry 6 }

    -- 1.3.6.1.4.1.2011.2.25.3.70.20.114.140.1.7
    g1j1Pmvar2HisVldty OBJECT-TYPE
        SYNTAX ValidflagType
        MAX-ACCESS read-only
        STATUS current
        DESCRIPTION
            "Validity."
        ::= { g1j1Pmvar2HisEntry 7 }

    -- 1.3.6.1.4.1.2011.2.25.3.70.20.149
    ethvcgport OBJECT IDENTIFIER ::= { rtnData 149 }

    -- 1.3.6.1.4.1.2011.2.25.3.70.20.149.100
    ethvcgportPmCurTable OBJECT-TYPE
        SYNTAX SEQUENCE OF EthvcgportPmCurEntry
        MAX-ACCESS not-accessible
        STATUS current
        DESCRIPTION
            "ethvcgportDataPm30sCur."
        ::= { ethvcgport 100 }

    -- 1.3.6.1.4.1.2011.2.25.3.70.20.149.100.1
    ethvcgportPmCurEntry OBJECT-TYPE
        SYNTAX EthvcgportPmCurEntry
        MAX-ACCESS not-accessible
        STATUS current
        DESCRIPTION
            "ethvcgportPmCur."
        INDEX{ ethvcgportPmCurEid,ethvcgportPmCurParaLen, ethvcgportPmCurPara }
        ::= { ethvcgportPmCurTable 1 }

    EthvcgportPmCurEntry ::=
        SEQUENCE {
            ethvcgportPmCurEid
                DataPmEventType,
            ethvcgportPmCurParaLen
                Unsigned32,
            ethvcgportPmCurPara
                OCTET STRING,
            ethvcgportPmCurMonValue
                Counter64,
            ethvcgportPmCurDatetime
                DateAndTime
        }

    -- 1.3.6.1.4.1.2011.2.25.3.70.20.149.100.1.1
    ethvcgportPmCurEid OBJECT-TYPE
        SYNTAX DataPmEventType
        MAX-ACCESS read-only
        STATUS current
        DESCRIPTION
            "DataPmEid."
        ::= { ethvcgportPmCurEntry 1 }

    -- 1.3.6.1.4.1.2011.2.25.3.70.20.149.100.1.2
    ethvcgportPmCurParaLen OBJECT-TYPE
        SYNTAX Unsigned32
        MAX-ACCESS read-only
        STATUS current
        DESCRIPTION
            "ParaLen."
        ::= { ethvcgportPmCurEntry 2 }

    -- 1.3.6.1.4.1.2011.2.25.3.70.20.149.100.1.3
    ethvcgportPmCurPara OBJECT-TYPE
        SYNTAX OCTET STRING
        MAX-ACCESS read-only
        STATUS current
        DESCRIPTION
            "para"
        ::= { ethvcgportPmCurEntry 3 }

    -- 1.3.6.1.4.1.2011.2.25.3.70.20.149.100.1.4
    ethvcgportPmCurMonValue OBJECT-TYPE
        SYNTAX Counter64
        MAX-ACCESS read-only
        STATUS current
        DESCRIPTION
            "DataPmMonValue."
        ::= { ethvcgportPmCurEntry 4 }

    -- 1.3.6.1.4.1.2011.2.25.3.70.20.149.100.1.5
    ethvcgportPmCurDatetime OBJECT-TYPE
        SYNTAX DateAndTime
        MAX-ACCESS read-only
        STATUS current
        DESCRIPTION
            "Start Time."
        ::= { ethvcgportPmCurEntry 5 }

    -- 1.3.6.1.4.1.2011.2.25.3.70.20.149.110
    ethvcgportPm30sHisTable OBJECT-TYPE
        SYNTAX SEQUENCE OF EthvcgportPm30sHisEntry
        MAX-ACCESS not-accessible
        STATUS current
        DESCRIPTION
            "ethvcgportDataPm30sHis."
        ::= { ethvcgport 110 }

    -- 1.3.6.1.4.1.2011.2.25.3.70.20.149.110.1
    ethvcgportPm30sHisEntry OBJECT-TYPE
        SYNTAX EthvcgportPm30sHisEntry
        MAX-ACCESS not-accessible
        STATUS current
        DESCRIPTION
            "ethvcgportDataPm30sHis."
        INDEX{ ethvcgportPm30sHisEid,ethvcgportPm30sHisParaLen,ethvcgportPm30sHisPara,ethvcgportPm30sHisStartTime,ethvcgportPm30sHisEndTime }
        ::= { ethvcgportPm30sHisTable 1 }

    EthvcgportPm30sHisEntry ::=
        SEQUENCE {
            ethvcgportPm30sHisEid
                DataPmEventType,
            ethvcgportPm30sHisParaLen
                Unsigned32,
            ethvcgportPm30sHisPara
                OCTET STRING,
            ethvcgportPm30sHisMonValue
                Counter64,
            ethvcgportPm30sHisStartTime
                DateAndTime,
            ethvcgportPm30sHisEndTime
                DateAndTime,
            ethvcgportPm30sHisVldty
                ValidflagType
        }

    -- 1.3.6.1.4.1.2011.2.25.3.70.20.149.110.1.1
    ethvcgportPm30sHisEid OBJECT-TYPE
        SYNTAX DataPmEventType
        MAX-ACCESS read-only
        STATUS current
        DESCRIPTION
            "DataPmEid."
        ::= { ethvcgportPm30sHisEntry 1 }

    -- 1.3.6.1.4.1.2011.2.25.3.70.20.149.110.1.2
    ethvcgportPm30sHisParaLen OBJECT-TYPE
        SYNTAX Unsigned32
        MAX-ACCESS read-only
        STATUS current
        DESCRIPTION
            "ParaLen."
        ::= { ethvcgportPm30sHisEntry 2 }

    -- 1.3.6.1.4.1.2011.2.25.3.70.20.149.110.1.3
    ethvcgportPm30sHisPara OBJECT-TYPE
        SYNTAX OCTET STRING(SIZE (0..100))
        MAX-ACCESS read-only
        STATUS current
        DESCRIPTION
            "para"
        ::= { ethvcgportPm30sHisEntry 3 }

    -- 1.3.6.1.4.1.2011.2.25.3.70.20.149.110.1.4
    ethvcgportPm30sHisMonValue OBJECT-TYPE
        SYNTAX Counter64
        MAX-ACCESS read-only
        STATUS current
        DESCRIPTION
            "DataPmMonValue."
        ::= { ethvcgportPm30sHisEntry 4 }

    -- 1.3.6.1.4.1.2011.2.25.3.70.20.149.110.1.5
    ethvcgportPm30sHisStartTime OBJECT-TYPE
        SYNTAX DateAndTime
        MAX-ACCESS read-only
        STATUS current
        DESCRIPTION
            "Start Time."
        ::= { ethvcgportPm30sHisEntry 5 }

    -- 1.3.6.1.4.1.2011.2.25.3.70.20.149.110.1.6
    ethvcgportPm30sHisEndTime OBJECT-TYPE
        SYNTAX DateAndTime
        MAX-ACCESS read-only
        STATUS current
        DESCRIPTION
            "End Time."
        ::= { ethvcgportPm30sHisEntry 6 }

    -- 1.3.6.1.4.1.2011.2.25.3.70.20.149.110.1.7
    ethvcgportPm30sHisVldty OBJECT-TYPE
        SYNTAX ValidflagType
        MAX-ACCESS read-only
        STATUS current
        DESCRIPTION
            "Validity."
        ::= { ethvcgportPm30sHisEntry 7 }

    -- 1.3.6.1.4.1.2011.2.25.3.70.20.149.120
    ethvcgportPm30mHisTable OBJECT-TYPE
        SYNTAX SEQUENCE OF EthvcgportPm30mHisEntry
        MAX-ACCESS not-accessible
        STATUS current
        DESCRIPTION
            "ethvcgportPm30mHis."
        ::= { ethvcgport 120 }

    -- 1.3.6.1.4.1.2011.2.25.3.70.20.149.120.1
    ethvcgportPm30mHisEntry OBJECT-TYPE
        SYNTAX EthvcgportPm30mHisEntry
        MAX-ACCESS not-accessible
        STATUS current
        DESCRIPTION
            "ethvcgportPm30mHis."
        INDEX{ ethvcgportPm30mHisEid,ethvcgportPm30mHisParaLen,ethvcgportPm30mHisPara,ethvcgportPm30mHisStartTime,ethvcgportPm30mHisEndTime }
        ::= { ethvcgportPm30mHisTable 1 }

    EthvcgportPm30mHisEntry ::=
        SEQUENCE {
            ethvcgportPm30mHisEid
                DataPmEventType,
            ethvcgportPm30mHisParaLen
                Unsigned32,
            ethvcgportPm30mHisPara
                OCTET STRING,
            ethvcgportPm30mHisMonValue
                Counter64,
            ethvcgportPm30mHisStartTime
                DateAndTime,
            ethvcgportPm30mHisEndTime
                DateAndTime,
            ethvcgportPm30mHisVldty
                ValidflagType
        }

    -- 1.3.6.1.4.1.2011.2.25.3.70.20.149.120.1.1
    ethvcgportPm30mHisEid OBJECT-TYPE
        SYNTAX DataPmEventType
        MAX-ACCESS read-only
        STATUS current
        DESCRIPTION
            "DataPmEid."
        ::= { ethvcgportPm30mHisEntry 1 }

    -- 1.3.6.1.4.1.2011.2.25.3.70.20.149.120.1.2
    ethvcgportPm30mHisParaLen OBJECT-TYPE
        SYNTAX Unsigned32
        MAX-ACCESS read-only
        STATUS current
        DESCRIPTION
            "ParaLen."
        ::= { ethvcgportPm30mHisEntry 2 }

    -- 1.3.6.1.4.1.2011.2.25.3.70.20.149.120.1.3
    ethvcgportPm30mHisPara OBJECT-TYPE
        SYNTAX OCTET STRING(SIZE (0..100))
        MAX-ACCESS read-only
        STATUS current
        DESCRIPTION
            "para"
        ::= { ethvcgportPm30mHisEntry 3 }

    -- 1.3.6.1.4.1.2011.2.25.3.70.20.149.120.1.4
    ethvcgportPm30mHisMonValue OBJECT-TYPE
        SYNTAX Counter64
        MAX-ACCESS read-only
        STATUS current
        DESCRIPTION
            "DataPmMonValue."
        ::= { ethvcgportPm30mHisEntry 4 }

    -- 1.3.6.1.4.1.2011.2.25.3.70.20.149.120.1.5
    ethvcgportPm30mHisStartTime OBJECT-TYPE
        SYNTAX DateAndTime
        MAX-ACCESS read-only
        STATUS current
        DESCRIPTION
            "Start Time."
        ::= { ethvcgportPm30mHisEntry 5 }

    -- 1.3.6.1.4.1.2011.2.25.3.70.20.149.120.1.6
    ethvcgportPm30mHisEndTime OBJECT-TYPE
        SYNTAX DateAndTime
        MAX-ACCESS read-only
        STATUS current
        DESCRIPTION
            "End Time."
        ::= { ethvcgportPm30mHisEntry 6 }

    -- 1.3.6.1.4.1.2011.2.25.3.70.20.149.120.1.7
    ethvcgportPm30mHisVldty OBJECT-TYPE
        SYNTAX ValidflagType
        MAX-ACCESS read-only
        STATUS current
        DESCRIPTION
            "Validity."
        ::= { ethvcgportPm30mHisEntry 7 }

    -- 1.3.6.1.4.1.2011.2.25.3.70.20.149.130
    ethvcgportPmvar1HisTable OBJECT-TYPE
        SYNTAX SEQUENCE OF EthvcgportPmvar1HisEntry
        MAX-ACCESS not-accessible
        STATUS current
        DESCRIPTION
            "ethvcgportPmvar1His."
        ::= { ethvcgport 130 }

    -- 1.3.6.1.4.1.2011.2.25.3.70.20.149.130.1
    ethvcgportPmvar1HisEntry OBJECT-TYPE
        SYNTAX EthvcgportPmvar1HisEntry
        MAX-ACCESS not-accessible
        STATUS current
        DESCRIPTION
            "ethvcgportPmvar1His."
        INDEX{ ethvcgportPmvar1HisEid,ethvcgportPmvar1HisParaLen,ethvcgportPmvar1HisPara,ethvcgportPmvar1HisStartTime,ethvcgportPmvar1HisEndTime }
        ::= { ethvcgportPmvar1HisTable 1 }

    EthvcgportPmvar1HisEntry ::=
        SEQUENCE {
            ethvcgportPmvar1HisEid
                DataPmEventType,
            ethvcgportPmvar1HisParaLen
                Unsigned32,
            ethvcgportPmvar1HisPara
                OCTET STRING,
            ethvcgportPmvar1HisMonValue
                Counter64,
            ethvcgportPmvar1HisStartTime
                DateAndTime,
            ethvcgportPmvar1HisEndTime
                DateAndTime,
            ethvcgportPmvar1HisVldty
                ValidflagType
        }

    -- 1.3.6.1.4.1.2011.2.25.3.70.20.149.130.1.1
    ethvcgportPmvar1HisEid OBJECT-TYPE
        SYNTAX DataPmEventType
        MAX-ACCESS read-only
        STATUS current
        DESCRIPTION
            "DataPmEid."
        ::= { ethvcgportPmvar1HisEntry 1 }

    -- 1.3.6.1.4.1.2011.2.25.3.70.20.149.130.1.2
    ethvcgportPmvar1HisParaLen OBJECT-TYPE
        SYNTAX Unsigned32
        MAX-ACCESS read-only
        STATUS current
        DESCRIPTION
            "ParaLen."
        ::= { ethvcgportPmvar1HisEntry 2 }

    -- 1.3.6.1.4.1.2011.2.25.3.70.20.149.130.1.3
    ethvcgportPmvar1HisPara OBJECT-TYPE
        SYNTAX OCTET STRING (SIZE (0..100))
        MAX-ACCESS read-only
        STATUS current
        DESCRIPTION
            "para"
        ::= { ethvcgportPmvar1HisEntry 3 }

    -- 1.3.6.1.4.1.2011.2.25.3.70.20.149.130.1.4
    ethvcgportPmvar1HisMonValue OBJECT-TYPE
        SYNTAX Counter64
        MAX-ACCESS read-only
        STATUS current
        DESCRIPTION
            "DataPmMonValue."
        ::= { ethvcgportPmvar1HisEntry 4 }

    -- 1.3.6.1.4.1.2011.2.25.3.70.20.149.130.1.5
    ethvcgportPmvar1HisStartTime OBJECT-TYPE
        SYNTAX DateAndTime
        MAX-ACCESS read-only
        STATUS current
        DESCRIPTION
            "Start Time."
        ::= { ethvcgportPmvar1HisEntry 5 }

    -- 1.3.6.1.4.1.2011.2.25.3.70.20.149.130.1.6
    ethvcgportPmvar1HisEndTime OBJECT-TYPE
        SYNTAX DateAndTime
        MAX-ACCESS read-only
        STATUS current
        DESCRIPTION
            "End Time."
        ::= { ethvcgportPmvar1HisEntry 6 }

    -- 1.3.6.1.4.1.2011.2.25.3.70.20.149.130.1.7
    ethvcgportPmvar1HisVldty OBJECT-TYPE
        SYNTAX ValidflagType
        MAX-ACCESS read-only
        STATUS current
        DESCRIPTION
            "Validity."
        ::= { ethvcgportPmvar1HisEntry 7 }

    -- 1.3.6.1.4.1.2011.2.25.3.70.20.149.140
    ethvcgportPmvar2HisTable OBJECT-TYPE
        SYNTAX SEQUENCE OF EthvcgportPmvar2HisEntry
        MAX-ACCESS not-accessible
        STATUS current
        DESCRIPTION
            "ethvcgportPmvar2His."
        ::= { ethvcgport 140 }

    -- 1.3.6.1.4.1.2011.2.25.3.70.20.149.140.1
    ethvcgportPmvar2HisEntry OBJECT-TYPE
        SYNTAX EthvcgportPmvar2HisEntry
        MAX-ACCESS not-accessible
        STATUS current
        DESCRIPTION
            "ethvcgportPmvar2His."
        INDEX{ ethvcgportPmvar2HisEid,ethvcgportPmvar2HisParaLen,ethvcgportPmvar2HisPara,ethvcgportPmvar2HisStartTime,ethvcgportPmvar2HisEndTime }
        ::= { ethvcgportPmvar2HisTable 1 }

    EthvcgportPmvar2HisEntry ::=
        SEQUENCE {
            ethvcgportPmvar2HisEid
                DataPmEventType,
            ethvcgportPmvar2HisParaLen
                Unsigned32,
            ethvcgportPmvar2HisPara
                OCTET STRING,
            ethvcgportPmvar2HisMonValue
                Counter64,
            ethvcgportPmvar2HisStartTime
                DateAndTime,
            ethvcgportPmvar2HisEndTime
                DateAndTime,
            ethvcgportPmvar2HisVldty
                ValidflagType
        }

    -- 1.3.6.1.4.1.2011.2.25.3.70.20.149.140.1.1
    ethvcgportPmvar2HisEid OBJECT-TYPE
        SYNTAX DataPmEventType
        MAX-ACCESS read-only
        STATUS current
        DESCRIPTION
            "DataPmEid."
        ::= { ethvcgportPmvar2HisEntry 1 }

    -- 1.3.6.1.4.1.2011.2.25.3.70.20.149.140.1.2
    ethvcgportPmvar2HisParaLen OBJECT-TYPE
        SYNTAX Unsigned32
        MAX-ACCESS read-only
        STATUS current
        DESCRIPTION
            "ParaLen."
        ::= { ethvcgportPmvar2HisEntry 2 }

    -- 1.3.6.1.4.1.2011.2.25.3.70.20.149.140.1.3
    ethvcgportPmvar2HisPara OBJECT-TYPE
        SYNTAX OCTET STRING(SIZE (0..100))
        MAX-ACCESS read-only
        STATUS current
        DESCRIPTION
            "para"
        ::= { ethvcgportPmvar2HisEntry 3 }

    -- 1.3.6.1.4.1.2011.2.25.3.70.20.149.140.1.4
    ethvcgportPmvar2HisMonValue OBJECT-TYPE
        SYNTAX Counter64
        MAX-ACCESS read-only
        STATUS current
        DESCRIPTION
            "DataPmMonValue."
        ::= { ethvcgportPmvar2HisEntry 4 }

    -- 1.3.6.1.4.1.2011.2.25.3.70.20.149.140.1.5
    ethvcgportPmvar2HisStartTime OBJECT-TYPE
        SYNTAX DateAndTime
        MAX-ACCESS read-only
        STATUS current
        DESCRIPTION
            "Start Time."
        ::= { ethvcgportPmvar2HisEntry 5 }

    -- 1.3.6.1.4.1.2011.2.25.3.70.20.149.140.1.6
    ethvcgportPmvar2HisEndTime OBJECT-TYPE
        SYNTAX DateAndTime
        MAX-ACCESS read-only
        STATUS current
        DESCRIPTION
            "End Time."
        ::= { ethvcgportPmvar2HisEntry 6 }

    -- 1.3.6.1.4.1.2011.2.25.3.70.20.149.140.1.7
    ethvcgportPmvar2HisVldty OBJECT-TYPE
        SYNTAX ValidflagType
        MAX-ACCESS read-only
        STATUS current
        DESCRIPTION
            "Validity."
        ::= { ethvcgportPmvar2HisEntry 7 }

    -- 1.3.6.1.4.1.2011.2.25.3.70.20.209
    portflow OBJECT IDENTIFIER ::= { rtnData 209 }

    -- 1.3.6.1.4.1.2011.2.25.3.70.20.209.100
    portflowPmCurTable OBJECT-TYPE
        SYNTAX SEQUENCE OF PortflowPmCurEntry
        MAX-ACCESS not-accessible
        STATUS current
        DESCRIPTION
            "portflowDataPm30sCur."
        ::= { portflow 100 }

    -- 1.3.6.1.4.1.2011.2.25.3.70.20.209.100.1
    portflowPmCurEntry OBJECT-TYPE
        SYNTAX PortflowPmCurEntry
        MAX-ACCESS not-accessible
        STATUS current
        DESCRIPTION
            "portflowPmCur."
        INDEX{ portflowPmCurEid,portflowPmCurParaLen, portflowPmCurPara }
        ::= { portflowPmCurTable 1 }

    PortflowPmCurEntry ::=
        SEQUENCE {
            portflowPmCurEid
                DataPmEventType,
            portflowPmCurParaLen
                Unsigned32,
            portflowPmCurPara
                OCTET STRING,
            portflowPmCurMonValue
                Counter64,
            portflowPmCurDatetime
                DateAndTime
        }

    -- 1.3.6.1.4.1.2011.2.25.3.70.20.209.100.1.1
    portflowPmCurEid OBJECT-TYPE
        SYNTAX DataPmEventType
        MAX-ACCESS read-only
        STATUS current
        DESCRIPTION
            "DataPmEid."
        ::= { portflowPmCurEntry 1 }

    -- 1.3.6.1.4.1.2011.2.25.3.70.20.209.100.1.2
    portflowPmCurParaLen OBJECT-TYPE
        SYNTAX Unsigned32
        MAX-ACCESS read-only
        STATUS current
        DESCRIPTION
            "ParaLen."
        ::= { portflowPmCurEntry 2 }

    -- 1.3.6.1.4.1.2011.2.25.3.70.20.209.100.1.3
    portflowPmCurPara OBJECT-TYPE
        SYNTAX OCTET STRING
        MAX-ACCESS read-only
        STATUS current
        DESCRIPTION
            "para"
        ::= { portflowPmCurEntry 3 }

    -- 1.3.6.1.4.1.2011.2.25.3.70.20.209.100.1.4
    portflowPmCurMonValue OBJECT-TYPE
        SYNTAX Counter64
        MAX-ACCESS read-only
        STATUS current
        DESCRIPTION
            "DataPmMonValue."
        ::= { portflowPmCurEntry 4 }

    -- 1.3.6.1.4.1.2011.2.25.3.70.20.209.100.1.5
    portflowPmCurDatetime OBJECT-TYPE
        SYNTAX DateAndTime
        MAX-ACCESS read-only
        STATUS current
        DESCRIPTION
            "Start Time."
        ::= { portflowPmCurEntry 5 }

    -- 1.3.6.1.4.1.2011.2.25.3.70.20.209.110
    portflowPm30sHisTable OBJECT-TYPE
        SYNTAX SEQUENCE OF PortflowPm30sHisEntry
        MAX-ACCESS not-accessible
        STATUS current
        DESCRIPTION
            "portflowDataPm30sHis."
        ::= { portflow 110 }

    -- 1.3.6.1.4.1.2011.2.25.3.70.20.209.110.1
    portflowPm30sHisEntry OBJECT-TYPE
        SYNTAX PortflowPm30sHisEntry
        MAX-ACCESS not-accessible
        STATUS current
        DESCRIPTION
            "portflowDataPm30sHis."
        INDEX{ portflowPm30sHisEid,portflowPm30sHisParaLen,portflowPm30sHisPara,portflowPm30sHisStartTime,portflowPm30sHisEndTime }
        ::= { portflowPm30sHisTable 1 }

    PortflowPm30sHisEntry ::=
        SEQUENCE {
            portflowPm30sHisEid
                DataPmEventType,
            portflowPm30sHisParaLen
                Unsigned32,
            portflowPm30sHisPara
                OCTET STRING,
            portflowPm30sHisMonValue
                Counter64,
            portflowPm30sHisStartTime
                DateAndTime,
            portflowPm30sHisEndTime
                DateAndTime,
            portflowPm30sHisVldty
                ValidflagType
        }

    -- 1.3.6.1.4.1.2011.2.25.3.70.20.209.110.1.1
    portflowPm30sHisEid OBJECT-TYPE
        SYNTAX DataPmEventType
        MAX-ACCESS read-only
        STATUS current
        DESCRIPTION
            "DataPmEid."
        ::= { portflowPm30sHisEntry 1 }

    -- 1.3.6.1.4.1.2011.2.25.3.70.20.209.110.1.2
    portflowPm30sHisParaLen OBJECT-TYPE
        SYNTAX Unsigned32
        MAX-ACCESS read-only
        STATUS current
        DESCRIPTION
            "ParaLen."
        ::= { portflowPm30sHisEntry 2 }

    -- 1.3.6.1.4.1.2011.2.25.3.70.20.209.110.1.3
    portflowPm30sHisPara OBJECT-TYPE
        SYNTAX OCTET STRING(SIZE (0..100))
        MAX-ACCESS read-only
        STATUS current
        DESCRIPTION
            "para"
        ::= { portflowPm30sHisEntry 3 }

    -- 1.3.6.1.4.1.2011.2.25.3.70.20.209.110.1.4
    portflowPm30sHisMonValue OBJECT-TYPE
        SYNTAX Counter64
        MAX-ACCESS read-only
        STATUS current
        DESCRIPTION
            "DataPmMonValue."
        ::= { portflowPm30sHisEntry 4 }

    -- 1.3.6.1.4.1.2011.2.25.3.70.20.209.110.1.5
    portflowPm30sHisStartTime OBJECT-TYPE
        SYNTAX DateAndTime
        MAX-ACCESS read-only
        STATUS current
        DESCRIPTION
            "Start Time."
        ::= { portflowPm30sHisEntry 5 }

    -- 1.3.6.1.4.1.2011.2.25.3.70.20.209.110.1.6
    portflowPm30sHisEndTime OBJECT-TYPE
        SYNTAX DateAndTime
        MAX-ACCESS read-only
        STATUS current
        DESCRIPTION
            "End Time."
        ::= { portflowPm30sHisEntry 6 }

    -- 1.3.6.1.4.1.2011.2.25.3.70.20.209.110.1.7
    portflowPm30sHisVldty OBJECT-TYPE
        SYNTAX ValidflagType
        MAX-ACCESS read-only
        STATUS current
        DESCRIPTION
            "Validity."
        ::= { portflowPm30sHisEntry 7 }

    -- 1.3.6.1.4.1.2011.2.25.3.70.20.209.120
    portflowPm30mHisTable OBJECT-TYPE
        SYNTAX SEQUENCE OF PortflowPm30mHisEntry
        MAX-ACCESS not-accessible
        STATUS current
        DESCRIPTION
            "portflowPm30mHis."
        ::= { portflow 120 }

    -- 1.3.6.1.4.1.2011.2.25.3.70.20.209.120.1
    portflowPm30mHisEntry OBJECT-TYPE
        SYNTAX PortflowPm30mHisEntry
        MAX-ACCESS not-accessible
        STATUS current
        DESCRIPTION
            "portflowPm30mHis."
        INDEX{ portflowPm30mHisEid,portflowPm30mHisParaLen,portflowPm30mHisPara,portflowPm30mHisStartTime,portflowPm30mHisEndTime }
        ::= { portflowPm30mHisTable 1 }

    PortflowPm30mHisEntry ::=
        SEQUENCE {
            portflowPm30mHisEid
                DataPmEventType,
            portflowPm30mHisParaLen
                Unsigned32,
            portflowPm30mHisPara
                OCTET STRING,
            portflowPm30mHisMonValue
                Counter64,
            portflowPm30mHisStartTime
                DateAndTime,
            portflowPm30mHisEndTime
                DateAndTime,
            portflowPm30mHisVldty
                ValidflagType
        }

    -- 1.3.6.1.4.1.2011.2.25.3.70.20.209.120.1.1
    portflowPm30mHisEid OBJECT-TYPE
        SYNTAX DataPmEventType
        MAX-ACCESS read-only
        STATUS current
        DESCRIPTION
            "DataPmEid."
        ::= { portflowPm30mHisEntry 1 }

    -- 1.3.6.1.4.1.2011.2.25.3.70.20.209.120.1.2
    portflowPm30mHisParaLen OBJECT-TYPE
        SYNTAX Unsigned32
        MAX-ACCESS read-only
        STATUS current
        DESCRIPTION
            "ParaLen."
        ::= { portflowPm30mHisEntry 2 }

    -- 1.3.6.1.4.1.2011.2.25.3.70.20.209.120.1.3
    portflowPm30mHisPara OBJECT-TYPE
        SYNTAX OCTET STRING(SIZE (0..100))
        MAX-ACCESS read-only
        STATUS current
        DESCRIPTION
            "para"
        ::= { portflowPm30mHisEntry 3 }

    -- 1.3.6.1.4.1.2011.2.25.3.70.20.209.120.1.4
    portflowPm30mHisMonValue OBJECT-TYPE
        SYNTAX Counter64
        MAX-ACCESS read-only
        STATUS current
        DESCRIPTION
            "DataPmMonValue."
        ::= { portflowPm30mHisEntry 4 }

    -- 1.3.6.1.4.1.2011.2.25.3.70.20.209.120.1.5
    portflowPm30mHisStartTime OBJECT-TYPE
        SYNTAX DateAndTime
        MAX-ACCESS read-only
        STATUS current
        DESCRIPTION
            "Start Time."
        ::= { portflowPm30mHisEntry 5 }

    -- 1.3.6.1.4.1.2011.2.25.3.70.20.209.120.1.6
    portflowPm30mHisEndTime OBJECT-TYPE
        SYNTAX DateAndTime
        MAX-ACCESS read-only
        STATUS current
        DESCRIPTION
            "End Time."
        ::= { portflowPm30mHisEntry 6 }

    -- 1.3.6.1.4.1.2011.2.25.3.70.20.209.120.1.7
    portflowPm30mHisVldty OBJECT-TYPE
        SYNTAX ValidflagType
        MAX-ACCESS read-only
        STATUS current
        DESCRIPTION
            "Validity."
        ::= { portflowPm30mHisEntry 7 }

    -- 1.3.6.1.4.1.2011.2.25.3.70.20.209.130
    portflowPmvar1HisTable OBJECT-TYPE
        SYNTAX SEQUENCE OF PortflowPmvar1HisEntry
        MAX-ACCESS not-accessible
        STATUS current
        DESCRIPTION
            "portflowPmvar1His."
        ::= { portflow 130 }

    -- 1.3.6.1.4.1.2011.2.25.3.70.20.209.130.1
    portflowPmvar1HisEntry OBJECT-TYPE
        SYNTAX PortflowPmvar1HisEntry
        MAX-ACCESS not-accessible
        STATUS current
        DESCRIPTION
            "portflowPmvar1His."
        INDEX{ portflowPmvar1HisEid,portflowPmvar1HisParaLen,portflowPmvar1HisPara,portflowPmvar1HisStartTime,portflowPmvar1HisEndTime }
        ::= { portflowPmvar1HisTable 1 }

    PortflowPmvar1HisEntry ::=
        SEQUENCE {
            portflowPmvar1HisEid
                DataPmEventType,
            portflowPmvar1HisParaLen
                Unsigned32,
            portflowPmvar1HisPara
                OCTET STRING,
            portflowPmvar1HisMonValue
                Counter64,
            portflowPmvar1HisStartTime
                DateAndTime,
            portflowPmvar1HisEndTime
                DateAndTime,
            portflowPmvar1HisVldty
                ValidflagType
        }

    -- 1.3.6.1.4.1.2011.2.25.3.70.20.209.130.1.1
    portflowPmvar1HisEid OBJECT-TYPE
        SYNTAX DataPmEventType
        MAX-ACCESS read-only
        STATUS current
        DESCRIPTION
            "DataPmEid."
        ::= { portflowPmvar1HisEntry 1 }

    -- 1.3.6.1.4.1.2011.2.25.3.70.20.209.130.1.2
    portflowPmvar1HisParaLen OBJECT-TYPE
        SYNTAX Unsigned32
        MAX-ACCESS read-only
        STATUS current
        DESCRIPTION
            "ParaLen."
        ::= { portflowPmvar1HisEntry 2 }

    -- 1.3.6.1.4.1.2011.2.25.3.70.20.209.130.1.3
    portflowPmvar1HisPara OBJECT-TYPE
        SYNTAX OCTET STRING (SIZE (0..100))
        MAX-ACCESS read-only
        STATUS current
        DESCRIPTION
            "para"
        ::= { portflowPmvar1HisEntry 3 }

    -- 1.3.6.1.4.1.2011.2.25.3.70.20.209.130.1.4
    portflowPmvar1HisMonValue OBJECT-TYPE
        SYNTAX Counter64
        MAX-ACCESS read-only
        STATUS current
        DESCRIPTION
            "DataPmMonValue."
        ::= { portflowPmvar1HisEntry 4 }

    -- 1.3.6.1.4.1.2011.2.25.3.70.20.209.130.1.5
    portflowPmvar1HisStartTime OBJECT-TYPE
        SYNTAX DateAndTime
        MAX-ACCESS read-only
        STATUS current
        DESCRIPTION
            "Start Time."
        ::= { portflowPmvar1HisEntry 5 }

    -- 1.3.6.1.4.1.2011.2.25.3.70.20.209.130.1.6
    portflowPmvar1HisEndTime OBJECT-TYPE
        SYNTAX DateAndTime
        MAX-ACCESS read-only
        STATUS current
        DESCRIPTION
            "End Time."
        ::= { portflowPmvar1HisEntry 6 }

    -- 1.3.6.1.4.1.2011.2.25.3.70.20.209.130.1.7
    portflowPmvar1HisVldty OBJECT-TYPE
        SYNTAX ValidflagType
        MAX-ACCESS read-only
        STATUS current
        DESCRIPTION
            "Validity."
        ::= { portflowPmvar1HisEntry 7 }

    -- 1.3.6.1.4.1.2011.2.25.3.70.20.209.140
    portflowPmvar2HisTable OBJECT-TYPE
        SYNTAX SEQUENCE OF PortflowPmvar2HisEntry
        MAX-ACCESS not-accessible
        STATUS current
        DESCRIPTION
            "portflowPmvar2His."
        ::= { portflow 140 }

    -- 1.3.6.1.4.1.2011.2.25.3.70.20.209.140.1
    portflowPmvar2HisEntry OBJECT-TYPE
        SYNTAX PortflowPmvar2HisEntry
        MAX-ACCESS not-accessible
        STATUS current
        DESCRIPTION
            "portflowPmvar2His."
        INDEX{ portflowPmvar2HisEid,portflowPmvar2HisParaLen,portflowPmvar2HisPara,portflowPmvar2HisStartTime,portflowPmvar2HisEndTime }
        ::= { portflowPmvar2HisTable 1 }

    PortflowPmvar2HisEntry ::=
        SEQUENCE {
            portflowPmvar2HisEid
                DataPmEventType,
            portflowPmvar2HisParaLen
                Unsigned32,
            portflowPmvar2HisPara
                OCTET STRING,
            portflowPmvar2HisMonValue
                Counter64,
            portflowPmvar2HisStartTime
                DateAndTime,
            portflowPmvar2HisEndTime
                DateAndTime,
            portflowPmvar2HisVldty
                ValidflagType
        }

    -- 1.3.6.1.4.1.2011.2.25.3.70.20.209.140.1.1
    portflowPmvar2HisEid OBJECT-TYPE
        SYNTAX DataPmEventType
        MAX-ACCESS read-only
        STATUS current
        DESCRIPTION
            "DataPmEid."
        ::= { portflowPmvar2HisEntry 1 }

    -- 1.3.6.1.4.1.2011.2.25.3.70.20.209.140.1.2
    portflowPmvar2HisParaLen OBJECT-TYPE
        SYNTAX Unsigned32
        MAX-ACCESS read-only
        STATUS current
        DESCRIPTION
            "ParaLen."
        ::= { portflowPmvar2HisEntry 2 }

    -- 1.3.6.1.4.1.2011.2.25.3.70.20.209.140.1.3
    portflowPmvar2HisPara OBJECT-TYPE
        SYNTAX OCTET STRING(SIZE (0..100))
        MAX-ACCESS read-only
        STATUS current
        DESCRIPTION
            "para"
        ::= { portflowPmvar2HisEntry 3 }

    -- 1.3.6.1.4.1.2011.2.25.3.70.20.209.140.1.4
    portflowPmvar2HisMonValue OBJECT-TYPE
        SYNTAX Counter64
        MAX-ACCESS read-only
        STATUS current
        DESCRIPTION
            "DataPmMonValue."
        ::= { portflowPmvar2HisEntry 4 }

    -- 1.3.6.1.4.1.2011.2.25.3.70.20.209.140.1.5
    portflowPmvar2HisStartTime OBJECT-TYPE
        SYNTAX DateAndTime
        MAX-ACCESS read-only
        STATUS current
        DESCRIPTION
            "Start Time."
        ::= { portflowPmvar2HisEntry 5 }

    -- 1.3.6.1.4.1.2011.2.25.3.70.20.209.140.1.6
    portflowPmvar2HisEndTime OBJECT-TYPE
        SYNTAX DateAndTime
        MAX-ACCESS read-only
        STATUS current
        DESCRIPTION
            "End Time."
        ::= { portflowPmvar2HisEntry 6 }

    -- 1.3.6.1.4.1.2011.2.25.3.70.20.209.140.1.7
    portflowPmvar2HisVldty OBJECT-TYPE
        SYNTAX ValidflagType
        MAX-ACCESS read-only
        STATUS current
        DESCRIPTION
            "Validity."
        ::= { portflowPmvar2HisEntry 7 }

    -- 1.3.6.1.4.1.2011.2.25.3.70.20.212
    cvlanpriofds OBJECT IDENTIFIER ::= { rtnData 212 }

    -- 1.3.6.1.4.1.2011.2.25.3.70.20.212.100
    cvlanpriofdsPmCurTable OBJECT-TYPE
        SYNTAX SEQUENCE OF CvlanpriofdsPmCurEntry
        MAX-ACCESS not-accessible
        STATUS current
        DESCRIPTION
            "cvlanpriofdsDataPm30sCur."
        ::= { cvlanpriofds 100 }

    -- 1.3.6.1.4.1.2011.2.25.3.70.20.212.100.1
    cvlanpriofdsPmCurEntry OBJECT-TYPE
        SYNTAX CvlanpriofdsPmCurEntry
        MAX-ACCESS not-accessible
        STATUS current
        DESCRIPTION
            "cvlanpriofdsPmCur."
        INDEX{ cvlanpriofdsPmCurEid,cvlanpriofdsPmCurParaLen, cvlanpriofdsPmCurPara }
        ::= { cvlanpriofdsPmCurTable 1 }

    CvlanpriofdsPmCurEntry ::=
        SEQUENCE {
            cvlanpriofdsPmCurEid
                DataPmEventType,
            cvlanpriofdsPmCurParaLen
                Unsigned32,
            cvlanpriofdsPmCurPara
                OCTET STRING,
            cvlanpriofdsPmCurMonValue
                Counter64,
            cvlanpriofdsPmCurDatetime
                DateAndTime
        }

    -- 1.3.6.1.4.1.2011.2.25.3.70.20.212.100.1.1
    cvlanpriofdsPmCurEid OBJECT-TYPE
        SYNTAX DataPmEventType
        MAX-ACCESS read-only
        STATUS current
        DESCRIPTION
            "DataPmEid."
        ::= { cvlanpriofdsPmCurEntry 1 }

    -- 1.3.6.1.4.1.2011.2.25.3.70.20.212.100.1.2
    cvlanpriofdsPmCurParaLen OBJECT-TYPE
        SYNTAX Unsigned32
        MAX-ACCESS read-only
        STATUS current
        DESCRIPTION
            "ParaLen."
        ::= { cvlanpriofdsPmCurEntry 2 }

    -- 1.3.6.1.4.1.2011.2.25.3.70.20.212.100.1.3
    cvlanpriofdsPmCurPara OBJECT-TYPE
        SYNTAX OCTET STRING
        MAX-ACCESS read-only
        STATUS current
        DESCRIPTION
            "para"
        ::= { cvlanpriofdsPmCurEntry 3 }

    -- 1.3.6.1.4.1.2011.2.25.3.70.20.212.100.1.4
    cvlanpriofdsPmCurMonValue OBJECT-TYPE
        SYNTAX Counter64
        MAX-ACCESS read-only
        STATUS current
        DESCRIPTION
            "DataPmMonValue."
        ::= { cvlanpriofdsPmCurEntry 4 }

    -- 1.3.6.1.4.1.2011.2.25.3.70.20.212.100.1.5
    cvlanpriofdsPmCurDatetime OBJECT-TYPE
        SYNTAX DateAndTime
        MAX-ACCESS read-only
        STATUS current
        DESCRIPTION
            "Start Time."
        ::= { cvlanpriofdsPmCurEntry 5 }

    -- 1.3.6.1.4.1.2011.2.25.3.70.20.212.110
    cvlanpriofdsPm30sHisTable OBJECT-TYPE
        SYNTAX SEQUENCE OF CvlanpriofdsPm30sHisEntry
        MAX-ACCESS not-accessible
        STATUS current
        DESCRIPTION
            "cvlanpriofdsDataPm30sHis."
        ::= { cvlanpriofds 110 }

    -- 1.3.6.1.4.1.2011.2.25.3.70.20.212.110.1
    cvlanpriofdsPm30sHisEntry OBJECT-TYPE
        SYNTAX CvlanpriofdsPm30sHisEntry
        MAX-ACCESS not-accessible
        STATUS current
        DESCRIPTION
            "cvlanpriofdsDataPm30sHis."
        INDEX{ cvlanpriofdsPm30sHisEid,cvlanpriofdsPm30sHisParaLen,cvlanpriofdsPm30sHisPara,cvlanpriofdsPm30sHisStartTime,cvlanpriofdsPm30sHisEndTime }
        ::= { cvlanpriofdsPm30sHisTable 1 }

    CvlanpriofdsPm30sHisEntry ::=
        SEQUENCE {
            cvlanpriofdsPm30sHisEid
                DataPmEventType,
            cvlanpriofdsPm30sHisParaLen
                Unsigned32,
            cvlanpriofdsPm30sHisPara
                OCTET STRING,
            cvlanpriofdsPm30sHisMonValue
                Counter64,
            cvlanpriofdsPm30sHisStartTime
                DateAndTime,
            cvlanpriofdsPm30sHisEndTime
                DateAndTime,
            cvlanpriofdsPm30sHisVldty
                ValidflagType
        }

    -- 1.3.6.1.4.1.2011.2.25.3.70.20.212.110.1.1
    cvlanpriofdsPm30sHisEid OBJECT-TYPE
        SYNTAX DataPmEventType
        MAX-ACCESS read-only
        STATUS current
        DESCRIPTION
            "DataPmEid."
        ::= { cvlanpriofdsPm30sHisEntry 1 }

    -- 1.3.6.1.4.1.2011.2.25.3.70.20.212.110.1.2
    cvlanpriofdsPm30sHisParaLen OBJECT-TYPE
        SYNTAX Unsigned32
        MAX-ACCESS read-only
        STATUS current
        DESCRIPTION
            "ParaLen."
        ::= { cvlanpriofdsPm30sHisEntry 2 }

    -- 1.3.6.1.4.1.2011.2.25.3.70.20.212.110.1.3
    cvlanpriofdsPm30sHisPara OBJECT-TYPE
        SYNTAX OCTET STRING(SIZE (0..100))
        MAX-ACCESS read-only
        STATUS current
        DESCRIPTION
            "para"
        ::= { cvlanpriofdsPm30sHisEntry 3 }

    -- 1.3.6.1.4.1.2011.2.25.3.70.20.212.110.1.4
    cvlanpriofdsPm30sHisMonValue OBJECT-TYPE
        SYNTAX Counter64
        MAX-ACCESS read-only
        STATUS current
        DESCRIPTION
            "DataPmMonValue."
        ::= { cvlanpriofdsPm30sHisEntry 4 }

    -- 1.3.6.1.4.1.2011.2.25.3.70.20.212.110.1.5
    cvlanpriofdsPm30sHisStartTime OBJECT-TYPE
        SYNTAX DateAndTime
        MAX-ACCESS read-only
        STATUS current
        DESCRIPTION
            "Start Time."
        ::= { cvlanpriofdsPm30sHisEntry 5 }

    -- 1.3.6.1.4.1.2011.2.25.3.70.20.212.110.1.6
    cvlanpriofdsPm30sHisEndTime OBJECT-TYPE
        SYNTAX DateAndTime
        MAX-ACCESS read-only
        STATUS current
        DESCRIPTION
            "End Time."
        ::= { cvlanpriofdsPm30sHisEntry 6 }

    -- 1.3.6.1.4.1.2011.2.25.3.70.20.212.110.1.7
    cvlanpriofdsPm30sHisVldty OBJECT-TYPE
        SYNTAX ValidflagType
        MAX-ACCESS read-only
        STATUS current
        DESCRIPTION
            "Validity."
        ::= { cvlanpriofdsPm30sHisEntry 7 }

    -- 1.3.6.1.4.1.2011.2.25.3.70.20.212.120
    cvlanpriofdsPm30mHisTable OBJECT-TYPE
        SYNTAX SEQUENCE OF CvlanpriofdsPm30mHisEntry
        MAX-ACCESS not-accessible
        STATUS current
        DESCRIPTION
            "cvlanpriofdsPm30mHis."
        ::= { cvlanpriofds 120 }

    -- 1.3.6.1.4.1.2011.2.25.3.70.20.212.120.1
    cvlanpriofdsPm30mHisEntry OBJECT-TYPE
        SYNTAX CvlanpriofdsPm30mHisEntry
        MAX-ACCESS not-accessible
        STATUS current
        DESCRIPTION
            "cvlanpriofdsPm30mHis."
        INDEX{ cvlanpriofdsPm30mHisEid,cvlanpriofdsPm30mHisParaLen,cvlanpriofdsPm30mHisPara,cvlanpriofdsPm30mHisStartTime,cvlanpriofdsPm30mHisEndTime }
        ::= { cvlanpriofdsPm30mHisTable 1 }

    CvlanpriofdsPm30mHisEntry ::=
        SEQUENCE {
            cvlanpriofdsPm30mHisEid
                DataPmEventType,
            cvlanpriofdsPm30mHisParaLen
                Unsigned32,
            cvlanpriofdsPm30mHisPara
                OCTET STRING,
            cvlanpriofdsPm30mHisMonValue
                Counter64,
            cvlanpriofdsPm30mHisStartTime
                DateAndTime,
            cvlanpriofdsPm30mHisEndTime
                DateAndTime,
            cvlanpriofdsPm30mHisVldty
                ValidflagType
        }

    -- 1.3.6.1.4.1.2011.2.25.3.70.20.212.120.1.1
    cvlanpriofdsPm30mHisEid OBJECT-TYPE
        SYNTAX DataPmEventType
        MAX-ACCESS read-only
        STATUS current
        DESCRIPTION
            "DataPmEid."
        ::= { cvlanpriofdsPm30mHisEntry 1 }

    -- 1.3.6.1.4.1.2011.2.25.3.70.20.212.120.1.2
    cvlanpriofdsPm30mHisParaLen OBJECT-TYPE
        SYNTAX Unsigned32
        MAX-ACCESS read-only
        STATUS current
        DESCRIPTION
            "ParaLen."
        ::= { cvlanpriofdsPm30mHisEntry 2 }

    -- 1.3.6.1.4.1.2011.2.25.3.70.20.212.120.1.3
    cvlanpriofdsPm30mHisPara OBJECT-TYPE
        SYNTAX OCTET STRING(SIZE (0..100))
        MAX-ACCESS read-only
        STATUS current
        DESCRIPTION
            "para"
        ::= { cvlanpriofdsPm30mHisEntry 3 }

    -- 1.3.6.1.4.1.2011.2.25.3.70.20.212.120.1.4
    cvlanpriofdsPm30mHisMonValue OBJECT-TYPE
        SYNTAX Counter64
        MAX-ACCESS read-only
        STATUS current
        DESCRIPTION
            "DataPmMonValue."
        ::= { cvlanpriofdsPm30mHisEntry 4 }

    -- 1.3.6.1.4.1.2011.2.25.3.70.20.212.120.1.5
    cvlanpriofdsPm30mHisStartTime OBJECT-TYPE
        SYNTAX DateAndTime
        MAX-ACCESS read-only
        STATUS current
        DESCRIPTION
            "Start Time."
        ::= { cvlanpriofdsPm30mHisEntry 5 }

    -- 1.3.6.1.4.1.2011.2.25.3.70.20.212.120.1.6
    cvlanpriofdsPm30mHisEndTime OBJECT-TYPE
        SYNTAX DateAndTime
        MAX-ACCESS read-only
        STATUS current
        DESCRIPTION
            "End Time."
        ::= { cvlanpriofdsPm30mHisEntry 6 }

    -- 1.3.6.1.4.1.2011.2.25.3.70.20.212.120.1.7
    cvlanpriofdsPm30mHisVldty OBJECT-TYPE
        SYNTAX ValidflagType
        MAX-ACCESS read-only
        STATUS current
        DESCRIPTION
            "Validity."
        ::= { cvlanpriofdsPm30mHisEntry 7 }

    -- 1.3.6.1.4.1.2011.2.25.3.70.20.212.130
    cvlanpriofdsPmvar1HisTable OBJECT-TYPE
        SYNTAX SEQUENCE OF CvlanpriofdsPmvar1HisEntry
        MAX-ACCESS not-accessible
        STATUS current
        DESCRIPTION
            "cvlanpriofdsPmvar1His."
        ::= { cvlanpriofds 130 }

    -- 1.3.6.1.4.1.2011.2.25.3.70.20.212.130.1
    cvlanpriofdsPmvar1HisEntry OBJECT-TYPE
        SYNTAX CvlanpriofdsPmvar1HisEntry
        MAX-ACCESS not-accessible
        STATUS current
        DESCRIPTION
            "cvlanpriofdsPmvar1His."
        INDEX{ cvlanpriofdsPmvar1HisEid,cvlanpriofdsPmvar1HisParaLen,cvlanpriofdsPmvar1HisPara,cvlanpriofdsPmvar1HisStartTime,cvlanpriofdsPmvar1HisEndTime }
        ::= { cvlanpriofdsPmvar1HisTable 1 }

    CvlanpriofdsPmvar1HisEntry ::=
        SEQUENCE {
            cvlanpriofdsPmvar1HisEid
                DataPmEventType,
            cvlanpriofdsPmvar1HisParaLen
                Unsigned32,
            cvlanpriofdsPmvar1HisPara
                OCTET STRING,
            cvlanpriofdsPmvar1HisMonValue
                Counter64,
            cvlanpriofdsPmvar1HisStartTime
                DateAndTime,
            cvlanpriofdsPmvar1HisEndTime
                DateAndTime,
            cvlanpriofdsPmvar1HisVldty
                ValidflagType
        }

    -- 1.3.6.1.4.1.2011.2.25.3.70.20.212.130.1.1
    cvlanpriofdsPmvar1HisEid OBJECT-TYPE
        SYNTAX DataPmEventType
        MAX-ACCESS read-only
        STATUS current
        DESCRIPTION
            "DataPmEid."
        ::= { cvlanpriofdsPmvar1HisEntry 1 }

    -- 1.3.6.1.4.1.2011.2.25.3.70.20.212.130.1.2
    cvlanpriofdsPmvar1HisParaLen OBJECT-TYPE
        SYNTAX Unsigned32
        MAX-ACCESS read-only
        STATUS current
        DESCRIPTION
            "ParaLen."
        ::= { cvlanpriofdsPmvar1HisEntry 2 }

    -- 1.3.6.1.4.1.2011.2.25.3.70.20.212.130.1.3
    cvlanpriofdsPmvar1HisPara OBJECT-TYPE
        SYNTAX OCTET STRING (SIZE (0..100))
        MAX-ACCESS read-only
        STATUS current
        DESCRIPTION
            "para"
        ::= { cvlanpriofdsPmvar1HisEntry 3 }

    -- 1.3.6.1.4.1.2011.2.25.3.70.20.212.130.1.4
    cvlanpriofdsPmvar1HisMonValue OBJECT-TYPE
        SYNTAX Counter64
        MAX-ACCESS read-only
        STATUS current
        DESCRIPTION
            "DataPmMonValue."
        ::= { cvlanpriofdsPmvar1HisEntry 4 }

    -- 1.3.6.1.4.1.2011.2.25.3.70.20.212.130.1.5
    cvlanpriofdsPmvar1HisStartTime OBJECT-TYPE
        SYNTAX DateAndTime
        MAX-ACCESS read-only
        STATUS current
        DESCRIPTION
            "Start Time."
        ::= { cvlanpriofdsPmvar1HisEntry 5 }

    -- 1.3.6.1.4.1.2011.2.25.3.70.20.212.130.1.6
    cvlanpriofdsPmvar1HisEndTime OBJECT-TYPE
        SYNTAX DateAndTime
        MAX-ACCESS read-only
        STATUS current
        DESCRIPTION
            "End Time."
        ::= { cvlanpriofdsPmvar1HisEntry 6 }

    -- 1.3.6.1.4.1.2011.2.25.3.70.20.212.130.1.7
    cvlanpriofdsPmvar1HisVldty OBJECT-TYPE
        SYNTAX ValidflagType
        MAX-ACCESS read-only
        STATUS current
        DESCRIPTION
            "Validity."
        ::= { cvlanpriofdsPmvar1HisEntry 7 }

    -- 1.3.6.1.4.1.2011.2.25.3.70.20.212.140
    cvlanpriofdsPmvar2HisTable OBJECT-TYPE
        SYNTAX SEQUENCE OF CvlanpriofdsPmvar2HisEntry
        MAX-ACCESS not-accessible
        STATUS current
        DESCRIPTION
            "cvlanpriofdsPmvar2His."
        ::= { cvlanpriofds 140 }

    -- 1.3.6.1.4.1.2011.2.25.3.70.20.212.140.1
    cvlanpriofdsPmvar2HisEntry OBJECT-TYPE
        SYNTAX CvlanpriofdsPmvar2HisEntry
        MAX-ACCESS not-accessible
        STATUS current
        DESCRIPTION
            "cvlanpriofdsPmvar2His."
        INDEX{ cvlanpriofdsPmvar2HisEid,cvlanpriofdsPmvar2HisParaLen,cvlanpriofdsPmvar2HisPara,cvlanpriofdsPmvar2HisStartTime,cvlanpriofdsPmvar2HisEndTime }
        ::= { cvlanpriofdsPmvar2HisTable 1 }

    CvlanpriofdsPmvar2HisEntry ::=
        SEQUENCE {
            cvlanpriofdsPmvar2HisEid
                DataPmEventType,
            cvlanpriofdsPmvar2HisParaLen
                Unsigned32,
            cvlanpriofdsPmvar2HisPara
                OCTET STRING,
            cvlanpriofdsPmvar2HisMonValue
                Counter64,
            cvlanpriofdsPmvar2HisStartTime
                DateAndTime,
            cvlanpriofdsPmvar2HisEndTime
                DateAndTime,
            cvlanpriofdsPmvar2HisVldty
                ValidflagType
        }

    -- 1.3.6.1.4.1.2011.2.25.3.70.20.212.140.1.1
    cvlanpriofdsPmvar2HisEid OBJECT-TYPE
        SYNTAX DataPmEventType
        MAX-ACCESS read-only
        STATUS current
        DESCRIPTION
            "DataPmEid."
        ::= { cvlanpriofdsPmvar2HisEntry 1 }

    -- 1.3.6.1.4.1.2011.2.25.3.70.20.212.140.1.2
    cvlanpriofdsPmvar2HisParaLen OBJECT-TYPE
        SYNTAX Unsigned32
        MAX-ACCESS read-only
        STATUS current
        DESCRIPTION
            "ParaLen."
        ::= { cvlanpriofdsPmvar2HisEntry 2 }

    -- 1.3.6.1.4.1.2011.2.25.3.70.20.212.140.1.3
    cvlanpriofdsPmvar2HisPara OBJECT-TYPE
        SYNTAX OCTET STRING(SIZE (0..100))
        MAX-ACCESS read-only
        STATUS current
        DESCRIPTION
            "para"
        ::= { cvlanpriofdsPmvar2HisEntry 3 }

    -- 1.3.6.1.4.1.2011.2.25.3.70.20.212.140.1.4
    cvlanpriofdsPmvar2HisMonValue OBJECT-TYPE
        SYNTAX Counter64
        MAX-ACCESS read-only
        STATUS current
        DESCRIPTION
            "DataPmMonValue."
        ::= { cvlanpriofdsPmvar2HisEntry 4 }

    -- 1.3.6.1.4.1.2011.2.25.3.70.20.212.140.1.5
    cvlanpriofdsPmvar2HisStartTime OBJECT-TYPE
        SYNTAX DateAndTime
        MAX-ACCESS read-only
        STATUS current
        DESCRIPTION
            "Start Time."
        ::= { cvlanpriofdsPmvar2HisEntry 5 }

    -- 1.3.6.1.4.1.2011.2.25.3.70.20.212.140.1.6
    cvlanpriofdsPmvar2HisEndTime OBJECT-TYPE
        SYNTAX DateAndTime
        MAX-ACCESS read-only
        STATUS current
        DESCRIPTION
            "End Time."
        ::= { cvlanpriofdsPmvar2HisEntry 6 }

    -- 1.3.6.1.4.1.2011.2.25.3.70.20.212.140.1.7
    cvlanpriofdsPmvar2HisVldty OBJECT-TYPE
        SYNTAX ValidflagType
        MAX-ACCESS read-only
        STATUS current
        DESCRIPTION
            "Validity."
        ::= { cvlanpriofdsPmvar2HisEntry 7 }

    -- 1.3.6.1.4.1.2011.2.25.3.70.20.213
    svlanpriofds OBJECT IDENTIFIER ::= { rtnData 213 }

    -- 1.3.6.1.4.1.2011.2.25.3.70.20.213.100
    svlanpriofdsPmCurTable OBJECT-TYPE
        SYNTAX SEQUENCE OF SvlanpriofdsPmCurEntry
        MAX-ACCESS not-accessible
        STATUS current
        DESCRIPTION
            "svlanpriofdsDataPm30sCur."
        ::= { svlanpriofds 100 }

    -- 1.3.6.1.4.1.2011.2.25.3.70.20.213.100.1
    svlanpriofdsPmCurEntry OBJECT-TYPE
        SYNTAX SvlanpriofdsPmCurEntry
        MAX-ACCESS not-accessible
        STATUS current
        DESCRIPTION
            "svlanpriofdsPmCur."
        INDEX{ svlanpriofdsPmCurEid,svlanpriofdsPmCurParaLen,svlanpriofdsPmCurPara }
        ::= { svlanpriofdsPmCurTable 1 }

    SvlanpriofdsPmCurEntry ::=
        SEQUENCE {
            svlanpriofdsPmCurEid
                DataPmEventType,
            svlanpriofdsPmCurParaLen
                Unsigned32,
            svlanpriofdsPmCurPara
                OCTET STRING,
            svlanpriofdsPmCurMonValue
                Counter64,
            svlanpriofdsPmCurDatetime
                DateAndTime
        }

    -- 1.3.6.1.4.1.2011.2.25.3.70.20.213.100.1.1
    svlanpriofdsPmCurEid OBJECT-TYPE
        SYNTAX DataPmEventType
        MAX-ACCESS read-only
        STATUS current
        DESCRIPTION
            "DataPmEid."
        ::= { svlanpriofdsPmCurEntry 1 }

    -- 1.3.6.1.4.1.2011.2.25.3.70.20.213.100.1.2
    svlanpriofdsPmCurParaLen OBJECT-TYPE
        SYNTAX Unsigned32
        MAX-ACCESS read-only
        STATUS current
        DESCRIPTION
            "ParaLen."
        ::= { svlanpriofdsPmCurEntry 2 }

    -- 1.3.6.1.4.1.2011.2.25.3.70.20.213.100.1.3
    svlanpriofdsPmCurPara OBJECT-TYPE
        SYNTAX OCTET STRING
        MAX-ACCESS read-only
        STATUS current
        DESCRIPTION
            "para"
        ::= { svlanpriofdsPmCurEntry 3 }

    -- 1.3.6.1.4.1.2011.2.25.3.70.20.213.100.1.4
    svlanpriofdsPmCurMonValue OBJECT-TYPE
        SYNTAX Counter64
        MAX-ACCESS read-only
        STATUS current
        DESCRIPTION
            "DataPmMonValue."
        ::= { svlanpriofdsPmCurEntry 4 }

    -- 1.3.6.1.4.1.2011.2.25.3.70.20.213.100.1.5
    svlanpriofdsPmCurDatetime OBJECT-TYPE
        SYNTAX DateAndTime
        MAX-ACCESS read-only
        STATUS current
        DESCRIPTION
            "Start Time."
        ::= { svlanpriofdsPmCurEntry 5 }

    -- 1.3.6.1.4.1.2011.2.25.3.70.20.213.110
    svlanpriofdsPm30sHisTable OBJECT-TYPE
        SYNTAX SEQUENCE OF SvlanpriofdsPm30sHisEntry
        MAX-ACCESS not-accessible
        STATUS current
        DESCRIPTION
            "svlanpriofdsDataPm30sHis."
        ::= { svlanpriofds 110 }

    -- 1.3.6.1.4.1.2011.2.25.3.70.20.213.110.1
    svlanpriofdsPm30sHisEntry OBJECT-TYPE
        SYNTAX SvlanpriofdsPm30sHisEntry
        MAX-ACCESS not-accessible
        STATUS current
        DESCRIPTION
            "svlanpriofdsDataPm30sHis."
        INDEX{ svlanpriofdsPm30sHisEid,svlanpriofdsPm30sHisParaLen,svlanpriofdsPm30sHisPara,svlanpriofdsPm30sHisStartTime,svlanpriofdsPm30sHisEndTime }
        ::= { svlanpriofdsPm30sHisTable 1 }

    SvlanpriofdsPm30sHisEntry ::=
        SEQUENCE {
            svlanpriofdsPm30sHisEid
                DataPmEventType,
            svlanpriofdsPm30sHisParaLen
                Unsigned32,
            svlanpriofdsPm30sHisPara
                OCTET STRING,
            svlanpriofdsPm30sHisMonValue
                Counter64,
            svlanpriofdsPm30sHisStartTime
                DateAndTime,
            svlanpriofdsPm30sHisEndTime
                DateAndTime,
            svlanpriofdsPm30sHisVldty
                ValidflagType
        }

    -- 1.3.6.1.4.1.2011.2.25.3.70.20.213.110.1.1
    svlanpriofdsPm30sHisEid OBJECT-TYPE
        SYNTAX DataPmEventType
        MAX-ACCESS read-only
        STATUS current
        DESCRIPTION
            "DataPmEid."
        ::= { svlanpriofdsPm30sHisEntry 1 }

    -- 1.3.6.1.4.1.2011.2.25.3.70.20.213.110.1.2
    svlanpriofdsPm30sHisParaLen OBJECT-TYPE
        SYNTAX Unsigned32
        MAX-ACCESS read-only
        STATUS current
        DESCRIPTION
            "ParaLen."
        ::= { svlanpriofdsPm30sHisEntry 2 }

    -- 1.3.6.1.4.1.2011.2.25.3.70.20.213.110.1.3
    svlanpriofdsPm30sHisPara OBJECT-TYPE
        SYNTAX OCTET STRING(SIZE (0..100))
        MAX-ACCESS read-only
        STATUS current
        DESCRIPTION
            "para"
        ::= { svlanpriofdsPm30sHisEntry 3 }

    -- 1.3.6.1.4.1.2011.2.25.3.70.20.213.110.1.4
    svlanpriofdsPm30sHisMonValue OBJECT-TYPE
        SYNTAX Counter64
        MAX-ACCESS read-only
        STATUS current
        DESCRIPTION
            "DataPmMonValue."
        ::= { svlanpriofdsPm30sHisEntry 4 }

    -- 1.3.6.1.4.1.2011.2.25.3.70.20.213.110.1.5
    svlanpriofdsPm30sHisStartTime OBJECT-TYPE
        SYNTAX DateAndTime
        MAX-ACCESS read-only
        STATUS current
        DESCRIPTION
            "Start Time."
        ::= { svlanpriofdsPm30sHisEntry 5 }

    -- 1.3.6.1.4.1.2011.2.25.3.70.20.213.110.1.6
    svlanpriofdsPm30sHisEndTime OBJECT-TYPE
        SYNTAX DateAndTime
        MAX-ACCESS read-only
        STATUS current
        DESCRIPTION
            "End Time."
        ::= { svlanpriofdsPm30sHisEntry 6 }

    -- 1.3.6.1.4.1.2011.2.25.3.70.20.213.110.1.7
    svlanpriofdsPm30sHisVldty OBJECT-TYPE
        SYNTAX ValidflagType
        MAX-ACCESS read-only
        STATUS current
        DESCRIPTION
            "Validity."
        ::= { svlanpriofdsPm30sHisEntry 7 }

    -- 1.3.6.1.4.1.2011.2.25.3.70.20.213.120
    svlanpriofdsPm30mHisTable OBJECT-TYPE
        SYNTAX SEQUENCE OF SvlanpriofdsPm30mHisEntry
        MAX-ACCESS not-accessible
        STATUS current
        DESCRIPTION
            "svlanpriofdsPm30mHis."
        ::= { svlanpriofds 120 }

    -- 1.3.6.1.4.1.2011.2.25.3.70.20.213.120.1
    svlanpriofdsPm30mHisEntry OBJECT-TYPE
        SYNTAX SvlanpriofdsPm30mHisEntry
        MAX-ACCESS not-accessible
        STATUS current
        DESCRIPTION
            "svlanpriofdsPm30mHis."
        INDEX{ svlanpriofdsPm30mHisEid,svlanpriofdsPm30mHisParaLen,svlanpriofdsPm30mHisPara,svlanpriofdsPm30mHisStartTime,svlanpriofdsPm30mHisEndTime }
        ::= { svlanpriofdsPm30mHisTable 1 }

    SvlanpriofdsPm30mHisEntry ::=
        SEQUENCE {
            svlanpriofdsPm30mHisEid
                DataPmEventType,
            svlanpriofdsPm30mHisParaLen
                Unsigned32,
            svlanpriofdsPm30mHisPara
                OCTET STRING,
            svlanpriofdsPm30mHisMonValue
                Counter64,
            svlanpriofdsPm30mHisStartTime
                DateAndTime,
            svlanpriofdsPm30mHisEndTime
                DateAndTime,
            svlanpriofdsPm30mHisVldty
                ValidflagType
        }

    -- 1.3.6.1.4.1.2011.2.25.3.70.20.213.120.1.1
    svlanpriofdsPm30mHisEid OBJECT-TYPE
        SYNTAX DataPmEventType
        MAX-ACCESS read-only
        STATUS current
        DESCRIPTION
            "DataPmEid."
        ::= { svlanpriofdsPm30mHisEntry 1 }

    -- 1.3.6.1.4.1.2011.2.25.3.70.20.213.120.1.2
    svlanpriofdsPm30mHisParaLen OBJECT-TYPE
        SYNTAX Unsigned32
        MAX-ACCESS read-only
        STATUS current
        DESCRIPTION
            "ParaLen."
        ::= { svlanpriofdsPm30mHisEntry 2 }

    -- 1.3.6.1.4.1.2011.2.25.3.70.20.213.120.1.3
    svlanpriofdsPm30mHisPara OBJECT-TYPE
        SYNTAX OCTET STRING(SIZE (0..100))
        MAX-ACCESS read-only
        STATUS current
        DESCRIPTION
            "para"
        ::= { svlanpriofdsPm30mHisEntry 3 }

    -- 1.3.6.1.4.1.2011.2.25.3.70.20.213.120.1.4
    svlanpriofdsPm30mHisMonValue OBJECT-TYPE
        SYNTAX Counter64
        MAX-ACCESS read-only
        STATUS current
        DESCRIPTION
            "DataPmMonValue."
        ::= { svlanpriofdsPm30mHisEntry 4 }

    -- 1.3.6.1.4.1.2011.2.25.3.70.20.213.120.1.5
    svlanpriofdsPm30mHisStartTime OBJECT-TYPE
        SYNTAX DateAndTime
        MAX-ACCESS read-only
        STATUS current
        DESCRIPTION
            "Start Time."
        ::= { svlanpriofdsPm30mHisEntry 5 }

    -- 1.3.6.1.4.1.2011.2.25.3.70.20.213.120.1.6
    svlanpriofdsPm30mHisEndTime OBJECT-TYPE
        SYNTAX DateAndTime
        MAX-ACCESS read-only
        STATUS current
        DESCRIPTION
            "End Time."
        ::= { svlanpriofdsPm30mHisEntry 6 }

    -- 1.3.6.1.4.1.2011.2.25.3.70.20.213.120.1.7
    svlanpriofdsPm30mHisVldty OBJECT-TYPE
        SYNTAX ValidflagType
        MAX-ACCESS read-only
        STATUS current
        DESCRIPTION
            "Validity."
        ::= { svlanpriofdsPm30mHisEntry 7 }

    -- 1.3.6.1.4.1.2011.2.25.3.70.20.213.130
    svlanpriofdsPmvar1HisTable OBJECT-TYPE
        SYNTAX SEQUENCE OF SvlanpriofdsPmvar1HisEntry
        MAX-ACCESS not-accessible
        STATUS current
        DESCRIPTION
            "svlanpriofdsPmvar1His."
        ::= { svlanpriofds 130 }

    -- 1.3.6.1.4.1.2011.2.25.3.70.20.213.130.1
    svlanpriofdsPmvar1HisEntry OBJECT-TYPE
        SYNTAX SvlanpriofdsPmvar1HisEntry
        MAX-ACCESS not-accessible
        STATUS current
        DESCRIPTION
            "svlanpriofdsPmvar1His."
        INDEX{ svlanpriofdsPmvar1HisEid,svlanpriofdsPmvar1HisParaLen,svlanpriofdsPmvar1HisPara,svlanpriofdsPmvar1HisStartTime,svlanpriofdsPmvar1HisEndTime }
        ::= { svlanpriofdsPmvar1HisTable 1 }

    SvlanpriofdsPmvar1HisEntry ::=
        SEQUENCE {
            svlanpriofdsPmvar1HisEid
                DataPmEventType,
            svlanpriofdsPmvar1HisParaLen
                Unsigned32,
            svlanpriofdsPmvar1HisPara
                OCTET STRING,
            svlanpriofdsPmvar1HisMonValue
                Counter64,
            svlanpriofdsPmvar1HisStartTime
                DateAndTime,
            svlanpriofdsPmvar1HisEndTime
                DateAndTime,
            svlanpriofdsPmvar1HisVldty
                ValidflagType
        }

    -- 1.3.6.1.4.1.2011.2.25.3.70.20.213.130.1.1
    svlanpriofdsPmvar1HisEid OBJECT-TYPE
        SYNTAX DataPmEventType
        MAX-ACCESS read-only
        STATUS current
        DESCRIPTION
            "DataPmEid."
        ::= { svlanpriofdsPmvar1HisEntry 1 }

    -- 1.3.6.1.4.1.2011.2.25.3.70.20.213.130.1.2
    svlanpriofdsPmvar1HisParaLen OBJECT-TYPE
        SYNTAX Unsigned32
        MAX-ACCESS read-only
        STATUS current
        DESCRIPTION
            "ParaLen."
        ::= { svlanpriofdsPmvar1HisEntry 2 }

    -- 1.3.6.1.4.1.2011.2.25.3.70.20.213.130.1.3
    svlanpriofdsPmvar1HisPara OBJECT-TYPE
        SYNTAX OCTET STRING (SIZE (0..100))
        MAX-ACCESS read-only
        STATUS current
        DESCRIPTION
            "para"
        ::= { svlanpriofdsPmvar1HisEntry 3 }

    -- 1.3.6.1.4.1.2011.2.25.3.70.20.213.130.1.4
    svlanpriofdsPmvar1HisMonValue OBJECT-TYPE
        SYNTAX Counter64
        MAX-ACCESS read-only
        STATUS current
        DESCRIPTION
            "DataPmMonValue."
        ::= { svlanpriofdsPmvar1HisEntry 4 }

    -- 1.3.6.1.4.1.2011.2.25.3.70.20.213.130.1.5
    svlanpriofdsPmvar1HisStartTime OBJECT-TYPE
        SYNTAX DateAndTime
        MAX-ACCESS read-only
        STATUS current
        DESCRIPTION
            "Start Time."
        ::= { svlanpriofdsPmvar1HisEntry 5 }

    -- 1.3.6.1.4.1.2011.2.25.3.70.20.213.130.1.6
    svlanpriofdsPmvar1HisEndTime OBJECT-TYPE
        SYNTAX DateAndTime
        MAX-ACCESS read-only
        STATUS current
        DESCRIPTION
            "End Time."
        ::= { svlanpriofdsPmvar1HisEntry 6 }

    -- 1.3.6.1.4.1.2011.2.25.3.70.20.213.130.1.7
    svlanpriofdsPmvar1HisVldty OBJECT-TYPE
        SYNTAX ValidflagType
        MAX-ACCESS read-only
        STATUS current
        DESCRIPTION
            "Validity."
        ::= { svlanpriofdsPmvar1HisEntry 7 }

    -- 1.3.6.1.4.1.2011.2.25.3.70.20.213.140
    svlanpriofdsPmvar2HisTable OBJECT-TYPE
        SYNTAX SEQUENCE OF SvlanpriofdsPmvar2HisEntry
        MAX-ACCESS not-accessible
        STATUS current
        DESCRIPTION
            "svlanpriofdsPmvar2His."
        ::= { svlanpriofds 140 }

    -- 1.3.6.1.4.1.2011.2.25.3.70.20.213.140.1
    svlanpriofdsPmvar2HisEntry OBJECT-TYPE
        SYNTAX SvlanpriofdsPmvar2HisEntry
        MAX-ACCESS not-accessible
        STATUS current
        DESCRIPTION
            "svlanpriofdsPmvar2His."
        INDEX{ svlanpriofdsPmvar2HisEid,svlanpriofdsPmvar2HisParaLen,svlanpriofdsPmvar2HisPara,svlanpriofdsPmvar2HisStartTime,svlanpriofdsPmvar2HisEndTime }
        ::= { svlanpriofdsPmvar2HisTable 1 }

    SvlanpriofdsPmvar2HisEntry ::=
        SEQUENCE {
            svlanpriofdsPmvar2HisEid
                DataPmEventType,
            svlanpriofdsPmvar2HisParaLen
                Unsigned32,
            svlanpriofdsPmvar2HisPara
                OCTET STRING,
            svlanpriofdsPmvar2HisMonValue
                Counter64,
            svlanpriofdsPmvar2HisStartTime
                DateAndTime,
            svlanpriofdsPmvar2HisEndTime
                DateAndTime,
            svlanpriofdsPmvar2HisVldty
                ValidflagType
        }

    -- 1.3.6.1.4.1.2011.2.25.3.70.20.213.140.1.1
    svlanpriofdsPmvar2HisEid OBJECT-TYPE
        SYNTAX DataPmEventType
        MAX-ACCESS read-only
        STATUS current
        DESCRIPTION
            "DataPmEid."
        ::= { svlanpriofdsPmvar2HisEntry 1 }

    -- 1.3.6.1.4.1.2011.2.25.3.70.20.213.140.1.2
    svlanpriofdsPmvar2HisParaLen OBJECT-TYPE
        SYNTAX Unsigned32
        MAX-ACCESS read-only
        STATUS current
        DESCRIPTION
            "ParaLen."
        ::= { svlanpriofdsPmvar2HisEntry 2 }

    -- 1.3.6.1.4.1.2011.2.25.3.70.20.213.140.1.3
    svlanpriofdsPmvar2HisPara OBJECT-TYPE
        SYNTAX OCTET STRING(SIZE (0..100))
        MAX-ACCESS read-only
        STATUS current
        DESCRIPTION
            "para"
        ::= { svlanpriofdsPmvar2HisEntry 3 }

    -- 1.3.6.1.4.1.2011.2.25.3.70.20.213.140.1.4
    svlanpriofdsPmvar2HisMonValue OBJECT-TYPE
        SYNTAX Counter64
        MAX-ACCESS read-only
        STATUS current
        DESCRIPTION
            "DataPmMonValue."
        ::= { svlanpriofdsPmvar2HisEntry 4 }

    -- 1.3.6.1.4.1.2011.2.25.3.70.20.213.140.1.5
    svlanpriofdsPmvar2HisStartTime OBJECT-TYPE
        SYNTAX DateAndTime
        MAX-ACCESS read-only
        STATUS current
        DESCRIPTION
            "Start Time."
        ::= { svlanpriofdsPmvar2HisEntry 5 }

    -- 1.3.6.1.4.1.2011.2.25.3.70.20.213.140.1.6
    svlanpriofdsPmvar2HisEndTime OBJECT-TYPE
        SYNTAX DateAndTime
        MAX-ACCESS read-only
        STATUS current
        DESCRIPTION
            "End Time."
        ::= { svlanpriofdsPmvar2HisEntry 6 }

    -- 1.3.6.1.4.1.2011.2.25.3.70.20.213.140.1.7
    svlanpriofdsPmvar2HisVldty OBJECT-TYPE
        SYNTAX ValidflagType
        MAX-ACCESS read-only
        STATUS current
        DESCRIPTION
            "Validity."
        ::= { svlanpriofdsPmvar2HisEntry 7 }

    -- 1.3.6.1.4.1.2011.2.25.3.70.20.214
    ipdscpofds OBJECT IDENTIFIER ::= { rtnData 214 }

    -- 1.3.6.1.4.1.2011.2.25.3.70.20.214.100
    ipdscpofdsPmCurTable OBJECT-TYPE
        SYNTAX SEQUENCE OF IpdscpofdsPmCurEntry
        MAX-ACCESS not-accessible
        STATUS current
        DESCRIPTION
            "ipdscpofdsDataPm30sCur."
        ::= { ipdscpofds 100 }

    -- 1.3.6.1.4.1.2011.2.25.3.70.20.214.100.1
    ipdscpofdsPmCurEntry OBJECT-TYPE
        SYNTAX IpdscpofdsPmCurEntry
        MAX-ACCESS not-accessible
        STATUS current
        DESCRIPTION
            "ipdscpofdsPmCur."
        INDEX{ ipdscpofdsPmCurEid, ipdscpofdsPmCurParaLen, ipdscpofdsPmCurPara }
        ::= { ipdscpofdsPmCurTable 1 }

    IpdscpofdsPmCurEntry ::=
        SEQUENCE {
            ipdscpofdsPmCurEid
                DataPmEventType,
            ipdscpofdsPmCurParaLen
                Unsigned32,
            ipdscpofdsPmCurPara
                OCTET STRING,
            ipdscpofdsPmCurMonValue
                Counter64,
            ipdscpofdsPmCurDatetime
                DateAndTime
        }

    -- 1.3.6.1.4.1.2011.2.25.3.70.20.214.100.1.1
    ipdscpofdsPmCurEid OBJECT-TYPE
        SYNTAX DataPmEventType
        MAX-ACCESS read-only
        STATUS current
        DESCRIPTION
            "DataPmEid."
        ::= { ipdscpofdsPmCurEntry 1 }

    -- 1.3.6.1.4.1.2011.2.25.3.70.20.214.100.1.2
    ipdscpofdsPmCurParaLen OBJECT-TYPE
        SYNTAX Unsigned32
        MAX-ACCESS read-only
        STATUS current
        DESCRIPTION
            "ParaLen."
        ::= { ipdscpofdsPmCurEntry 2 }

    -- 1.3.6.1.4.1.2011.2.25.3.70.20.214.100.1.3
    ipdscpofdsPmCurPara OBJECT-TYPE
        SYNTAX OCTET STRING
        MAX-ACCESS read-only
        STATUS current
        DESCRIPTION
            "para"
        ::= { ipdscpofdsPmCurEntry 3 }

    -- 1.3.6.1.4.1.2011.2.25.3.70.20.214.100.1.4
    ipdscpofdsPmCurMonValue OBJECT-TYPE
        SYNTAX Counter64
        MAX-ACCESS read-only
        STATUS current
        DESCRIPTION
            "DataPmMonValue."
        ::= { ipdscpofdsPmCurEntry 4 }

    -- 1.3.6.1.4.1.2011.2.25.3.70.20.214.100.1.5
    ipdscpofdsPmCurDatetime OBJECT-TYPE
        SYNTAX DateAndTime
        MAX-ACCESS read-only
        STATUS current
        DESCRIPTION
            "Start Time."
        ::= { ipdscpofdsPmCurEntry 5 }

    -- 1.3.6.1.4.1.2011.2.25.3.70.20.214.110
    ipdscpofdsPm30sHisTable OBJECT-TYPE
        SYNTAX SEQUENCE OF IpdscpofdsPm30sHisEntry
        MAX-ACCESS not-accessible
        STATUS current
        DESCRIPTION
            "ipdscpofdsDataPm30sHis."
        ::= { ipdscpofds 110 }

    -- 1.3.6.1.4.1.2011.2.25.3.70.20.214.110.1
    ipdscpofdsPm30sHisEntry OBJECT-TYPE
        SYNTAX IpdscpofdsPm30sHisEntry
        MAX-ACCESS not-accessible
        STATUS current
        DESCRIPTION
            "ipdscpofdsDataPm30sHis."
        INDEX{ ipdscpofdsPm30sHisEid,ipdscpofdsPm30sHisParaLen,ipdscpofdsPm30sHisPara,ipdscpofdsPm30sHisStartTime,ipdscpofdsPm30sHisEndTime }
        ::= { ipdscpofdsPm30sHisTable 1 }

    IpdscpofdsPm30sHisEntry ::=
        SEQUENCE {
            ipdscpofdsPm30sHisEid
                DataPmEventType,
            ipdscpofdsPm30sHisParaLen
                Unsigned32,
            ipdscpofdsPm30sHisPara
                OCTET STRING,
            ipdscpofdsPm30sHisMonValue
                Counter64,
            ipdscpofdsPm30sHisStartTime
                DateAndTime,
            ipdscpofdsPm30sHisEndTime
                DateAndTime,
            ipdscpofdsPm30sHisVldty
                ValidflagType
        }

    -- 1.3.6.1.4.1.2011.2.25.3.70.20.214.110.1.1
    ipdscpofdsPm30sHisEid OBJECT-TYPE
        SYNTAX DataPmEventType
        MAX-ACCESS read-only
        STATUS current
        DESCRIPTION
            "DataPmEid."
        ::= { ipdscpofdsPm30sHisEntry 1 }

    -- 1.3.6.1.4.1.2011.2.25.3.70.20.214.110.1.2
    ipdscpofdsPm30sHisParaLen OBJECT-TYPE
        SYNTAX Unsigned32
        MAX-ACCESS read-only
        STATUS current
        DESCRIPTION
            "ParaLen."
        ::= { ipdscpofdsPm30sHisEntry 2 }

    -- 1.3.6.1.4.1.2011.2.25.3.70.20.214.110.1.3
    ipdscpofdsPm30sHisPara OBJECT-TYPE
        SYNTAX OCTET STRING(SIZE (0..100))
        MAX-ACCESS read-only
        STATUS current
        DESCRIPTION
            "para"
        ::= { ipdscpofdsPm30sHisEntry 3 }

    -- 1.3.6.1.4.1.2011.2.25.3.70.20.214.110.1.4
    ipdscpofdsPm30sHisMonValue OBJECT-TYPE
        SYNTAX Counter64
        MAX-ACCESS read-only
        STATUS current
        DESCRIPTION
            "DataPmMonValue."
        ::= { ipdscpofdsPm30sHisEntry 4 }

    -- 1.3.6.1.4.1.2011.2.25.3.70.20.214.110.1.5
    ipdscpofdsPm30sHisStartTime OBJECT-TYPE
        SYNTAX DateAndTime
        MAX-ACCESS read-only
        STATUS current
        DESCRIPTION
            "Start Time."
        ::= { ipdscpofdsPm30sHisEntry 5 }

    -- 1.3.6.1.4.1.2011.2.25.3.70.20.214.110.1.6
    ipdscpofdsPm30sHisEndTime OBJECT-TYPE
        SYNTAX DateAndTime
        MAX-ACCESS read-only
        STATUS current
        DESCRIPTION
            "End Time."
        ::= { ipdscpofdsPm30sHisEntry 6 }

    -- 1.3.6.1.4.1.2011.2.25.3.70.20.214.110.1.7
    ipdscpofdsPm30sHisVldty OBJECT-TYPE
        SYNTAX ValidflagType
        MAX-ACCESS read-only
        STATUS current
        DESCRIPTION
            "Validity."
        ::= { ipdscpofdsPm30sHisEntry 7 }

    -- 1.3.6.1.4.1.2011.2.25.3.70.20.214.120
    ipdscpofdsPm30mHisTable OBJECT-TYPE
        SYNTAX SEQUENCE OF IpdscpofdsPm30mHisEntry
        MAX-ACCESS not-accessible
        STATUS current
        DESCRIPTION
            "ipdscpofdsPm30mHis."
        ::= { ipdscpofds 120 }

    -- 1.3.6.1.4.1.2011.2.25.3.70.20.214.120.1
    ipdscpofdsPm30mHisEntry OBJECT-TYPE
        SYNTAX IpdscpofdsPm30mHisEntry
        MAX-ACCESS not-accessible
        STATUS current
        DESCRIPTION
            "ipdscpofdsPm30mHis."
        INDEX{ ipdscpofdsPm30mHisEid,ipdscpofdsPm30mHisParaLen,ipdscpofdsPm30mHisPara,ipdscpofdsPm30mHisStartTime,ipdscpofdsPm30mHisEndTime }
        ::= { ipdscpofdsPm30mHisTable 1 }

    IpdscpofdsPm30mHisEntry ::=
        SEQUENCE {
            ipdscpofdsPm30mHisEid
                DataPmEventType,
            ipdscpofdsPm30mHisParaLen
                Unsigned32,
            ipdscpofdsPm30mHisPara
                OCTET STRING,
            ipdscpofdsPm30mHisMonValue
                Counter64,
            ipdscpofdsPm30mHisStartTime
                DateAndTime,
            ipdscpofdsPm30mHisEndTime
                DateAndTime,
            ipdscpofdsPm30mHisVldty
                ValidflagType
        }

    -- 1.3.6.1.4.1.2011.2.25.3.70.20.214.120.1.1
    ipdscpofdsPm30mHisEid OBJECT-TYPE
        SYNTAX DataPmEventType
        MAX-ACCESS read-only
        STATUS current
        DESCRIPTION
            "DataPmEid."
        ::= { ipdscpofdsPm30mHisEntry 1 }

    -- 1.3.6.1.4.1.2011.2.25.3.70.20.214.120.1.2
    ipdscpofdsPm30mHisParaLen OBJECT-TYPE
        SYNTAX Unsigned32
        MAX-ACCESS read-only
        STATUS current
        DESCRIPTION
            "ParaLen."
        ::= { ipdscpofdsPm30mHisEntry 2 }

    -- 1.3.6.1.4.1.2011.2.25.3.70.20.214.120.1.3
    ipdscpofdsPm30mHisPara OBJECT-TYPE
        SYNTAX OCTET STRING(SIZE (0..100))
        MAX-ACCESS read-only
        STATUS current
        DESCRIPTION
            "para"
        ::= { ipdscpofdsPm30mHisEntry 3 }

    -- 1.3.6.1.4.1.2011.2.25.3.70.20.214.120.1.4
    ipdscpofdsPm30mHisMonValue OBJECT-TYPE
        SYNTAX Counter64
        MAX-ACCESS read-only
        STATUS current
        DESCRIPTION
            "DataPmMonValue."
        ::= { ipdscpofdsPm30mHisEntry 4 }

    -- 1.3.6.1.4.1.2011.2.25.3.70.20.214.120.1.5
    ipdscpofdsPm30mHisStartTime OBJECT-TYPE
        SYNTAX DateAndTime
        MAX-ACCESS read-only
        STATUS current
        DESCRIPTION
            "Start Time."
        ::= { ipdscpofdsPm30mHisEntry 5 }

    -- 1.3.6.1.4.1.2011.2.25.3.70.20.214.120.1.6
    ipdscpofdsPm30mHisEndTime OBJECT-TYPE
        SYNTAX DateAndTime
        MAX-ACCESS read-only
        STATUS current
        DESCRIPTION
            "End Time."
        ::= { ipdscpofdsPm30mHisEntry 6 }

    -- 1.3.6.1.4.1.2011.2.25.3.70.20.214.120.1.7
    ipdscpofdsPm30mHisVldty OBJECT-TYPE
        SYNTAX ValidflagType
        MAX-ACCESS read-only
        STATUS current
        DESCRIPTION
            "Validity."
        ::= { ipdscpofdsPm30mHisEntry 7 }

    -- 1.3.6.1.4.1.2011.2.25.3.70.20.214.130
    ipdscpofdsPmvar1HisTable OBJECT-TYPE
        SYNTAX SEQUENCE OF IpdscpofdsPmvar1HisEntry
        MAX-ACCESS not-accessible
        STATUS current
        DESCRIPTION
            "ipdscpofdsPmvar1His."
        ::= { ipdscpofds 130 }

    -- 1.3.6.1.4.1.2011.2.25.3.70.20.214.130.1
    ipdscpofdsPmvar1HisEntry OBJECT-TYPE
        SYNTAX IpdscpofdsPmvar1HisEntry
        MAX-ACCESS not-accessible
        STATUS current
        DESCRIPTION
            "ipdscpofdsPmvar1His."
        INDEX{ ipdscpofdsPmvar1HisEid,ipdscpofdsPmvar1HisParaLen,ipdscpofdsPmvar1HisPara,ipdscpofdsPmvar1HisStartTime,ipdscpofdsPmvar1HisEndTime }
        ::= { ipdscpofdsPmvar1HisTable 1 }

    IpdscpofdsPmvar1HisEntry ::=
        SEQUENCE {
            ipdscpofdsPmvar1HisEid
                DataPmEventType,
            ipdscpofdsPmvar1HisParaLen
                Unsigned32,
            ipdscpofdsPmvar1HisPara
                OCTET STRING,
            ipdscpofdsPmvar1HisMonValue
                Counter64,
            ipdscpofdsPmvar1HisStartTime
                DateAndTime,
            ipdscpofdsPmvar1HisEndTime
                DateAndTime,
            ipdscpofdsPmvar1HisVldty
                ValidflagType
        }

    -- 1.3.6.1.4.1.2011.2.25.3.70.20.214.130.1.1
    ipdscpofdsPmvar1HisEid OBJECT-TYPE
        SYNTAX DataPmEventType
        MAX-ACCESS read-only
        STATUS current
        DESCRIPTION
            "DataPmEid."
        ::= { ipdscpofdsPmvar1HisEntry 1 }

    -- 1.3.6.1.4.1.2011.2.25.3.70.20.214.130.1.2
    ipdscpofdsPmvar1HisParaLen OBJECT-TYPE
        SYNTAX Unsigned32
        MAX-ACCESS read-only
        STATUS current
        DESCRIPTION
            "ParaLen."
        ::= { ipdscpofdsPmvar1HisEntry 2 }

    -- 1.3.6.1.4.1.2011.2.25.3.70.20.214.130.1.3
    ipdscpofdsPmvar1HisPara OBJECT-TYPE
        SYNTAX OCTET STRING (SIZE (0..100))
        MAX-ACCESS read-only
        STATUS current
        DESCRIPTION
            "para"
        ::= { ipdscpofdsPmvar1HisEntry 3 }

    -- 1.3.6.1.4.1.2011.2.25.3.70.20.214.130.1.4
    ipdscpofdsPmvar1HisMonValue OBJECT-TYPE
        SYNTAX Counter64
        MAX-ACCESS read-only
        STATUS current
        DESCRIPTION
            "DataPmMonValue."
        ::= { ipdscpofdsPmvar1HisEntry 4 }

    -- 1.3.6.1.4.1.2011.2.25.3.70.20.214.130.1.5
    ipdscpofdsPmvar1HisStartTime OBJECT-TYPE
        SYNTAX DateAndTime
        MAX-ACCESS read-only
        STATUS current
        DESCRIPTION
            "Start Time."
        ::= { ipdscpofdsPmvar1HisEntry 5 }

    -- 1.3.6.1.4.1.2011.2.25.3.70.20.214.130.1.6
    ipdscpofdsPmvar1HisEndTime OBJECT-TYPE
        SYNTAX DateAndTime
        MAX-ACCESS read-only
        STATUS current
        DESCRIPTION
            "End Time."
        ::= { ipdscpofdsPmvar1HisEntry 6 }

    -- 1.3.6.1.4.1.2011.2.25.3.70.20.214.130.1.7
    ipdscpofdsPmvar1HisVldty OBJECT-TYPE
        SYNTAX ValidflagType
        MAX-ACCESS read-only
        STATUS current
        DESCRIPTION
            "Validity."
        ::= { ipdscpofdsPmvar1HisEntry 7 }

    -- 1.3.6.1.4.1.2011.2.25.3.70.20.214.140
    ipdscpofdsPmvar2HisTable OBJECT-TYPE
        SYNTAX SEQUENCE OF IpdscpofdsPmvar2HisEntry
        MAX-ACCESS not-accessible
        STATUS current
        DESCRIPTION
            "ipdscpofdsPmvar2His."
        ::= { ipdscpofds 140 }

    -- 1.3.6.1.4.1.2011.2.25.3.70.20.214.140.1
    ipdscpofdsPmvar2HisEntry OBJECT-TYPE
        SYNTAX IpdscpofdsPmvar2HisEntry
        MAX-ACCESS not-accessible
        STATUS current
        DESCRIPTION
            "ipdscpofdsPmvar2His."
        INDEX{ ipdscpofdsPmvar2HisEid,ipdscpofdsPmvar2HisParaLen,ipdscpofdsPmvar2HisPara,ipdscpofdsPmvar2HisStartTime,ipdscpofdsPmvar2HisEndTime }
        ::= { ipdscpofdsPmvar2HisTable 1 }

    IpdscpofdsPmvar2HisEntry ::=
        SEQUENCE {
            ipdscpofdsPmvar2HisEid
                DataPmEventType,
            ipdscpofdsPmvar2HisParaLen
                Unsigned32,
            ipdscpofdsPmvar2HisPara
                OCTET STRING,
            ipdscpofdsPmvar2HisMonValue
                Counter64,
            ipdscpofdsPmvar2HisStartTime
                DateAndTime,
            ipdscpofdsPmvar2HisEndTime
                DateAndTime,
            ipdscpofdsPmvar2HisVldty
                ValidflagType
        }

    -- 1.3.6.1.4.1.2011.2.25.3.70.20.214.140.1.1
    ipdscpofdsPmvar2HisEid OBJECT-TYPE
        SYNTAX DataPmEventType
        MAX-ACCESS read-only
        STATUS current
        DESCRIPTION
            "DataPmEid."
        ::= { ipdscpofdsPmvar2HisEntry 1 }

    -- 1.3.6.1.4.1.2011.2.25.3.70.20.214.140.1.2
    ipdscpofdsPmvar2HisParaLen OBJECT-TYPE
        SYNTAX Unsigned32
        MAX-ACCESS read-only
        STATUS current
        DESCRIPTION
            "ParaLen."
        ::= { ipdscpofdsPmvar2HisEntry 2 }

    -- 1.3.6.1.4.1.2011.2.25.3.70.20.214.140.1.3
    ipdscpofdsPmvar2HisPara OBJECT-TYPE
        SYNTAX OCTET STRING(SIZE (0..100))
        MAX-ACCESS read-only
        STATUS current
        DESCRIPTION
            "para"
        ::= { ipdscpofdsPmvar2HisEntry 3 }

    -- 1.3.6.1.4.1.2011.2.25.3.70.20.214.140.1.4
    ipdscpofdsPmvar2HisMonValue OBJECT-TYPE
        SYNTAX Counter64
        MAX-ACCESS read-only
        STATUS current
        DESCRIPTION
            "DataPmMonValue."
        ::= { ipdscpofdsPmvar2HisEntry 4 }

    -- 1.3.6.1.4.1.2011.2.25.3.70.20.214.140.1.5
    ipdscpofdsPmvar2HisStartTime OBJECT-TYPE
        SYNTAX DateAndTime
        MAX-ACCESS read-only
        STATUS current
        DESCRIPTION
            "Start Time."
        ::= { ipdscpofdsPmvar2HisEntry 5 }

    -- 1.3.6.1.4.1.2011.2.25.3.70.20.214.140.1.6
    ipdscpofdsPmvar2HisEndTime OBJECT-TYPE
        SYNTAX DateAndTime
        MAX-ACCESS read-only
        STATUS current
        DESCRIPTION
            "End Time."
        ::= { ipdscpofdsPmvar2HisEntry 6 }

    -- 1.3.6.1.4.1.2011.2.25.3.70.20.214.140.1.7
    ipdscpofdsPmvar2HisVldty OBJECT-TYPE
        SYNTAX ValidflagType
        MAX-ACCESS read-only
        STATUS current
        DESCRIPTION
            "Validity."
        ::= { ipdscpofdsPmvar2HisEntry 7 }

    -- 1.3.6.1.4.1.2011.2.25.3.70.20.215
    vlanofvuni OBJECT IDENTIFIER ::= { rtnData 215 }

    -- 1.3.6.1.4.1.2011.2.25.3.70.20.215.100
    vlanofvuniPmCurTable OBJECT-TYPE
        SYNTAX SEQUENCE OF VlanofvuniPmCurEntry
        MAX-ACCESS not-accessible
        STATUS current
        DESCRIPTION
            "vlanofvuniDataPm30sCur."
        ::= { vlanofvuni 100 }

    -- 1.3.6.1.4.1.2011.2.25.3.70.20.215.100.1
    vlanofvuniPmCurEntry OBJECT-TYPE
        SYNTAX VlanofvuniPmCurEntry
        MAX-ACCESS not-accessible
        STATUS current
        DESCRIPTION
            "vlanofvuniPmCur."
        INDEX{ vlanofvuniPmCurEid,vlanofvuniPmCurParaLen, vlanofvuniPmCurPara }
        ::= { vlanofvuniPmCurTable 1 }

    VlanofvuniPmCurEntry ::=
        SEQUENCE {
            vlanofvuniPmCurEid
                DataPmEventType,
            vlanofvuniPmCurParaLen
                Unsigned32,
            vlanofvuniPmCurPara
                OCTET STRING,
            vlanofvuniPmCurMonValue
                Counter64,
            vlanofvuniPmCurDatetime
                DateAndTime
        }

    -- 1.3.6.1.4.1.2011.2.25.3.70.20.215.100.1.1
    vlanofvuniPmCurEid OBJECT-TYPE
        SYNTAX DataPmEventType
        MAX-ACCESS read-only
        STATUS current
        DESCRIPTION
            "DataPmEid."
        ::= { vlanofvuniPmCurEntry 1 }

    -- 1.3.6.1.4.1.2011.2.25.3.70.20.215.100.1.2
    vlanofvuniPmCurParaLen OBJECT-TYPE
        SYNTAX Unsigned32
        MAX-ACCESS read-only
        STATUS current
        DESCRIPTION
            "ParaLen."
        ::= { vlanofvuniPmCurEntry 2 }

    -- 1.3.6.1.4.1.2011.2.25.3.70.20.215.100.1.3
    vlanofvuniPmCurPara OBJECT-TYPE
        SYNTAX OCTET STRING
        MAX-ACCESS read-only
        STATUS current
        DESCRIPTION
            "para"
        ::= { vlanofvuniPmCurEntry 3 }

    -- 1.3.6.1.4.1.2011.2.25.3.70.20.215.100.1.4
    vlanofvuniPmCurMonValue OBJECT-TYPE
        SYNTAX Counter64
        MAX-ACCESS read-only
        STATUS current
        DESCRIPTION
            "DataPmMonValue."
        ::= { vlanofvuniPmCurEntry 4 }

    -- 1.3.6.1.4.1.2011.2.25.3.70.20.215.100.1.5
    vlanofvuniPmCurDatetime OBJECT-TYPE
        SYNTAX DateAndTime
        MAX-ACCESS read-only
        STATUS current
        DESCRIPTION
            "Start Time."
        ::= { vlanofvuniPmCurEntry 5 }

    -- 1.3.6.1.4.1.2011.2.25.3.70.20.215.110
    vlanofvuniPm30sHisTable OBJECT-TYPE
        SYNTAX SEQUENCE OF VlanofvuniPm30sHisEntry
        MAX-ACCESS not-accessible
        STATUS current
        DESCRIPTION
            "vlanofvuniDataPm30sHis."
        ::= { vlanofvuni 110 }

    -- 1.3.6.1.4.1.2011.2.25.3.70.20.215.110.1
    vlanofvuniPm30sHisEntry OBJECT-TYPE
        SYNTAX VlanofvuniPm30sHisEntry
        MAX-ACCESS not-accessible
        STATUS current
        DESCRIPTION
            "vlanofvuniDataPm30sHis."
        INDEX{ vlanofvuniPm30sHisEid,vlanofvuniPm30sHisParaLen,vlanofvuniPm30sHisPara,vlanofvuniPm30sHisStartTime,vlanofvuniPm30sHisEndTime }
        ::= { vlanofvuniPm30sHisTable 1 }

    VlanofvuniPm30sHisEntry ::=
        SEQUENCE {
            vlanofvuniPm30sHisEid
                DataPmEventType,
            vlanofvuniPm30sHisParaLen
                Unsigned32,
            vlanofvuniPm30sHisPara
                OCTET STRING,
            vlanofvuniPm30sHisMonValue
                Counter64,
            vlanofvuniPm30sHisStartTime
                DateAndTime,
            vlanofvuniPm30sHisEndTime
                DateAndTime,
            vlanofvuniPm30sHisVldty
                ValidflagType
        }

    -- 1.3.6.1.4.1.2011.2.25.3.70.20.215.110.1.1
    vlanofvuniPm30sHisEid OBJECT-TYPE
        SYNTAX DataPmEventType
        MAX-ACCESS read-only
        STATUS current
        DESCRIPTION
            "DataPmEid."
        ::= { vlanofvuniPm30sHisEntry 1 }

    -- 1.3.6.1.4.1.2011.2.25.3.70.20.215.110.1.2
    vlanofvuniPm30sHisParaLen OBJECT-TYPE
        SYNTAX Unsigned32
        MAX-ACCESS read-only
        STATUS current
        DESCRIPTION
            "ParaLen."
        ::= { vlanofvuniPm30sHisEntry 2 }

    -- 1.3.6.1.4.1.2011.2.25.3.70.20.215.110.1.3
    vlanofvuniPm30sHisPara OBJECT-TYPE
        SYNTAX OCTET STRING(SIZE (0..100))
        MAX-ACCESS read-only
        STATUS current
        DESCRIPTION
            "para"
        ::= { vlanofvuniPm30sHisEntry 3 }

    -- 1.3.6.1.4.1.2011.2.25.3.70.20.215.110.1.4
    vlanofvuniPm30sHisMonValue OBJECT-TYPE
        SYNTAX Counter64
        MAX-ACCESS read-only
        STATUS current
        DESCRIPTION
            "DataPmMonValue."
        ::= { vlanofvuniPm30sHisEntry 4 }

    -- 1.3.6.1.4.1.2011.2.25.3.70.20.215.110.1.5
    vlanofvuniPm30sHisStartTime OBJECT-TYPE
        SYNTAX DateAndTime
        MAX-ACCESS read-only
        STATUS current
        DESCRIPTION
            "Start Time."
        ::= { vlanofvuniPm30sHisEntry 5 }

    -- 1.3.6.1.4.1.2011.2.25.3.70.20.215.110.1.6
    vlanofvuniPm30sHisEndTime OBJECT-TYPE
        SYNTAX DateAndTime
        MAX-ACCESS read-only
        STATUS current
        DESCRIPTION
            "End Time."
        ::= { vlanofvuniPm30sHisEntry 6 }

    -- 1.3.6.1.4.1.2011.2.25.3.70.20.215.110.1.7
    vlanofvuniPm30sHisVldty OBJECT-TYPE
        SYNTAX ValidflagType
        MAX-ACCESS read-only
        STATUS current
        DESCRIPTION
            "Validity."
        ::= { vlanofvuniPm30sHisEntry 7 }

    -- 1.3.6.1.4.1.2011.2.25.3.70.20.215.120
    vlanofvuniPm30mHisTable OBJECT-TYPE
        SYNTAX SEQUENCE OF VlanofvuniPm30mHisEntry
        MAX-ACCESS not-accessible
        STATUS current
        DESCRIPTION
            "vlanofvuniPm30mHis."
        ::= { vlanofvuni 120 }

    -- 1.3.6.1.4.1.2011.2.25.3.70.20.215.120.1
    vlanofvuniPm30mHisEntry OBJECT-TYPE
        SYNTAX VlanofvuniPm30mHisEntry
        MAX-ACCESS not-accessible
        STATUS current
        DESCRIPTION
            "vlanofvuniPm30mHis."
        INDEX{ vlanofvuniPm30mHisEid,vlanofvuniPm30mHisParaLen,vlanofvuniPm30mHisPara,vlanofvuniPm30mHisStartTime,vlanofvuniPm30mHisEndTime }
        ::= { vlanofvuniPm30mHisTable 1 }

    VlanofvuniPm30mHisEntry ::=
        SEQUENCE {
            vlanofvuniPm30mHisEid
                DataPmEventType,
            vlanofvuniPm30mHisParaLen
                Unsigned32,
            vlanofvuniPm30mHisPara
                OCTET STRING,
            vlanofvuniPm30mHisMonValue
                Counter64,
            vlanofvuniPm30mHisStartTime
                DateAndTime,
            vlanofvuniPm30mHisEndTime
                DateAndTime,
            vlanofvuniPm30mHisVldty
                ValidflagType
        }

    -- 1.3.6.1.4.1.2011.2.25.3.70.20.215.120.1.1
    vlanofvuniPm30mHisEid OBJECT-TYPE
        SYNTAX DataPmEventType
        MAX-ACCESS read-only
        STATUS current
        DESCRIPTION
            "DataPmEid."
        ::= { vlanofvuniPm30mHisEntry 1 }

    -- 1.3.6.1.4.1.2011.2.25.3.70.20.215.120.1.2
    vlanofvuniPm30mHisParaLen OBJECT-TYPE
        SYNTAX Unsigned32
        MAX-ACCESS read-only
        STATUS current
        DESCRIPTION
            "ParaLen."
        ::= { vlanofvuniPm30mHisEntry 2 }

    -- 1.3.6.1.4.1.2011.2.25.3.70.20.215.120.1.3
    vlanofvuniPm30mHisPara OBJECT-TYPE
        SYNTAX OCTET STRING(SIZE (0..100))
        MAX-ACCESS read-only
        STATUS current
        DESCRIPTION
            "para"
        ::= { vlanofvuniPm30mHisEntry 3 }

    -- 1.3.6.1.4.1.2011.2.25.3.70.20.215.120.1.4
    vlanofvuniPm30mHisMonValue OBJECT-TYPE
        SYNTAX Counter64
        MAX-ACCESS read-only
        STATUS current
        DESCRIPTION
            "DataPmMonValue."
        ::= { vlanofvuniPm30mHisEntry 4 }

    -- 1.3.6.1.4.1.2011.2.25.3.70.20.215.120.1.5
    vlanofvuniPm30mHisStartTime OBJECT-TYPE
        SYNTAX DateAndTime
        MAX-ACCESS read-only
        STATUS current
        DESCRIPTION
            "Start Time."
        ::= { vlanofvuniPm30mHisEntry 5 }

    -- 1.3.6.1.4.1.2011.2.25.3.70.20.215.120.1.6
    vlanofvuniPm30mHisEndTime OBJECT-TYPE
        SYNTAX DateAndTime
        MAX-ACCESS read-only
        STATUS current
        DESCRIPTION
            "End Time."
        ::= { vlanofvuniPm30mHisEntry 6 }

    -- 1.3.6.1.4.1.2011.2.25.3.70.20.215.120.1.7
    vlanofvuniPm30mHisVldty OBJECT-TYPE
        SYNTAX ValidflagType
        MAX-ACCESS read-only
        STATUS current
        DESCRIPTION
            "Validity."
        ::= { vlanofvuniPm30mHisEntry 7 }

    -- 1.3.6.1.4.1.2011.2.25.3.70.20.215.130
    vlanofvuniPmvar1HisTable OBJECT-TYPE
        SYNTAX SEQUENCE OF VlanofvuniPmvar1HisEntry
        MAX-ACCESS not-accessible
        STATUS current
        DESCRIPTION
            "vlanofvuniPmvar1His."
        ::= { vlanofvuni 130 }

    -- 1.3.6.1.4.1.2011.2.25.3.70.20.215.130.1
    vlanofvuniPmvar1HisEntry OBJECT-TYPE
        SYNTAX VlanofvuniPmvar1HisEntry
        MAX-ACCESS not-accessible
        STATUS current
        DESCRIPTION
            "vlanofvuniPmvar1His."
        INDEX{ vlanofvuniPmvar1HisEid,vlanofvuniPmvar1HisParaLen,vlanofvuniPmvar1HisPara,vlanofvuniPmvar1HisStartTime,vlanofvuniPmvar1HisEndTime }
        ::= { vlanofvuniPmvar1HisTable 1 }

    VlanofvuniPmvar1HisEntry ::=
        SEQUENCE {
            vlanofvuniPmvar1HisEid
                DataPmEventType,
            vlanofvuniPmvar1HisParaLen
                Unsigned32,
            vlanofvuniPmvar1HisPara
                OCTET STRING,
            vlanofvuniPmvar1HisMonValue
                Counter64,
            vlanofvuniPmvar1HisStartTime
                DateAndTime,
            vlanofvuniPmvar1HisEndTime
                DateAndTime,
            vlanofvuniPmvar1HisVldty
                ValidflagType
        }

    -- 1.3.6.1.4.1.2011.2.25.3.70.20.215.130.1.1
    vlanofvuniPmvar1HisEid OBJECT-TYPE
        SYNTAX DataPmEventType
        MAX-ACCESS read-only
        STATUS current
        DESCRIPTION
            "DataPmEid."
        ::= { vlanofvuniPmvar1HisEntry 1 }

    -- 1.3.6.1.4.1.2011.2.25.3.70.20.215.130.1.2
    vlanofvuniPmvar1HisParaLen OBJECT-TYPE
        SYNTAX Unsigned32
        MAX-ACCESS read-only
        STATUS current
        DESCRIPTION
            "ParaLen."
        ::= { vlanofvuniPmvar1HisEntry 2 }

    -- 1.3.6.1.4.1.2011.2.25.3.70.20.215.130.1.3
    vlanofvuniPmvar1HisPara OBJECT-TYPE
        SYNTAX OCTET STRING (SIZE (0..100))
        MAX-ACCESS read-only
        STATUS current
        DESCRIPTION
            "para"
        ::= { vlanofvuniPmvar1HisEntry 3 }

    -- 1.3.6.1.4.1.2011.2.25.3.70.20.215.130.1.4
    vlanofvuniPmvar1HisMonValue OBJECT-TYPE
        SYNTAX Counter64
        MAX-ACCESS read-only
        STATUS current
        DESCRIPTION
            "DataPmMonValue."
        ::= { vlanofvuniPmvar1HisEntry 4 }

    -- 1.3.6.1.4.1.2011.2.25.3.70.20.215.130.1.5
    vlanofvuniPmvar1HisStartTime OBJECT-TYPE
        SYNTAX DateAndTime
        MAX-ACCESS read-only
        STATUS current
        DESCRIPTION
            "Start Time."
        ::= { vlanofvuniPmvar1HisEntry 5 }

    -- 1.3.6.1.4.1.2011.2.25.3.70.20.215.130.1.6
    vlanofvuniPmvar1HisEndTime OBJECT-TYPE
        SYNTAX DateAndTime
        MAX-ACCESS read-only
        STATUS current
        DESCRIPTION
            "End Time."
        ::= { vlanofvuniPmvar1HisEntry 6 }

    -- 1.3.6.1.4.1.2011.2.25.3.70.20.215.130.1.7
    vlanofvuniPmvar1HisVldty OBJECT-TYPE
        SYNTAX ValidflagType
        MAX-ACCESS read-only
        STATUS current
        DESCRIPTION
            "Validity."
        ::= { vlanofvuniPmvar1HisEntry 7 }

    -- 1.3.6.1.4.1.2011.2.25.3.70.20.215.140
    vlanofvuniPmvar2HisTable OBJECT-TYPE
        SYNTAX SEQUENCE OF VlanofvuniPmvar2HisEntry
        MAX-ACCESS not-accessible
        STATUS current
        DESCRIPTION
            "vlanofvuniPmvar2His."
        ::= { vlanofvuni 140 }

    -- 1.3.6.1.4.1.2011.2.25.3.70.20.215.140.1
    vlanofvuniPmvar2HisEntry OBJECT-TYPE
        SYNTAX VlanofvuniPmvar2HisEntry
        MAX-ACCESS not-accessible
        STATUS current
        DESCRIPTION
            "vlanofvuniPmvar2His."
        INDEX{ vlanofvuniPmvar2HisEid,vlanofvuniPmvar2HisParaLen,vlanofvuniPmvar2HisPara,vlanofvuniPmvar2HisStartTime,vlanofvuniPmvar2HisEndTime }
        ::= { vlanofvuniPmvar2HisTable 1 }

    VlanofvuniPmvar2HisEntry ::=
        SEQUENCE {
            vlanofvuniPmvar2HisEid
                DataPmEventType,
            vlanofvuniPmvar2HisParaLen
                Unsigned32,
            vlanofvuniPmvar2HisPara
                OCTET STRING,
            vlanofvuniPmvar2HisMonValue
                Counter64,
            vlanofvuniPmvar2HisStartTime
                DateAndTime,
            vlanofvuniPmvar2HisEndTime
                DateAndTime,
            vlanofvuniPmvar2HisVldty
                ValidflagType
        }

    -- 1.3.6.1.4.1.2011.2.25.3.70.20.215.140.1.1
    vlanofvuniPmvar2HisEid OBJECT-TYPE
        SYNTAX DataPmEventType
        MAX-ACCESS read-only
        STATUS current
        DESCRIPTION
            "DataPmEid."
        ::= { vlanofvuniPmvar2HisEntry 1 }

    -- 1.3.6.1.4.1.2011.2.25.3.70.20.215.140.1.2
    vlanofvuniPmvar2HisParaLen OBJECT-TYPE
        SYNTAX Unsigned32
        MAX-ACCESS read-only
        STATUS current
        DESCRIPTION
            "ParaLen."
        ::= { vlanofvuniPmvar2HisEntry 2 }

    -- 1.3.6.1.4.1.2011.2.25.3.70.20.215.140.1.3
    vlanofvuniPmvar2HisPara OBJECT-TYPE
        SYNTAX OCTET STRING(SIZE (0..100))
        MAX-ACCESS read-only
        STATUS current
        DESCRIPTION
            "para"
        ::= { vlanofvuniPmvar2HisEntry 3 }

    -- 1.3.6.1.4.1.2011.2.25.3.70.20.215.140.1.4
    vlanofvuniPmvar2HisMonValue OBJECT-TYPE
        SYNTAX Counter64
        MAX-ACCESS read-only
        STATUS current
        DESCRIPTION
            "DataPmMonValue."
        ::= { vlanofvuniPmvar2HisEntry 4 }

    -- 1.3.6.1.4.1.2011.2.25.3.70.20.215.140.1.5
    vlanofvuniPmvar2HisStartTime OBJECT-TYPE
        SYNTAX DateAndTime
        MAX-ACCESS read-only
        STATUS current
        DESCRIPTION
            "Start Time."
        ::= { vlanofvuniPmvar2HisEntry 5 }

    -- 1.3.6.1.4.1.2011.2.25.3.70.20.215.140.1.6
    vlanofvuniPmvar2HisEndTime OBJECT-TYPE
        SYNTAX DateAndTime
        MAX-ACCESS read-only
        STATUS current
        DESCRIPTION
            "End Time."
        ::= { vlanofvuniPmvar2HisEntry 6 }

    -- 1.3.6.1.4.1.2011.2.25.3.70.20.215.140.1.7
    vlanofvuniPmvar2HisVldty OBJECT-TYPE
        SYNTAX ValidflagType
        MAX-ACCESS read-only
        STATUS current
        DESCRIPTION
            "Validity."
        ::= { vlanofvuniPmvar2HisEntry 7 }

    -- 1.3.6.1.4.1.2011.2.25.3.70.20.155
    virtualPort OBJECT IDENTIFIER ::= { rtnData 155 }

    -- 1.3.6.1.4.1.2011.2.25.3.70.20.155.100
    virtualPortPmCurTable OBJECT-TYPE
        SYNTAX SEQUENCE OF VirtualPortPmCurEntry
        MAX-ACCESS not-accessible
        STATUS current
        DESCRIPTION
            "virtualPortDataPm30sCur."
        ::= { virtualPort 100 }

    -- 1.3.6.1.4.1.2011.2.25.3.70.20.155.100.1
    virtualPortPmCurEntry OBJECT-TYPE
        SYNTAX VirtualPortPmCurEntry
        MAX-ACCESS not-accessible
        STATUS current
        DESCRIPTION
            "virtualPortPmCur."
        INDEX{ virtualPortPmCurEid,virtualPortPmCurParaLen,virtualPortPmCurPara }
        ::= { virtualPortPmCurTable 1 }

    VirtualPortPmCurEntry ::=
        SEQUENCE {
            virtualPortPmCurEid
                DataPmEventType,
            virtualPortPmCurParaLen
                Unsigned32,
            virtualPortPmCurPara
                OCTET STRING,
            virtualPortPmCurMonValue
                Counter64,
            virtualPortPmCurDatetime
                DateAndTime
        }

    -- 1.3.6.1.4.1.2011.2.25.3.70.20.155.100.1.1
    virtualPortPmCurEid OBJECT-TYPE
        SYNTAX DataPmEventType
        MAX-ACCESS read-only
        STATUS current
        DESCRIPTION
            "DataPmEid."
        ::= { virtualPortPmCurEntry 1 }

    -- 1.3.6.1.4.1.2011.2.25.3.70.20.155.100.1.2
    virtualPortPmCurParaLen OBJECT-TYPE
        SYNTAX Unsigned32
        MAX-ACCESS read-only
        STATUS current
        DESCRIPTION
            "ParaLen."
        ::= { virtualPortPmCurEntry 2 }

    -- 1.3.6.1.4.1.2011.2.25.3.70.20.155.100.1.3
    virtualPortPmCurPara OBJECT-TYPE
        SYNTAX OCTET STRING
        MAX-ACCESS read-only
        STATUS current
        DESCRIPTION
            "para"
        ::= { virtualPortPmCurEntry 3 }

    -- 1.3.6.1.4.1.2011.2.25.3.70.20.155.100.1.4
    virtualPortPmCurMonValue OBJECT-TYPE
        SYNTAX Counter64
        MAX-ACCESS read-only
        STATUS current
        DESCRIPTION
            "DataPmMonValue."
        ::= { virtualPortPmCurEntry 4 }

    -- 1.3.6.1.4.1.2011.2.25.3.70.20.155.100.1.5
    virtualPortPmCurDatetime OBJECT-TYPE
        SYNTAX DateAndTime
        MAX-ACCESS read-only
        STATUS current
        DESCRIPTION
            "Start Time."
        ::= { virtualPortPmCurEntry 5 }

    -- 1.3.6.1.4.1.2011.2.25.3.70.20.155.110
    virtualPortPm30sHisTable OBJECT-TYPE
        SYNTAX SEQUENCE OF VirtualPortPm30sHisEntry
        MAX-ACCESS not-accessible
        STATUS current
        DESCRIPTION
            "virtualPortDataPm30sHis."
        ::= { virtualPort 110 }

    -- 1.3.6.1.4.1.2011.2.25.3.70.20.155.110.1
    virtualPortPm30sHisEntry OBJECT-TYPE
        SYNTAX VirtualPortPm30sHisEntry
        MAX-ACCESS not-accessible
        STATUS current
        DESCRIPTION
            "virtualPortDataPm30sHis."
        INDEX{ virtualPortPm30sHisEid,virtualPortPm30sHisParaLen,virtualPortPm30sHisPara,virtualPortPm30sHisStartTime,virtualPortPm30sHisEndTime }
        ::= { virtualPortPm30sHisTable 1 }

    VirtualPortPm30sHisEntry ::=
        SEQUENCE {
            virtualPortPm30sHisEid
                DataPmEventType,
            virtualPortPm30sHisParaLen
                Unsigned32,
            virtualPortPm30sHisPara
                OCTET STRING,
            virtualPortPm30sHisMonValue
                Counter64,
            virtualPortPm30sHisStartTime
                DateAndTime,
            virtualPortPm30sHisEndTime
                DateAndTime,
            virtualPortPm30sHisVldty
                ValidflagType
        }

    -- 1.3.6.1.4.1.2011.2.25.3.70.20.155.110.1.1
    virtualPortPm30sHisEid OBJECT-TYPE
        SYNTAX DataPmEventType
        MAX-ACCESS read-only
        STATUS current
        DESCRIPTION
            "DataPmEid."
        ::= { virtualPortPm30sHisEntry 1 }

    -- 1.3.6.1.4.1.2011.2.25.3.70.20.155.110.1.2
    virtualPortPm30sHisParaLen OBJECT-TYPE
        SYNTAX Unsigned32
        MAX-ACCESS read-only
        STATUS current
        DESCRIPTION
            "ParaLen."
        ::= { virtualPortPm30sHisEntry 2 }

    -- 1.3.6.1.4.1.2011.2.25.3.70.20.155.110.1.3
    virtualPortPm30sHisPara OBJECT-TYPE
        SYNTAX OCTET STRING(SIZE (0..100))
        MAX-ACCESS read-only
        STATUS current
        DESCRIPTION
            "para"
        ::= { virtualPortPm30sHisEntry 3 }

    -- 1.3.6.1.4.1.2011.2.25.3.70.20.155.110.1.4
    virtualPortPm30sHisMonValue OBJECT-TYPE
        SYNTAX Counter64
        MAX-ACCESS read-only
        STATUS current
        DESCRIPTION
            "DataPmMonValue."
        ::= { virtualPortPm30sHisEntry 4 }

    -- 1.3.6.1.4.1.2011.2.25.3.70.20.155.110.1.5
    virtualPortPm30sHisStartTime OBJECT-TYPE
        SYNTAX DateAndTime
        MAX-ACCESS read-only
        STATUS current
        DESCRIPTION
            "Start Time."
        ::= { virtualPortPm30sHisEntry 5 }

    -- 1.3.6.1.4.1.2011.2.25.3.70.20.155.110.1.6
    virtualPortPm30sHisEndTime OBJECT-TYPE
        SYNTAX DateAndTime
        MAX-ACCESS read-only
        STATUS current
        DESCRIPTION
            "End Time."
        ::= { virtualPortPm30sHisEntry 6 }

    -- 1.3.6.1.4.1.2011.2.25.3.70.20.155.110.1.7
    virtualPortPm30sHisVldty OBJECT-TYPE
        SYNTAX ValidflagType
        MAX-ACCESS read-only
        STATUS current
        DESCRIPTION
            "Validity."
        ::= { virtualPortPm30sHisEntry 7 }

    -- 1.3.6.1.4.1.2011.2.25.3.70.20.155.120
    virtualPortPm30mHisTable OBJECT-TYPE
        SYNTAX SEQUENCE OF VirtualPortPm30mHisEntry
        MAX-ACCESS not-accessible
        STATUS current
        DESCRIPTION
            "virtualPortPm30mHis."
        ::= { virtualPort 120 }

    -- 1.3.6.1.4.1.2011.2.25.3.70.20.155.120.1
    virtualPortPm30mHisEntry OBJECT-TYPE
        SYNTAX VirtualPortPm30mHisEntry
        MAX-ACCESS not-accessible
        STATUS current
        DESCRIPTION
            "virtualPortPm30mHis."
        INDEX{ virtualPortPm30mHisEid,virtualPortPm30mHisParaLen,virtualPortPm30mHisPara,virtualPortPm30mHisStartTime,virtualPortPm30mHisEndTime }
        ::= { virtualPortPm30mHisTable 1 }

    VirtualPortPm30mHisEntry ::=
        SEQUENCE {
            virtualPortPm30mHisEid
                DataPmEventType,
            virtualPortPm30mHisParaLen
                Unsigned32,
            virtualPortPm30mHisPara
                OCTET STRING,
            virtualPortPm30mHisMonValue
                Counter64,
            virtualPortPm30mHisStartTime
                DateAndTime,
            virtualPortPm30mHisEndTime
                DateAndTime,
            virtualPortPm30mHisVldty
                ValidflagType
        }

    -- 1.3.6.1.4.1.2011.2.25.3.70.20.155.120.1.1
    virtualPortPm30mHisEid OBJECT-TYPE
        SYNTAX DataPmEventType
        MAX-ACCESS read-only
        STATUS current
        DESCRIPTION
            "DataPmEid."
        ::= { virtualPortPm30mHisEntry 1 }

    -- 1.3.6.1.4.1.2011.2.25.3.70.20.155.120.1.2
    virtualPortPm30mHisParaLen OBJECT-TYPE
        SYNTAX Unsigned32
        MAX-ACCESS read-only
        STATUS current
        DESCRIPTION
            "ParaLen."
        ::= { virtualPortPm30mHisEntry 2 }

    -- 1.3.6.1.4.1.2011.2.25.3.70.20.155.120.1.3
    virtualPortPm30mHisPara OBJECT-TYPE
        SYNTAX OCTET STRING(SIZE (0..100))
        MAX-ACCESS read-only
        STATUS current
        DESCRIPTION
            "para"
        ::= { virtualPortPm30mHisEntry 3 }

    -- 1.3.6.1.4.1.2011.2.25.3.70.20.155.120.1.4
    virtualPortPm30mHisMonValue OBJECT-TYPE
        SYNTAX Counter64
        MAX-ACCESS read-only
        STATUS current
        DESCRIPTION
            "DataPmMonValue."
        ::= { virtualPortPm30mHisEntry 4 }

    -- 1.3.6.1.4.1.2011.2.25.3.70.20.155.120.1.5
    virtualPortPm30mHisStartTime OBJECT-TYPE
        SYNTAX DateAndTime
        MAX-ACCESS read-only
        STATUS current
        DESCRIPTION
            "Start Time."
        ::= { virtualPortPm30mHisEntry 5 }

    -- 1.3.6.1.4.1.2011.2.25.3.70.20.155.120.1.6
    virtualPortPm30mHisEndTime OBJECT-TYPE
        SYNTAX DateAndTime
        MAX-ACCESS read-only
        STATUS current
        DESCRIPTION
            "End Time."
        ::= { virtualPortPm30mHisEntry 6 }

    -- 1.3.6.1.4.1.2011.2.25.3.70.20.155.120.1.7
    virtualPortPm30mHisVldty OBJECT-TYPE
        SYNTAX ValidflagType
        MAX-ACCESS read-only
        STATUS current
        DESCRIPTION
            "Validity."
        ::= { virtualPortPm30mHisEntry 7 }

    -- 1.3.6.1.4.1.2011.2.25.3.70.20.155.130
    virtualPortPmvar1HisTable OBJECT-TYPE
        SYNTAX SEQUENCE OF VirtualPortPmvar1HisEntry
        MAX-ACCESS not-accessible
        STATUS current
        DESCRIPTION
            "virtualPortPmvar1His."
        ::= { virtualPort 130 }

    -- 1.3.6.1.4.1.2011.2.25.3.70.20.155.130.1
    virtualPortPmvar1HisEntry OBJECT-TYPE
        SYNTAX VirtualPortPmvar1HisEntry
        MAX-ACCESS not-accessible
        STATUS current
        DESCRIPTION
            "virtualPortPmvar1His."
        INDEX{ virtualPortPmvar1HisEid,virtualPortPmvar1HisParaLen,virtualPortPmvar1HisPara,virtualPortPmvar1HisStartTime,virtualPortPmvar1HisEndTime }
        ::= { virtualPortPmvar1HisTable 1 }

    VirtualPortPmvar1HisEntry ::=
        SEQUENCE {
            virtualPortPmvar1HisEid
                DataPmEventType,
            virtualPortPmvar1HisParaLen
                Unsigned32,
            virtualPortPmvar1HisPara
                OCTET STRING,
            virtualPortPmvar1HisMonValue
                Counter64,
            virtualPortPmvar1HisStartTime
                DateAndTime,
            virtualPortPmvar1HisEndTime
                DateAndTime,
            virtualPortPmvar1HisVldty
                ValidflagType
        }

    -- 1.3.6.1.4.1.2011.2.25.3.70.20.155.130.1.1
    virtualPortPmvar1HisEid OBJECT-TYPE
        SYNTAX DataPmEventType
        MAX-ACCESS read-only
        STATUS current
        DESCRIPTION
            "DataPmEid."
        ::= { virtualPortPmvar1HisEntry 1 }

    -- 1.3.6.1.4.1.2011.2.25.3.70.20.155.130.1.2
    virtualPortPmvar1HisParaLen OBJECT-TYPE
        SYNTAX Unsigned32
        MAX-ACCESS read-only
        STATUS current
        DESCRIPTION
            "ParaLen."
        ::= { virtualPortPmvar1HisEntry 2 }

    -- 1.3.6.1.4.1.2011.2.25.3.70.20.155.130.1.3
    virtualPortPmvar1HisPara OBJECT-TYPE
        SYNTAX OCTET STRING (SIZE (0..100))
        MAX-ACCESS read-only
        STATUS current
        DESCRIPTION
            "para"
        ::= { virtualPortPmvar1HisEntry 3 }

    -- 1.3.6.1.4.1.2011.2.25.3.70.20.155.130.1.4
    virtualPortPmvar1HisMonValue OBJECT-TYPE
        SYNTAX Counter64
        MAX-ACCESS read-only
        STATUS current
        DESCRIPTION
            "DataPmMonValue."
        ::= { virtualPortPmvar1HisEntry 4 }

    -- 1.3.6.1.4.1.2011.2.25.3.70.20.155.130.1.5
    virtualPortPmvar1HisStartTime OBJECT-TYPE
        SYNTAX DateAndTime
        MAX-ACCESS read-only
        STATUS current
        DESCRIPTION
            "Start Time."
        ::= { virtualPortPmvar1HisEntry 5 }

    -- 1.3.6.1.4.1.2011.2.25.3.70.20.155.130.1.6
    virtualPortPmvar1HisEndTime OBJECT-TYPE
        SYNTAX DateAndTime
        MAX-ACCESS read-only
        STATUS current
        DESCRIPTION
            "End Time."
        ::= { virtualPortPmvar1HisEntry 6 }

    -- 1.3.6.1.4.1.2011.2.25.3.70.20.155.130.1.7
    virtualPortPmvar1HisVldty OBJECT-TYPE
        SYNTAX ValidflagType
        MAX-ACCESS read-only
        STATUS current
        DESCRIPTION
            "Validity."
        ::= { virtualPortPmvar1HisEntry 7 }

    -- 1.3.6.1.4.1.2011.2.25.3.70.20.155.140
    virtualPortPmvar2HisTable OBJECT-TYPE
        SYNTAX SEQUENCE OF VirtualPortPmvar2HisEntry
        MAX-ACCESS not-accessible
        STATUS current
        DESCRIPTION
            "virtualPortPmvar2His."
        ::= { virtualPort 140 }

    -- 1.3.6.1.4.1.2011.2.25.3.70.20.155.140.1
    virtualPortPmvar2HisEntry OBJECT-TYPE
        SYNTAX VirtualPortPmvar2HisEntry
        MAX-ACCESS not-accessible
        STATUS current
        DESCRIPTION
            "virtualPortPmvar2His."
        INDEX{ virtualPortPmvar2HisEid,virtualPortPmvar2HisParaLen,virtualPortPmvar2HisPara,virtualPortPmvar2HisStartTime,virtualPortPmvar2HisEndTime }
        ::= { virtualPortPmvar2HisTable 1 }

    VirtualPortPmvar2HisEntry ::=
        SEQUENCE {
            virtualPortPmvar2HisEid
                DataPmEventType,
            virtualPortPmvar2HisParaLen
                Unsigned32,
            virtualPortPmvar2HisPara
                OCTET STRING,
            virtualPortPmvar2HisMonValue
                Counter64,
            virtualPortPmvar2HisStartTime
                DateAndTime,
            virtualPortPmvar2HisEndTime
                DateAndTime,
            virtualPortPmvar2HisVldty
                ValidflagType
        }

    -- 1.3.6.1.4.1.2011.2.25.3.70.20.155.140.1.1
    virtualPortPmvar2HisEid OBJECT-TYPE
        SYNTAX DataPmEventType
        MAX-ACCESS read-only
        STATUS current
        DESCRIPTION
            "DataPmEid."
        ::= { virtualPortPmvar2HisEntry 1 }

    -- 1.3.6.1.4.1.2011.2.25.3.70.20.155.140.1.2
    virtualPortPmvar2HisParaLen OBJECT-TYPE
        SYNTAX Unsigned32
        MAX-ACCESS read-only
        STATUS current
        DESCRIPTION
            "ParaLen."
        ::= { virtualPortPmvar2HisEntry 2 }

    -- 1.3.6.1.4.1.2011.2.25.3.70.20.155.140.1.3
    virtualPortPmvar2HisPara OBJECT-TYPE
        SYNTAX OCTET STRING(SIZE (0..100))
        MAX-ACCESS read-only
        STATUS current
        DESCRIPTION
            "para"
        ::= { virtualPortPmvar2HisEntry 3 }

    -- 1.3.6.1.4.1.2011.2.25.3.70.20.155.140.1.4
    virtualPortPmvar2HisMonValue OBJECT-TYPE
        SYNTAX Counter64
        MAX-ACCESS read-only
        STATUS current
        DESCRIPTION
            "DataPmMonValue."
        ::= { virtualPortPmvar2HisEntry 4 }

    -- 1.3.6.1.4.1.2011.2.25.3.70.20.155.140.1.5
    virtualPortPmvar2HisStartTime OBJECT-TYPE
        SYNTAX DateAndTime
        MAX-ACCESS read-only
        STATUS current
        DESCRIPTION
            "Start Time."
        ::= { virtualPortPmvar2HisEntry 5 }

    -- 1.3.6.1.4.1.2011.2.25.3.70.20.155.140.1.6
    virtualPortPmvar2HisEndTime OBJECT-TYPE
        SYNTAX DateAndTime
        MAX-ACCESS read-only
        STATUS current
        DESCRIPTION
            "End Time."
        ::= { virtualPortPmvar2HisEntry 6 }

    -- 1.3.6.1.4.1.2011.2.25.3.70.20.155.140.1.7
    virtualPortPmvar2HisVldty OBJECT-TYPE
        SYNTAX ValidflagType
        MAX-ACCESS read-only
        STATUS current
        DESCRIPTION
            "Validity."
        ::= { virtualPortPmvar2HisEntry 7 }

    -- 1.3.6.1.4.1.2011.2.25.3.70.20.222
    vuniqueue OBJECT IDENTIFIER ::= { rtnData 222 }

    -- 1.3.6.1.4.1.2011.2.25.3.70.20.222.100
    vuniqueuePmCurTable OBJECT-TYPE
        SYNTAX SEQUENCE OF VuniqueuePmCurEntry
        MAX-ACCESS not-accessible
        STATUS current
        DESCRIPTION
            "vuniqueueDataPm30sCur."
        ::= { vuniqueue 100 }

    -- 1.3.6.1.4.1.2011.2.25.3.70.20.222.100.1
    vuniqueuePmCurEntry OBJECT-TYPE
        SYNTAX VuniqueuePmCurEntry
        MAX-ACCESS not-accessible
        STATUS current
        DESCRIPTION
            "vuniqueuePmCur."
        INDEX{ vuniqueuePmCurEid, vuniqueuePmCurParaLen, vuniqueuePmCurPara }
        ::= { vuniqueuePmCurTable 1 }

    VuniqueuePmCurEntry ::=
        SEQUENCE {
            vuniqueuePmCurEid
                DataPmEventType,
            vuniqueuePmCurParaLen
                Unsigned32,
            vuniqueuePmCurPara
                OCTET STRING,
            vuniqueuePmCurMonValue
                Counter64,
            vuniqueuePmCurDatetime
                DateAndTime
        }

    -- 1.3.6.1.4.1.2011.2.25.3.70.20.222.100.1.1
    vuniqueuePmCurEid OBJECT-TYPE
        SYNTAX DataPmEventType
        MAX-ACCESS read-only
        STATUS current
        DESCRIPTION
            "DataPmEid."
        ::= { vuniqueuePmCurEntry 1 }

    -- 1.3.6.1.4.1.2011.2.25.3.70.20.222.100.1.2
    vuniqueuePmCurParaLen OBJECT-TYPE
        SYNTAX Unsigned32
        MAX-ACCESS read-only
        STATUS current
        DESCRIPTION
            "ParaLen."
        ::= { vuniqueuePmCurEntry 2 }

    -- 1.3.6.1.4.1.2011.2.25.3.70.20.222.100.1.3
    vuniqueuePmCurPara OBJECT-TYPE
        SYNTAX OCTET STRING
        MAX-ACCESS read-only
        STATUS current
        DESCRIPTION
            "para"
        ::= { vuniqueuePmCurEntry 3 }

    -- 1.3.6.1.4.1.2011.2.25.3.70.20.222.100.1.4
    vuniqueuePmCurMonValue OBJECT-TYPE
        SYNTAX Counter64
        MAX-ACCESS read-only
        STATUS current
        DESCRIPTION
            "DataPmMonValue."
        ::= { vuniqueuePmCurEntry 4 }

    -- 1.3.6.1.4.1.2011.2.25.3.70.20.222.100.1.5
    vuniqueuePmCurDatetime OBJECT-TYPE
        SYNTAX DateAndTime
        MAX-ACCESS read-only
        STATUS current
        DESCRIPTION
            "Start Time."
        ::= { vuniqueuePmCurEntry 5 }

    -- 1.3.6.1.4.1.2011.2.25.3.70.20.222.110
    vuniqueuePm30sHisTable OBJECT-TYPE
        SYNTAX SEQUENCE OF VuniqueuePm30sHisEntry
        MAX-ACCESS not-accessible
        STATUS current
        DESCRIPTION
            "vuniqueueDataPm30sHis."
        ::= { vuniqueue 110 }

    -- 1.3.6.1.4.1.2011.2.25.3.70.20.222.110.1
    vuniqueuePm30sHisEntry OBJECT-TYPE
        SYNTAX VuniqueuePm30sHisEntry
        MAX-ACCESS not-accessible
        STATUS current
        DESCRIPTION
            "vuniqueueDataPm30sHis."
        INDEX{ vuniqueuePm30sHisEid, vuniqueuePm30sHisParaLen, vuniqueuePm30sHisPara, vuniqueuePm30sHisStartTime, vuniqueuePm30sHisEndTime }
        ::= { vuniqueuePm30sHisTable 1 }

    VuniqueuePm30sHisEntry ::=
        SEQUENCE {
            vuniqueuePm30sHisEid
                DataPmEventType,
            vuniqueuePm30sHisParaLen
                Unsigned32,
            vuniqueuePm30sHisPara
                OCTET STRING,
            vuniqueuePm30sHisMonValue
                Counter64,
            vuniqueuePm30sHisStartTime
                DateAndTime,
            vuniqueuePm30sHisEndTime
                DateAndTime,
            vuniqueuePm30sHisVldty
                ValidflagType
        }

    -- 1.3.6.1.4.1.2011.2.25.3.70.20.222.110.1.1
    vuniqueuePm30sHisEid OBJECT-TYPE
        SYNTAX DataPmEventType
        MAX-ACCESS read-only
        STATUS current
        DESCRIPTION
            "DataPmEid."
        ::= { vuniqueuePm30sHisEntry 1 }

    -- 1.3.6.1.4.1.2011.2.25.3.70.20.222.110.1.2
    vuniqueuePm30sHisParaLen OBJECT-TYPE
        SYNTAX Unsigned32
        MAX-ACCESS read-only
        STATUS current
        DESCRIPTION
            "ParaLen."
        ::= { vuniqueuePm30sHisEntry 2 }

    -- 1.3.6.1.4.1.2011.2.25.3.70.20.222.110.1.3
    vuniqueuePm30sHisPara OBJECT-TYPE
        SYNTAX OCTET STRING (SIZE (0..100))
        MAX-ACCESS read-only
        STATUS current
        DESCRIPTION
            "para"
        ::= { vuniqueuePm30sHisEntry 3 }

    -- 1.3.6.1.4.1.2011.2.25.3.70.20.222.110.1.4
    vuniqueuePm30sHisMonValue OBJECT-TYPE
        SYNTAX Counter64
        MAX-ACCESS read-only
        STATUS current
        DESCRIPTION
            "DataPmMonValue."
        ::= { vuniqueuePm30sHisEntry 4 }

    -- 1.3.6.1.4.1.2011.2.25.3.70.20.222.110.1.5
    vuniqueuePm30sHisStartTime OBJECT-TYPE
        SYNTAX DateAndTime
        MAX-ACCESS read-only
        STATUS current
        DESCRIPTION
            "Start Time."
        ::= { vuniqueuePm30sHisEntry 5 }

    -- 1.3.6.1.4.1.2011.2.25.3.70.20.222.110.1.6
    vuniqueuePm30sHisEndTime OBJECT-TYPE
        SYNTAX DateAndTime
        MAX-ACCESS read-only
        STATUS current
        DESCRIPTION
            "End Time."
        ::= { vuniqueuePm30sHisEntry 6 }

    -- 1.3.6.1.4.1.2011.2.25.3.70.20.222.110.1.7
    vuniqueuePm30sHisVldty OBJECT-TYPE
        SYNTAX ValidflagType
        MAX-ACCESS read-only
        STATUS current
        DESCRIPTION
            "Validity."
        ::= { vuniqueuePm30sHisEntry 7 }

    -- 1.3.6.1.4.1.2011.2.25.3.70.20.222.120
    vuniqueuePm30mHisTable OBJECT-TYPE
        SYNTAX SEQUENCE OF VuniqueuePm30mHisEntry
        MAX-ACCESS not-accessible
        STATUS current
        DESCRIPTION
            "vuniqueuePm30mHis."
        ::= { vuniqueue 120 }

    -- 1.3.6.1.4.1.2011.2.25.3.70.20.222.120.1
    vuniqueuePm30mHisEntry OBJECT-TYPE
        SYNTAX VuniqueuePm30mHisEntry
        MAX-ACCESS not-accessible
        STATUS current
        DESCRIPTION
            "vuniqueuePm30mHis."
        INDEX{ vuniqueuePm30mHisEid, vuniqueuePm30mHisParaLen, vuniqueuePm30mHisPara, vuniqueuePm30mHisStartTime, vuniqueuePm30mHisEndTime }
        ::= { vuniqueuePm30mHisTable 1 }

    VuniqueuePm30mHisEntry ::=
        SEQUENCE {
            vuniqueuePm30mHisEid
                DataPmEventType,
            vuniqueuePm30mHisParaLen
                Unsigned32,
            vuniqueuePm30mHisPara
                OCTET STRING,
            vuniqueuePm30mHisMonValue
                Counter64,
            vuniqueuePm30mHisStartTime
                DateAndTime,
            vuniqueuePm30mHisEndTime
                DateAndTime,
            vuniqueuePm30mHisVldty
                ValidflagType
        }

    -- 1.3.6.1.4.1.2011.2.25.3.70.20.222.120.1.1
    vuniqueuePm30mHisEid OBJECT-TYPE
        SYNTAX DataPmEventType
        MAX-ACCESS read-only
        STATUS current
        DESCRIPTION
            "DataPmEid."
        ::= { vuniqueuePm30mHisEntry 1 }

    -- 1.3.6.1.4.1.2011.2.25.3.70.20.222.120.1.2
    vuniqueuePm30mHisParaLen OBJECT-TYPE
        SYNTAX Unsigned32
        MAX-ACCESS read-only
        STATUS current
        DESCRIPTION
            "ParaLen."
        ::= { vuniqueuePm30mHisEntry 2 }

    -- 1.3.6.1.4.1.2011.2.25.3.70.20.222.120.1.3
    vuniqueuePm30mHisPara OBJECT-TYPE
        SYNTAX OCTET STRING (SIZE(0..100))
        MAX-ACCESS read-only
        STATUS current
        DESCRIPTION
            "para"
        ::= { vuniqueuePm30mHisEntry 3 }

    -- 1.3.6.1.4.1.2011.2.25.3.70.20.222.120.1.4
    vuniqueuePm30mHisMonValue OBJECT-TYPE
        SYNTAX Counter64
        MAX-ACCESS read-only
        STATUS current
        DESCRIPTION
            "DataPmMonValue."
        ::= { vuniqueuePm30mHisEntry 4 }

    -- 1.3.6.1.4.1.2011.2.25.3.70.20.222.120.1.5
    vuniqueuePm30mHisStartTime OBJECT-TYPE
        SYNTAX DateAndTime
        MAX-ACCESS read-only
        STATUS current
        DESCRIPTION
            "Start Time."
        ::= { vuniqueuePm30mHisEntry 5 }

    -- 1.3.6.1.4.1.2011.2.25.3.70.20.222.120.1.6
    vuniqueuePm30mHisEndTime OBJECT-TYPE
        SYNTAX DateAndTime
        MAX-ACCESS read-only
        STATUS current
        DESCRIPTION
            "End Time."
        ::= { vuniqueuePm30mHisEntry 6 }

    -- 1.3.6.1.4.1.2011.2.25.3.70.20.222.120.1.7
    vuniqueuePm30mHisVldty OBJECT-TYPE
        SYNTAX ValidflagType
        MAX-ACCESS read-only
        STATUS current
        DESCRIPTION
            "Validity."
        ::= { vuniqueuePm30mHisEntry 7 }

    -- 1.3.6.1.4.1.2011.2.25.3.70.20.222.130
    vuniqueuePmvar1HisTable OBJECT-TYPE
        SYNTAX SEQUENCE OF VuniqueuePmvar1HisEntry
        MAX-ACCESS not-accessible
        STATUS current
        DESCRIPTION
            "vuniqueuePmvar1His."
        ::= { vuniqueue 130 }

    -- 1.3.6.1.4.1.2011.2.25.3.70.20.222.130.1
    vuniqueuePmvar1HisEntry OBJECT-TYPE
        SYNTAX VuniqueuePmvar1HisEntry
        MAX-ACCESS not-accessible
        STATUS current
        DESCRIPTION
            "vuniqueuePmvar1His."
        INDEX{ vuniqueuePmvar1HisEid, vuniqueuePmvar1HisParaLen, vuniqueuePmvar1HisPara, vuniqueuePmvar1HisStartTime, vuniqueuePmvar1HisEndTime }
        ::= { vuniqueuePmvar1HisTable 1 }

    VuniqueuePmvar1HisEntry ::=
        SEQUENCE {
            vuniqueuePmvar1HisEid
                DataPmEventType,
            vuniqueuePmvar1HisParaLen
                Unsigned32,
            vuniqueuePmvar1HisPara
                OCTET STRING,
            vuniqueuePmvar1HisMonValue
                Counter64,
            vuniqueuePmvar1HisStartTime
                DateAndTime,
            vuniqueuePmvar1HisEndTime
                DateAndTime,
            vuniqueuePmvar1HisVldty
                ValidflagType
        }

    -- 1.3.6.1.4.1.2011.2.25.3.70.20.222.130.1.1
    vuniqueuePmvar1HisEid OBJECT-TYPE
        SYNTAX DataPmEventType
        MAX-ACCESS read-only
        STATUS current
        DESCRIPTION
            "DataPmEid."
        ::= { vuniqueuePmvar1HisEntry 1 }

    -- 1.3.6.1.4.1.2011.2.25.3.70.20.222.130.1.2
    vuniqueuePmvar1HisParaLen OBJECT-TYPE
        SYNTAX Unsigned32
        MAX-ACCESS read-only
        STATUS current
        DESCRIPTION
            "ParaLen."
        ::= { vuniqueuePmvar1HisEntry 2 }

    -- 1.3.6.1.4.1.2011.2.25.3.70.20.222.130.1.3
    vuniqueuePmvar1HisPara OBJECT-TYPE
        SYNTAX OCTET STRING (SIZE (0..100))
        MAX-ACCESS read-only
        STATUS current
        DESCRIPTION
            "para"
        ::= { vuniqueuePmvar1HisEntry 3 }

    -- 1.3.6.1.4.1.2011.2.25.3.70.20.222.130.1.4
    vuniqueuePmvar1HisMonValue OBJECT-TYPE
        SYNTAX Counter64
        MAX-ACCESS read-only
        STATUS current
        DESCRIPTION
            "DataPmMonValue."
        ::= { vuniqueuePmvar1HisEntry 4 }

    -- 1.3.6.1.4.1.2011.2.25.3.70.20.222.130.1.5
    vuniqueuePmvar1HisStartTime OBJECT-TYPE
        SYNTAX DateAndTime
        MAX-ACCESS read-only
        STATUS current
        DESCRIPTION
            "Start Time."
        ::= { vuniqueuePmvar1HisEntry 5 }

    -- 1.3.6.1.4.1.2011.2.25.3.70.20.222.130.1.6
    vuniqueuePmvar1HisEndTime OBJECT-TYPE
        SYNTAX DateAndTime
        MAX-ACCESS read-only
        STATUS current
        DESCRIPTION
            "End Time."
        ::= { vuniqueuePmvar1HisEntry 6 }

    -- 1.3.6.1.4.1.2011.2.25.3.70.20.222.130.1.7
    vuniqueuePmvar1HisVldty OBJECT-TYPE
        SYNTAX ValidflagType
        MAX-ACCESS read-only
        STATUS current
        DESCRIPTION
            "Validity."
        ::= { vuniqueuePmvar1HisEntry 7 }

    -- 1.3.6.1.4.1.2011.2.25.3.70.20.222.140
    vuniqueuePmvar2HisTable OBJECT-TYPE
        SYNTAX SEQUENCE OF VuniqueuePmvar2HisEntry
        MAX-ACCESS not-accessible
        STATUS current
        DESCRIPTION
            "vuniqueuePmvar2His."
        ::= { vuniqueue 140 }

    -- 1.3.6.1.4.1.2011.2.25.3.70.20.222.140.1
    vuniqueuePmvar2HisEntry OBJECT-TYPE
        SYNTAX VuniqueuePmvar2HisEntry
        MAX-ACCESS not-accessible
        STATUS current
        DESCRIPTION
            "vuniqueuePmvar2His."
        INDEX{ vuniqueuePmvar2HisEid, vuniqueuePmvar2HisParaLen, vuniqueuePmvar2HisPara, vuniqueuePmvar2HisStartTime, vuniqueuePmvar2HisEndTime }
        ::= { vuniqueuePmvar2HisTable 1 }

    VuniqueuePmvar2HisEntry ::=
        SEQUENCE {
            vuniqueuePmvar2HisEid
                DataPmEventType,
            vuniqueuePmvar2HisParaLen
                Unsigned32,
            vuniqueuePmvar2HisPara
                OCTET STRING,
            vuniqueuePmvar2HisMonValue
                Counter64,
            vuniqueuePmvar2HisStartTime
                DateAndTime,
            vuniqueuePmvar2HisEndTime
                DateAndTime,
            vuniqueuePmvar2HisVldty
                ValidflagType
        }

    -- 1.3.6.1.4.1.2011.2.25.3.70.20.222.140.1.1
    vuniqueuePmvar2HisEid OBJECT-TYPE
        SYNTAX DataPmEventType
        MAX-ACCESS read-only
        STATUS current
        DESCRIPTION
            "DataPmEid."
        ::= { vuniqueuePmvar2HisEntry 1 }

    -- 1.3.6.1.4.1.2011.2.25.3.70.20.222.140.1.2
    vuniqueuePmvar2HisParaLen OBJECT-TYPE
        SYNTAX Unsigned32
        MAX-ACCESS read-only
        STATUS current
        DESCRIPTION
            "ParaLen."
        ::= { vuniqueuePmvar2HisEntry 2 }

    -- 1.3.6.1.4.1.2011.2.25.3.70.20.222.140.1.3
    vuniqueuePmvar2HisPara OBJECT-TYPE
        SYNTAX OCTET STRING (SIZE (0..100))
        MAX-ACCESS read-only
        STATUS current
        DESCRIPTION
            "para"
        ::= { vuniqueuePmvar2HisEntry 3 }

    -- 1.3.6.1.4.1.2011.2.25.3.70.20.222.140.1.4
    vuniqueuePmvar2HisMonValue OBJECT-TYPE
        SYNTAX Counter64
        MAX-ACCESS read-only
        STATUS current
        DESCRIPTION
            "DataPmMonValue."
        ::= { vuniqueuePmvar2HisEntry 4 }

    -- 1.3.6.1.4.1.2011.2.25.3.70.20.222.140.1.5
    vuniqueuePmvar2HisStartTime OBJECT-TYPE
        SYNTAX DateAndTime
        MAX-ACCESS read-only
        STATUS current
        DESCRIPTION
            "Start Time."
        ::= { vuniqueuePmvar2HisEntry 5 }

    -- 1.3.6.1.4.1.2011.2.25.3.70.20.222.140.1.6
    vuniqueuePmvar2HisEndTime OBJECT-TYPE
        SYNTAX DateAndTime
        MAX-ACCESS read-only
        STATUS current
        DESCRIPTION
            "End Time."
        ::= { vuniqueuePmvar2HisEntry 6 }

    -- 1.3.6.1.4.1.2011.2.25.3.70.20.222.140.1.7
    vuniqueuePmvar2HisVldty OBJECT-TYPE
        SYNTAX ValidflagType
        MAX-ACCESS read-only
        STATUS current
        DESCRIPTION
            "Validity."
        ::= { vuniqueuePmvar2HisEntry 7 }

    -- 1.3.6.1.4.1.2011.2.25.3.70.20.223
    pwqueue OBJECT IDENTIFIER ::= { rtnData 223 }

    -- 1.3.6.1.4.1.2011.2.25.3.70.20.223.100
    pwqueuePmCurTable OBJECT-TYPE
        SYNTAX SEQUENCE OF PwqueuePmCurEntry
        MAX-ACCESS not-accessible
        STATUS current
        DESCRIPTION
            "pwqueueDataPm30sCur."
        ::= { pwqueue 100 }

    -- 1.3.6.1.4.1.2011.2.25.3.70.20.223.100.1
    pwqueuePmCurEntry OBJECT-TYPE
        SYNTAX PwqueuePmCurEntry
        MAX-ACCESS not-accessible
        STATUS current
        DESCRIPTION
            "pwqueuePmCur."
        INDEX{ pwqueuePmCurEid, pwqueuePmCurParaLen, pwqueuePmCurPara }
        ::= { pwqueuePmCurTable 1 }

    PwqueuePmCurEntry ::=
        SEQUENCE {
            pwqueuePmCurEid
                DataPmEventType,
            pwqueuePmCurParaLen
                Unsigned32,
            pwqueuePmCurPara
                OCTET STRING,
            pwqueuePmCurMonValue
                Counter64,
            pwqueuePmCurDatetime
                DateAndTime
        }

    -- 1.3.6.1.4.1.2011.2.25.3.70.20.223.100.1.1
    pwqueuePmCurEid OBJECT-TYPE
        SYNTAX DataPmEventType
        MAX-ACCESS read-only
        STATUS current
        DESCRIPTION
            "DataPmEid."
        ::= { pwqueuePmCurEntry 1 }

    -- 1.3.6.1.4.1.2011.2.25.3.70.20.223.100.1.2
    pwqueuePmCurParaLen OBJECT-TYPE
        SYNTAX Unsigned32
        MAX-ACCESS read-only
        STATUS current
        DESCRIPTION
            "ParaLen."
        ::= { pwqueuePmCurEntry 2 }

    -- 1.3.6.1.4.1.2011.2.25.3.70.20.223.100.1.3
    pwqueuePmCurPara OBJECT-TYPE
        SYNTAX OCTET STRING
        MAX-ACCESS read-only
        STATUS current
        DESCRIPTION
            "para"
        ::= { pwqueuePmCurEntry 3 }

    -- 1.3.6.1.4.1.2011.2.25.3.70.20.223.100.1.4
    pwqueuePmCurMonValue OBJECT-TYPE
        SYNTAX Counter64
        MAX-ACCESS read-only
        STATUS current
        DESCRIPTION
            "DataPmMonValue."
        ::= { pwqueuePmCurEntry 4 }

    -- 1.3.6.1.4.1.2011.2.25.3.70.20.223.100.1.5
    pwqueuePmCurDatetime OBJECT-TYPE
        SYNTAX DateAndTime
        MAX-ACCESS read-only
        STATUS current
        DESCRIPTION
            "Start Time."
        ::= { pwqueuePmCurEntry 5 }

    -- 1.3.6.1.4.1.2011.2.25.3.70.20.223.110
    pwqueuePm30sHisTable OBJECT-TYPE
        SYNTAX SEQUENCE OF PwqueuePm30sHisEntry
        MAX-ACCESS not-accessible
        STATUS current
        DESCRIPTION
            "pwqueueDataPm30sHis."
        ::= { pwqueue 110 }

    -- 1.3.6.1.4.1.2011.2.25.3.70.20.223.110.1
    pwqueuePm30sHisEntry OBJECT-TYPE
        SYNTAX PwqueuePm30sHisEntry
        MAX-ACCESS not-accessible
        STATUS current
        DESCRIPTION
            "pwqueueDataPm30sHis."
        INDEX{ pwqueuePm30sHisEid, pwqueuePm30sHisParaLen, pwqueuePm30sHisPara, pwqueuePm30sHisStartTime, pwqueuePm30sHisEndTime }
        ::= { pwqueuePm30sHisTable 1 }

    PwqueuePm30sHisEntry ::=
        SEQUENCE {
            pwqueuePm30sHisEid
                DataPmEventType,
            pwqueuePm30sHisParaLen
                Unsigned32,
            pwqueuePm30sHisPara
                OCTET STRING,
            pwqueuePm30sHisMonValue
                Counter64,
            pwqueuePm30sHisStartTime
                DateAndTime,
            pwqueuePm30sHisEndTime
                DateAndTime,
            pwqueuePm30sHisVldty
                ValidflagType
        }

    -- 1.3.6.1.4.1.2011.2.25.3.70.20.223.110.1.1
    pwqueuePm30sHisEid OBJECT-TYPE
        SYNTAX DataPmEventType
        MAX-ACCESS read-only
        STATUS current
        DESCRIPTION
            "DataPmEid."
        ::= { pwqueuePm30sHisEntry 1 }

    -- 1.3.6.1.4.1.2011.2.25.3.70.20.223.110.1.2
    pwqueuePm30sHisParaLen OBJECT-TYPE
        SYNTAX Unsigned32
        MAX-ACCESS read-only
        STATUS current
        DESCRIPTION
            "ParaLen."
        ::= { pwqueuePm30sHisEntry 2 }

    -- 1.3.6.1.4.1.2011.2.25.3.70.20.223.110.1.3
    pwqueuePm30sHisPara OBJECT-TYPE
        SYNTAX OCTET STRING (SIZE (0..100))
        MAX-ACCESS read-only
        STATUS current
        DESCRIPTION
            "para"
        ::= { pwqueuePm30sHisEntry 3 }

    -- 1.3.6.1.4.1.2011.2.25.3.70.20.223.110.1.4
    pwqueuePm30sHisMonValue OBJECT-TYPE
        SYNTAX Counter64
        MAX-ACCESS read-only
        STATUS current
        DESCRIPTION
            "DataPmMonValue."
        ::= { pwqueuePm30sHisEntry 4 }

    -- 1.3.6.1.4.1.2011.2.25.3.70.20.223.110.1.5
    pwqueuePm30sHisStartTime OBJECT-TYPE
        SYNTAX DateAndTime
        MAX-ACCESS read-only
        STATUS current
        DESCRIPTION
            "Start Time."
        ::= { pwqueuePm30sHisEntry 5 }

    -- 1.3.6.1.4.1.2011.2.25.3.70.20.223.110.1.6
    pwqueuePm30sHisEndTime OBJECT-TYPE
        SYNTAX DateAndTime
        MAX-ACCESS read-only
        STATUS current
        DESCRIPTION
            "End Time."
        ::= { pwqueuePm30sHisEntry 6 }

    -- 1.3.6.1.4.1.2011.2.25.3.70.20.223.110.1.7
    pwqueuePm30sHisVldty OBJECT-TYPE
        SYNTAX ValidflagType
        MAX-ACCESS read-only
        STATUS current
        DESCRIPTION
            "Validity."
        ::= { pwqueuePm30sHisEntry 7 }

    -- 1.3.6.1.4.1.2011.2.25.3.70.20.223.120
    pwqueuePm30mHisTable OBJECT-TYPE
        SYNTAX SEQUENCE OF PwqueuePm30mHisEntry
        MAX-ACCESS not-accessible
        STATUS current
        DESCRIPTION
            "pwqueuePm30mHis."
        ::= { pwqueue 120 }

    -- 1.3.6.1.4.1.2011.2.25.3.70.20.223.120.1
    pwqueuePm30mHisEntry OBJECT-TYPE
        SYNTAX PwqueuePm30mHisEntry
        MAX-ACCESS not-accessible
        STATUS current
        DESCRIPTION
            "pwqueuePm30mHis."
        INDEX{ pwqueuePm30mHisEid, pwqueuePm30mHisParaLen, pwqueuePm30mHisPara, pwqueuePm30mHisStartTime, pwqueuePm30mHisEndTime }
        ::= { pwqueuePm30mHisTable 1 }

    PwqueuePm30mHisEntry ::=
        SEQUENCE {
            pwqueuePm30mHisEid
                DataPmEventType,
            pwqueuePm30mHisParaLen
                Unsigned32,
            pwqueuePm30mHisPara
                OCTET STRING,
            pwqueuePm30mHisMonValue
                Counter64,
            pwqueuePm30mHisStartTime
                DateAndTime,
            pwqueuePm30mHisEndTime
                DateAndTime,
            pwqueuePm30mHisVldty
                ValidflagType
        }

    -- 1.3.6.1.4.1.2011.2.25.3.70.20.223.120.1.1
    pwqueuePm30mHisEid OBJECT-TYPE
        SYNTAX DataPmEventType
        MAX-ACCESS read-only
        STATUS current
        DESCRIPTION
            "DataPmEid."
        ::= { pwqueuePm30mHisEntry 1 }

    -- 1.3.6.1.4.1.2011.2.25.3.70.20.223.120.1.2
    pwqueuePm30mHisParaLen OBJECT-TYPE
        SYNTAX Unsigned32
        MAX-ACCESS read-only
        STATUS current
        DESCRIPTION
            "ParaLen."
        ::= { pwqueuePm30mHisEntry 2 }

    -- 1.3.6.1.4.1.2011.2.25.3.70.20.223.120.1.3
    pwqueuePm30mHisPara OBJECT-TYPE
        SYNTAX OCTET STRING (SIZE(0..100))
        MAX-ACCESS read-only
        STATUS current
        DESCRIPTION
            "para"
        ::= { pwqueuePm30mHisEntry 3 }

    -- 1.3.6.1.4.1.2011.2.25.3.70.20.223.120.1.4
    pwqueuePm30mHisMonValue OBJECT-TYPE
        SYNTAX Counter64
        MAX-ACCESS read-only
        STATUS current
        DESCRIPTION
            "DataPmMonValue."
        ::= { pwqueuePm30mHisEntry 4 }

    -- 1.3.6.1.4.1.2011.2.25.3.70.20.223.120.1.5
    pwqueuePm30mHisStartTime OBJECT-TYPE
        SYNTAX DateAndTime
        MAX-ACCESS read-only
        STATUS current
        DESCRIPTION
            "Start Time."
        ::= { pwqueuePm30mHisEntry 5 }

    -- 1.3.6.1.4.1.2011.2.25.3.70.20.223.120.1.6
    pwqueuePm30mHisEndTime OBJECT-TYPE
        SYNTAX DateAndTime
        MAX-ACCESS read-only
        STATUS current
        DESCRIPTION
            "End Time."
        ::= { pwqueuePm30mHisEntry 6 }

    -- 1.3.6.1.4.1.2011.2.25.3.70.20.223.120.1.7
    pwqueuePm30mHisVldty OBJECT-TYPE
        SYNTAX ValidflagType
        MAX-ACCESS read-only
        STATUS current
        DESCRIPTION
            "Validity."
        ::= { pwqueuePm30mHisEntry 7 }

    -- 1.3.6.1.4.1.2011.2.25.3.70.20.223.130
    pwqueuePmvar1HisTable OBJECT-TYPE
        SYNTAX SEQUENCE OF PwqueuePmvar1HisEntry
        MAX-ACCESS not-accessible
        STATUS current
        DESCRIPTION
            "pwqueuePmvar1His."
        ::= { pwqueue 130 }

    -- 1.3.6.1.4.1.2011.2.25.3.70.20.223.130.1
    pwqueuePmvar1HisEntry OBJECT-TYPE
        SYNTAX PwqueuePmvar1HisEntry
        MAX-ACCESS not-accessible
        STATUS current
        DESCRIPTION
            "pwqueuePmvar1His."
        INDEX{ pwqueuePmvar1HisEid, pwqueuePmvar1HisParaLen, pwqueuePmvar1HisPara, pwqueuePmvar1HisStartTime, pwqueuePmvar1HisEndTime }
        ::= { pwqueuePmvar1HisTable 1 }

    PwqueuePmvar1HisEntry ::=
        SEQUENCE {
            pwqueuePmvar1HisEid
                DataPmEventType,
            pwqueuePmvar1HisParaLen
                Unsigned32,
            pwqueuePmvar1HisPara
                OCTET STRING,
            pwqueuePmvar1HisMonValue
                Counter64,
            pwqueuePmvar1HisStartTime
                DateAndTime,
            pwqueuePmvar1HisEndTime
                DateAndTime,
            pwqueuePmvar1HisVldty
                ValidflagType
        }

    -- 1.3.6.1.4.1.2011.2.25.3.70.20.223.130.1.1
    pwqueuePmvar1HisEid OBJECT-TYPE
        SYNTAX DataPmEventType
        MAX-ACCESS read-only
        STATUS current
        DESCRIPTION
            "DataPmEid."
        ::= { pwqueuePmvar1HisEntry 1 }

    -- 1.3.6.1.4.1.2011.2.25.3.70.20.223.130.1.2
    pwqueuePmvar1HisParaLen OBJECT-TYPE
        SYNTAX Unsigned32
        MAX-ACCESS read-only
        STATUS current
        DESCRIPTION
            "ParaLen."
        ::= { pwqueuePmvar1HisEntry 2 }

    -- 1.3.6.1.4.1.2011.2.25.3.70.20.223.130.1.3
    pwqueuePmvar1HisPara OBJECT-TYPE
        SYNTAX OCTET STRING (SIZE (0..100))
        MAX-ACCESS read-only
        STATUS current
        DESCRIPTION
            "para"
        ::= { pwqueuePmvar1HisEntry 3 }

    -- 1.3.6.1.4.1.2011.2.25.3.70.20.223.130.1.4
    pwqueuePmvar1HisMonValue OBJECT-TYPE
        SYNTAX Counter64
        MAX-ACCESS read-only
        STATUS current
        DESCRIPTION
            "DataPmMonValue."
        ::= { pwqueuePmvar1HisEntry 4 }

    -- 1.3.6.1.4.1.2011.2.25.3.70.20.223.130.1.5
    pwqueuePmvar1HisStartTime OBJECT-TYPE
        SYNTAX DateAndTime
        MAX-ACCESS read-only
        STATUS current
        DESCRIPTION
            "Start Time."
        ::= { pwqueuePmvar1HisEntry 5 }

    -- 1.3.6.1.4.1.2011.2.25.3.70.20.223.130.1.6
    pwqueuePmvar1HisEndTime OBJECT-TYPE
        SYNTAX DateAndTime
        MAX-ACCESS read-only
        STATUS current
        DESCRIPTION
            "End Time."
        ::= { pwqueuePmvar1HisEntry 6 }

    -- 1.3.6.1.4.1.2011.2.25.3.70.20.223.130.1.7
    pwqueuePmvar1HisVldty OBJECT-TYPE
        SYNTAX ValidflagType
        MAX-ACCESS read-only
        STATUS current
        DESCRIPTION
            "Validity."
        ::= { pwqueuePmvar1HisEntry 7 }

    -- 1.3.6.1.4.1.2011.2.25.3.70.20.223.140
    pwqueuePmvar2HisTable OBJECT-TYPE
        SYNTAX SEQUENCE OF PwqueuePmvar2HisEntry
        MAX-ACCESS not-accessible
        STATUS current
        DESCRIPTION
            "pwqueuePmvar2His."
        ::= { pwqueue 140 }

    -- 1.3.6.1.4.1.2011.2.25.3.70.20.223.140.1
    pwqueuePmvar2HisEntry OBJECT-TYPE
        SYNTAX PwqueuePmvar2HisEntry
        MAX-ACCESS not-accessible
        STATUS current
        DESCRIPTION
            "pwqueuePmvar2His."
        INDEX{ pwqueuePmvar2HisEid, pwqueuePmvar2HisParaLen, pwqueuePmvar2HisPara, pwqueuePmvar2HisStartTime, pwqueuePmvar2HisEndTime }
        ::= { pwqueuePmvar2HisTable 1 }

    PwqueuePmvar2HisEntry ::=
        SEQUENCE {
            pwqueuePmvar2HisEid
                DataPmEventType,
            pwqueuePmvar2HisParaLen
                Unsigned32,
            pwqueuePmvar2HisPara
                OCTET STRING,
            pwqueuePmvar2HisMonValue
                Counter64,
            pwqueuePmvar2HisStartTime
                DateAndTime,
            pwqueuePmvar2HisEndTime
                DateAndTime,
            pwqueuePmvar2HisVldty
                ValidflagType
        }

    -- 1.3.6.1.4.1.2011.2.25.3.70.20.223.140.1.1
    pwqueuePmvar2HisEid OBJECT-TYPE
        SYNTAX DataPmEventType
        MAX-ACCESS read-only
        STATUS current
        DESCRIPTION
            "DataPmEid."
        ::= { pwqueuePmvar2HisEntry 1 }

    -- 1.3.6.1.4.1.2011.2.25.3.70.20.223.140.1.2
    pwqueuePmvar2HisParaLen OBJECT-TYPE
        SYNTAX Unsigned32
        MAX-ACCESS read-only
        STATUS current
        DESCRIPTION
            "ParaLen."
        ::= { pwqueuePmvar2HisEntry 2 }

    -- 1.3.6.1.4.1.2011.2.25.3.70.20.223.140.1.3
    pwqueuePmvar2HisPara OBJECT-TYPE
        SYNTAX OCTET STRING (SIZE (0..100))
        MAX-ACCESS read-only
        STATUS current
        DESCRIPTION
            "para"
        ::= { pwqueuePmvar2HisEntry 3 }

    -- 1.3.6.1.4.1.2011.2.25.3.70.20.223.140.1.4
    pwqueuePmvar2HisMonValue OBJECT-TYPE
        SYNTAX Counter64
        MAX-ACCESS read-only
        STATUS current
        DESCRIPTION
            "DataPmMonValue."
        ::= { pwqueuePmvar2HisEntry 4 }

    -- 1.3.6.1.4.1.2011.2.25.3.70.20.223.140.1.5
    pwqueuePmvar2HisStartTime OBJECT-TYPE
        SYNTAX DateAndTime
        MAX-ACCESS read-only
        STATUS current
        DESCRIPTION
            "Start Time."
        ::= { pwqueuePmvar2HisEntry 5 }

    -- 1.3.6.1.4.1.2011.2.25.3.70.20.223.140.1.6
    pwqueuePmvar2HisEndTime OBJECT-TYPE
        SYNTAX DateAndTime
        MAX-ACCESS read-only
        STATUS current
        DESCRIPTION
            "End Time."
        ::= { pwqueuePmvar2HisEntry 6 }

    -- 1.3.6.1.4.1.2011.2.25.3.70.20.223.140.1.7
    pwqueuePmvar2HisVldty OBJECT-TYPE
        SYNTAX ValidflagType
        MAX-ACCESS read-only
        STATUS current
        DESCRIPTION
            "Validity."
        ::= { pwqueuePmvar2HisEntry 7 }

    -- 1.3.6.1.4.1.2011.2.25.3.70.20.227
    pla OBJECT IDENTIFIER ::= { rtnData 227 }

    -- 1.3.6.1.4.1.2011.2.25.3.70.20.227.100
    plaPmCurTable OBJECT-TYPE
        SYNTAX SEQUENCE OF PlaPmCurEntry
        MAX-ACCESS not-accessible
        STATUS current
        DESCRIPTION
            "plaDataPm30sCur."
        ::= { pla 100 }

    -- 1.3.6.1.4.1.2011.2.25.3.70.20.227.100.1
    plaPmCurEntry OBJECT-TYPE
        SYNTAX PlaPmCurEntry
        MAX-ACCESS not-accessible
        STATUS current
        DESCRIPTION
            "plaPmCur."
        INDEX{ plaPmCurEid, plaPmCurParaLen, plaPmCurPara }
        ::= { plaPmCurTable 1 }

    PlaPmCurEntry ::=
        SEQUENCE {
            plaPmCurEid
                DataPmEventType,
            plaPmCurParaLen
                Unsigned32,
            plaPmCurPara
                OCTET STRING,
            plaPmCurMonValue
                Counter64,
            plaPmCurDatetime
                DateAndTime
        }

    -- 1.3.6.1.4.1.2011.2.25.3.70.20.227.100.1.1
    plaPmCurEid OBJECT-TYPE
        SYNTAX DataPmEventType
        MAX-ACCESS read-only
        STATUS current
        DESCRIPTION
            "DataPmEid."
        ::= { plaPmCurEntry 1 }

    -- 1.3.6.1.4.1.2011.2.25.3.70.20.227.100.1.2
    plaPmCurParaLen OBJECT-TYPE
        SYNTAX Unsigned32
        MAX-ACCESS read-only
        STATUS current
        DESCRIPTION
            "ParaLen."
        ::= { plaPmCurEntry 2 }

    -- 1.3.6.1.4.1.2011.2.25.3.70.20.227.100.1.3
    plaPmCurPara OBJECT-TYPE
        SYNTAX OCTET STRING
        MAX-ACCESS read-only
        STATUS current
        DESCRIPTION
            "para"
        ::= { plaPmCurEntry 3 }

    -- 1.3.6.1.4.1.2011.2.25.3.70.20.227.100.1.4
    plaPmCurMonValue OBJECT-TYPE
        SYNTAX Counter64
        MAX-ACCESS read-only
        STATUS current
        DESCRIPTION
            "DataPmMonValue."
        ::= { plaPmCurEntry 4 }

    -- 1.3.6.1.4.1.2011.2.25.3.70.20.227.100.1.5
    plaPmCurDatetime OBJECT-TYPE
        SYNTAX DateAndTime
        MAX-ACCESS read-only
        STATUS current
        DESCRIPTION
            "Start Time."
        ::= { plaPmCurEntry 5 }

    -- 1.3.6.1.4.1.2011.2.25.3.70.20.227.110
    plaPm30sHisTable OBJECT-TYPE
        SYNTAX SEQUENCE OF PlaPm30sHisEntry
        MAX-ACCESS not-accessible
        STATUS current
        DESCRIPTION
            "plaDataPm30sHis."
        ::= { pla 110 }

    -- 1.3.6.1.4.1.2011.2.25.3.70.20.227.110.1
    plaPm30sHisEntry OBJECT-TYPE
        SYNTAX PlaPm30sHisEntry
        MAX-ACCESS not-accessible
        STATUS current
        DESCRIPTION
            "plaDataPm30sHis."
        INDEX{ plaPm30sHisEid, plaPm30sHisParaLen, plaPm30sHisPara, plaPm30sHisStartTime, plaPm30sHisEndTime }
        ::= { plaPm30sHisTable 1 }

    PlaPm30sHisEntry ::=
        SEQUENCE {
            plaPm30sHisEid
                DataPmEventType,
            plaPm30sHisParaLen
                Unsigned32,
            plaPm30sHisPara
                OCTET STRING,
            plaPm30sHisMonValue
                Counter64,
            plaPm30sHisStartTime
                DateAndTime,
            plaPm30sHisEndTime
                DateAndTime,
            plaPm30sHisVldty
                ValidflagType
        }

    -- 1.3.6.1.4.1.2011.2.25.3.70.20.227.110.1.1
    plaPm30sHisEid OBJECT-TYPE
        SYNTAX DataPmEventType
        MAX-ACCESS read-only
        STATUS current
        DESCRIPTION
            "DataPmEid."
        ::= { plaPm30sHisEntry 1 }

    -- 1.3.6.1.4.1.2011.2.25.3.70.20.227.110.1.2
    plaPm30sHisParaLen OBJECT-TYPE
        SYNTAX Unsigned32
        MAX-ACCESS read-only
        STATUS current
        DESCRIPTION
            "ParaLen."
        ::= { plaPm30sHisEntry 2 }

    -- 1.3.6.1.4.1.2011.2.25.3.70.20.227.110.1.3
    plaPm30sHisPara OBJECT-TYPE
        SYNTAX OCTET STRING (SIZE (0..100))
        MAX-ACCESS read-only
        STATUS current
        DESCRIPTION
            "para"
        ::= { plaPm30sHisEntry 3 }

    -- 1.3.6.1.4.1.2011.2.25.3.70.20.227.110.1.4
    plaPm30sHisMonValue OBJECT-TYPE
        SYNTAX Counter64
        MAX-ACCESS read-only
        STATUS current
        DESCRIPTION
            "DataPmMonValue."
        ::= { plaPm30sHisEntry 4 }

    -- 1.3.6.1.4.1.2011.2.25.3.70.20.227.110.1.5
    plaPm30sHisStartTime OBJECT-TYPE
        SYNTAX DateAndTime
        MAX-ACCESS read-only
        STATUS current
        DESCRIPTION
            "Start Time."
        ::= { plaPm30sHisEntry 5 }

    -- 1.3.6.1.4.1.2011.2.25.3.70.20.227.110.1.6
    plaPm30sHisEndTime OBJECT-TYPE
        SYNTAX DateAndTime
        MAX-ACCESS read-only
        STATUS current
        DESCRIPTION
            "End Time."
        ::= { plaPm30sHisEntry 6 }

    -- 1.3.6.1.4.1.2011.2.25.3.70.20.227.110.1.7
    plaPm30sHisVldty OBJECT-TYPE
        SYNTAX ValidflagType
        MAX-ACCESS read-only
        STATUS current
        DESCRIPTION
            "Validity."
        ::= { plaPm30sHisEntry 7 }

    -- 1.3.6.1.4.1.2011.2.25.3.70.20.227.120
    plaPm30mHisTable OBJECT-TYPE
        SYNTAX SEQUENCE OF PlaPm30mHisEntry
        MAX-ACCESS not-accessible
        STATUS current
        DESCRIPTION
            "plaPm30mHis."
        ::= { pla 120 }

    -- 1.3.6.1.4.1.2011.2.25.3.70.20.227.120.1
    plaPm30mHisEntry OBJECT-TYPE
        SYNTAX PlaPm30mHisEntry
        MAX-ACCESS not-accessible
        STATUS current
        DESCRIPTION
            "plaPm30mHis."
        INDEX{ plaPm30mHisEid, plaPm30mHisParaLen, plaPm30mHisPara, plaPm30mHisStartTime, plaPm30mHisEndTime }
        ::= { plaPm30mHisTable 1 }

    PlaPm30mHisEntry ::=
        SEQUENCE {
            plaPm30mHisEid
                DataPmEventType,
            plaPm30mHisParaLen
                Unsigned32,
            plaPm30mHisPara
                OCTET STRING,
            plaPm30mHisMonValue
                Counter64,
            plaPm30mHisStartTime
                DateAndTime,
            plaPm30mHisEndTime
                DateAndTime,
            plaPm30mHisVldty
                ValidflagType
        }

    -- 1.3.6.1.4.1.2011.2.25.3.70.20.227.120.1.1
    plaPm30mHisEid OBJECT-TYPE
        SYNTAX DataPmEventType
        MAX-ACCESS read-only
        STATUS current
        DESCRIPTION
            "DataPmEid."
        ::= { plaPm30mHisEntry 1 }

    -- 1.3.6.1.4.1.2011.2.25.3.70.20.227.120.1.2
    plaPm30mHisParaLen OBJECT-TYPE
        SYNTAX Unsigned32
        MAX-ACCESS read-only
        STATUS current
        DESCRIPTION
            "ParaLen."
        ::= { plaPm30mHisEntry 2 }

    -- 1.3.6.1.4.1.2011.2.25.3.70.20.227.120.1.3
    plaPm30mHisPara OBJECT-TYPE
        SYNTAX OCTET STRING (SIZE(0..100))
        MAX-ACCESS read-only
        STATUS current
        DESCRIPTION
            "para"
        ::= { plaPm30mHisEntry 3 }

    -- 1.3.6.1.4.1.2011.2.25.3.70.20.227.120.1.4
    plaPm30mHisMonValue OBJECT-TYPE
        SYNTAX Counter64
        MAX-ACCESS read-only
        STATUS current
        DESCRIPTION
            "DataPmMonValue."
        ::= { plaPm30mHisEntry 4 }

    -- 1.3.6.1.4.1.2011.2.25.3.70.20.227.120.1.5
    plaPm30mHisStartTime OBJECT-TYPE
        SYNTAX DateAndTime
        MAX-ACCESS read-only
        STATUS current
        DESCRIPTION
            "Start Time."
        ::= { plaPm30mHisEntry 5 }

    -- 1.3.6.1.4.1.2011.2.25.3.70.20.227.120.1.6
    plaPm30mHisEndTime OBJECT-TYPE
        SYNTAX DateAndTime
        MAX-ACCESS read-only
        STATUS current
        DESCRIPTION
            "End Time."
        ::= { plaPm30mHisEntry 6 }

    -- 1.3.6.1.4.1.2011.2.25.3.70.20.227.120.1.7
    plaPm30mHisVldty OBJECT-TYPE
        SYNTAX ValidflagType
        MAX-ACCESS read-only
        STATUS current
        DESCRIPTION
            "Validity."
        ::= { plaPm30mHisEntry 7 }

    -- 1.3.6.1.4.1.2011.2.25.3.70.20.227.130
    plaPmvar1HisTable OBJECT-TYPE
        SYNTAX SEQUENCE OF PlaPmvar1HisEntry
        MAX-ACCESS not-accessible
        STATUS current
        DESCRIPTION
            "plaPmvar1His."
        ::= { pla 130 }

    -- 1.3.6.1.4.1.2011.2.25.3.70.20.227.130.1
    plaPmvar1HisEntry OBJECT-TYPE
        SYNTAX PlaPmvar1HisEntry
        MAX-ACCESS not-accessible
        STATUS current
        DESCRIPTION
            "plaPmvar1His."
        INDEX{ plaPmvar1HisEid, plaPmvar1HisParaLen, plaPmvar1HisPara, plaPmvar1HisStartTime, plaPmvar1HisEndTime }
        ::= { plaPmvar1HisTable 1 }

    PlaPmvar1HisEntry ::=
        SEQUENCE {
            plaPmvar1HisEid
                DataPmEventType,
            plaPmvar1HisParaLen
                Unsigned32,
            plaPmvar1HisPara
                OCTET STRING,
            plaPmvar1HisMonValue
                Counter64,
            plaPmvar1HisStartTime
                DateAndTime,
            plaPmvar1HisEndTime
                DateAndTime,
            plaPmvar1HisVldty
                ValidflagType
        }

    -- 1.3.6.1.4.1.2011.2.25.3.70.20.227.130.1.1
    plaPmvar1HisEid OBJECT-TYPE
        SYNTAX DataPmEventType
        MAX-ACCESS read-only
        STATUS current
        DESCRIPTION
            "DataPmEid."
        ::= { plaPmvar1HisEntry 1 }

    -- 1.3.6.1.4.1.2011.2.25.3.70.20.227.130.1.2
    plaPmvar1HisParaLen OBJECT-TYPE
        SYNTAX Unsigned32
        MAX-ACCESS read-only
        STATUS current
        DESCRIPTION
            "ParaLen."
        ::= { plaPmvar1HisEntry 2 }

    -- 1.3.6.1.4.1.2011.2.25.3.70.20.227.130.1.3
    plaPmvar1HisPara OBJECT-TYPE
        SYNTAX OCTET STRING (SIZE (0..100))
        MAX-ACCESS read-only
        STATUS current
        DESCRIPTION
            "para"
        ::= { plaPmvar1HisEntry 3 }

    -- 1.3.6.1.4.1.2011.2.25.3.70.20.227.130.1.4
    plaPmvar1HisMonValue OBJECT-TYPE
        SYNTAX Counter64
        MAX-ACCESS read-only
        STATUS current
        DESCRIPTION
            "DataPmMonValue."
        ::= { plaPmvar1HisEntry 4 }

    -- 1.3.6.1.4.1.2011.2.25.3.70.20.227.130.1.5
    plaPmvar1HisStartTime OBJECT-TYPE
        SYNTAX DateAndTime
        MAX-ACCESS read-only
        STATUS current
        DESCRIPTION
            "Start Time."
        ::= { plaPmvar1HisEntry 5 }

    -- 1.3.6.1.4.1.2011.2.25.3.70.20.227.130.1.6
    plaPmvar1HisEndTime OBJECT-TYPE
        SYNTAX DateAndTime
        MAX-ACCESS read-only
        STATUS current
        DESCRIPTION
            "End Time."
        ::= { plaPmvar1HisEntry 6 }

    -- 1.3.6.1.4.1.2011.2.25.3.70.20.227.130.1.7
    plaPmvar1HisVldty OBJECT-TYPE
        SYNTAX ValidflagType
        MAX-ACCESS read-only
        STATUS current
        DESCRIPTION
            "Validity."
        ::= { plaPmvar1HisEntry 7 }

    -- 1.3.6.1.4.1.2011.2.25.3.70.20.227.140
    plaPmvar2HisTable OBJECT-TYPE
        SYNTAX SEQUENCE OF PlaPmvar2HisEntry
        MAX-ACCESS not-accessible
        STATUS current
        DESCRIPTION
            "plaPmvar2His."
        ::= { pla 140 }

    -- 1.3.6.1.4.1.2011.2.25.3.70.20.227.140.1
    plaPmvar2HisEntry OBJECT-TYPE
        SYNTAX PlaPmvar2HisEntry
        MAX-ACCESS not-accessible
        STATUS current
        DESCRIPTION
            "plaPmvar2His."
        INDEX{ plaPmvar2HisEid, plaPmvar2HisParaLen, plaPmvar2HisPara, plaPmvar2HisStartTime, plaPmvar2HisEndTime }
        ::= { plaPmvar2HisTable 1 }

    PlaPmvar2HisEntry ::=
        SEQUENCE {
            plaPmvar2HisEid
                DataPmEventType,
            plaPmvar2HisParaLen
                Unsigned32,
            plaPmvar2HisPara
                OCTET STRING,
            plaPmvar2HisMonValue
                Counter64,
            plaPmvar2HisStartTime
                DateAndTime,
            plaPmvar2HisEndTime
                DateAndTime,
            plaPmvar2HisVldty
                ValidflagType
        }

    -- 1.3.6.1.4.1.2011.2.25.3.70.20.227.140.1.1
    plaPmvar2HisEid OBJECT-TYPE
        SYNTAX DataPmEventType
        MAX-ACCESS read-only
        STATUS current
        DESCRIPTION
            "DataPmEid."
        ::= { plaPmvar2HisEntry 1 }

    -- 1.3.6.1.4.1.2011.2.25.3.70.20.227.140.1.2
    plaPmvar2HisParaLen OBJECT-TYPE
        SYNTAX Unsigned32
        MAX-ACCESS read-only
        STATUS current
        DESCRIPTION
            "ParaLen."
        ::= { plaPmvar2HisEntry 2 }

    -- 1.3.6.1.4.1.2011.2.25.3.70.20.227.140.1.3
    plaPmvar2HisPara OBJECT-TYPE
        SYNTAX OCTET STRING (SIZE (0..100))
        MAX-ACCESS read-only
        STATUS current
        DESCRIPTION
            "para"
        ::= { plaPmvar2HisEntry 3 }

    -- 1.3.6.1.4.1.2011.2.25.3.70.20.227.140.1.4
    plaPmvar2HisMonValue OBJECT-TYPE
        SYNTAX Counter64
        MAX-ACCESS read-only
        STATUS current
        DESCRIPTION
            "DataPmMonValue."
        ::= { plaPmvar2HisEntry 4 }

    -- 1.3.6.1.4.1.2011.2.25.3.70.20.227.140.1.5
    plaPmvar2HisStartTime OBJECT-TYPE
        SYNTAX DateAndTime
        MAX-ACCESS read-only
        STATUS current
        DESCRIPTION
            "Start Time."
        ::= { plaPmvar2HisEntry 5 }

    -- 1.3.6.1.4.1.2011.2.25.3.70.20.227.140.1.6
    plaPmvar2HisEndTime OBJECT-TYPE
        SYNTAX DateAndTime
        MAX-ACCESS read-only
        STATUS current
        DESCRIPTION
            "End Time."
        ::= { plaPmvar2HisEntry 6 }

    -- 1.3.6.1.4.1.2011.2.25.3.70.20.227.140.1.7
    plaPmvar2HisVldty OBJECT-TYPE
        SYNTAX ValidflagType
        MAX-ACCESS read-only
        STATUS current
        DESCRIPTION
            "Validity."
        ::= { plaPmvar2HisEntry 7 }

    -- 1.3.6.1.4.1.2011.2.25.3.70.20.228
    nmsport OBJECT IDENTIFIER ::= { rtnData 228 }

    -- 1.3.6.1.4.1.2011.2.25.3.70.20.228.100
    nmsportPmCurTable OBJECT-TYPE
        SYNTAX SEQUENCE OF NmsportPmCurEntry
        MAX-ACCESS not-accessible
        STATUS current
        DESCRIPTION
            "nmsportDataPm30sCur."
        ::= { nmsport 100 }

    -- 1.3.6.1.4.1.2011.2.25.3.70.20.228.100.1
    nmsportPmCurEntry OBJECT-TYPE
        SYNTAX NmsportPmCurEntry
        MAX-ACCESS not-accessible
        STATUS current
        DESCRIPTION
            "nmsportPmCur."
        INDEX{ nmsportPmCurEid, nmsportPmCurParaLen, nmsportPmCurPara }
        ::= { nmsportPmCurTable 1 }

    NmsportPmCurEntry ::=
        SEQUENCE {
            nmsportPmCurEid
                DataPmEventType,
            nmsportPmCurParaLen
                Unsigned32,
            nmsportPmCurPara
                OCTET STRING,
            nmsportPmCurMonValue
                Counter64,
            nmsportPmCurDatetime
                DateAndTime
        }

    -- 1.3.6.1.4.1.2011.2.25.3.70.20.228.100.1.1
    nmsportPmCurEid OBJECT-TYPE
        SYNTAX DataPmEventType
        MAX-ACCESS read-only
        STATUS current
        DESCRIPTION
            "DataPmEid."
        ::= { nmsportPmCurEntry 1 }

    -- 1.3.6.1.4.1.2011.2.25.3.70.20.228.100.1.2
    nmsportPmCurParaLen OBJECT-TYPE
        SYNTAX Unsigned32
        MAX-ACCESS read-only
        STATUS current
        DESCRIPTION
            "ParaLen."
        ::= { nmsportPmCurEntry 2 }

    -- 1.3.6.1.4.1.2011.2.25.3.70.20.228.100.1.3
    nmsportPmCurPara OBJECT-TYPE
        SYNTAX OCTET STRING
        MAX-ACCESS read-only
        STATUS current
        DESCRIPTION
            "para"
        ::= { nmsportPmCurEntry 3 }

    -- 1.3.6.1.4.1.2011.2.25.3.70.20.228.100.1.4
    nmsportPmCurMonValue OBJECT-TYPE
        SYNTAX Counter64
        MAX-ACCESS read-only
        STATUS current
        DESCRIPTION
            "DataPmMonValue."
        ::= { nmsportPmCurEntry 4 }

    -- 1.3.6.1.4.1.2011.2.25.3.70.20.228.100.1.5
    nmsportPmCurDatetime OBJECT-TYPE
        SYNTAX DateAndTime
        MAX-ACCESS read-only
        STATUS current
        DESCRIPTION
            "Start Time."
        ::= { nmsportPmCurEntry 5 }

    -- 1.3.6.1.4.1.2011.2.25.3.70.20.228.110
    nmsportPm30sHisTable OBJECT-TYPE
        SYNTAX SEQUENCE OF NmsportPm30sHisEntry
        MAX-ACCESS not-accessible
        STATUS current
        DESCRIPTION
            "nmsportDataPm30sHis."
        ::= { nmsport 110 }

    -- 1.3.6.1.4.1.2011.2.25.3.70.20.228.110.1
    nmsportPm30sHisEntry OBJECT-TYPE
        SYNTAX NmsportPm30sHisEntry
        MAX-ACCESS not-accessible
        STATUS current
        DESCRIPTION
            "nmsportDataPm30sHis."
        INDEX{ nmsportPm30sHisEid, nmsportPm30sHisParaLen, nmsportPm30sHisPara, nmsportPm30sHisStartTime, nmsportPm30sHisEndTime }
        ::= { nmsportPm30sHisTable 1 }

    NmsportPm30sHisEntry ::=
        SEQUENCE {
            nmsportPm30sHisEid
                DataPmEventType,
            nmsportPm30sHisParaLen
                Unsigned32,
            nmsportPm30sHisPara
                OCTET STRING,
            nmsportPm30sHisMonValue
                Counter64,
            nmsportPm30sHisStartTime
                DateAndTime,
            nmsportPm30sHisEndTime
                DateAndTime,
            nmsportPm30sHisVldty
                ValidflagType
        }

    -- 1.3.6.1.4.1.2011.2.25.3.70.20.228.110.1.1
    nmsportPm30sHisEid OBJECT-TYPE
        SYNTAX DataPmEventType
        MAX-ACCESS read-only
        STATUS current
        DESCRIPTION
            "DataPmEid."
        ::= { nmsportPm30sHisEntry 1 }

    -- 1.3.6.1.4.1.2011.2.25.3.70.20.228.110.1.2
    nmsportPm30sHisParaLen OBJECT-TYPE
        SYNTAX Unsigned32
        MAX-ACCESS read-only
        STATUS current
        DESCRIPTION
            "ParaLen."
        ::= { nmsportPm30sHisEntry 2 }

    -- 1.3.6.1.4.1.2011.2.25.3.70.20.228.110.1.3
    nmsportPm30sHisPara OBJECT-TYPE
        SYNTAX OCTET STRING (SIZE (0..100))
        MAX-ACCESS read-only
        STATUS current
        DESCRIPTION
            "para"
        ::= { nmsportPm30sHisEntry 3 }

    -- 1.3.6.1.4.1.2011.2.25.3.70.20.228.110.1.4
    nmsportPm30sHisMonValue OBJECT-TYPE
        SYNTAX Counter64
        MAX-ACCESS read-only
        STATUS current
        DESCRIPTION
            "DataPmMonValue."
        ::= { nmsportPm30sHisEntry 4 }

    -- 1.3.6.1.4.1.2011.2.25.3.70.20.228.110.1.5
    nmsportPm30sHisStartTime OBJECT-TYPE
        SYNTAX DateAndTime
        MAX-ACCESS read-only
        STATUS current
        DESCRIPTION
            "Start Time."
        ::= { nmsportPm30sHisEntry 5 }

    -- 1.3.6.1.4.1.2011.2.25.3.70.20.228.110.1.6
    nmsportPm30sHisEndTime OBJECT-TYPE
        SYNTAX DateAndTime
        MAX-ACCESS read-only
        STATUS current
        DESCRIPTION
            "End Time."
        ::= { nmsportPm30sHisEntry 6 }

    -- 1.3.6.1.4.1.2011.2.25.3.70.20.228.110.1.7
    nmsportPm30sHisVldty OBJECT-TYPE
        SYNTAX ValidflagType
        MAX-ACCESS read-only
        STATUS current
        DESCRIPTION
            "Validity."
        ::= { nmsportPm30sHisEntry 7 }

    -- 1.3.6.1.4.1.2011.2.25.3.70.20.228.120
    nmsportPm30mHisTable OBJECT-TYPE
        SYNTAX SEQUENCE OF NmsportPm30mHisEntry
        MAX-ACCESS not-accessible
        STATUS current
        DESCRIPTION
            "nmsportPm30mHis."
        ::= { nmsport 120 }

    -- 1.3.6.1.4.1.2011.2.25.3.70.20.228.120.1
    nmsportPm30mHisEntry OBJECT-TYPE
        SYNTAX NmsportPm30mHisEntry
        MAX-ACCESS not-accessible
        STATUS current
        DESCRIPTION
            "nmsportPm30mHis."
        INDEX{ nmsportPm30mHisEid, nmsportPm30mHisParaLen, nmsportPm30mHisPara, nmsportPm30mHisStartTime, nmsportPm30mHisEndTime }
        ::= { nmsportPm30mHisTable 1 }

    NmsportPm30mHisEntry ::=
        SEQUENCE {
            nmsportPm30mHisEid
                DataPmEventType,
            nmsportPm30mHisParaLen
                Unsigned32,
            nmsportPm30mHisPara
                OCTET STRING,
            nmsportPm30mHisMonValue
                Counter64,
            nmsportPm30mHisStartTime
                DateAndTime,
            nmsportPm30mHisEndTime
                DateAndTime,
            nmsportPm30mHisVldty
                ValidflagType
        }

    -- 1.3.6.1.4.1.2011.2.25.3.70.20.228.120.1.1
    nmsportPm30mHisEid OBJECT-TYPE
        SYNTAX DataPmEventType
        MAX-ACCESS read-only
        STATUS current
        DESCRIPTION
            "DataPmEid."
        ::= { nmsportPm30mHisEntry 1 }

    -- 1.3.6.1.4.1.2011.2.25.3.70.20.228.120.1.2
    nmsportPm30mHisParaLen OBJECT-TYPE
        SYNTAX Unsigned32
        MAX-ACCESS read-only
        STATUS current
        DESCRIPTION
            "ParaLen."
        ::= { nmsportPm30mHisEntry 2 }

    -- 1.3.6.1.4.1.2011.2.25.3.70.20.228.120.1.3
    nmsportPm30mHisPara OBJECT-TYPE
        SYNTAX OCTET STRING (SIZE (0..100))
        MAX-ACCESS read-only
        STATUS current
        DESCRIPTION
            "para"
        ::= { nmsportPm30mHisEntry 3 }

    -- 1.3.6.1.4.1.2011.2.25.3.70.20.228.120.1.4
    nmsportPm30mHisMonValue OBJECT-TYPE
        SYNTAX Counter64
        MAX-ACCESS read-only
        STATUS current
        DESCRIPTION
            "DataPmMonValue."
        ::= { nmsportPm30mHisEntry 4 }

    -- 1.3.6.1.4.1.2011.2.25.3.70.20.228.120.1.5
    nmsportPm30mHisStartTime OBJECT-TYPE
        SYNTAX DateAndTime
        MAX-ACCESS read-only
        STATUS current
        DESCRIPTION
            "Start Time."
        ::= { nmsportPm30mHisEntry 5 }

    -- 1.3.6.1.4.1.2011.2.25.3.70.20.228.120.1.6
    nmsportPm30mHisEndTime OBJECT-TYPE
        SYNTAX DateAndTime
        MAX-ACCESS read-only
        STATUS current
        DESCRIPTION
            "End Time."
        ::= { nmsportPm30mHisEntry 6 }

    -- 1.3.6.1.4.1.2011.2.25.3.70.20.228.120.1.7
    nmsportPm30mHisVldty OBJECT-TYPE
        SYNTAX ValidflagType
        MAX-ACCESS read-only
        STATUS current
        DESCRIPTION
            "Validity."
        ::= { nmsportPm30mHisEntry 7 }

    -- 1.3.6.1.4.1.2011.2.25.3.70.20.228.130
    nmsportPmvar1HisTable OBJECT-TYPE
        SYNTAX SEQUENCE OF NmsportPmvar1HisEntry
        MAX-ACCESS not-accessible
        STATUS current
        DESCRIPTION
            "nmsportPmvar1His."
        ::= { nmsport 130 }

    -- 1.3.6.1.4.1.2011.2.25.3.70.20.228.130.1
    nmsportPmvar1HisEntry OBJECT-TYPE
        SYNTAX NmsportPmvar1HisEntry
        MAX-ACCESS not-accessible
        STATUS current
        DESCRIPTION
            "nmsportPmvar1His."
        INDEX{ nmsportPmvar1HisEid, nmsportPmvar1HisParaLen, nmsportPmvar1HisPara, nmsportPmvar1HisStartTime, nmsportPmvar1HisEndTime }
        ::= { nmsportPmvar1HisTable 1 }

    NmsportPmvar1HisEntry ::=
        SEQUENCE {
            nmsportPmvar1HisEid
                DataPmEventType,
            nmsportPmvar1HisParaLen
                Unsigned32,
            nmsportPmvar1HisPara
                OCTET STRING,
            nmsportPmvar1HisMonValue
                Counter64,
            nmsportPmvar1HisStartTime
                DateAndTime,
            nmsportPmvar1HisEndTime
                DateAndTime,
            nmsportPmvar1HisVldty
                ValidflagType
        }

    -- 1.3.6.1.4.1.2011.2.25.3.70.20.228.130.1.1
    nmsportPmvar1HisEid OBJECT-TYPE
        SYNTAX DataPmEventType
        MAX-ACCESS read-only
        STATUS current
        DESCRIPTION
            "DataPmEid."
        ::= { nmsportPmvar1HisEntry 1 }

    -- 1.3.6.1.4.1.2011.2.25.3.70.20.228.130.1.2
    nmsportPmvar1HisParaLen OBJECT-TYPE
        SYNTAX Unsigned32
        MAX-ACCESS read-only
        STATUS current
        DESCRIPTION
            "ParaLen."
        ::= { nmsportPmvar1HisEntry 2 }

    -- 1.3.6.1.4.1.2011.2.25.3.70.20.228.130.1.3
    nmsportPmvar1HisPara OBJECT-TYPE
        SYNTAX OCTET STRING (SIZE (0..100))
        MAX-ACCESS read-only
        STATUS current
        DESCRIPTION
            "para"
        ::= { nmsportPmvar1HisEntry 3 }

    -- 1.3.6.1.4.1.2011.2.25.3.70.20.228.130.1.4
    nmsportPmvar1HisMonValue OBJECT-TYPE
        SYNTAX Counter64
        MAX-ACCESS read-only
        STATUS current
        DESCRIPTION
            "DataPmMonValue."
        ::= { nmsportPmvar1HisEntry 4 }

    -- 1.3.6.1.4.1.2011.2.25.3.70.20.228.130.1.5
    nmsportPmvar1HisStartTime OBJECT-TYPE
        SYNTAX DateAndTime
        MAX-ACCESS read-only
        STATUS current
        DESCRIPTION
            "Start Time."
        ::= { nmsportPmvar1HisEntry 5 }

    -- 1.3.6.1.4.1.2011.2.25.3.70.20.228.130.1.6
    nmsportPmvar1HisEndTime OBJECT-TYPE
        SYNTAX DateAndTime
        MAX-ACCESS read-only
        STATUS current
        DESCRIPTION
            "End Time."
        ::= { nmsportPmvar1HisEntry 6 }

    -- 1.3.6.1.4.1.2011.2.25.3.70.20.228.130.1.7
    nmsportPmvar1HisVldty OBJECT-TYPE
        SYNTAX ValidflagType
        MAX-ACCESS read-only
        STATUS current
        DESCRIPTION
            "Validity."
        ::= { nmsportPmvar1HisEntry 7 }

    -- 1.3.6.1.4.1.2011.2.25.3.70.20.228.140
    nmsportPmvar2HisTable OBJECT-TYPE
        SYNTAX SEQUENCE OF NmsportPmvar2HisEntry
        MAX-ACCESS not-accessible
        STATUS current
        DESCRIPTION
            "nmsportPmvar2His."
        ::= { nmsport 140 }

    -- 1.3.6.1.4.1.2011.2.25.3.70.20.228.140.1
    nmsportPmvar2HisEntry OBJECT-TYPE
        SYNTAX NmsportPmvar2HisEntry
        MAX-ACCESS not-accessible
        STATUS current
        DESCRIPTION
            "nmsportPmvar2His."
        INDEX{ nmsportPmvar2HisEid, nmsportPmvar2HisParaLen, nmsportPmvar2HisPara, nmsportPmvar2HisStartTime, nmsportPmvar2HisEndTime }
        ::= { nmsportPmvar2HisTable 1 }

    NmsportPmvar2HisEntry ::=
        SEQUENCE {
            nmsportPmvar2HisEid
                DataPmEventType,
            nmsportPmvar2HisParaLen
                Unsigned32,
            nmsportPmvar2HisPara
                OCTET STRING,
            nmsportPmvar2HisMonValue
                Counter64,
            nmsportPmvar2HisStartTime
                DateAndTime,
            nmsportPmvar2HisEndTime
                DateAndTime,
            nmsportPmvar2HisVldty
                ValidflagType
        }

    -- 1.3.6.1.4.1.2011.2.25.3.70.20.228.140.1.1
    nmsportPmvar2HisEid OBJECT-TYPE
        SYNTAX DataPmEventType
        MAX-ACCESS read-only
        STATUS current
        DESCRIPTION
            "DataPmEid."
        ::= { nmsportPmvar2HisEntry 1 }

    -- 1.3.6.1.4.1.2011.2.25.3.70.20.228.140.1.2
    nmsportPmvar2HisParaLen OBJECT-TYPE
        SYNTAX Unsigned32
        MAX-ACCESS read-only
        STATUS current
        DESCRIPTION
            "ParaLen."
        ::= { nmsportPmvar2HisEntry 2 }

    -- 1.3.6.1.4.1.2011.2.25.3.70.20.228.140.1.3
    nmsportPmvar2HisPara OBJECT-TYPE
        SYNTAX OCTET STRING
        MAX-ACCESS read-only
        STATUS current
        DESCRIPTION
            "para"
        ::= { nmsportPmvar2HisEntry 3 }

    -- 1.3.6.1.4.1.2011.2.25.3.70.20.228.140.1.4
    nmsportPmvar2HisMonValue OBJECT-TYPE
        SYNTAX Counter64
        MAX-ACCESS read-only
        STATUS current
        DESCRIPTION
            "DataPmMonValue."
        ::= { nmsportPmvar2HisEntry 4 }

    -- 1.3.6.1.4.1.2011.2.25.3.70.20.228.140.1.5
    nmsportPmvar2HisStartTime OBJECT-TYPE
        SYNTAX DateAndTime
        MAX-ACCESS read-only
        STATUS current
        DESCRIPTION
            "Start Time."
        ::= { nmsportPmvar2HisEntry 5 }

    -- 1.3.6.1.4.1.2011.2.25.3.70.20.228.140.1.6
    nmsportPmvar2HisEndTime OBJECT-TYPE
        SYNTAX DateAndTime
        MAX-ACCESS read-only
        STATUS current
        DESCRIPTION
            "End Time."
        ::= { nmsportPmvar2HisEntry 6 }

    -- 1.3.6.1.4.1.2011.2.25.3.70.20.228.140.1.7
    nmsportPmvar2HisVldty OBJECT-TYPE
        SYNTAX ValidflagType
        MAX-ACCESS read-only
        STATUS current
        DESCRIPTION
            "Validity."
        ::= { nmsportPmvar2HisEntry 7 }

    -- 1.3.6.1.4.1.2011.2.25.3.70.20.230
    testidperf OBJECT IDENTIFIER ::= { rtnData 230 }

    -- 1.3.6.1.4.1.2011.2.25.3.70.20.230.100
    testidperfPmCurTable OBJECT-TYPE
        SYNTAX SEQUENCE OF TestidperfPmCurEntry
        MAX-ACCESS not-accessible
        STATUS current
        DESCRIPTION
            "testidperfDataPm30sCur."
        ::= { testidperf 100 }

    -- 1.3.6.1.4.1.2011.2.25.3.70.20.230.100.1
    testidperfPmCurEntry OBJECT-TYPE
        SYNTAX TestidperfPmCurEntry
        MAX-ACCESS not-accessible
        STATUS current
        DESCRIPTION
            "testidperfPmCur."
        INDEX{ testidperfPmCurEid, testidperfPmCurParaLen, testidperfPmCurPara }
        ::= { testidperfPmCurTable 1 }

    TestidperfPmCurEntry ::=
        SEQUENCE {
            testidperfPmCurEid
                DataPmEventType,
            testidperfPmCurParaLen
                Unsigned32,
            testidperfPmCurPara
                OCTET STRING,
            testidperfPmCurMonValue
                Counter64,
            testidperfPmCurDatetime
                DateAndTime
        }

    -- 1.3.6.1.4.1.2011.2.25.3.70.20.230.100.1.1
    testidperfPmCurEid OBJECT-TYPE
        SYNTAX DataPmEventType
        MAX-ACCESS read-only
        STATUS current
        DESCRIPTION
            "DataPmEid."
        ::= { testidperfPmCurEntry 1 }

    -- 1.3.6.1.4.1.2011.2.25.3.70.20.230.100.1.2
    testidperfPmCurParaLen OBJECT-TYPE
        SYNTAX Unsigned32
        MAX-ACCESS read-only
        STATUS current
        DESCRIPTION
            "ParaLen."
        ::= { testidperfPmCurEntry 2 }

    -- 1.3.6.1.4.1.2011.2.25.3.70.20.230.100.1.3
    testidperfPmCurPara OBJECT-TYPE
        SYNTAX OCTET STRING
        MAX-ACCESS read-only
        STATUS current
        DESCRIPTION
            "para"
        ::= { testidperfPmCurEntry 3 }

    -- 1.3.6.1.4.1.2011.2.25.3.70.20.230.100.1.4
    testidperfPmCurMonValue OBJECT-TYPE
        SYNTAX Counter64
        MAX-ACCESS read-only
        STATUS current
        DESCRIPTION
            "DataPmMonValue."
        ::= { testidperfPmCurEntry 4 }

    -- 1.3.6.1.4.1.2011.2.25.3.70.20.230.100.1.5
    testidperfPmCurDatetime OBJECT-TYPE
        SYNTAX DateAndTime
        MAX-ACCESS read-only
        STATUS current
        DESCRIPTION
            "Start Time."
        ::= { testidperfPmCurEntry 5 }

    -- 1.3.6.1.4.1.2011.2.25.3.70.20.230.110
    testidperfPm30sHisTable OBJECT-TYPE
        SYNTAX SEQUENCE OF TestidperfPm30sHisEntry
        MAX-ACCESS not-accessible
        STATUS current
        DESCRIPTION
            "testidperfDataPm30sHis"
        ::= { testidperf 110 }

    -- 1.3.6.1.4.1.2011.2.25.3.70.20.230.110.1
    testidperfPm30sHisEntry OBJECT-TYPE
        SYNTAX TestidperfPm30sHisEntry
        MAX-ACCESS not-accessible
        STATUS current
        DESCRIPTION
            "testidperfDataPm30sHis"
        INDEX{ testidperfPm30sHisEid, testidperfPm30sHisParaLen, testidperfPm30sHisPara, testidperfPm30sHisStartTime, testidperfPm30sHisEndTime }
        ::= { testidperfPm30sHisTable 1 }

    TestidperfPm30sHisEntry ::=
        SEQUENCE {
            testidperfPm30sHisEid
                DataPmEventType,
            testidperfPm30sHisParaLen
                Unsigned32,
            testidperfPm30sHisPara
                OCTET STRING,
            testidperfPm30sHisMonValue
                Counter64,
            testidperfPm30sHisStartTime
                DateAndTime,
            testidperfPm30sHisEndTime
                DateAndTime,
            testidperfPm30sHisVldty
                ValidflagType
        }

    -- 1.3.6.1.4.1.2011.2.25.3.70.20.230.110.1.1
    testidperfPm30sHisEid OBJECT-TYPE
        SYNTAX DataPmEventType
        MAX-ACCESS read-only
        STATUS current
        DESCRIPTION
            "DataPmEid."
        ::= { testidperfPm30sHisEntry 1 }

    -- 1.3.6.1.4.1.2011.2.25.3.70.20.230.110.1.2
    testidperfPm30sHisParaLen OBJECT-TYPE
        SYNTAX Unsigned32
        MAX-ACCESS read-only
        STATUS current
        DESCRIPTION
            "ParaLen."
        ::= { testidperfPm30sHisEntry 2 }

    -- 1.3.6.1.4.1.2011.2.25.3.70.20.230.110.1.3
    testidperfPm30sHisPara OBJECT-TYPE
        SYNTAX OCTET STRING (SIZE (0..100))
        MAX-ACCESS read-only
        STATUS current
        DESCRIPTION
            "para"
        ::= { testidperfPm30sHisEntry 3 }

    -- 1.3.6.1.4.1.2011.2.25.3.70.20.230.110.1.4
    testidperfPm30sHisMonValue OBJECT-TYPE
        SYNTAX Counter64
        MAX-ACCESS read-only
        STATUS current
        DESCRIPTION
            "DataPmMonValue."
        ::= { testidperfPm30sHisEntry 4 }

    -- 1.3.6.1.4.1.2011.2.25.3.70.20.230.110.1.5
    testidperfPm30sHisStartTime OBJECT-TYPE
        SYNTAX DateAndTime
        MAX-ACCESS read-only
        STATUS current
        DESCRIPTION
            "Start Time."
        ::= { testidperfPm30sHisEntry 5 }

    -- 1.3.6.1.4.1.2011.2.25.3.70.20.230.110.1.6
    testidperfPm30sHisEndTime OBJECT-TYPE
        SYNTAX DateAndTime
        MAX-ACCESS read-only
        STATUS current
        DESCRIPTION
            "End Time."
        ::= { testidperfPm30sHisEntry 6 }

    -- 1.3.6.1.4.1.2011.2.25.3.70.20.230.110.1.7
    testidperfPm30sHisVldty OBJECT-TYPE
        SYNTAX ValidflagType
        MAX-ACCESS read-only
        STATUS current
        DESCRIPTION
            "Validity."
        ::= { testidperfPm30sHisEntry 7 }

    -- 1.3.6.1.4.1.2011.2.25.3.70.20.230.120
    testidperfPm30mHisTable OBJECT-TYPE
        SYNTAX SEQUENCE OF TestidperfPm30mHisEntry
        MAX-ACCESS not-accessible
        STATUS current
        DESCRIPTION
            "testidperfPm30mHis"
        ::= { testidperf 120 }

    -- 1.3.6.1.4.1.2011.2.25.3.70.20.230.120.1
    testidperfPm30mHisEntry OBJECT-TYPE
        SYNTAX TestidperfPm30mHisEntry
        MAX-ACCESS not-accessible
        STATUS current
        DESCRIPTION
            "testidperfPm30mHis."
        INDEX{ testidperfPm30mHisEid, testidperfPm30mHisParaLen, testidperfPm30mHisPara, testidperfPm30mHisStartTime, testidperfPm30mHisEndTime }
        ::= { testidperfPm30mHisTable 1 }

    TestidperfPm30mHisEntry ::=
        SEQUENCE {
            testidperfPm30mHisEid
                DataPmEventType,
            testidperfPm30mHisParaLen
                Unsigned32,
            testidperfPm30mHisPara
                OCTET STRING,
            testidperfPm30mHisMonValue
                Counter64,
            testidperfPm30mHisStartTime
                DateAndTime,
            testidperfPm30mHisEndTime
                DateAndTime,
            testidperfPm30mHisVldty
                ValidflagType
        }

    -- 1.3.6.1.4.1.2011.2.25.3.70.20.230.120.1.1
    testidperfPm30mHisEid OBJECT-TYPE
        SYNTAX DataPmEventType
        MAX-ACCESS read-only
        STATUS current
        DESCRIPTION
            "DataPmEid."
        ::= { testidperfPm30mHisEntry 1 }

    -- 1.3.6.1.4.1.2011.2.25.3.70.20.230.120.1.2
    testidperfPm30mHisParaLen OBJECT-TYPE
        SYNTAX Unsigned32
        MAX-ACCESS read-only
        STATUS current
        DESCRIPTION
            "ParaLen."
        ::= { testidperfPm30mHisEntry 2 }

    -- 1.3.6.1.4.1.2011.2.25.3.70.20.230.120.1.3
    testidperfPm30mHisPara OBJECT-TYPE
        SYNTAX OCTET STRING (SIZE (0..100))
        MAX-ACCESS read-only
        STATUS current
        DESCRIPTION
            "para"
        ::= { testidperfPm30mHisEntry 3 }

    -- 1.3.6.1.4.1.2011.2.25.3.70.20.230.120.1.4
    testidperfPm30mHisMonValue OBJECT-TYPE
        SYNTAX Counter64
        MAX-ACCESS read-only
        STATUS current
        DESCRIPTION
            "DataPmMonValue."
        ::= { testidperfPm30mHisEntry 4 }

    -- 1.3.6.1.4.1.2011.2.25.3.70.20.230.120.1.5
    testidperfPm30mHisStartTime OBJECT-TYPE
        SYNTAX DateAndTime
        MAX-ACCESS read-only
        STATUS current
        DESCRIPTION
            "Start Time."
        ::= { testidperfPm30mHisEntry 5 }

    -- 1.3.6.1.4.1.2011.2.25.3.70.20.230.120.1.6
    testidperfPm30mHisEndTime OBJECT-TYPE
        SYNTAX DateAndTime
        MAX-ACCESS read-only
        STATUS current
        DESCRIPTION
            "End Time."
        ::= { testidperfPm30mHisEntry 6 }

    -- 1.3.6.1.4.1.2011.2.25.3.70.20.230.120.1.7
    testidperfPm30mHisVldty OBJECT-TYPE
        SYNTAX ValidflagType
        MAX-ACCESS read-only
        STATUS current
        DESCRIPTION
            "Validity."
        ::= { testidperfPm30mHisEntry 7 }

    -- 1.3.6.1.4.1.2011.2.25.3.70.20.230.130
    testidperfPmvar1HisTable OBJECT-TYPE
        SYNTAX SEQUENCE OF TestidperfPmvar1HisEntry
        MAX-ACCESS not-accessible
        STATUS current
        DESCRIPTION
            "testidperfPmVar1His"
        ::= { testidperf 130 }

    -- 1.3.6.1.4.1.2011.2.25.3.70.20.230.130.1
    testidperfPmvar1HisEntry OBJECT-TYPE
        SYNTAX TestidperfPmvar1HisEntry
        MAX-ACCESS not-accessible
        STATUS current
        DESCRIPTION
            "testidperfPmvar1His."
        INDEX{ testidperfPmvar1HisEid, testidperfPmvar1HisParaLen, testidperfPmvar1HisPara, testidperfPmvar1HisStartTime, testidperfPmvar1HisEndTime }
        ::= { testidperfPmvar1HisTable 1 }

    TestidperfPmvar1HisEntry ::=
        SEQUENCE {
            testidperfPmvar1HisEid
                DataPmEventType,
            testidperfPmvar1HisParaLen
                Unsigned32,
            testidperfPmvar1HisPara
                OCTET STRING,
            testidperfPmvar1HisMonValue
                Counter64,
            testidperfPmvar1HisStartTime
                DateAndTime,
            testidperfPmvar1HisEndTime
                DateAndTime,
            testidperfPmvar1HisVldty
                ValidflagType
        }

    -- 1.3.6.1.4.1.2011.2.25.3.70.20.230.130.1.1
    testidperfPmvar1HisEid OBJECT-TYPE
        SYNTAX DataPmEventType
        MAX-ACCESS read-only
        STATUS current
        DESCRIPTION
            "DataPmEid."
        ::= { testidperfPmvar1HisEntry 1 }

    -- 1.3.6.1.4.1.2011.2.25.3.70.20.230.130.1.2
    testidperfPmvar1HisParaLen OBJECT-TYPE
        SYNTAX Unsigned32
        MAX-ACCESS read-only
        STATUS current
        DESCRIPTION
            "ParaLen."
        ::= { testidperfPmvar1HisEntry 2 }

    -- 1.3.6.1.4.1.2011.2.25.3.70.20.230.130.1.3
    testidperfPmvar1HisPara OBJECT-TYPE
        SYNTAX OCTET STRING (SIZE (0..100))
        MAX-ACCESS read-only
        STATUS current
        DESCRIPTION
            "para"
        ::= { testidperfPmvar1HisEntry 3 }

    -- 1.3.6.1.4.1.2011.2.25.3.70.20.230.130.1.4
    testidperfPmvar1HisMonValue OBJECT-TYPE
        SYNTAX Counter64
        MAX-ACCESS read-only
        STATUS current
        DESCRIPTION
            "DataPmMonValue."
        ::= { testidperfPmvar1HisEntry 4 }

    -- 1.3.6.1.4.1.2011.2.25.3.70.20.230.130.1.5
    testidperfPmvar1HisStartTime OBJECT-TYPE
        SYNTAX DateAndTime
        MAX-ACCESS read-only
        STATUS current
        DESCRIPTION
            "Start Time."
        ::= { testidperfPmvar1HisEntry 5 }

    -- 1.3.6.1.4.1.2011.2.25.3.70.20.230.130.1.6
    testidperfPmvar1HisEndTime OBJECT-TYPE
        SYNTAX DateAndTime
        MAX-ACCESS read-only
        STATUS current
        DESCRIPTION
            "End Time."
        ::= { testidperfPmvar1HisEntry 6 }

    -- 1.3.6.1.4.1.2011.2.25.3.70.20.230.130.1.7
    testidperfPmvar1HisVldty OBJECT-TYPE
        SYNTAX ValidflagType
        MAX-ACCESS read-only
        STATUS current
        DESCRIPTION
            "Validity."
        ::= { testidperfPmvar1HisEntry 7 }

    -- 1.3.6.1.4.1.2011.2.25.3.70.20.230.140
    testidperfPmvar2HisTable OBJECT-TYPE
        SYNTAX SEQUENCE OF TestidperfPmvar2HisEntry
        MAX-ACCESS not-accessible
        STATUS current
        DESCRIPTION
            "testidperfPmvar2His"
        ::= { testidperf 140 }

    -- 1.3.6.1.4.1.2011.2.25.3.70.20.230.140.1
    testidperfPmvar2HisEntry OBJECT-TYPE
        SYNTAX TestidperfPmvar2HisEntry
        MAX-ACCESS not-accessible
        STATUS current
        DESCRIPTION
            "testidperfPmvar2His."
        INDEX{ testidperfPmvar2HisEid, testidperfPmvar2HisParaLen, testidperfPmvar2HisPara, testidperfPmvar2HisStartTime, testidperfPmvar2HisEndTime }
        ::= { testidperfPmvar2HisTable 1 }

    TestidperfPmvar2HisEntry ::=
        SEQUENCE {
            testidperfPmvar2HisEid
                DataPmEventType,
            testidperfPmvar2HisParaLen
                Unsigned32,
            testidperfPmvar2HisPara
                OCTET STRING,
            testidperfPmvar2HisMonValue
                Counter64,
            testidperfPmvar2HisStartTime
                DateAndTime,
            testidperfPmvar2HisEndTime
                DateAndTime,
            testidperfPmvar2HisVldty
                ValidflagType
        }

    -- 1.3.6.1.4.1.2011.2.25.3.70.20.230.140.1.1
    testidperfPmvar2HisEid OBJECT-TYPE
        SYNTAX DataPmEventType
        MAX-ACCESS read-only
        STATUS current
        DESCRIPTION
            "DataPmEid."
        ::= { testidperfPmvar2HisEntry 1 }

    -- 1.3.6.1.4.1.2011.2.25.3.70.20.230.140.1.2
    testidperfPmvar2HisParaLen OBJECT-TYPE
        SYNTAX Unsigned32
        MAX-ACCESS read-only
        STATUS current
        DESCRIPTION
            "ParaLen."
        ::= { testidperfPmvar2HisEntry 2 }

    -- 1.3.6.1.4.1.2011.2.25.3.70.20.230.140.1.3
    testidperfPmvar2HisPara OBJECT-TYPE
        SYNTAX OCTET STRING (SIZE (0..100))
        MAX-ACCESS read-only
        STATUS current
        DESCRIPTION
            "para"
        ::= { testidperfPmvar2HisEntry 3 }

    -- 1.3.6.1.4.1.2011.2.25.3.70.20.230.140.1.4
    testidperfPmvar2HisMonValue OBJECT-TYPE
        SYNTAX Counter64
        MAX-ACCESS read-only
        STATUS current
        DESCRIPTION
            "DataPmMonValue."
        ::= { testidperfPmvar2HisEntry 4 }

    -- 1.3.6.1.4.1.2011.2.25.3.70.20.230.140.1.5
    testidperfPmvar2HisStartTime OBJECT-TYPE
        SYNTAX DateAndTime
        MAX-ACCESS read-only
        STATUS current
        DESCRIPTION
            "Start Time."
        ::= { testidperfPmvar2HisEntry 5 }

    -- 1.3.6.1.4.1.2011.2.25.3.70.20.230.140.1.6
    testidperfPmvar2HisEndTime OBJECT-TYPE
        SYNTAX DateAndTime
        MAX-ACCESS read-only
        STATUS current
        DESCRIPTION
            "End Time."
        ::= { testidperfPmvar2HisEntry 6 }

    -- 1.3.6.1.4.1.2011.2.25.3.70.20.230.140.1.7
    testidperfPmvar2HisVldty OBJECT-TYPE
        SYNTAX ValidflagType
        MAX-ACCESS read-only
        STATUS current
        DESCRIPTION
            "Validity."
        ::= { testidperfPmvar2HisEntry 7 }

    -- 1.3.6.1.4.1.2011.2.25.3.70.20.253
    xpic OBJECT IDENTIFIER ::= { rtnData 253 }

    -- 1.3.6.1.4.1.2011.2.25.3.70.20.253.100
    xpicPmCurTable OBJECT-TYPE
        SYNTAX SEQUENCE OF XpicPmCurEntry
        MAX-ACCESS not-accessible
        STATUS current
        DESCRIPTION
            "xpicDataPm30sCur."
        ::= { xpic 100 }

    -- 1.3.6.1.4.1.2011.2.25.3.70.20.253.100.1
    xpicPmCurEntry OBJECT-TYPE
        SYNTAX XpicPmCurEntry
        MAX-ACCESS not-accessible
        STATUS current
        DESCRIPTION
            "xpicPmCur."
        INDEX{ xpicPmCurEid,xpicPmCurParaLen,xpicPmCurPara }
        ::= { xpicPmCurTable 1 }

    XpicPmCurEntry ::=
        SEQUENCE {
            xpicPmCurEid
                DataPmEventType,
            xpicPmCurParaLen
                Unsigned32,
            xpicPmCurPara
                OCTET STRING,
            xpicPmCurMonValue
                Counter64,
            xpicPmCurDatetime
                DateAndTime
        }

    -- 1.3.6.1.4.1.2011.2.25.3.70.20.253.100.1.1
    xpicPmCurEid OBJECT-TYPE
        SYNTAX DataPmEventType
        MAX-ACCESS read-only
        STATUS current
        DESCRIPTION
            "DataPmEid."
        ::= { xpicPmCurEntry 1 }

    -- 1.3.6.1.4.1.2011.2.25.3.70.20.253.100.1.2
    xpicPmCurParaLen OBJECT-TYPE
        SYNTAX Unsigned32
        MAX-ACCESS read-only
        STATUS current
        DESCRIPTION
            "ParaLen."
        ::= { xpicPmCurEntry 2 }

    -- 1.3.6.1.4.1.2011.2.25.3.70.20.253.100.1.3
    xpicPmCurPara OBJECT-TYPE
        SYNTAX OCTET STRING
        MAX-ACCESS read-only
        STATUS current
        DESCRIPTION
            "para"
        ::= { xpicPmCurEntry 3 }

    -- 1.3.6.1.4.1.2011.2.25.3.70.20.253.100.1.4
    xpicPmCurMonValue OBJECT-TYPE
        SYNTAX Counter64
        MAX-ACCESS read-only
        STATUS current
        DESCRIPTION
            "DataPmMonValue."
        ::= { xpicPmCurEntry 4 }

    -- 1.3.6.1.4.1.2011.2.25.3.70.20.253.100.1.5
    xpicPmCurDatetime OBJECT-TYPE
        SYNTAX DateAndTime
        MAX-ACCESS read-only
        STATUS current
        DESCRIPTION
            "Start Time."
        ::= { xpicPmCurEntry 5 }

    -- 1.3.6.1.4.1.2011.2.25.3.70.20.253.110
    xpicPm30sHisTable OBJECT-TYPE
        SYNTAX SEQUENCE OF XpicPm30sHisEntry
        MAX-ACCESS not-accessible
        STATUS current
        DESCRIPTION
            "xpicDataPm30sHis."
        ::= { xpic 110 }

    -- 1.3.6.1.4.1.2011.2.25.3.70.20.253.110.1
    xpicPm30sHisEntry OBJECT-TYPE
        SYNTAX XpicPm30sHisEntry
        MAX-ACCESS not-accessible
        STATUS current
        DESCRIPTION
            "xpicDataPm30sHis."
        INDEX{ xpicPm30sHisEid,xpicPm30sHisParaLen,xpicPm30sHisPara,xpicPm30sHisStartTime,xpicPm30sHisEndTime }
        ::= { xpicPm30sHisTable 1 }

    XpicPm30sHisEntry ::=
        SEQUENCE {
            xpicPm30sHisEid
                DataPmEventType,
            xpicPm30sHisParaLen
                Unsigned32,
            xpicPm30sHisPara
                OCTET STRING,
            xpicPm30sHisMonValue
                Counter64,
            xpicPm30sHisStartTime
                DateAndTime,
            xpicPm30sHisEndTime
                DateAndTime,
            xpicPm30sHisVldty
                ValidflagType
        }

    -- 1.3.6.1.4.1.2011.2.25.3.70.20.253.110.1.1
    xpicPm30sHisEid OBJECT-TYPE
        SYNTAX DataPmEventType
        MAX-ACCESS read-only
        STATUS current
        DESCRIPTION
            "DataPmEid."
        ::= { xpicPm30sHisEntry 1 }

    -- 1.3.6.1.4.1.2011.2.25.3.70.20.253.110.1.2
    xpicPm30sHisParaLen OBJECT-TYPE
        SYNTAX Unsigned32
        MAX-ACCESS read-only
        STATUS current
        DESCRIPTION
            "ParaLen."
        ::= { xpicPm30sHisEntry 2 }

    -- 1.3.6.1.4.1.2011.2.25.3.70.20.253.110.1.3
    xpicPm30sHisPara OBJECT-TYPE
        SYNTAX OCTET STRING(SIZE (0..100))
        MAX-ACCESS read-only
        STATUS current
        DESCRIPTION
            "para"
        ::= { xpicPm30sHisEntry 3 }

    -- 1.3.6.1.4.1.2011.2.25.3.70.20.253.110.1.4
    xpicPm30sHisMonValue OBJECT-TYPE
        SYNTAX Counter64
        MAX-ACCESS read-only
        STATUS current
        DESCRIPTION
            "DataPmMonValue."
        ::= { xpicPm30sHisEntry 4 }

    -- 1.3.6.1.4.1.2011.2.25.3.70.20.253.110.1.5
    xpicPm30sHisStartTime OBJECT-TYPE
        SYNTAX DateAndTime
        MAX-ACCESS read-only
        STATUS current
        DESCRIPTION
            "Start Time."
        ::= { xpicPm30sHisEntry 5 }

    -- 1.3.6.1.4.1.2011.2.25.3.70.20.253.110.1.6
    xpicPm30sHisEndTime OBJECT-TYPE
        SYNTAX DateAndTime
        MAX-ACCESS read-only
        STATUS current
        DESCRIPTION
            "End Time."
        ::= { xpicPm30sHisEntry 6 }

    -- 1.3.6.1.4.1.2011.2.25.3.70.20.253.110.1.7
    xpicPm30sHisVldty OBJECT-TYPE
        SYNTAX ValidflagType
        MAX-ACCESS read-only
        STATUS current
        DESCRIPTION
            "Validity."
        ::= { xpicPm30sHisEntry 7 }

    -- 1.3.6.1.4.1.2011.2.25.3.70.20.253.120
    xpicPm30mHisTable OBJECT-TYPE
        SYNTAX SEQUENCE OF XpicPm30mHisEntry
        MAX-ACCESS not-accessible
        STATUS current
        DESCRIPTION
            "xpicPm30mHis."
        ::= { xpic 120 }

    -- 1.3.6.1.4.1.2011.2.25.3.70.20.253.120.1
    xpicPm30mHisEntry OBJECT-TYPE
        SYNTAX XpicPm30mHisEntry
        MAX-ACCESS not-accessible
        STATUS current
        DESCRIPTION
            "xpicPm30mHis."
        INDEX{ xpicPm30mHisEid,xpicPm30mHisParaLen,xpicPm30mHisPara,xpicPm30mHisStartTime,xpicPm30mHisEndTime }
        ::= { xpicPm30mHisTable 1 }

    XpicPm30mHisEntry ::=
        SEQUENCE {
            xpicPm30mHisEid
                DataPmEventType,
            xpicPm30mHisParaLen
                Unsigned32,
            xpicPm30mHisPara
                OCTET STRING,
            xpicPm30mHisMonValue
                Counter64,
            xpicPm30mHisStartTime
                DateAndTime,
            xpicPm30mHisEndTime
                DateAndTime,
            xpicPm30mHisVldty
                ValidflagType
        }

    -- 1.3.6.1.4.1.2011.2.25.3.70.20.253.120.1.1
    xpicPm30mHisEid OBJECT-TYPE
        SYNTAX DataPmEventType
        MAX-ACCESS read-only
        STATUS current
        DESCRIPTION
            "DataPmEid."
        ::= { xpicPm30mHisEntry 1 }

    -- 1.3.6.1.4.1.2011.2.25.3.70.20.253.120.1.2
    xpicPm30mHisParaLen OBJECT-TYPE
        SYNTAX Unsigned32
        MAX-ACCESS read-only
        STATUS current
        DESCRIPTION
            "ParaLen."
        ::= { xpicPm30mHisEntry 2 }

    -- 1.3.6.1.4.1.2011.2.25.3.70.20.253.120.1.3
    xpicPm30mHisPara OBJECT-TYPE
        SYNTAX OCTET STRING(SIZE (0..100))
        MAX-ACCESS read-only
        STATUS current
        DESCRIPTION
            "para"
        ::= { xpicPm30mHisEntry 3 }

    -- 1.3.6.1.4.1.2011.2.25.3.70.20.253.120.1.4
    xpicPm30mHisMonValue OBJECT-TYPE
        SYNTAX Counter64
        MAX-ACCESS read-only
        STATUS current
        DESCRIPTION
            "DataPmMonValue."
        ::= { xpicPm30mHisEntry 4 }

    -- 1.3.6.1.4.1.2011.2.25.3.70.20.253.120.1.5
    xpicPm30mHisStartTime OBJECT-TYPE
        SYNTAX DateAndTime
        MAX-ACCESS read-only
        STATUS current
        DESCRIPTION
            "Start Time."
        ::= { xpicPm30mHisEntry 5 }

    -- 1.3.6.1.4.1.2011.2.25.3.70.20.253.120.1.6
    xpicPm30mHisEndTime OBJECT-TYPE
        SYNTAX DateAndTime
        MAX-ACCESS read-only
        STATUS current
        DESCRIPTION
            "End Time."
        ::= { xpicPm30mHisEntry 6 }

    -- 1.3.6.1.4.1.2011.2.25.3.70.20.253.120.1.7
    xpicPm30mHisVldty OBJECT-TYPE
        SYNTAX ValidflagType
        MAX-ACCESS read-only
        STATUS current
        DESCRIPTION
            "Validity."
        ::= { xpicPm30mHisEntry 7 }

    -- 1.3.6.1.4.1.2011.2.25.3.70.20.253.130
    xpicPmvar1HisTable OBJECT-TYPE
        SYNTAX SEQUENCE OF XpicPmvar1HisEntry
        MAX-ACCESS not-accessible
        STATUS current
        DESCRIPTION
            "xpicPmvar1His."
        ::= { xpic 130 }

    -- 1.3.6.1.4.1.2011.2.25.3.70.20.253.130.1
    xpicPmvar1HisEntry OBJECT-TYPE
        SYNTAX XpicPmvar1HisEntry
        MAX-ACCESS not-accessible
        STATUS current
        DESCRIPTION
            "xpicPmvar1His."
        INDEX{ xpicPmvar1HisEid,xpicPmvar1HisParaLen,xpicPmvar1HisPara,xpicPmvar1HisStartTime,xpicPmvar1HisEndTime }
        ::= { xpicPmvar1HisTable 1 }

    XpicPmvar1HisEntry ::=
        SEQUENCE {
            xpicPmvar1HisEid
                DataPmEventType,
            xpicPmvar1HisParaLen
                Unsigned32,
            xpicPmvar1HisPara
                OCTET STRING,
            xpicPmvar1HisMonValue
                Counter64,
            xpicPmvar1HisStartTime
                DateAndTime,
            xpicPmvar1HisEndTime
                DateAndTime,
            xpicPmvar1HisVldty
                ValidflagType
        }

    -- 1.3.6.1.4.1.2011.2.25.3.70.20.253.130.1.1
    xpicPmvar1HisEid OBJECT-TYPE
        SYNTAX DataPmEventType
        MAX-ACCESS read-only
        STATUS current
        DESCRIPTION
            "DataPmEid."
        ::= { xpicPmvar1HisEntry 1 }

    -- 1.3.6.1.4.1.2011.2.25.3.70.20.253.130.1.2
    xpicPmvar1HisParaLen OBJECT-TYPE
        SYNTAX Unsigned32
        MAX-ACCESS read-only
        STATUS current
        DESCRIPTION
            "ParaLen."
        ::= { xpicPmvar1HisEntry 2 }

    -- 1.3.6.1.4.1.2011.2.25.3.70.20.253.130.1.3
    xpicPmvar1HisPara OBJECT-TYPE
        SYNTAX OCTET STRING (SIZE (0..100))
        MAX-ACCESS read-only
        STATUS current
        DESCRIPTION
            "para"
        ::= { xpicPmvar1HisEntry 3 }

    -- 1.3.6.1.4.1.2011.2.25.3.70.20.253.130.1.4
    xpicPmvar1HisMonValue OBJECT-TYPE
        SYNTAX Counter64
        MAX-ACCESS read-only
        STATUS current
        DESCRIPTION
            "DataPmMonValue."
        ::= { xpicPmvar1HisEntry 4 }

    -- 1.3.6.1.4.1.2011.2.25.3.70.20.253.130.1.5
    xpicPmvar1HisStartTime OBJECT-TYPE
        SYNTAX DateAndTime
        MAX-ACCESS read-only
        STATUS current
        DESCRIPTION
            "Start Time."
        ::= { xpicPmvar1HisEntry 5 }

    -- 1.3.6.1.4.1.2011.2.25.3.70.20.253.130.1.6
    xpicPmvar1HisEndTime OBJECT-TYPE
        SYNTAX DateAndTime
        MAX-ACCESS read-only
        STATUS current
        DESCRIPTION
            "End Time."
        ::= { xpicPmvar1HisEntry 6 }

    -- 1.3.6.1.4.1.2011.2.25.3.70.20.253.130.1.7
    xpicPmvar1HisVldty OBJECT-TYPE
        SYNTAX ValidflagType
        MAX-ACCESS read-only
        STATUS current
        DESCRIPTION
            "Validity."
        ::= { xpicPmvar1HisEntry 7 }

    -- 1.3.6.1.4.1.2011.2.25.3.70.20.253.140
    xpicPmvar2HisTable OBJECT-TYPE
        SYNTAX SEQUENCE OF XpicPmvar2HisEntry
        MAX-ACCESS not-accessible
        STATUS current
        DESCRIPTION
            "xpicPmvar2His."
        ::= { xpic 140 }

    -- 1.3.6.1.4.1.2011.2.25.3.70.20.253.140.1
    xpicPmvar2HisEntry OBJECT-TYPE
        SYNTAX XpicPmvar2HisEntry
        MAX-ACCESS not-accessible
        STATUS current
        DESCRIPTION
            "xpicPmvar2His."
        INDEX{ xpicPmvar2HisEid,xpicPmvar2HisParaLen,xpicPmvar2HisPara,xpicPmvar2HisStartTime,xpicPmvar2HisEndTime }
        ::= { xpicPmvar2HisTable 1 }

    XpicPmvar2HisEntry ::=
        SEQUENCE {
            xpicPmvar2HisEid
                DataPmEventType,
            xpicPmvar2HisParaLen
                Unsigned32,
            xpicPmvar2HisPara
                OCTET STRING,
            xpicPmvar2HisMonValue
                Counter64,
            xpicPmvar2HisStartTime
                DateAndTime,
            xpicPmvar2HisEndTime
                DateAndTime,
            xpicPmvar2HisVldty
                ValidflagType
        }

    -- 1.3.6.1.4.1.2011.2.25.3.70.20.253.140.1.1
    xpicPmvar2HisEid OBJECT-TYPE
        SYNTAX DataPmEventType
        MAX-ACCESS read-only
        STATUS current
        DESCRIPTION
            "DataPmEid."
        ::= { xpicPmvar2HisEntry 1 }

    -- 1.3.6.1.4.1.2011.2.25.3.70.20.253.140.1.2
    xpicPmvar2HisParaLen OBJECT-TYPE
        SYNTAX Unsigned32
        MAX-ACCESS read-only
        STATUS current
        DESCRIPTION
            "ParaLen."
        ::= { xpicPmvar2HisEntry 2 }

    -- 1.3.6.1.4.1.2011.2.25.3.70.20.253.140.1.3
    xpicPmvar2HisPara OBJECT-TYPE
        SYNTAX OCTET STRING(SIZE (0..100))
        MAX-ACCESS read-only
        STATUS current
        DESCRIPTION
            "para"
        ::= { xpicPmvar2HisEntry 3 }

    -- 1.3.6.1.4.1.2011.2.25.3.70.20.253.140.1.4
    xpicPmvar2HisMonValue OBJECT-TYPE
        SYNTAX Counter64
        MAX-ACCESS read-only
        STATUS current
        DESCRIPTION
            "DataPmMonValue."
        ::= { xpicPmvar2HisEntry 4 }

    -- 1.3.6.1.4.1.2011.2.25.3.70.20.253.140.1.5
    xpicPmvar2HisStartTime OBJECT-TYPE
        SYNTAX DateAndTime
        MAX-ACCESS read-only
        STATUS current
        DESCRIPTION
            "Start Time."
        ::= { xpicPmvar2HisEntry 5 }

    -- 1.3.6.1.4.1.2011.2.25.3.70.20.253.140.1.6
    xpicPmvar2HisEndTime OBJECT-TYPE
        SYNTAX DateAndTime
        MAX-ACCESS read-only
        STATUS current
        DESCRIPTION
            "End Time."
        ::= { xpicPmvar2HisEntry 6 }

    -- 1.3.6.1.4.1.2011.2.25.3.70.20.253.140.1.7
    xpicPmvar2HisVldty OBJECT-TYPE
        SYNTAX ValidflagType
        MAX-ACCESS read-only
        STATUS current
        DESCRIPTION
            "Validity."
        ::= { xpicPmvar2HisEntry 7 }

    -- 1.3.6.1.4.1.2011.2.25.3.70.20.254
    nj1 OBJECT IDENTIFIER ::= { rtnData 254 }

    -- 1.3.6.1.4.1.2011.2.25.3.70.20.254.100
    nj1PmCurTable OBJECT-TYPE
        SYNTAX SEQUENCE OF Nj1PmCurEntry
        MAX-ACCESS not-accessible
        STATUS current
        DESCRIPTION
            "nj1DataPm30sCur."
        ::= { nj1 100 }

    -- 1.3.6.1.4.1.2011.2.25.3.70.20.254.100.1
    nj1PmCurEntry OBJECT-TYPE
        SYNTAX Nj1PmCurEntry
        MAX-ACCESS not-accessible
        STATUS current
        DESCRIPTION
            "nj1PmCur."
        INDEX{ nj1PmCurEid, nj1PmCurParaLen, nj1PmCurPara }
        ::= { nj1PmCurTable 1 }

    Nj1PmCurEntry ::=
        SEQUENCE {
            nj1PmCurEid
                DataPmEventType,
            nj1PmCurParaLen
                Unsigned32,
            nj1PmCurPara
                OCTET STRING,
            nj1PmCurMonValue
                Counter64,
            nj1PmCurDatetime
                DateAndTime
        }

    -- 1.3.6.1.4.1.2011.2.25.3.70.20.254.100.1.1
    nj1PmCurEid OBJECT-TYPE
        SYNTAX DataPmEventType
        MAX-ACCESS read-only
        STATUS current
        DESCRIPTION
            "DataPmEid."
        ::= { nj1PmCurEntry 1 }

    -- 1.3.6.1.4.1.2011.2.25.3.70.20.254.100.1.2
    nj1PmCurParaLen OBJECT-TYPE
        SYNTAX Unsigned32
        MAX-ACCESS read-only
        STATUS current
        DESCRIPTION
            "ParaLen."
        ::= { nj1PmCurEntry 2 }

    -- 1.3.6.1.4.1.2011.2.25.3.70.20.254.100.1.3
    nj1PmCurPara OBJECT-TYPE
        SYNTAX OCTET STRING
        MAX-ACCESS read-only
        STATUS current
        DESCRIPTION
            "para"
        ::= { nj1PmCurEntry 3 }

    -- 1.3.6.1.4.1.2011.2.25.3.70.20.254.100.1.4
    nj1PmCurMonValue OBJECT-TYPE
        SYNTAX Counter64
        MAX-ACCESS read-only
        STATUS current
        DESCRIPTION
            "DataPmMonValue."
        ::= { nj1PmCurEntry 4 }

    -- 1.3.6.1.4.1.2011.2.25.3.70.20.254.100.1.5
    nj1PmCurDatetime OBJECT-TYPE
        SYNTAX DateAndTime
        MAX-ACCESS read-only
        STATUS current
        DESCRIPTION
            "Start Time."
        ::= { nj1PmCurEntry 5 }

    -- 1.3.6.1.4.1.2011.2.25.3.70.20.254.110
    nj1Pm30sHisTable OBJECT-TYPE
        SYNTAX SEQUENCE OF Nj1Pm30sHisEntry
        MAX-ACCESS not-accessible
        STATUS current
        DESCRIPTION
            "nj1DataPm30sHis."
        ::= { nj1 110 }

    -- 1.3.6.1.4.1.2011.2.25.3.70.20.254.110.1
    nj1Pm30sHisEntry OBJECT-TYPE
        SYNTAX Nj1Pm30sHisEntry
        MAX-ACCESS not-accessible
        STATUS current
        DESCRIPTION
            "nj1DataPm30sHis."
        INDEX{ nj1Pm30sHisEid,nj1Pm30sHisParaLen,nj1Pm30sHisPara,nj1Pm30sHisStartTime,nj1Pm30sHisEndTime }
        ::= { nj1Pm30sHisTable 1 }

    Nj1Pm30sHisEntry ::=
        SEQUENCE {
            nj1Pm30sHisEid
                DataPmEventType,
            nj1Pm30sHisParaLen
                Unsigned32,
            nj1Pm30sHisPara
                OCTET STRING,
            nj1Pm30sHisMonValue
                Counter64,
            nj1Pm30sHisStartTime
                DateAndTime,
            nj1Pm30sHisEndTime
                DateAndTime,
            nj1Pm30sHisVldty
                ValidflagType
        }

    -- 1.3.6.1.4.1.2011.2.25.3.70.20.254.110.1.1
    nj1Pm30sHisEid OBJECT-TYPE
        SYNTAX DataPmEventType
        MAX-ACCESS read-only
        STATUS current
        DESCRIPTION
            "DataPmEid."
        ::= { nj1Pm30sHisEntry 1 }

    -- 1.3.6.1.4.1.2011.2.25.3.70.20.254.110.1.2
    nj1Pm30sHisParaLen OBJECT-TYPE
        SYNTAX Unsigned32
        MAX-ACCESS read-only
        STATUS current
        DESCRIPTION
            "ParaLen."
        ::= { nj1Pm30sHisEntry 2 }

    -- 1.3.6.1.4.1.2011.2.25.3.70.20.254.110.1.3
    nj1Pm30sHisPara OBJECT-TYPE
        SYNTAX OCTET STRING(SIZE (0..100))
        MAX-ACCESS read-only
        STATUS current
        DESCRIPTION
            "para"
        ::= { nj1Pm30sHisEntry 3 }

    -- 1.3.6.1.4.1.2011.2.25.3.70.20.254.110.1.4
    nj1Pm30sHisMonValue OBJECT-TYPE
        SYNTAX Counter64
        MAX-ACCESS read-only
        STATUS current
        DESCRIPTION
            "DataPmMonValue."
        ::= { nj1Pm30sHisEntry 4 }

    -- 1.3.6.1.4.1.2011.2.25.3.70.20.254.110.1.5
    nj1Pm30sHisStartTime OBJECT-TYPE
        SYNTAX DateAndTime
        MAX-ACCESS read-only
        STATUS current
        DESCRIPTION
            "Start Time."
        ::= { nj1Pm30sHisEntry 5 }

    -- 1.3.6.1.4.1.2011.2.25.3.70.20.254.110.1.6
    nj1Pm30sHisEndTime OBJECT-TYPE
        SYNTAX DateAndTime
        MAX-ACCESS read-only
        STATUS current
        DESCRIPTION
            "End Time."
        ::= { nj1Pm30sHisEntry 6 }

    -- 1.3.6.1.4.1.2011.2.25.3.70.20.254.110.1.7
    nj1Pm30sHisVldty OBJECT-TYPE
        SYNTAX ValidflagType
        MAX-ACCESS read-only
        STATUS current
        DESCRIPTION
            "Validity."
        ::= { nj1Pm30sHisEntry 7 }

    -- 1.3.6.1.4.1.2011.2.25.3.70.20.254.120
    nj1Pm30mHisTable OBJECT-TYPE
        SYNTAX SEQUENCE OF Nj1Pm30mHisEntry
        MAX-ACCESS not-accessible
        STATUS current
        DESCRIPTION
            "nj1Pm30mHis."
        ::= { nj1 120 }

    -- 1.3.6.1.4.1.2011.2.25.3.70.20.254.120.1
    nj1Pm30mHisEntry OBJECT-TYPE
        SYNTAX Nj1Pm30mHisEntry
        MAX-ACCESS not-accessible
        STATUS current
        DESCRIPTION
            "nj1Pm30mHis."
        INDEX{ nj1Pm30mHisEid,nj1Pm30mHisParaLen,nj1Pm30mHisPara,nj1Pm30mHisStartTime,nj1Pm30mHisEndTime }
        ::= { nj1Pm30mHisTable 1 }

    Nj1Pm30mHisEntry ::=
        SEQUENCE {
            nj1Pm30mHisEid
                DataPmEventType,
            nj1Pm30mHisParaLen
                Unsigned32,
            nj1Pm30mHisPara
                OCTET STRING,
            nj1Pm30mHisMonValue
                Counter64,
            nj1Pm30mHisStartTime
                DateAndTime,
            nj1Pm30mHisEndTime
                DateAndTime,
            nj1Pm30mHisVldty
                ValidflagType
        }

    -- 1.3.6.1.4.1.2011.2.25.3.70.20.254.120.1.1
    nj1Pm30mHisEid OBJECT-TYPE
        SYNTAX DataPmEventType
        MAX-ACCESS read-only
        STATUS current
        DESCRIPTION
            "DataPmEid."
        ::= { nj1Pm30mHisEntry 1 }

    -- 1.3.6.1.4.1.2011.2.25.3.70.20.254.120.1.2
    nj1Pm30mHisParaLen OBJECT-TYPE
        SYNTAX Unsigned32
        MAX-ACCESS read-only
        STATUS current
        DESCRIPTION
            "ParaLen."
        ::= { nj1Pm30mHisEntry 2 }

    -- 1.3.6.1.4.1.2011.2.25.3.70.20.254.120.1.3
    nj1Pm30mHisPara OBJECT-TYPE
        SYNTAX OCTET STRING(SIZE (0..100))
        MAX-ACCESS read-only
        STATUS current
        DESCRIPTION
            "para"
        ::= { nj1Pm30mHisEntry 3 }

    -- 1.3.6.1.4.1.2011.2.25.3.70.20.254.120.1.4
    nj1Pm30mHisMonValue OBJECT-TYPE
        SYNTAX Counter64
        MAX-ACCESS read-only
        STATUS current
        DESCRIPTION
            "DataPmMonValue."
        ::= { nj1Pm30mHisEntry 4 }

    -- 1.3.6.1.4.1.2011.2.25.3.70.20.254.120.1.5
    nj1Pm30mHisStartTime OBJECT-TYPE
        SYNTAX DateAndTime
        MAX-ACCESS read-only
        STATUS current
        DESCRIPTION
            "Start Time."
        ::= { nj1Pm30mHisEntry 5 }

    -- 1.3.6.1.4.1.2011.2.25.3.70.20.254.120.1.6
    nj1Pm30mHisEndTime OBJECT-TYPE
        SYNTAX DateAndTime
        MAX-ACCESS read-only
        STATUS current
        DESCRIPTION
            "End Time."
        ::= { nj1Pm30mHisEntry 6 }

    -- 1.3.6.1.4.1.2011.2.25.3.70.20.254.120.1.7
    nj1Pm30mHisVldty OBJECT-TYPE
        SYNTAX ValidflagType
        MAX-ACCESS read-only
        STATUS current
        DESCRIPTION
            "Validity."
        ::= { nj1Pm30mHisEntry 7 }

    -- 1.3.6.1.4.1.2011.2.25.3.70.20.254.130
    nj1Pmvar1HisTable OBJECT-TYPE
        SYNTAX SEQUENCE OF Nj1Pmvar1HisEntry
        MAX-ACCESS not-accessible
        STATUS current
        DESCRIPTION
            "nj1Pmvar1His."
        ::= { nj1 130 }

    -- 1.3.6.1.4.1.2011.2.25.3.70.20.254.130.1
    nj1Pmvar1HisEntry OBJECT-TYPE
        SYNTAX Nj1Pmvar1HisEntry
        MAX-ACCESS not-accessible
        STATUS current
        DESCRIPTION
            "nj1Pmvar1His."
        INDEX{ nj1Pmvar1HisEid,nj1Pmvar1HisParaLen,nj1Pmvar1HisPara,nj1Pmvar1HisStartTime,nj1Pmvar1HisEndTime }
        ::= { nj1Pmvar1HisTable 1 }

    Nj1Pmvar1HisEntry ::=
        SEQUENCE {
            nj1Pmvar1HisEid
                DataPmEventType,
            nj1Pmvar1HisParaLen
                Unsigned32,
            nj1Pmvar1HisPara
                OCTET STRING,
            nj1Pmvar1HisMonValue
                Counter64,
            nj1Pmvar1HisStartTime
                DateAndTime,
            nj1Pmvar1HisEndTime
                DateAndTime,
            nj1Pmvar1HisVldty
                ValidflagType
        }

    -- 1.3.6.1.4.1.2011.2.25.3.70.20.254.130.1.1
    nj1Pmvar1HisEid OBJECT-TYPE
        SYNTAX DataPmEventType
        MAX-ACCESS read-only
        STATUS current
        DESCRIPTION
            "DataPmEid."
        ::= { nj1Pmvar1HisEntry 1 }

    -- 1.3.6.1.4.1.2011.2.25.3.70.20.254.130.1.2
    nj1Pmvar1HisParaLen OBJECT-TYPE
        SYNTAX Unsigned32
        MAX-ACCESS read-only
        STATUS current
        DESCRIPTION
            "ParaLen."
        ::= { nj1Pmvar1HisEntry 2 }

    -- 1.3.6.1.4.1.2011.2.25.3.70.20.254.130.1.3
    nj1Pmvar1HisPara OBJECT-TYPE
        SYNTAX OCTET STRING (SIZE (0..100))
        MAX-ACCESS read-only
        STATUS current
        DESCRIPTION
            "para"
        ::= { nj1Pmvar1HisEntry 3 }

    -- 1.3.6.1.4.1.2011.2.25.3.70.20.254.130.1.4
    nj1Pmvar1HisMonValue OBJECT-TYPE
        SYNTAX Counter64
        MAX-ACCESS read-only
        STATUS current
        DESCRIPTION
            "DataPmMonValue."
        ::= { nj1Pmvar1HisEntry 4 }

    -- 1.3.6.1.4.1.2011.2.25.3.70.20.254.130.1.5
    nj1Pmvar1HisStartTime OBJECT-TYPE
        SYNTAX DateAndTime
        MAX-ACCESS read-only
        STATUS current
        DESCRIPTION
            "Start Time."
        ::= { nj1Pmvar1HisEntry 5 }

    -- 1.3.6.1.4.1.2011.2.25.3.70.20.254.130.1.6
    nj1Pmvar1HisEndTime OBJECT-TYPE
        SYNTAX DateAndTime
        MAX-ACCESS read-only
        STATUS current
        DESCRIPTION
            "End Time."
        ::= { nj1Pmvar1HisEntry 6 }

    -- 1.3.6.1.4.1.2011.2.25.3.70.20.254.130.1.7
    nj1Pmvar1HisVldty OBJECT-TYPE
        SYNTAX ValidflagType
        MAX-ACCESS read-only
        STATUS current
        DESCRIPTION
            "Validity."
        ::= { nj1Pmvar1HisEntry 7 }

    -- 1.3.6.1.4.1.2011.2.25.3.70.20.254.140
    nj1Pmvar2HisTable OBJECT-TYPE
        SYNTAX SEQUENCE OF Nj1Pmvar2HisEntry
        MAX-ACCESS not-accessible
        STATUS current
        DESCRIPTION
            "nj1Pmvar2His."
        ::= { nj1 140 }

    -- 1.3.6.1.4.1.2011.2.25.3.70.20.254.140.1
    nj1Pmvar2HisEntry OBJECT-TYPE
        SYNTAX Nj1Pmvar2HisEntry
        MAX-ACCESS not-accessible
        STATUS current
        DESCRIPTION
            "nj1Pmvar2His."
        INDEX{ nj1Pmvar2HisEid,nj1Pmvar2HisParaLen,nj1Pmvar2HisPara,nj1Pmvar2HisStartTime,nj1Pmvar2HisEndTime }
        ::= { nj1Pmvar2HisTable 1 }

    Nj1Pmvar2HisEntry ::=
        SEQUENCE {
            nj1Pmvar2HisEid
                DataPmEventType,
            nj1Pmvar2HisParaLen
                Unsigned32,
            nj1Pmvar2HisPara
                OCTET STRING,
            nj1Pmvar2HisMonValue
                Counter64,
            nj1Pmvar2HisStartTime
                DateAndTime,
            nj1Pmvar2HisEndTime
                DateAndTime,
            nj1Pmvar2HisVldty
                ValidflagType
        }

    -- 1.3.6.1.4.1.2011.2.25.3.70.20.254.140.1.1
    nj1Pmvar2HisEid OBJECT-TYPE
        SYNTAX DataPmEventType
        MAX-ACCESS read-only
        STATUS current
        DESCRIPTION
            "DataPmEid."
        ::= { nj1Pmvar2HisEntry 1 }

    -- 1.3.6.1.4.1.2011.2.25.3.70.20.254.140.1.2
    nj1Pmvar2HisParaLen OBJECT-TYPE
        SYNTAX Unsigned32
        MAX-ACCESS read-only
        STATUS current
        DESCRIPTION
            "ParaLen."
        ::= { nj1Pmvar2HisEntry 2 }

    -- 1.3.6.1.4.1.2011.2.25.3.70.20.254.140.1.3
    nj1Pmvar2HisPara OBJECT-TYPE
        SYNTAX OCTET STRING(SIZE (0..100))
        MAX-ACCESS read-only
        STATUS current
        DESCRIPTION
            "para"
        ::= { nj1Pmvar2HisEntry 3 }

    -- 1.3.6.1.4.1.2011.2.25.3.70.20.254.140.1.4
    nj1Pmvar2HisMonValue OBJECT-TYPE
        SYNTAX Counter64
        MAX-ACCESS read-only
        STATUS current
        DESCRIPTION
            "DataPmMonValue."
        ::= { nj1Pmvar2HisEntry 4 }

    -- 1.3.6.1.4.1.2011.2.25.3.70.20.254.140.1.5
    nj1Pmvar2HisStartTime OBJECT-TYPE
        SYNTAX DateAndTime
        MAX-ACCESS read-only
        STATUS current
        DESCRIPTION
            "Start Time."
        ::= { nj1Pmvar2HisEntry 5 }

    -- 1.3.6.1.4.1.2011.2.25.3.70.20.254.140.1.6
    nj1Pmvar2HisEndTime OBJECT-TYPE
        SYNTAX DateAndTime
        MAX-ACCESS read-only
        STATUS current
        DESCRIPTION
            "End Time."
        ::= { nj1Pmvar2HisEntry 6 }

    -- 1.3.6.1.4.1.2011.2.25.3.70.20.254.140.1.7
    nj1Pmvar2HisVldty OBJECT-TYPE
        SYNTAX ValidflagType
        MAX-ACCESS read-only
        STATUS current
        DESCRIPTION
            "Validity."
        ::= { nj1Pmvar2HisEntry 7 }

    -- 1.3.6.1.4.1.2011.2.25.3.70.20.265
    newmepperf OBJECT IDENTIFIER ::= { rtnData 265 }

    -- 1.3.6.1.4.1.2011.2.25.3.70.20.265.100
    newmepperfPmCurTable OBJECT-TYPE
        SYNTAX SEQUENCE OF NewmepperfPmCurEntry
        MAX-ACCESS not-accessible
        STATUS current
        DESCRIPTION
            "newmepperfDataPm30sCur."
        ::= { newmepperf 100 }

    -- 1.3.6.1.4.1.2011.2.25.3.70.20.265.100.1
    newmepperfPmCurEntry OBJECT-TYPE
        SYNTAX NewmepperfPmCurEntry
        MAX-ACCESS not-accessible
        STATUS current
        DESCRIPTION
            "newmepperfPmCur."
        INDEX{ newmepperfPmCurEid, newmepperfPmCurParaLen, newmepperfPmCurPara }
        ::= { newmepperfPmCurTable 1 }

    NewmepperfPmCurEntry ::=
        SEQUENCE {
            newmepperfPmCurEid
                DataPmEventType,
            newmepperfPmCurParaLen
                Unsigned32,
            newmepperfPmCurPara
                OCTET STRING,
            newmepperfPmCurMonValue
                Counter64,
            newmepperfPmCurDatetime
                DateAndTime
        }

    -- 1.3.6.1.4.1.2011.2.25.3.70.20.265.100.1.1
    newmepperfPmCurEid OBJECT-TYPE
        SYNTAX DataPmEventType
        MAX-ACCESS read-only
        STATUS current
        DESCRIPTION
            "DataPmEid."
        ::= { newmepperfPmCurEntry 1 }

    -- 1.3.6.1.4.1.2011.2.25.3.70.20.265.100.1.2
    newmepperfPmCurParaLen OBJECT-TYPE
        SYNTAX Unsigned32
        MAX-ACCESS read-only
        STATUS current
        DESCRIPTION
            "ParaLen."
        ::= { newmepperfPmCurEntry 2 }

    -- 1.3.6.1.4.1.2011.2.25.3.70.20.265.100.1.3
    newmepperfPmCurPara OBJECT-TYPE
        SYNTAX OCTET STRING
        MAX-ACCESS read-only
        STATUS current
        DESCRIPTION
            "para"
        ::= { newmepperfPmCurEntry 3 }

    -- 1.3.6.1.4.1.2011.2.25.3.70.20.265.100.1.4
    newmepperfPmCurMonValue OBJECT-TYPE
        SYNTAX Counter64
        MAX-ACCESS read-only
        STATUS current
        DESCRIPTION
            "DataPmMonValue."
        ::= { newmepperfPmCurEntry 4 }

    -- 1.3.6.1.4.1.2011.2.25.3.70.20.265.100.1.5
    newmepperfPmCurDatetime OBJECT-TYPE
        SYNTAX DateAndTime
        MAX-ACCESS read-only
        STATUS current
        DESCRIPTION
            "Start Time."
        ::= { newmepperfPmCurEntry 5 }

    -- 1.3.6.1.4.1.2011.2.25.3.70.20.265.110
    newmepperfPm30sHisTable OBJECT-TYPE
        SYNTAX SEQUENCE OF NewmepperfPm30sHisEntry
        MAX-ACCESS not-accessible
        STATUS current
        DESCRIPTION
            "newmepperfDataPm30sHis."
        ::= { newmepperf 110 }

    -- 1.3.6.1.4.1.2011.2.25.3.70.20.265.110.1
    newmepperfPm30sHisEntry OBJECT-TYPE
        SYNTAX NewmepperfPm30sHisEntry
        MAX-ACCESS not-accessible
        STATUS current
        DESCRIPTION
            "newmepperfDataPm30sHis."
        INDEX{ newmepperfPm30sHisEid,newmepperfPm30sHisParaLen,newmepperfPm30sHisPara,newmepperfPm30sHisStartTime,newmepperfPm30sHisEndTime }
        ::= { newmepperfPm30sHisTable 1 }

    NewmepperfPm30sHisEntry ::=
        SEQUENCE {
            newmepperfPm30sHisEid
                DataPmEventType,
            newmepperfPm30sHisParaLen
                Unsigned32,
            newmepperfPm30sHisPara
                OCTET STRING,
            newmepperfPm30sHisMonValue
                Counter64,
            newmepperfPm30sHisStartTime
                DateAndTime,
            newmepperfPm30sHisEndTime
                DateAndTime,
            newmepperfPm30sHisVldty
                ValidflagType
        }

    -- 1.3.6.1.4.1.2011.2.25.3.70.20.265.110.1.1
    newmepperfPm30sHisEid OBJECT-TYPE
        SYNTAX DataPmEventType
        MAX-ACCESS read-only
        STATUS current
        DESCRIPTION
            "DataPmEid."
        ::= { newmepperfPm30sHisEntry 1 }

    -- 1.3.6.1.4.1.2011.2.25.3.70.20.265.110.1.2
    newmepperfPm30sHisParaLen OBJECT-TYPE
        SYNTAX Unsigned32
        MAX-ACCESS read-only
        STATUS current
        DESCRIPTION
            "ParaLen."
        ::= { newmepperfPm30sHisEntry 2 }

    -- 1.3.6.1.4.1.2011.2.25.3.70.20.265.110.1.3
    newmepperfPm30sHisPara OBJECT-TYPE
        SYNTAX OCTET STRING(SIZE (0..100))
        MAX-ACCESS read-only
        STATUS current
        DESCRIPTION
            "para"
        ::= { newmepperfPm30sHisEntry 3 }

    -- 1.3.6.1.4.1.2011.2.25.3.70.20.265.110.1.4
    newmepperfPm30sHisMonValue OBJECT-TYPE
        SYNTAX Counter64
        MAX-ACCESS read-only
        STATUS current
        DESCRIPTION
            "DataPmMonValue."
        ::= { newmepperfPm30sHisEntry 4 }

    -- 1.3.6.1.4.1.2011.2.25.3.70.20.265.110.1.5
    newmepperfPm30sHisStartTime OBJECT-TYPE
        SYNTAX DateAndTime
        MAX-ACCESS read-only
        STATUS current
        DESCRIPTION
            "Start Time."
        ::= { newmepperfPm30sHisEntry 5 }

    -- 1.3.6.1.4.1.2011.2.25.3.70.20.265.110.1.6
    newmepperfPm30sHisEndTime OBJECT-TYPE
        SYNTAX DateAndTime
        MAX-ACCESS read-only
        STATUS current
        DESCRIPTION
            "End Time."
        ::= { newmepperfPm30sHisEntry 6 }

    -- 1.3.6.1.4.1.2011.2.25.3.70.20.265.110.1.7
    newmepperfPm30sHisVldty OBJECT-TYPE
        SYNTAX ValidflagType
        MAX-ACCESS read-only
        STATUS current
        DESCRIPTION
            "Validity."
        ::= { newmepperfPm30sHisEntry 7 }

    -- 1.3.6.1.4.1.2011.2.25.3.70.20.265.120
    newmepperfPm30mHisTable OBJECT-TYPE
        SYNTAX SEQUENCE OF NewmepperfPm30mHisEntry
        MAX-ACCESS not-accessible
        STATUS current
        DESCRIPTION
            "newmepperfPm30mHis."
        ::= { newmepperf 120 }

    -- 1.3.6.1.4.1.2011.2.25.3.70.20.265.120.1
    newmepperfPm30mHisEntry OBJECT-TYPE
        SYNTAX NewmepperfPm30mHisEntry
        MAX-ACCESS not-accessible
        STATUS current
        DESCRIPTION
            "newmepperfPm30mHis."
        INDEX{ newmepperfPm30mHisEid,newmepperfPm30mHisParaLen,newmepperfPm30mHisPara,newmepperfPm30mHisStartTime,newmepperfPm30mHisEndTime }
        ::= { newmepperfPm30mHisTable 1 }

    NewmepperfPm30mHisEntry ::=
        SEQUENCE {
            newmepperfPm30mHisEid
                DataPmEventType,
            newmepperfPm30mHisParaLen
                Unsigned32,
            newmepperfPm30mHisPara
                OCTET STRING,
            newmepperfPm30mHisMonValue
                Counter64,
            newmepperfPm30mHisStartTime
                DateAndTime,
            newmepperfPm30mHisEndTime
                DateAndTime,
            newmepperfPm30mHisVldty
                ValidflagType
        }

    -- 1.3.6.1.4.1.2011.2.25.3.70.20.265.120.1.1
    newmepperfPm30mHisEid OBJECT-TYPE
        SYNTAX DataPmEventType
        MAX-ACCESS read-only
        STATUS current
        DESCRIPTION
            "DataPmEid."
        ::= { newmepperfPm30mHisEntry 1 }

    -- 1.3.6.1.4.1.2011.2.25.3.70.20.265.120.1.2
    newmepperfPm30mHisParaLen OBJECT-TYPE
        SYNTAX Unsigned32
        MAX-ACCESS read-only
        STATUS current
        DESCRIPTION
            "ParaLen."
        ::= { newmepperfPm30mHisEntry 2 }

    -- 1.3.6.1.4.1.2011.2.25.3.70.20.265.120.1.3
    newmepperfPm30mHisPara OBJECT-TYPE
        SYNTAX OCTET STRING(SIZE (0..100))
        MAX-ACCESS read-only
        STATUS current
        DESCRIPTION
            "para"
        ::= { newmepperfPm30mHisEntry 3 }

    -- 1.3.6.1.4.1.2011.2.25.3.70.20.265.120.1.4
    newmepperfPm30mHisMonValue OBJECT-TYPE
        SYNTAX Counter64
        MAX-ACCESS read-only
        STATUS current
        DESCRIPTION
            "DataPmMonValue."
        ::= { newmepperfPm30mHisEntry 4 }

    -- 1.3.6.1.4.1.2011.2.25.3.70.20.265.120.1.5
    newmepperfPm30mHisStartTime OBJECT-TYPE
        SYNTAX DateAndTime
        MAX-ACCESS read-only
        STATUS current
        DESCRIPTION
            "Start Time."
        ::= { newmepperfPm30mHisEntry 5 }

    -- 1.3.6.1.4.1.2011.2.25.3.70.20.265.120.1.6
    newmepperfPm30mHisEndTime OBJECT-TYPE
        SYNTAX DateAndTime
        MAX-ACCESS read-only
        STATUS current
        DESCRIPTION
            "End Time."
        ::= { newmepperfPm30mHisEntry 6 }

    -- 1.3.6.1.4.1.2011.2.25.3.70.20.265.120.1.7
    newmepperfPm30mHisVldty OBJECT-TYPE
        SYNTAX ValidflagType
        MAX-ACCESS read-only
        STATUS current
        DESCRIPTION
            "Validity."
        ::= { newmepperfPm30mHisEntry 7 }

    -- 1.3.6.1.4.1.2011.2.25.3.70.20.265.130
    newmepperfPmvar1HisTable OBJECT-TYPE
        SYNTAX SEQUENCE OF NewmepperfPmvar1HisEntry
        MAX-ACCESS not-accessible
        STATUS current
        DESCRIPTION
            "newmepperfPmvar1His."
        ::= { newmepperf 130 }

    -- 1.3.6.1.4.1.2011.2.25.3.70.20.265.130.1
    newmepperfPmvar1HisEntry OBJECT-TYPE
        SYNTAX NewmepperfPmvar1HisEntry
        MAX-ACCESS not-accessible
        STATUS current
        DESCRIPTION
            "newmepperfPmvar1His."
        INDEX{ newmepperfPmvar1HisEid,newmepperfPmvar1HisParaLen,newmepperfPmvar1HisPara,newmepperfPmvar1HisStartTime,newmepperfPmvar1HisEndTime }
        ::= { newmepperfPmvar1HisTable 1 }

    NewmepperfPmvar1HisEntry ::=
        SEQUENCE {
            newmepperfPmvar1HisEid
                DataPmEventType,
            newmepperfPmvar1HisParaLen
                Unsigned32,
            newmepperfPmvar1HisPara
                OCTET STRING,
            newmepperfPmvar1HisMonValue
                Counter64,
            newmepperfPmvar1HisStartTime
                DateAndTime,
            newmepperfPmvar1HisEndTime
                DateAndTime,
            newmepperfPmvar1HisVldty
                ValidflagType
        }

    -- 1.3.6.1.4.1.2011.2.25.3.70.20.265.130.1.1
    newmepperfPmvar1HisEid OBJECT-TYPE
        SYNTAX DataPmEventType
        MAX-ACCESS read-only
        STATUS current
        DESCRIPTION
            "DataPmEid."
        ::= { newmepperfPmvar1HisEntry 1 }

    -- 1.3.6.1.4.1.2011.2.25.3.70.20.265.130.1.2
    newmepperfPmvar1HisParaLen OBJECT-TYPE
        SYNTAX Unsigned32
        MAX-ACCESS read-only
        STATUS current
        DESCRIPTION
            "ParaLen."
        ::= { newmepperfPmvar1HisEntry 2 }

    -- 1.3.6.1.4.1.2011.2.25.3.70.20.265.130.1.3
    newmepperfPmvar1HisPara OBJECT-TYPE
        SYNTAX OCTET STRING (SIZE (0..100))
        MAX-ACCESS read-only
        STATUS current
        DESCRIPTION
            "para"
        ::= { newmepperfPmvar1HisEntry 3 }

    -- 1.3.6.1.4.1.2011.2.25.3.70.20.265.130.1.4
    newmepperfPmvar1HisMonValue OBJECT-TYPE
        SYNTAX Counter64
        MAX-ACCESS read-only
        STATUS current
        DESCRIPTION
            "DataPmMonValue."
        ::= { newmepperfPmvar1HisEntry 4 }

    -- 1.3.6.1.4.1.2011.2.25.3.70.20.265.130.1.5
    newmepperfPmvar1HisStartTime OBJECT-TYPE
        SYNTAX DateAndTime
        MAX-ACCESS read-only
        STATUS current
        DESCRIPTION
            "Start Time."
        ::= { newmepperfPmvar1HisEntry 5 }

    -- 1.3.6.1.4.1.2011.2.25.3.70.20.265.130.1.6
    newmepperfPmvar1HisEndTime OBJECT-TYPE
        SYNTAX DateAndTime
        MAX-ACCESS read-only
        STATUS current
        DESCRIPTION
            "End Time."
        ::= { newmepperfPmvar1HisEntry 6 }

    -- 1.3.6.1.4.1.2011.2.25.3.70.20.265.130.1.7
    newmepperfPmvar1HisVldty OBJECT-TYPE
        SYNTAX ValidflagType
        MAX-ACCESS read-only
        STATUS current
        DESCRIPTION
            "Validity."
        ::= { newmepperfPmvar1HisEntry 7 }

    -- 1.3.6.1.4.1.2011.2.25.3.70.20.265.140
    newmepperfPmvar2HisTable OBJECT-TYPE
        SYNTAX SEQUENCE OF NewmepperfPmvar2HisEntry
        MAX-ACCESS not-accessible
        STATUS current
        DESCRIPTION
            "newmepperfPmvar2His."
        ::= { newmepperf 140 }

    -- 1.3.6.1.4.1.2011.2.25.3.70.20.265.140.1
    newmepperfPmvar2HisEntry OBJECT-TYPE
        SYNTAX NewmepperfPmvar2HisEntry
        MAX-ACCESS not-accessible
        STATUS current
        DESCRIPTION
            "newmepperfPmvar2His."
        INDEX{ newmepperfPmvar2HisEid,newmepperfPmvar2HisParaLen,newmepperfPmvar2HisPara,newmepperfPmvar2HisStartTime,newmepperfPmvar2HisEndTime }
        ::= { newmepperfPmvar2HisTable 1 }

    NewmepperfPmvar2HisEntry ::=
        SEQUENCE {
            newmepperfPmvar2HisEid
                DataPmEventType,
            newmepperfPmvar2HisParaLen
                Unsigned32,
            newmepperfPmvar2HisPara
                OCTET STRING,
            newmepperfPmvar2HisMonValue
                Counter64,
            newmepperfPmvar2HisStartTime
                DateAndTime,
            newmepperfPmvar2HisEndTime
                DateAndTime,
            newmepperfPmvar2HisVldty
                ValidflagType
        }

    -- 1.3.6.1.4.1.2011.2.25.3.70.20.265.140.1.1
    newmepperfPmvar2HisEid OBJECT-TYPE
        SYNTAX DataPmEventType
        MAX-ACCESS read-only
        STATUS current
        DESCRIPTION
            "DataPmEid."
        ::= { newmepperfPmvar2HisEntry 1 }

    -- 1.3.6.1.4.1.2011.2.25.3.70.20.265.140.1.2
    newmepperfPmvar2HisParaLen OBJECT-TYPE
        SYNTAX Unsigned32
        MAX-ACCESS read-only
        STATUS current
        DESCRIPTION
            "ParaLen."
        ::= { newmepperfPmvar2HisEntry 2 }

    -- 1.3.6.1.4.1.2011.2.25.3.70.20.265.140.1.3
    newmepperfPmvar2HisPara OBJECT-TYPE
        SYNTAX OCTET STRING(SIZE (0..100))
        MAX-ACCESS read-only
        STATUS current
        DESCRIPTION
            "para"
        ::= { newmepperfPmvar2HisEntry 3 }

    -- 1.3.6.1.4.1.2011.2.25.3.70.20.265.140.1.4
    newmepperfPmvar2HisMonValue OBJECT-TYPE
        SYNTAX Counter64
        MAX-ACCESS read-only
        STATUS current
        DESCRIPTION
            "DataPmMonValue."
        ::= { newmepperfPmvar2HisEntry 4 }

    -- 1.3.6.1.4.1.2011.2.25.3.70.20.265.140.1.5
    newmepperfPmvar2HisStartTime OBJECT-TYPE
        SYNTAX DateAndTime
        MAX-ACCESS read-only
        STATUS current
        DESCRIPTION
            "Start Time."
        ::= { newmepperfPmvar2HisEntry 5 }

    -- 1.3.6.1.4.1.2011.2.25.3.70.20.265.140.1.6
    newmepperfPmvar2HisEndTime OBJECT-TYPE
        SYNTAX DateAndTime
        MAX-ACCESS read-only
        STATUS current
        DESCRIPTION
            "End Time."
        ::= { newmepperfPmvar2HisEntry 6 }

    -- 1.3.6.1.4.1.2011.2.25.3.70.20.265.140.1.7
    newmepperfPmvar2HisVldty OBJECT-TYPE
        SYNTAX ValidflagType
        MAX-ACCESS read-only
        STATUS current
        DESCRIPTION
            "Validity."
        ::= { newmepperfPmvar2HisEntry 7 }

		
    -- 1.3.6.1.4.1.2011.2.25.3.70.20.300
    optixRtnDataConformance OBJECT IDENTIFIER ::= { rtnData 300 }

    -- 1.3.6.1.4.1.2011.2.25.3.70.20.300.1
    optixRtnDataGroups OBJECT IDENTIFIER ::= { optixRtnDataConformance 1 }

    -- 1.3.6.1.4.1.2011.2.25.3.70.20.300.1.1
    optixRtnDataObjectGroup OBJECT-GROUP
        OBJECTS {tunnelPmCurEid, tunnelPmCurMonValue, tunnelPmCurVldty, tunnelPmCurDatetime, tunnelPmCurParaLen, 
                tunnelPmCurPara, tunnelPm30sHisEid, tunnelPm30sHisMonValue, tunnelPm30sHisVldty, tunnelPm30sHisDatetime, 
                tunnelPm30sHisParaLen, tunnelPm30sHisPara, tunnelPm30mHisEid, tunnelPm30mHisMonValue, tunnelPm30mHisVldty, 
                tunnelPm30mHisDatetime, tunnelPm30mHisParaLen, tunnelPm30mHisPara, tunnelPmvar1HisEid, tunnelPmvar1HisMonValue, 
                tunnelPmvar1HisVldty, tunnelPmvar1HisDatetime, tunnelPmvar1HisParaLen, tunnelPmvar1HisPara, tunnelPmvar2HisEid, tunnelPmvar2HisMonValue, 
                tunnelPmvar2HisVldty, tunnelPmvar2HisDatetime, tunnelPmvar2HisParaLen, tunnelPmvar2HisPara, pwofatmPmCurEid, pwofatmPmCurMonValue, pwofatmPmCurVldty, pwofatmPmCurDatetime, pwofatmPmCurParaLen, 
                pwofatmPmCurPara, pwofatmPm30sHisEid, pwofatmPm30sHisMonValue, pwofatmPm30sHisVldty, pwofatmPm30sHisDatetime, 
                pwofatmPm30sHisParaLen, pwofatmPm30sHisPara, pwofatmPm30mHisEid, pwofatmPm30mHisMonValue, pwofatmPm30mHisVldty, 
                pwofatmPm30mHisDatetime, pwofatmPm30mHisParaLen, pwofatmPm30mHisPara, pwofatmPmvar1HisEid, pwofatmPmvar1HisMonValue, 
                pwofatmPmvar1HisVldty, pwofatmPmvar1HisDatetime, pwofatmPmvar1HisParaLen, pwofatmPmvar1HisPara, pwofatmPmvar2HisEid, pwofatmPmvar2HisMonValue, 
                pwofatmPmvar2HisVldty, pwofatmPmvar2HisDatetime, pwofatmPmvar2HisParaLen, pwofatmPmvar2HisPara, pwofcesPmCurEid, pwofcesPmCurMonValue, pwofcesPmCurVldty, pwofcesPmCurDatetime, pwofcesPmCurParaLen, 
                pwofcesPmCurPara, pwofcesPm30sHisEid, pwofcesPm30sHisMonValue, pwofcesPm30sHisVldty, pwofcesPm30sHisDatetime, 
                pwofcesPm30sHisParaLen, pwofcesPm30sHisPara, pwofcesPm30mHisEid, pwofcesPm30mHisMonValue, pwofcesPm30mHisVldty, 
                pwofcesPm30mHisDatetime, pwofcesPm30mHisParaLen, pwofcesPm30mHisPara, pwofcesPmvar1HisEid, pwofcesPmvar1HisMonValue, 
                pwofcesPmvar1HisVldty, pwofcesPmvar1HisDatetime, pwofcesPmvar1HisParaLen, pwofcesPmvar1HisPara, pwofcesPmvar2HisEid, pwofcesPmvar2HisMonValue, 
                pwofcesPmvar2HisVldty, pwofcesPmvar2HisDatetime, pwofcesPmvar2HisParaLen, pwofcesPmvar2HisPara,pwofl2vpnPmCurEid, pwofl2vpnPmCurMonValue, pwofl2vpnPmCurVldty, pwofl2vpnPmCurDatetime, pwofl2vpnPmCurParaLen, 
                pwofl2vpnPmCurPara, pwofl2vpnPm30sHisEid, pwofl2vpnPm30sHisMonValue, pwofl2vpnPm30sHisVldty, pwofl2vpnPm30sHisDatetime, 
                pwofl2vpnPm30sHisParaLen, pwofl2vpnPm30sHisPara, pwofl2vpnPm30mHisEid, pwofl2vpnPm30mHisMonValue, pwofl2vpnPm30mHisVldty, 
                pwofl2vpnPm30mHisDatetime, pwofl2vpnPm30mHisParaLen, pwofl2vpnPm30mHisPara, pwofl2vpnPmvar1HisEid, pwofl2vpnPmvar1HisMonValue, 
                pwofl2vpnPmvar1HisVldty, pwofl2vpnPmvar1HisDatetime, pwofl2vpnPmvar1HisParaLen, pwofl2vpnPmvar1HisPara, pwofl2vpnPmvar2HisEid, pwofl2vpnPmvar2HisMonValue, 
                pwofl2vpnPmvar2HisVldty, pwofl2vpnPmvar2HisDatetime, pwofl2vpnPmvar2HisParaLen, pwofl2vpnPmvar2HisPara, atmconnectionPmCurEid, atmconnectionPmCurMonValue, atmconnectionPmCurVldty, atmconnectionPmCurDatetime, atmconnectionPmCurParaLen, 
                atmconnectionPmCurPara, atmconnectionPm30sHisEid, atmconnectionPm30sHisMonValue, atmconnectionPm30sHisVldty, atmconnectionPm30sHisDatetime, 
                atmconnectionPm30sHisParaLen, atmconnectionPm30sHisPara, atmconnectionPm30mHisEid, atmconnectionPm30mHisMonValue, atmconnectionPm30mHisVldty, 
                atmconnectionPm30mHisDatetime, atmconnectionPm30mHisParaLen, atmconnectionPm30mHisPara, atmconnectionPmvar1HisEid, atmconnectionPmvar1HisMonValue, 
                atmconnectionPmvar1HisVldty, atmconnectionPmvar1HisDatetime, atmconnectionPmvar1HisParaLen, atmconnectionPmvar1HisPara, atmconnectionPmvar2HisEid, atmconnectionPmvar2HisMonValue, 
                atmconnectionPmvar2HisVldty, atmconnectionPmvar2HisDatetime, atmconnectionPmvar2HisParaLen, atmconnectionPmvar2HisPara, vuniofl2vpnPmCurEid, vuniofl2vpnPmCurMonValue, vuniofl2vpnPmCurVldty, vuniofl2vpnPmCurDatetime, vuniofl2vpnPmCurParaLen, 
                vuniofl2vpnPmCurPara, vuniofl2vpnPm30sHisEid, vuniofl2vpnPm30sHisMonValue, vuniofl2vpnPm30sHisVldty, vuniofl2vpnPm30sHisDatetime, 
                vuniofl2vpnPm30sHisParaLen, vuniofl2vpnPm30sHisPara, vuniofl2vpnPm30mHisEid, vuniofl2vpnPm30mHisMonValue, vuniofl2vpnPm30mHisVldty, 
                vuniofl2vpnPm30mHisDatetime, vuniofl2vpnPm30mHisParaLen, vuniofl2vpnPm30mHisPara, vuniofl2vpnPmvar1HisEid, vuniofl2vpnPmvar1HisMonValue, 
                vuniofl2vpnPmvar1HisVldty, vuniofl2vpnPmvar1HisDatetime, vuniofl2vpnPmvar1HisParaLen, vuniofl2vpnPmvar1HisPara, vuniofl2vpnPmvar2HisEid, vuniofl2vpnPmvar2HisMonValue, 
                vuniofl2vpnPmvar2HisVldty, vuniofl2vpnPmvar2HisDatetime, vuniofl2vpnPmvar2HisParaLen, vuniofl2vpnPmvar2HisPara, mlpppPmCurEid, mlpppPmCurMonValue, mlpppPmCurVldty, mlpppPmCurDatetime, mlpppPmCurParaLen, 
                mlpppPmCurPara, mlpppPm30sHisEid, mlpppPm30sHisMonValue, mlpppPm30sHisVldty, mlpppPm30sHisDatetime, 
                mlpppPm30sHisParaLen, mlpppPm30sHisPara, mlpppPm30mHisEid, mlpppPm30mHisMonValue, mlpppPm30mHisVldty, 
                mlpppPm30mHisDatetime, mlpppPm30mHisParaLen, mlpppPm30mHisPara, mlpppPmvar1HisEid, mlpppPmvar1HisMonValue, 
                mlpppPmvar1HisVldty, mlpppPmvar1HisDatetime, mlpppPmvar1HisParaLen, mlpppPmvar1HisPara, mlpppPmvar2HisEid,mlpppPmvar2HisMonValue, 
                mlpppPmvar2HisVldty, mlpppPmvar2HisDatetime, mlpppPmvar2HisParaLen, mlpppPmvar2HisPara,mepperfPmCurEid, mepperfPmCurMonValue, mepperfPmCurVldty, mepperfPmCurDatetime, mepperfPmCurParaLen, 
                mepperfPmCurPara, mepperfPm30sHisEid, mepperfPm30sHisMonValue, mepperfPm30sHisVldty, mepperfPm30sHisDatetime, 
                mepperfPm30sHisParaLen, mepperfPm30sHisPara, mepperfPm30mHisEid, mepperfPm30mHisMonValue, mepperfPm30mHisVldty, 
                mepperfPm30mHisDatetime, mepperfPm30mHisParaLen, mepperfPm30mHisPara, mepperfPmvar1HisEid, mepperfPmvar1HisMonValue, 
                mepperfPmvar1HisVldty, mepperfPmvar1HisDatetime, mepperfPmvar1HisParaLen, mepperfPmvar1HisPara, mepperfPmvar2HisEid,mepperfPmvar2HisMonValue, 
                mepperfPmvar2HisVldty, mepperfPmvar2HisDatetime, mepperfPmvar2HisParaLen, mepperfPmvar2HisPara,ethPortPmCurEid, ethPortPmCurMonValue, ethPortPmCurVldty, ethPortPmCurDatetime, ethPortPmCurParaLen, 
                ethPortPmCurPara, ethPortPm30sHisEid, ethPortPm30sHisMonValue, ethPortPm30sHisVldty, ethPortPm30sHisDatetime, 
                ethPortPm30sHisParaLen, ethPortPm30sHisPara, ethPortPm30mHisEid, ethPortPm30mHisMonValue, ethPortPm30mHisVldty, 
                ethPortPm30mHisDatetime, ethPortPm30mHisParaLen, ethPortPm30mHisPara, ethPortPmvar1HisEid, ethPortPmvar1HisMonValue, 
                ethPortPmvar1HisVldty, ethPortPmvar1HisDatetime, ethPortPmvar1HisParaLen, ethPortPmvar1HisPara, ethPortPmvar2HisEid, ethPortPmvar2HisMonValue, 
                ethPortPmvar2HisVldty, ethPortPmvar2HisDatetime, ethPortPmvar2HisParaLen, ethPortPmvar2HisPara, atmtrunkPmCurEid, atmtrunkPmCurMonValue, atmtrunkPmCurVldty, atmtrunkPmCurDatetime, atmtrunkPmCurParaLen, 
                atmtrunkPmCurPara, atmtrunkPm30sHisEid, atmtrunkPm30sHisMonValue, atmtrunkPm30sHisVldty, atmtrunkPm30sHisDatetime, 
                atmtrunkPm30sHisParaLen, atmtrunkPm30sHisPara, atmtrunkPm30mHisEid, atmtrunkPm30mHisMonValue, atmtrunkPm30mHisVldty, 
                atmtrunkPm30mHisDatetime, atmtrunkPm30mHisParaLen, atmtrunkPm30mHisPara, atmtrunkPmvar1HisEid, atmtrunkPmvar1HisMonValue, 
                atmtrunkPmvar1HisVldty, atmtrunkPmvar1HisDatetime, atmtrunkPmvar1HisParaLen, atmtrunkPmvar1HisPara, atmtrunkPmvar2HisEid, atmtrunkPmvar2HisMonValue, 
                atmtrunkPmvar2HisVldty, atmtrunkPmvar2HisDatetime, atmtrunkPmvar2HisParaLen, atmtrunkPmvar2HisPara, newportpriPmCurEid, newportpriPmCurMonValue, newportpriPmCurVldty, newportpriPmCurDatetime, newportpriPmCurParaLen, 
                newportpriPmCurPara, newportpriPm30sHisEid, newportpriPm30sHisMonValue, newportpriPm30sHisVldty, newportpriPm30sHisDatetime, 
                newportpriPm30sHisParaLen, newportpriPm30sHisPara, newportpriPm30mHisEid, newportpriPm30mHisMonValue, newportpriPm30mHisVldty, 
                newportpriPm30mHisDatetime, newportpriPm30mHisParaLen, newportpriPm30mHisPara, newportpriPmvar1HisEid, newportpriPmvar1HisMonValue, 
                newportpriPmvar1HisVldty, newportpriPmvar1HisDatetime, newportpriPmvar1HisParaLen, newportpriPmvar1HisPara, newportpriPmvar2HisEid,newportpriPmvar2HisMonValue, 
                newportpriPmvar2HisVldty, newportpriPmvar2HisDatetime, newportpriPmvar2HisParaLen, newportpriPmvar2HisPara,ethvcgportPmCurEid, ethvcgportPmCurMonValue, ethvcgportPmCurVldty, ethvcgportPmCurDatetime, ethvcgportPmCurParaLen, 
                g1j1PmCurEid, g1j1PmCurMonValue, g1j1PmCurVldty, g1j1PmCurDatetime, g1j1PmCurParaLen, 
                g1j1PmCurPara, g1j1Pm30sHisEid, g1j1Pm30sHisMonValue, g1j1Pm30sHisVldty, g1j1Pm30sHisDatetime, 
                g1j1Pm30sHisParaLen, g1j1Pm30sHisPara, g1j1Pm30mHisEid, g1j1Pm30mHisMonValue, g1j1Pm30mHisVldty, 
                g1j1Pm30mHisDatetime, g1j1Pm30mHisParaLen, g1j1Pm30mHisPara, g1j1Pmvar1HisEid, g1j1Pmvar1HisMonValue, 
                g1j1Pmvar1HisVldty, g1j1Pmvar1HisDatetime, g1j1Pmvar1HisParaLen, g1j1Pmvar1HisPara, g1j1Pmvar2HisEid, g1j1Pmvar2HisMonValue, 
                g1j1Pmvar2HisVldty, g1j1Pmvar2HisDatetime, g1j1Pmvar2HisParaLen, g1j1Pmvar2HisPara,
                ethvcgportPmCurPara, ethvcgportPm30sHisEid, ethvcgportPm30sHisMonValue, ethvcgportPm30sHisVldty, ethvcgportPm30sHisDatetime, 
                ethvcgportPm30sHisParaLen, ethvcgportPm30sHisPara, ethvcgportPm30mHisEid, ethvcgportPm30mHisMonValue, ethvcgportPm30mHisVldty, 
                ethvcgportPm30mHisDatetime, ethvcgportPm30mHisParaLen, ethvcgportPm30mHisPara, ethvcgportPmvar1HisEid, ethvcgportPmvar1HisMonValue, 
                ethvcgportPmvar1HisVldty, ethvcgportPmvar1HisDatetime, ethvcgportPmvar1HisParaLen, ethvcgportPmvar1HisPara, ethvcgportPmvar2HisEid, ethvcgportPmvar2HisMonValue, 
                ethvcgportPmvar2HisVldty, ethvcgportPmvar2HisDatetime, ethvcgportPmvar2HisParaLen, ethvcgportPmvar2HisPara,portflowPmCurEid, portflowPmCurMonValue, portflowPmCurVldty, portflowPmCurDatetime, portflowPmCurParaLen, 
                portflowPmCurPara, portflowPm30sHisEid, portflowPm30sHisMonValue, portflowPm30sHisVldty, portflowPm30sHisDatetime, 
                portflowPm30sHisParaLen, portflowPm30sHisPara, portflowPm30mHisEid, portflowPm30mHisMonValue, portflowPm30mHisVldty, 
                portflowPm30mHisDatetime, portflowPm30mHisParaLen, portflowPm30mHisPara, portflowPmvar1HisEid, portflowPmvar1HisMonValue, 
                portflowPmvar1HisVldty, portflowPmvar1HisDatetime, portflowPmvar1HisParaLen, portflowPmvar1HisPara, portflowPmvar2HisEid,portflowPmvar2HisMonValue, 
                portflowPmvar2HisVldty, portflowPmvar2HisDatetime, portflowPmvar2HisParaLen, portflowPmvar2HisPara,cvlanpriofdsPmCurEid, cvlanpriofdsPmCurMonValue, cvlanpriofdsPmCurVldty, cvlanpriofdsPmCurDatetime, cvlanpriofdsPmCurParaLen, 
                cvlanpriofdsPmCurPara, cvlanpriofdsPm30sHisEid, cvlanpriofdsPm30sHisMonValue, cvlanpriofdsPm30sHisVldty, cvlanpriofdsPm30sHisDatetime, 
                cvlanpriofdsPm30sHisParaLen, cvlanpriofdsPm30sHisPara, cvlanpriofdsPm30mHisEid, cvlanpriofdsPm30mHisMonValue, cvlanpriofdsPm30mHisVldty, 
                cvlanpriofdsPm30mHisDatetime, cvlanpriofdsPm30mHisParaLen, cvlanpriofdsPm30mHisPara, cvlanpriofdsPmvar1HisEid, cvlanpriofdsPmvar1HisMonValue, 
                cvlanpriofdsPmvar1HisVldty, cvlanpriofdsPmvar1HisDatetime, cvlanpriofdsPmvar1HisParaLen, cvlanpriofdsPmvar1HisPara, cvlanpriofdsPmvar2HisEid,cvlanpriofdsPmvar2HisMonValue, 
                cvlanpriofdsPmvar2HisVldty, cvlanpriofdsPmvar2HisDatetime, cvlanpriofdsPmvar2HisParaLen, cvlanpriofdsPmvar2HisPara,svlanpriofdsPmCurEid, svlanpriofdsPmCurMonValue, svlanpriofdsPmCurVldty, svlanpriofdsPmCurDatetime, svlanpriofdsPmCurParaLen, 
                svlanpriofdsPmCurPara, svlanpriofdsPm30sHisEid, svlanpriofdsPm30sHisMonValue, svlanpriofdsPm30sHisVldty, svlanpriofdsPm30sHisDatetime, 
                svlanpriofdsPm30sHisParaLen, svlanpriofdsPm30sHisPara, svlanpriofdsPm30mHisEid, svlanpriofdsPm30mHisMonValue, svlanpriofdsPm30mHisVldty, 
                svlanpriofdsPm30mHisDatetime, svlanpriofdsPm30mHisParaLen, svlanpriofdsPm30mHisPara, svlanpriofdsPmvar1HisEid, svlanpriofdsPmvar1HisMonValue, 
                svlanpriofdsPmvar1HisVldty, svlanpriofdsPmvar1HisDatetime, svlanpriofdsPmvar1HisParaLen, svlanpriofdsPmvar1HisPara, svlanpriofdsPmvar2HisEid,svlanpriofdsPmvar2HisMonValue, 
                svlanpriofdsPmvar2HisVldty, svlanpriofdsPmvar2HisDatetime, svlanpriofdsPmvar2HisParaLen, svlanpriofdsPmvar2HisPara,ipdscpofdsPmCurEid, ipdscpofdsPmCurMonValue, ipdscpofdsPmCurVldty, ipdscpofdsPmCurDatetime, ipdscpofdsPmCurParaLen, 
                ipdscpofdsPmCurPara, ipdscpofdsPm30sHisEid, ipdscpofdsPm30sHisMonValue, ipdscpofdsPm30sHisVldty, ipdscpofdsPm30sHisDatetime, 
                ipdscpofdsPm30sHisParaLen, ipdscpofdsPm30sHisPara, ipdscpofdsPm30mHisEid, ipdscpofdsPm30mHisMonValue, ipdscpofdsPm30mHisVldty, 
                ipdscpofdsPm30mHisDatetime, ipdscpofdsPm30mHisParaLen, ipdscpofdsPm30mHisPara, ipdscpofdsPmvar1HisEid, ipdscpofdsPmvar1HisMonValue, 
                ipdscpofdsPmvar1HisVldty, ipdscpofdsPmvar1HisDatetime, ipdscpofdsPmvar1HisParaLen, ipdscpofdsPmvar1HisPara, ipdscpofdsPmvar2HisEid,ipdscpofdsPmvar2HisMonValue, 
                ipdscpofdsPmvar2HisVldty, ipdscpofdsPmvar2HisDatetime, ipdscpofdsPmvar2HisParaLen, ipdscpofdsPmvar2HisPara,vlanofvuniPmCurEid, vlanofvuniPmCurMonValue, vlanofvuniPmCurVldty, vlanofvuniPmCurDatetime, vlanofvuniPmCurParaLen, 
                vlanofvuniPmCurPara, vlanofvuniPm30sHisEid, vlanofvuniPm30sHisMonValue, vlanofvuniPm30sHisVldty, vlanofvuniPm30sHisDatetime, 
                vlanofvuniPm30sHisParaLen, vlanofvuniPm30sHisPara, vlanofvuniPm30mHisEid, vlanofvuniPm30mHisMonValue, vlanofvuniPm30mHisVldty, 
                vlanofvuniPm30mHisDatetime, vlanofvuniPm30mHisParaLen, vlanofvuniPm30mHisPara, vlanofvuniPmvar1HisEid, vlanofvuniPmvar1HisMonValue, 
                vlanofvuniPmvar1HisVldty, vlanofvuniPmvar1HisDatetime, vlanofvuniPmvar1HisParaLen, vlanofvuniPmvar1HisPara, vlanofvuniPmvar2HisEid,vlanofvuniPmvar2HisMonValue, 
                vlanofvuniPmvar2HisVldty, vlanofvuniPmvar2HisDatetime, vlanofvuniPmvar2HisParaLen, vlanofvuniPmvar2HisPara,
                virtualPortPmCurEid, virtualPortPmCurMonValue, virtualPortPmCurVldty, virtualPortPmCurDatetime, virtualPortPmCurParaLen, 
                virtualPortPmCurPara, virtualPortPm30sHisEid, virtualPortPm30sHisMonValue, virtualPortPm30sHisVldty, virtualPortPm30sHisDatetime, 
                virtualPortPm30sHisParaLen, virtualPortPm30sHisPara, virtualPortPm30mHisEid, virtualPortPm30mHisMonValue, virtualPortPm30mHisVldty, 
                virtualPortPm30mHisDatetime, virtualPortPm30mHisParaLen, virtualPortPm30mHisPara, virtualPortPmvar1HisEid, virtualPortPmvar1HisMonValue, 
                virtualPortPmvar1HisVldty, virtualPortPmvar1HisDatetime, virtualPortPmvar1HisParaLen, virtualPortPmvar1HisPara, virtualPortPmvar2HisEid,virtualPortPmvar2HisMonValue, 
                virtualPortPmvar2HisVldty, virtualPortPmvar2HisDatetime, virtualPortPmvar2HisParaLen, virtualPortPmvar2HisPara,
                plaPmCurEid, plaPmCurMonValue, plaPmCurVldty, plaPmCurDatetime, plaPmCurParaLen, 
                plaPmCurPara, plaPm30sHisEid, plaPm30sHisMonValue, plaPm30sHisVldty, plaPm30sHisDatetime, 
                plaPm30sHisParaLen, plaPm30sHisPara, plaPm30mHisEid, plaPm30mHisMonValue, plaPm30mHisVldty, 
                plaPm30mHisDatetime, plaPm30mHisParaLen, plaPm30mHisPara, plaPmvar1HisEid, plaPmvar1HisMonValue, 
                plaPmvar1HisVldty, plaPmvar1HisDatetime, plaPmvar1HisParaLen, plaPmvar1HisPara, plaPmvar2HisEid, plaPmvar2HisMonValue, 
                plaPmvar2HisVldty, plaPmvar2HisDatetime, plaPmvar2HisParaLen, plaPmvar2HisPara,
                nmsportPmCurEid, nmsportPmCurMonValue, nmsportPmCurVldty, nmsportPmCurDatetime, nmsportPmCurParaLen, 
                nmsportPmCurPara, nmsportPm30sHisEid, nmsportPm30sHisMonValue, nmsportPm30sHisVldty, nmsportPm30sHisDatetime, 
                nmsportPm30sHisParaLen, nmsportPm30sHisPara, nmsportPm30mHisEid, nmsportPm30mHisMonValue, nmsportPm30mHisVldty, 
                nmsportPm30mHisDatetime, nmsportPm30mHisParaLen, nmsportPm30mHisPara, nmsportPmvar1HisEid, nmsportPmvar1HisMonValue, 
                nmsportPmvar1HisVldty, nmsportPmvar1HisDatetime, nmsportPmvar1HisParaLen, nmsportPmvar1HisPara, nmsportPmvar2HisEid, nmsportPmvar2HisMonValue, 
                nmsportPmvar2HisVldty, nmsportPmvar2HisDatetime, nmsportPmvar2HisParaLen, nmsportPmvar2HisPara,
                testidperfPmCurEid, testidperfPmCurMonValue, testidperfPmCurVldty, testidperfPmCurDatetime, testidperfPmCurParaLen, 
                testidperfPmCurPara, testidperfPm30sHisEid, testidperfPm30sHisMonValue, testidperfPm30sHisVldty, testidperfPm30sHisDatetime, 
                testidperfPm30sHisParaLen, testidperfPm30sHisPara, testidperfPm30mHisEid, testidperfPm30mHisMonValue, testidperfPm30mHisVldty, 
                testidperfPm30mHisDatetime, testidperfPm30mHisParaLen, testidperfPm30mHisPara, testidperfPmvar1HisEid, testidperfPmvar1HisMonValue, 
                testidperfPmvar1HisVldty, testidperfPmvar1HisDatetime, testidperfPmvar1HisParaLen, testidperfPmvar1HisPara, testidperfPmvar2HisEid, testidperfPmvar2HisMonValue, 
                testidperfPmvar2HisVldty, testidperfPmvar2HisDatetime, testidperfPmvar2HisParaLen, testidperfPmvar2HisPara,
                xpicPmCurEid, xpicPmCurMonValue, xpicPmCurVldty, xpicPmCurDatetime, xpicPmCurParaLen, 
                xpicPmCurPara, xpicPm30sHisEid, xpicPm30sHisMonValue, xpicPm30sHisVldty, xpicPm30sHisDatetime, 
                xpicPm30sHisParaLen, xpicPm30sHisPara, xpicPm30mHisEid, xpicPm30mHisMonValue, xpicPm30mHisVldty, 
                xpicPm30mHisDatetime, xpicPm30mHisParaLen, xpicPm30mHisPara, xpicPmvar1HisEid, xpicPmvar1HisMonValue, 
                xpicPmvar1HisVldty, xpicPmvar1HisDatetime, xpicPmvar1HisParaLen, xpicPmvar1HisPara, xpicPmvar2HisEid, xpicPmvar2HisMonValue, 
                xpicPmvar2HisVldty, xpicPmvar2HisDatetime, xpicPmvar2HisParaLen, xpicPmvar2HisPara,
                nj1PmCurEid, nj1PmCurMonValue, nj1PmCurVldty, nj1PmCurDatetime, nj1PmCurParaLen, 
                nj1PmCurPara, nj1Pm30sHisEid, nj1Pm30sHisMonValue, nj1Pm30sHisVldty, nj1Pm30sHisDatetime, 
                nj1Pm30sHisParaLen, nj1Pm30sHisPara, nj1Pm30mHisEid, nj1Pm30mHisMonValue, nj1Pm30mHisVldty, 
                nj1Pm30mHisDatetime, nj1Pm30mHisParaLen, nj1Pm30mHisPara, nj1Pmvar1HisEid, nj1Pmvar1HisMonValue, 
                nj1Pmvar1HisVldty, nj1Pmvar1HisDatetime, nj1Pmvar1HisParaLen, nj1Pmvar1HisPara, nj1Pmvar2HisEid, nj1Pmvar2HisMonValue, 
                nj1Pmvar2HisVldty, nj1Pmvar2HisDatetime, nj1Pmvar2HisParaLen, nj1Pmvar2HisPara,
                vuniqueueperfPmCurEid, vuniqueueperfPmCurMonValue, vuniqueueperfPmCurVldty, vuniqueueperfPmCurDatetime, vuniqueueperfPmCurParaLen, 
                vuniqueueperfPmCurPara, vuniqueueperfPm30sHisEid, vuniqueueperfPm30sHisMonValue, vuniqueueperfPm30sHisVldty, vuniqueueperfPm30sHisDatetime, 
                vuniqueueperfPm30sHisParaLen, vuniqueueperfPm30sHisPara, vuniqueueperfPm30mHisEid, vuniqueueperfPm30mHisMonValue, vuniqueueperfPm30mHisVldty, 
                vuniqueueperfPm30mHisDatetime, vuniqueueperfPm30mHisParaLen, vuniqueueperfPm30mHisPara, vuniqueueperfPmvar1HisEid, vuniqueueperfPmvar1HisMonValue, 
                vuniqueueperfPmvar1HisVldty, vuniqueueperfPmvar1HisDatetime, vuniqueueperfPmvar1HisParaLen, vuniqueueperfPmvar1HisPara, vuniqueueperfPmvar2HisEid, vuniqueueperfPmvar2HisMonValue, 
                vuniqueueperfPmvar2HisVldty, vuniqueueperfPmvar2HisDatetime, vuniqueueperfPmvar2HisParaLen, vuniqueueperfPmvar2HisPara,
                pwqueueperfPmCurEid, pwqueueperfPmCurMonValue, pwqueueperfPmCurVldty, pwqueueperfPmCurDatetime, pwqueueperfPmCurParaLen, 
                pwqueueperfPmCurPara, pwqueueperfPm30sHisEid, pwqueueperfPm30sHisMonValue, pwqueueperfPm30sHisVldty, pwqueueperfPm30sHisDatetime, 
                pwqueueperfPm30sHisParaLen, pwqueueperfPm30sHisPara, pwqueueperfPm30mHisEid, pwqueueperfPm30mHisMonValue, pwqueueperfPm30mHisVldty, 
                pwqueueperfPm30mHisDatetime, pwqueueperfPm30mHisParaLen, pwqueueperfPm30mHisPara, pwqueueperfPmvar1HisEid, pwqueueperfPmvar1HisMonValue, 
                pwqueueperfPmvar1HisVldty, pwqueueperfPmvar1HisDatetime, pwqueueperfPmvar1HisParaLen, pwqueueperfPmvar1HisPara, pwqueueperfPmvar2HisEid, pwqueueperfPmvar2HisMonValue, 
                pwqueueperfPmvar2HisVldty, pwqueueperfPmvar2HisDatetime, pwqueueperfPmvar2HisParaLen, pwqueueperfPmvar2HisPara
                }
        STATUS current
        DESCRIPTION
            "Enter the description of the created OBJECT-GROUP."
        ::= { optixRtnDataGroups 1 }

    -- 1.3.6.1.4.1.2011.2.25.3.70.20.300.2
    optixRtnDataCompliances OBJECT IDENTIFIER ::= { optixRtnDataConformance 2 }

    -- 1.3.6.1.4.1.2011.2.25.3.70.20.300.2.1
    optixRtnDatabasicCompliance MODULE-COMPLIANCE
        STATUS current
        DESCRIPTION
            "Enter the description of the created MODULE-COMPLIANCE."
        MODULE -- this module
                MANDATORY-GROUPS { optixRtnDataObjectGroup }
        ::= { optixRtnDataCompliances 1 }
        
    
END

--
-- OPTIX-GLOBAL-PM-DATA-RTN-MIB-V2.my
--
