-- OPTIX-GLOBAL-ALM-TRAPS-RTN-MIB
-- MIB generated by ExcelToMIB tool 1.0
-- 
-- =================================================================
--  Copyright (C) 2012 by HUAWEI TECHNOLOGIES. All rights reserved
-- 
-- Description:This MIB describes the Alarm interface of Huawei macrowave transmit
--  Reference:
--  Version: V1.00
--  History:
--  <author>,<date>,<contents>
-- =================================================================
--
OPTIX-GLOBAL-ALM-TRAPS-RTN-MIB DEFINITIONS ::= BEGIN
		IMPORTS
		
			optixGlobalTrap, rptAlmName, rptEvtSrvEff, rptEvtNtfcnCde, rptEvtNumber, 
			rptEvtState, rptEvtObjType, rptEvtPara, rptEvtStartTime, rptEvtEndTime			
				FROM OPTIX-GLOBAL-TRAPS-MIB			
			optixCommonGlobal			
				FROM OPTIX-OID-MIB			
        		PerformanceEventType,ValidflagType,ObjType,AlarmEventType,AlmDataSrvEffType,AlmDataNtfcnCdeType,DataPmEventType
           			FROM OPTIX-GLOBAL-TC-MIB
        		OBJECT-GROUP,MODULE-COMPLIANCE
            			FROM SNMPv2-CONF
	            DateAndTime,DisplayString
            			FROM SNMPv2-TC
        		Integer32,Unsigned32,OBJECT-TYPE,MODULE-IDENTITY,NOTIFICATION-TYPE
				FROM SNMPv2-SMI;

    -- 1.3.6.1.4.1.2011.2.25.3.40.40.40
    trapsAlm OBJECT IDENTIFIER ::= { optixGlobalTrap 40 }

    -- 1.3.6.1.4.1.2011.2.25.3.40.40.40.1
    almRLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of signal."
        ::= { trapsAlm 1 }

    -- 1.3.6.1.4.1.2011.2.25.3.40.40.40.3
    almRLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of clock."
        ::= { trapsAlm 3 }

    -- 1.3.6.1.4.1.2011.2.25.3.40.40.40.4
    almTLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Transmit loss of clock."
        ::= { trapsAlm 4 }

    -- 1.3.6.1.4.1.2011.2.25.3.40.40.40.5
    almROof NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Out of frame."
        ::= { trapsAlm 5 }

    -- 1.3.6.1.4.1.2011.2.25.3.40.40.40.6
    almNoBdSoft NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No board software alarm. The alarm occurs when the board does not have the necessary files, for example, loading software, manufacturing information and logic software or the software name is incorrect."
        ::= { trapsAlm 6 }

    -- 1.3.6.1.4.1.2011.2.25.3.40.40.40.8
    almRLof NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of frame on receiving line."
        ::= { trapsAlm 8 }

    -- 1.3.6.1.4.1.2011.2.25.3.40.40.40.9
    almTF NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Laser Transmission Failure."
        ::= { trapsAlm 9 }

    -- 1.3.6.1.4.1.2011.2.25.3.40.40.40.10
    almRsCrossTr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Regenerator section performance over threshold."
        ::= { trapsAlm 10 }

    -- 1.3.6.1.4.1.2011.2.25.3.40.40.40.12
    almB1Exc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Regenerator section (B1) excessive errors."
        ::= { trapsAlm 12 }

    -- 1.3.6.1.4.1.2011.2.25.3.40.40.40.14
    almTrLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The clock of the cross-connect board is faulty."
        ::= { trapsAlm 14 }

    -- 1.3.6.1.4.1.2011.2.25.3.40.40.40.16
    almHpCrossTr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: High order path bit errors crosses the threshold."
        ::= { trapsAlm 16 }

    -- 1.3.6.1.4.1.2011.2.25.3.40.40.40.25
    almInPwrAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Input power abnormal."
        ::= { trapsAlm 25 }

    -- 1.3.6.1.4.1.2011.2.25.3.40.40.40.26
    almOutPwrAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Output power abnormal."
        ::= { trapsAlm 26 }

    -- 1.3.6.1.4.1.2011.2.25.3.40.40.40.28
    almTempOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Board working temperature over threshold."
        ::= { trapsAlm 28 }

    -- 1.3.6.1.4.1.2011.2.25.3.40.40.40.29
    almTemHa NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Laser temperature is too high."
        ::= { trapsAlm 29 }

    -- 1.3.6.1.4.1.2011.2.25.3.40.40.40.30
    almTemLa NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Laser temperature is too low."
        ::= { trapsAlm 30 }

    -- 1.3.6.1.4.1.2011.2.25.3.40.40.40.31
    almInPwrHigh NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Input optical power is too high."
        ::= { trapsAlm 31 }

    -- 1.3.6.1.4.1.2011.2.25.3.40.40.40.32
    almInPwrLow NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Input optical power is too low."
        ::= { trapsAlm 32 }

    -- 1.3.6.1.4.1.2011.2.25.3.40.40.40.33
    almMsAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex section alarm indication."
        ::= { trapsAlm 33 }

    -- 1.3.6.1.4.1.2011.2.25.3.40.40.40.34
    almMsRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex section remote defect indication."
        ::= { trapsAlm 34 }

    -- 1.3.6.1.4.1.2011.2.25.3.40.40.40.35
    almB2Exc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex section(B2) excessive errors."
        ::= { trapsAlm 35 }

    -- 1.3.6.1.4.1.2011.2.25.3.40.40.40.36
    almB2Sd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex section(B2) signal degrade."
        ::= { trapsAlm 36 }

    -- 1.3.6.1.4.1.2011.2.25.3.40.40.40.37
    almMsRei NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex section remote error indication."
        ::= { trapsAlm 37 }

    -- 1.3.6.1.4.1.2011.2.25.3.40.40.40.38
    almMsCrossTr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex section performance over threshold."
        ::= { trapsAlm 38 }

    -- 1.3.6.1.4.1.2011.2.25.3.40.40.40.41
    almApsIndi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: APS state indication."
        ::= { trapsAlm 41 }

    -- 1.3.6.1.4.1.2011.2.25.3.40.40.40.42
    almApsFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: APS protection switching failure."
        ::= { trapsAlm 42 }

    -- 1.3.6.1.4.1.2011.2.25.3.40.40.40.48
    almLpRfi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Lower order path remote failure indication."
        ::= { trapsAlm 48 }

    -- 1.3.6.1.4.1.2011.2.25.3.40.40.40.49
    almLpCrossTr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Low order path bit errors over threshold."
        ::= { trapsAlm 49 }

    -- 1.3.6.1.4.1.2011.2.25.3.40.40.40.51
    almLpSizeErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: TU structure error.When the mapping structure of the TU services received at the board is inconsistent with that specified for the board, this alarm is reported"
        ::= { trapsAlm 51 }

    -- 1.3.6.1.4.1.2011.2.25.3.40.40.40.56
    almLsrWillDie NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Laser will be out of work."
        ::= { trapsAlm 56 }

    -- 1.3.6.1.4.1.2011.2.25.3.40.40.40.57
    almLsrNoFited NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Laser is not installed."
        ::= { trapsAlm 57 }

    -- 1.3.6.1.4.1.2011.2.25.3.40.40.40.58
    almLsrBcmAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Setover Current of the Laser over Threshold."
        ::= { trapsAlm 58 }

    -- 1.3.6.1.4.1.2011.2.25.3.40.40.40.64
    almOutPwrLow NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Output optical power too low."
        ::= { trapsAlm 64 }

    -- 1.3.6.1.4.1.2011.2.25.3.40.40.40.66
    almAuLop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: AU loss of pointer. When eight NDF frames or invalid pointer values are consecutively received on the receive side of the local optical interface, this alarm is reported."
        ::= { trapsAlm 66 }

    -- 1.3.6.1.4.1.2011.2.25.3.40.40.40.67
    almMsAdCrossTr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Multiplex Section Adaptation Performance Over Threshold."
        ::= { trapsAlm 67 }

    -- 1.3.6.1.4.1.2011.2.25.3.40.40.40.70
    almB3Sd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: High order path B3 signal degraded."
        ::= { trapsAlm 70 }

    -- 1.3.6.1.4.1.2011.2.25.3.40.40.40.71
    almB3Exc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Working temperature of the pump laser over threshold."
        ::= { trapsAlm 71 }

    -- 1.3.6.1.4.1.2011.2.25.3.40.40.40.72
    almAuAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: AU alarm indication."
        ::= { trapsAlm 72 }

    -- 1.3.6.1.4.1.2011.2.25.3.40.40.40.75
    almHpUneq NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No loading error in the higher order path."
        ::= { trapsAlm 75 }

    -- 1.3.6.1.4.1.2011.2.25.3.40.40.40.76
    almHpTim NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Higher order path tracking identification mismatch."
        ::= { trapsAlm 76 }

    -- 1.3.6.1.4.1.2011.2.25.3.40.40.40.77
    almHpSlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Higher order path signal identification mismatch."
        ::= { trapsAlm 77 }

    -- 1.3.6.1.4.1.2011.2.25.3.40.40.40.78
    almHpRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: High order path remote defect indication."
        ::= { trapsAlm 78 }

    -- 1.3.6.1.4.1.2011.2.25.3.40.40.40.79
    almHpRei NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: High order path remote error indication."
        ::= { trapsAlm 79 }

    -- 1.3.6.1.4.1.2011.2.25.3.40.40.40.81
    almHpLom NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Higher order Path Loss of Multiframe."
        ::= { trapsAlm 81 }

    -- 1.3.6.1.4.1.2011.2.25.3.40.40.40.82
    almTuLop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: TU Loss of Pointer."
        ::= { trapsAlm 82 }

    -- 1.3.6.1.4.1.2011.2.25.3.40.40.40.83
    almTuAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: TU alarm indication."
        ::= { trapsAlm 83 }

    -- 1.3.6.1.4.1.2011.2.25.3.40.40.40.84
    almHpAdCrossTr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: High order path adaption performance over threshold."
        ::= { trapsAlm 84 }

    -- 1.3.6.1.4.1.2011.2.25.3.40.40.40.87
    almJ0Mm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Trace identifier mismatch."
        ::= { trapsAlm 87 }

    -- 1.3.6.1.4.1.2011.2.25.3.40.40.40.88
    almLpRFifo NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: FIFO overflow on the receiving side of the lower order path."
        ::= { trapsAlm 88 }

    -- 1.3.6.1.4.1.2011.2.25.3.40.40.40.89
    almLpTFifo NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: FIFO overflow on the transmission side of the lower order path."
        ::= { trapsAlm 89 }

    -- 1.3.6.1.4.1.2011.2.25.3.40.40.40.90
    almLpUneq NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No payload indication of the lower order path."
        ::= { trapsAlm 90 }

    -- 1.3.6.1.4.1.2011.2.25.3.40.40.40.91
    almLpTim NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Lower order path tracking identification mismatch."
        ::= { trapsAlm 91 }

    -- 1.3.6.1.4.1.2011.2.25.3.40.40.40.92
    almLpSlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Lower order path signal label mismatch."
        ::= { trapsAlm 92 }

    -- 1.3.6.1.4.1.2011.2.25.3.40.40.40.93
    almLpRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Low order path remote defect indication."
        ::= { trapsAlm 93 }

    -- 1.3.6.1.4.1.2011.2.25.3.40.40.40.94
    almLpRei NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Low order path remote error indication."
        ::= { trapsAlm 94 }

    -- 1.3.6.1.4.1.2011.2.25.3.40.40.40.99
    almWRFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: this is an alarm indicating the failure of reading and writing the chip register"
        ::= { trapsAlm 99 }

    -- 1.3.6.1.4.1.2011.2.25.3.40.40.40.100
    almLTI NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of timing input."
        ::= { trapsAlm 100 }

    -- 1.3.6.1.4.1.2011.2.25.3.40.40.40.101
    almSynBad NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Synchronous Source Degrade."
        ::= { trapsAlm 101 }

    -- 1.3.6.1.4.1.2011.2.25.3.40.40.40.107
    almTAlos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: E1/T1 interface loss of analog signal."
        ::= { trapsAlm 107 }

    -- 1.3.6.1.4.1.2011.2.25.3.40.40.40.111
    almSyncCLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of synchronization source level."
        ::= { trapsAlm 111 }

    -- 1.3.6.1.4.1.2011.2.25.3.40.40.40.115
    almFanFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Fan failure."
        ::= { trapsAlm 115 }

    -- 1.3.6.1.4.1.2011.2.25.3.40.40.40.117
    almE1Los NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: 2M Line Loss Of Signal."
        ::= { trapsAlm 117 }

    -- 1.3.6.1.4.1.2011.2.25.3.40.40.40.118
    almUpE1Ais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: 2M up signal alarm indication."
        ::= { trapsAlm 118 }

    -- 1.3.6.1.4.1.2011.2.25.3.40.40.40.119
    almBdStatus NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Board not in position alarm."
        ::= { trapsAlm 119 }

    -- 1.3.6.1.4.1.2011.2.25.3.40.40.40.121
    almWrgBdType NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Wrong board type."
        ::= { trapsAlm 121 }

    -- 1.3.6.1.4.1.2011.2.25.3.40.40.40.125
    almPowerFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Power failure"
        ::= { trapsAlm 125 }

    -- 1.3.6.1.4.1.2011.2.25.3.40.40.40.139
    almALoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of clock in the upstream direction of the bus."
        ::= { trapsAlm 139 }

    -- 1.3.6.1.4.1.2011.2.25.3.40.40.40.141
    almRSErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Received Signal Error."
        ::= { trapsAlm 141 }

    -- 1.3.6.1.4.1.2011.2.25.3.40.40.40.159
    almRFRst NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Receiving FIFO Reset."
        ::= { trapsAlm 159 }

    -- 1.3.6.1.4.1.2011.2.25.3.40.40.40.160
    almTFRst NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Transmission FIFO Reset."
        ::= { trapsAlm 160 }

    -- 1.3.6.1.4.1.2011.2.25.3.40.40.40.163
    almRpLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss Of Receiving Phaselock Ring Clock."
        ::= { trapsAlm 163 }

    -- 1.3.6.1.4.1.2011.2.25.3.40.40.40.166
    almTempAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Temperature over threshold."
        ::= { trapsAlm 166 }

    -- 1.3.6.1.4.1.2011.2.25.3.40.40.40.175
    almB1SD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Regenerator section(B1) signal degraded."
        ::= { trapsAlm 175 }

    -- 1.3.6.1.4.1.2011.2.25.3.40.40.40.180
    almK1K2M NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: K1K2 Mismatch."
        ::= { trapsAlm 180 }

    -- 1.3.6.1.4.1.2011.2.25.3.40.40.40.181
    almK2M NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: K2 Mismatch."
        ::= { trapsAlm 181 }

    -- 1.3.6.1.4.1.2011.2.25.3.40.40.40.182
    almBipSD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: BIP signal degraded."
        ::= { trapsAlm 182 }

    -- 1.3.6.1.4.1.2011.2.25.3.40.40.40.183
    almBipExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: BIP excssive errors."
        ::= { trapsAlm 183 }

    -- 1.3.6.1.4.1.2011.2.25.3.40.40.40.184
    almExtSyncLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of External Synchronous Source."
        ::= { trapsAlm 184 }

    -- 1.3.6.1.4.1.2011.2.25.3.40.40.40.185
    almDbmsError NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: There is an error in the system database."
        ::= { trapsAlm 185 }

    -- 1.3.6.1.4.1.2011.2.25.3.40.40.40.189
    almTd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Laser transmitter degrade"
        ::= { trapsAlm 189 }

    -- 1.3.6.1.4.1.2011.2.25.3.40.40.40.193
    almS1SynChange NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Synchronous source changed in S1 mode."
        ::= { trapsAlm 193 }

    -- 1.3.6.1.4.1.2011.2.25.3.40.40.40.194
    almFpgaAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:FPGA Abnormal"
        ::= { trapsAlm 194 }

    -- 1.3.6.1.4.1.2011.2.25.3.40.40.40.197
    almNeStateInstall NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:NE in install state"
        ::= { trapsAlm 197 }

    -- 1.3.6.1.4.1.2011.2.25.3.40.40.40.198
    almDbmsProtectMode NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Databases in protection mode."
        ::= { trapsAlm 198 }

    -- 1.3.6.1.4.1.2011.2.25.3.40.40.40.199
    almCommunFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Inter-board communication failure."
        ::= { trapsAlm 199 }

    -- 1.3.6.1.4.1.2011.2.25.3.40.40.40.200
    almSecuAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The SECU_ALM is an alarm indicating that an illegal user fails to log in to the NE."
        ::= { trapsAlm 200 }

    -- 1.3.6.1.4.1.2011.2.25.3.40.40.40.201
    almDownE1Ais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: 2M down signal alarm indication."
        ::= { trapsAlm 201 }

    -- 1.3.6.1.4.1.2011.2.25.3.40.40.40.214
    almOCD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Out of Cell Delineation."
        ::= { trapsAlm 214 }

    -- 1.3.6.1.4.1.2011.2.25.3.40.40.40.215
    almNeSfLost NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of NE software."
        ::= { trapsAlm 215 }

    -- 1.3.6.1.4.1.2011.2.25.3.40.40.40.216
    almLCD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of cell delimitation."
        ::= { trapsAlm 216 }

    -- 1.3.6.1.4.1.2011.2.25.3.40.40.40.218
    almUHCS NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Uncorrected Header Check Sequence."
        ::= { trapsAlm 218 }

    -- 1.3.6.1.4.1.2011.2.25.3.40.40.40.219
    almCHCS NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Corrected Header Check Sequence."
        ::= { trapsAlm 219 }

    -- 1.3.6.1.4.1.2011.2.25.3.40.40.40.226
    almVpAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: VP alam indication signal."
        ::= { trapsAlm 226 }

    -- 1.3.6.1.4.1.2011.2.25.3.40.40.40.227
    almVpRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: VP remote defect indicator."
        ::= { trapsAlm 227 }

    -- 1.3.6.1.4.1.2011.2.25.3.40.40.40.228
    almVcAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: VC alam indication signal."
        ::= { trapsAlm 228 }

    -- 1.3.6.1.4.1.2011.2.25.3.40.40.40.229
    almVcRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: VC remote defect indicator."
        ::= { trapsAlm 229 }

    -- 1.3.6.1.4.1.2011.2.25.3.40.40.40.235
    almEthLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The ETH_LOS is an alarm indicating loss of network port connection. This alarm occurs when the Ethernet network port cannot receive Ethernet signals."
        ::= { trapsAlm 235 }

    -- 1.3.6.1.4.1.2011.2.25.3.40.40.40.236
    almHardBad NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm occurs when the board detects a hardware exception."
        ::= { trapsAlm 236 }

    -- 1.3.6.1.4.1.2011.2.25.3.40.40.40.240
    almLoopAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm occurs when service loopback is set."
        ::= { trapsAlm 240 }

    -- 1.3.6.1.4.1.2011.2.25.3.40.40.40.261
    almLinkErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Data link error."
        ::= { trapsAlm 261 }

    -- 1.3.6.1.4.1.2011.2.25.3.40.40.40.265
    almVoltLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of voltage."
        ::= { trapsAlm 265 }

    -- 1.3.6.1.4.1.2011.2.25.3.40.40.40.266
    almE1Loc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of upstream 2M clock."
        ::= { trapsAlm 266 }

    -- 1.3.6.1.4.1.2011.2.25.3.40.40.40.296
    almALS NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Automatic Laser Shutdown."
        ::= { trapsAlm 296 }

    -- 1.3.6.1.4.1.2011.2.25.3.40.40.40.333
    almClkNoTraceMode NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Clock entering into non-tracing running mode."
        ::= { trapsAlm 333 }

    -- 1.3.6.1.4.1.2011.2.25.3.40.40.40.336
    almApsManuStop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: MSP protocol is manually stopped."
        ::= { trapsAlm 336 }

    -- 1.3.6.1.4.1.2011.2.25.3.40.40.40.364
    almLaserClosed NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Laser Closed."
        ::= { trapsAlm 364 }

    -- 1.3.6.1.4.1.2011.2.25.3.40.40.40.377
    almBusErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Bus error."
        ::= { trapsAlm 377 }

    -- 1.3.6.1.4.1.2011.2.25.3.40.40.40.383
    almPowerAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: this alarm indicate that the voltage of the board power module is beyond the normal range."
        ::= { trapsAlm 383 }

    -- 1.3.6.1.4.1.2011.2.25.3.40.40.40.393
    almLaserModErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Wrong laser module"
        ::= { trapsAlm 393 }

    -- 1.3.6.1.4.1.2011.2.25.3.40.40.40.412
    almPowerAbnormal NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Power abnormal."
        ::= { trapsAlm 412 }

    -- 1.3.6.1.4.1.2011.2.25.3.40.40.40.423
    almSlaveBad NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm occurs when the board detects detects a fault of the connector between itself and the standby SCC board."
        ::= { trapsAlm 423 }

    -- 1.3.6.1.4.1.2011.2.25.3.40.40.40.432
    almModComFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Module communicates abnormally. The alarm occurs when the communication of the CPU and other internal modules of the board is abnormal."
        ::= { trapsAlm 432 }

    -- 1.3.6.1.4.1.2011.2.25.3.40.40.40.449
    almBiosStatus NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: BIOS status."
        ::= { trapsAlm 449 }

    -- 1.3.6.1.4.1.2011.2.25.3.40.40.40.571
    almNeSoftMM NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Inconsistency between the active and standby software."
        ::= { trapsAlm 571 }

    -- 1.3.6.1.4.1.2011.2.25.3.40.40.40.573
    almSwdlActivatedTimeOut NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Activation time out."
        ::= { trapsAlm 573 }

    -- 1.3.6.1.4.1.2011.2.25.3.40.40.40.574
    almSwdlNePkgCheck NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: the alarm indicate that a file in the software package is lost or the package loading fails to pass the check."
        ::= { trapsAlm 574 }

    -- 1.3.6.1.4.1.2011.2.25.3.40.40.40.575
    almSwdlChgmngNoMatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: NE software and the board software do not match."
        ::= { trapsAlm 575 }

    -- 1.3.6.1.4.1.2011.2.25.3.40.40.40.584
    almBootRomBad NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: this alarm indicate the BOOTROM data check failure. During the running of board software, the system periodically checks whether the BOOTROM data is damaged. This alarm occurs when the BOOTROM data is detected damaged."
        ::= { trapsAlm 584 }

    -- 1.3.6.1.4.1.2011.2.25.3.40.40.40.589
    almLicenceErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Licence Error."
        ::= { trapsAlm 589 }

    -- 1.3.6.1.4.1.2011.2.25.3.40.40.40.591
    almSyncFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Batch Backup Failure of the SCC Board Data."
        ::= { trapsAlm 591 }

    -- 1.3.6.1.4.1.2011.2.25.3.40.40.40.607
    almV5Vcais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "nul."
        ::= { trapsAlm 607 }

    -- 1.3.6.1.4.1.2011.2.25.3.40.40.40.619
    almLpsUniBiM NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: alarm of mismatch in unidirectional operation and bidirectional operation in msp_linear ."
        ::= { trapsAlm 619 }

    -- 1.3.6.1.4.1.2011.2.25.3.40.40.40.620
    almPatchfileNotexist NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: patchfile not exist ."
        ::= { trapsAlm 620 }

    -- 1.3.6.1.4.1.2011.2.25.3.40.40.40.621
    almPatchErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: patch error ."
        ::= { trapsAlm 621 }

    -- 1.3.6.1.4.1.2011.2.25.3.40.40.40.622
    almPatchNotConfirm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Activated patch has not been confirmed overtime"
        ::= { trapsAlm 622 }

    -- 1.3.6.1.4.1.2011.2.25.3.40.40.40.624
    almRtcFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: RTC time fail alarm"
        ::= { trapsAlm 624 }

    -- 1.3.6.1.4.1.2011.2.25.3.40.40.40.625
    almBdNotInstalled NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Logic board not installed."
        ::= { trapsAlm 625 }

    -- 1.3.6.1.4.1.2011.2.25.3.40.40.40.626
    almMwLim NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Microwave link identifier mismatch."
        ::= { trapsAlm 626 }

    -- 1.3.6.1.4.1.2011.2.25.3.40.40.40.631
    almMwLof NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: microwave loss of frame."
        ::= { trapsAlm 631 }

    -- 1.3.6.1.4.1.2011.2.25.3.40.40.40.635
    almRadioTslLow NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Radio transmission level too low."
        ::= { trapsAlm 635 }

    -- 1.3.6.1.4.1.2011.2.25.3.40.40.40.636
    almRadioTslHigh NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Radio transmission level too high."
        ::= { trapsAlm 636 }

    -- 1.3.6.1.4.1.2011.2.25.3.40.40.40.637
    almRadioRslHigh NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Radio receive level too high."
        ::= { trapsAlm 637 }

    -- 1.3.6.1.4.1.2011.2.25.3.40.40.40.638
    almRadioRslLow NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Radio receive level too low"
        ::= { trapsAlm 638 }

    -- 1.3.6.1.4.1.2011.2.25.3.40.40.40.639
    almRadioMute NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: radio transmission mute."
        ::= { trapsAlm 639 }

    -- 1.3.6.1.4.1.2011.2.25.3.40.40.40.640
    almConfigNoSupport NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: configuration not support."
        ::= { trapsAlm 640 }

    -- 1.3.6.1.4.1.2011.2.25.3.40.40.40.2569
    almSwdlPkgNoBdSoft NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No board software in the software package."
        ::= { trapsAlm 2569 }

    -- 1.3.6.1.4.1.2011.2.25.3.40.40.40.2570
    almSwdlRollbackFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: NE rollback failed."
        ::= { trapsAlm 2570 }

    -- 1.3.6.1.4.1.2011.2.25.3.40.40.40.2571
    almSwdlCommitFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Commit failure."
        ::= { trapsAlm 2571 }

    -- 1.3.6.1.4.1.2011.2.25.3.40.40.40.2572
    almSwdlInProcess NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Software downloading in process."
        ::= { trapsAlm 2572 }

    -- 1.3.6.1.4.1.2011.2.25.3.40.40.40.2573
    almSwdlPkgVerMM NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Inconsistency of software package versions."
        ::= { trapsAlm 2573 }

    -- 1.3.6.1.4.1.2011.2.25.3.40.40.40.2574
    almSwdlAutoMatchInh NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Automatic match inhibited."
        ::= { trapsAlm 2574 }

    -- 1.3.6.1.4.1.2011.2.25.3.40.40.40.12291
    almEthOamRmtLoop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The ETHOAM_RMT_LOOP is an alarm indicating the remote loopback of point-to-point Ethernet OAM. This alarm only occurs to the port with the point-to-point OAM protocol enabled. If the port is able to respond to loopback, it enters the loopback response state and reports the loopback response alarm after it receives the remote loopback enabling command sent by the opposite OAM port. The loopback initiator reports the loopback initiating alarm. If the port receives the loopback disabling command, it exits the loopback response state and ends the loopback response alarm. The loopback initiator end also ends the loopback initiating alarm."
        ::= { trapsAlm 12291 }

    -- 1.3.6.1.4.1.2011.2.25.3.40.40.40.12292
    almEthOamRmtSd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The EthOamRmtSd is an alarm indicating the remote SD of point-to-point Ethernet OAM. When the port with the OAM protocol enabled receives the link event message from the opposite end which indicates that the remote Ethernet performance degraded, this alarm occurs."
        ::= { trapsAlm 12292 }

    -- 1.3.6.1.4.1.2011.2.25.3.40.40.40.12293
    almEthOamRmtCritFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The EthOamRmtCritFault is an alarm indicating that a critical fault occurs to the remote end of point-to-point Ethernet OAM. When the port with the OAM protocol enabled receives the OAM message that contains critical fault information from the opposite end, this alarm occurs."
        ::= { trapsAlm 12293 }

    -- 1.3.6.1.4.1.2011.2.25.3.40.40.40.12294
    almEthOamDiscoverFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: EthOamDiscoverFail is an alarm indicating the point-to-point Ethernet OAM discovery failure. When the OAM protocol is enabled at the port of a board and the negotiation with the opposite equipment fails, this alarm occurs."
        ::= { trapsAlm 12294 }

    -- 1.3.6.1.4.1.2011.2.25.3.40.40.40.12298
    almExEthOamCCLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Continuity Check Message Loss"
        ::= { trapsAlm 12298 }

    -- 1.3.6.1.4.1.2011.2.25.3.40.40.40.12299
    almExEthOamMpidCnflct NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Maintenance Identify Conflict"
        ::= { trapsAlm 12299 }

    -- 1.3.6.1.4.1.2011.2.25.3.40.40.40.12300
    almLptRfi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LPT_RFI is a remote failure indication alarm of link state pass through. This alarm occurs when the link state pass through (LPT) detects the failure of the remote port or the LPT service network."
        ::= { trapsAlm 12300 }

    -- 1.3.6.1.4.1.2011.2.25.3.40.40.40.12301
    almFlowOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Port inflow over the limit"
        ::= { trapsAlm 12301 }

    -- 1.3.6.1.4.1.2011.2.25.3.40.40.40.12305
    almRelayAlarmCritical NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Critical relay alarm."
        ::= { trapsAlm 12305 }

    -- 1.3.6.1.4.1.2011.2.25.3.40.40.40.12306
    almRelayAlarmMajor NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Major relay alarm."
        ::= { trapsAlm 12306 }

    -- 1.3.6.1.4.1.2011.2.25.3.40.40.40.12307
    almRelayAlarmMinor NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Minor relay alarm."
        ::= { trapsAlm 12307 }

    -- 1.3.6.1.4.1.2011.2.25.3.40.40.40.12308
    almRelayAlarmIgnore NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Relay alarm warning."
        ::= { trapsAlm 12308 }

    -- 1.3.6.1.4.1.2011.2.25.3.40.40.40.12544
    almRemoteFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Remote defect alarm of ethernet port."
        ::= { trapsAlm 12544 }

    -- 1.3.6.1.4.1.2011.2.25.3.40.40.40.12545
    almLocalFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Local defect alarm of ethernet port."
        ::= { trapsAlm 12545 }

    -- 1.3.6.1.4.1.2011.2.25.3.40.40.40.12580
    almHardErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Hardware error."
        ::= { trapsAlm 12580 }

    -- 1.3.6.1.4.1.2011.2.25.3.40.40.40.12586
    almSysLogCommFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: the NE and the SYSLOG server have an abnormal connection or session in the TCP mode."
        ::= { trapsAlm 12586 }

    -- 1.3.6.1.4.1.2011.2.25.3.40.40.40.12587
    almMwRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Microwave remote defect indication."
        ::= { trapsAlm 12587 }

    -- 1.3.6.1.4.1.2011.2.25.3.40.40.40.12588
    almMwFecUncor NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Forward Error Correction code uncorrectable."
        ::= { trapsAlm 12588 }

    -- 1.3.6.1.4.1.2011.2.25.3.40.40.40.12589
    almIfInPwrAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Abnormal IF power received by ODU."
        ::= { trapsAlm 12589 }

    -- 1.3.6.1.4.1.2011.2.25.3.40.40.40.12593
    almWrgDevType NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Wrong device type."
        ::= { trapsAlm 12593 }

    -- 1.3.6.1.4.1.2011.2.25.3.40.40.40.12598
    almCFCardOffLine NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: CF Card offline."
        ::= { trapsAlm 12598 }

    -- 1.3.6.1.4.1.2011.2.25.3.40.40.40.12599
    almCFCardFailed NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: CF Card Failed."
        ::= { trapsAlm 12599 }

    -- 1.3.6.1.4.1.2011.2.25.3.40.40.40.12600
    almCFCardWRDisabled NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The CFCARD_W_R_DISABLED is an alarm indicating that reading and writing the CF card are disabled."
        ::= { trapsAlm 12600 }

    -- 1.3.6.1.4.1.2011.2.25.3.40.40.40.12767
    almEthOamSelfLoop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Ethernet OAM(802.3ah) self loop alarm"
        ::= { trapsAlm 12767 }

    -- 1.3.6.1.4.1.2011.2.25.3.40.40.40.12768
    almEthOamVcgSelfLoop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Ethernet OAM(802.3ah)self loop alarm"
        ::= { trapsAlm 12768 }

    -- 1.3.6.1.4.1.2011.2.25.3.40.40.40.12769
    almLagPortFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Port aggregation failure"
        ::= { trapsAlm 12769 }

    -- 1.3.6.1.4.1.2011.2.25.3.40.40.40.12770
    almLagVcPortFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: VCTRUNK aggregation failure"
        ::= { trapsAlm 12770 }

    -- 1.3.6.1.4.1.2011.2.25.3.40.40.40.12775
    almPatchDeactTimeout NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Patch Deactivation Timeout"
        ::= { trapsAlm 12775 }

    -- 1.3.6.1.4.1.2011.2.25.3.40.40.40.12776
    almPatchActTimeout NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Patch Activation Timeout"
        ::= { trapsAlm 12776 }

    -- 1.3.6.1.4.1.2011.2.25.3.40.40.40.12777
    almCFCardFull NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:CF card capacity fully used"
        ::= { trapsAlm 12777 }

    -- 1.3.6.1.4.1.2011.2.25.3.40.40.40.12786
    almEthNoFlow NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No traffic at Ethernet port."
        ::= { trapsAlm 12786 }

    -- 1.3.6.1.4.1.2011.2.25.3.40.40.40.12788
    almPortModeMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Working mode mismatch at remote FE port."
        ::= { trapsAlm 12788 }

    -- 1.3.6.1.4.1.2011.2.25.3.40.40.40.12790
    almPatchPkgErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Patch package file error."
        ::= { trapsAlm 12790 }

    -- 1.3.6.1.4.1.2011.2.25.3.40.40.40.12792
    almSyncDisable NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: State of auto-synchronization disabled."
        ::= { trapsAlm 12792 }

    -- 1.3.6.1.4.1.2011.2.25.3.40.40.40.12793
    almEthLinkDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of network interface connection."
        ::= { trapsAlm 12793 }

    -- 1.3.6.1.4.1.2011.2.25.3.40.40.40.12794
    almMacFcsExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: An alarm indicating that the number of FCS errors received over the Ethernet interface crosses the threshold."
        ::= { trapsAlm 12794 }

    -- 1.3.6.1.4.1.2011.2.25.3.40.40.40.12795
    almMacFcsSd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: An alarm indicating that FCS errors received over the Ethernet interface crosses the lower(degraded) threshold."
        ::= { trapsAlm 12795 }

    -- 1.3.6.1.4.1.2011.2.25.3.40.40.40.12796
    almCesLospktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss Packets Excess."
        ::= { trapsAlm 12796 }

    -- 1.3.6.1.4.1.2011.2.25.3.40.40.40.12797
    almCesMisorderpktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Misorder Dropped Packets Excess."
        ::= { trapsAlm 12797 }

    -- 1.3.6.1.4.1.2011.2.25.3.40.40.40.12798
    almCesStraypktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Stray Dropped Packets Excess."
        ::= { trapsAlm 12798 }

    -- 1.3.6.1.4.1.2011.2.25.3.40.40.40.12799
    almCesMalpktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Malformed Packets Excess alarm."
        ::= { trapsAlm 12799 }

    -- 1.3.6.1.4.1.2011.2.25.3.40.40.40.12800
    almCesJtrudrExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Jitter buffer underrun alarm."
        ::= { trapsAlm 12800 }

    -- 1.3.6.1.4.1.2011.2.25.3.40.40.40.12801
    almCesJtrovrExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Jitter buffer overrun alarm."
        ::= { trapsAlm 12801 }

    -- 1.3.6.1.4.1.2011.2.25.3.40.40.40.12802
    almCesRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Jitter buffer overrun alarm."
        ::= { trapsAlm 12802 }

    -- 1.3.6.1.4.1.2011.2.25.3.40.40.40.12803
    almMpDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "ML-PPP group failure."
        ::= { trapsAlm 12803 }

    -- 1.3.6.1.4.1.2011.2.25.3.40.40.40.12804
    almMpDelay NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Delay alarm."
        ::= { trapsAlm 12804 }

    -- 1.3.6.1.4.1.2011.2.25.3.40.40.40.12805
    almPppLcpFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "LCP negotiation failure."
        ::= { trapsAlm 12805 }

    -- 1.3.6.1.4.1.2011.2.25.3.40.40.40.12806
    almPppNcpFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "NCP negotiation alarm."
        ::= { trapsAlm 12806 }

    -- 1.3.6.1.4.1.2011.2.25.3.40.40.40.12807
    almFdbSizeAlmElan NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Mac fdb of elan used up."
        ::= { trapsAlm 12807 }

    -- 1.3.6.1.4.1.2011.2.25.3.40.40.40.12808
    almVpLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Lost of Continuity Check."
        ::= { trapsAlm 12808 }

    -- 1.3.6.1.4.1.2011.2.25.3.40.40.40.12809
    almVcLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Lost of Continuity Check."
        ::= { trapsAlm 12809 }

    -- 1.3.6.1.4.1.2011.2.25.3.40.40.40.12814
    almMplsTunnelLocv NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of Connectivity Verification defect."
        ::= { trapsAlm 12814 }

    -- 1.3.6.1.4.1.2011.2.25.3.40.40.40.12815
    almMplsTunnelExcess NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Receiving excess rate of CV."
        ::= { trapsAlm 12815 }

    -- 1.3.6.1.4.1.2011.2.25.3.40.40.40.12816
    almMplsTunnelMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Trail Termination Source Identifier Mismatch defect."
        ::= { trapsAlm 12816 }

    -- 1.3.6.1.4.1.2011.2.25.3.40.40.40.12817
    almMplsTunnelMismerge NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Trail Termination Source Identifier Mismerge defect."
        ::= { trapsAlm 12817 }

    -- 1.3.6.1.4.1.2011.2.25.3.40.40.40.12818
    almMplsTunnelUnknown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Unknown defect in the MPLS network."
        ::= { trapsAlm 12818 }

    -- 1.3.6.1.4.1.2011.2.25.3.40.40.40.12819
    almMplsTunnelBdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Backward Defect Indicator."
        ::= { trapsAlm 12819 }

    -- 1.3.6.1.4.1.2011.2.25.3.40.40.40.12820
    almMplsTunnelFdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Forward Defect Indicator."
        ::= { trapsAlm 12820 }

    -- 1.3.6.1.4.1.2011.2.25.3.40.40.40.12821
    almMplsTunnelSD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Signal Degrade."
        ::= { trapsAlm 12821 }

    -- 1.3.6.1.4.1.2011.2.25.3.40.40.40.12822
    almMplsTunnelSF NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Signal Fail."
        ::= { trapsAlm 12822 }

    -- 1.3.6.1.4.1.2011.2.25.3.40.40.40.12823
    almEthCfmMisMerge NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Trap of Alarm: Misconnection alarm"
        ::= { trapsAlm 12823 }

    -- 1.3.6.1.4.1.2011.2.25.3.40.40.40.12824
    almEthCfmUnexPeri NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Errored frame alarm"
        ::= { trapsAlm 12824 }

    -- 1.3.6.1.4.1.2011.2.25.3.40.40.40.12825
    almEthCfmLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of continuity"
        ::= { trapsAlm 12825 }

    -- 1.3.6.1.4.1.2011.2.25.3.40.40.40.12826
    almEthCfmRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Remote Defect Indication"
        ::= { trapsAlm 12826 }

    -- 1.3.6.1.4.1.2011.2.25.3.40.40.40.12827
    almEthEfmDf NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Discovery failure"
        ::= { trapsAlm 12827 }

    -- 1.3.6.1.4.1.2011.2.25.3.40.40.40.12828
    almEthEfmRemFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Remote failure"
        ::= { trapsAlm 12828 }

    -- 1.3.6.1.4.1.2011.2.25.3.40.40.40.12829
    almEthEfmEvent NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Remote link event"
        ::= { trapsAlm 12829 }

    -- 1.3.6.1.4.1.2011.2.25.3.40.40.40.12830
    almEthEfmLoopBack NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loopback alarm"
        ::= { trapsAlm 12830 }

    -- 1.3.6.1.4.1.2011.2.25.3.40.40.40.12831
    almEthApsTypeMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Mismatch of APS Protection Type."
        ::= { trapsAlm 12831 }

    -- 1.3.6.1.4.1.2011.2.25.3.40.40.40.12832
    almEthApsPathMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Working/Protection mismatch."
        ::= { trapsAlm 12832 }

    -- 1.3.6.1.4.1.2011.2.25.3.40.40.40.12833
    almEthApsSwitchFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Protection switching incomplete."
        ::= { trapsAlm 12833 }

    -- 1.3.6.1.4.1.2011.2.25.3.40.40.40.12834
    almEthApsLost NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: APS Frame Lost."
        ::= { trapsAlm 12834 }

    -- 1.3.6.1.4.1.2011.2.25.3.40.40.40.12836
    almLagMemberDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: LAG member unavailable"
        ::= { trapsAlm 12836 }

    -- 1.3.6.1.4.1.2011.2.25.3.40.40.40.12837
    almLagDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: LAG unavailable"
        ::= { trapsAlm 12837 }

    -- 1.3.6.1.4.1.2011.2.25.3.40.40.40.12838
    almImaGroupLeDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: IMA group Local Edge fail."
        ::= { trapsAlm 12838 }

    -- 1.3.6.1.4.1.2011.2.25.3.40.40.40.12839
    almImaGroupReDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: IMA group Remote Edge fail."
        ::= { trapsAlm 12839 }

    -- 1.3.6.1.4.1.2011.2.25.3.40.40.40.12852
    almPwDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: pw drop packets crosses the threshold."
        ::= { trapsAlm 12852 }

    -- 1.3.6.1.4.1.2011.2.25.3.40.40.40.12853
    almPwDroppktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: pw drop packets crosses the threshold."
        ::= { trapsAlm 12853 }

    -- 1.3.6.1.4.1.2011.2.25.3.40.40.40.12854
    almPwExcTraffic NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of OSC interface input optical power."
        ::= { trapsAlm 12854 }

    -- 1.3.6.1.4.1.2011.2.25.3.40.40.40.12860
    almLcsLimited NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The capacity exceeds the limitation specified by the license."
        ::= { trapsAlm 12860 }

    -- 1.3.6.1.4.1.2011.2.25.3.40.40.40.12861
    almLicenseLost NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of license file."
        ::= { trapsAlm 12861 }

    -- 1.3.6.1.4.1.2011.2.25.3.40.40.40.12862
    almXPICLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Loss of XPIC signal."
        ::= { trapsAlm 12862 }

    -- 1.3.6.1.4.1.2011.2.25.3.40.40.40.12863
    almIfCableOpen NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Open circuit of IF cable."
        ::= { trapsAlm 12863 }

    -- 1.3.6.1.4.1.2011.2.25.3.40.40.40.12864
    almIfModeUnSupported NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The IF mode is not supported."
        ::= { trapsAlm 12864 }

    -- 1.3.6.1.4.1.2011.2.25.3.40.40.40.12865
    almNp1SWIndi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: N+1 protection switching indication."
        ::= { trapsAlm 12865 }

    -- 1.3.6.1.4.1.2011.2.25.3.40.40.40.12866
    almNp1SWFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: N+1 automatic protection switching failure indication."
        ::= { trapsAlm 12866 }

    -- 1.3.6.1.4.1.2011.2.25.3.40.40.40.12867
    almNp1ManualStop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: N+1 APS protocol manually stopped."
        ::= { trapsAlm 12867 }

    -- 1.3.6.1.4.1.2011.2.25.3.40.40.40.12868
    almModTypeMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The module type that is set by the user does not match the actual module type."
        ::= { trapsAlm 12868 }

    -- 1.3.6.1.4.1.2011.2.25.3.40.40.40.12869
    almRpsIndi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Microwave protection switching alarm."
        ::= { trapsAlm 12869 }

    -- 1.3.6.1.4.1.2011.2.25.3.40.40.40.12870
    almMwBerEXC NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Microwave link excessive errors."
        ::= { trapsAlm 12870 }

    -- 1.3.6.1.4.1.2011.2.25.3.40.40.40.12871
    almMwBerSD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Microwave link signal degraded."
        ::= { trapsAlm 12871 }

    -- 1.3.6.1.4.1.2011.2.25.3.40.40.40.12872
    almPatchChgsccNotMatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Patch inconsistency after the SCC board is replaced."
        ::= { trapsAlm 12872 }

    -- 1.3.6.1.4.1.2011.2.25.3.40.40.40.12884
    almStormCurQuenumOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Alarm storm. Certain alarms on the SCC board may be lost when the alarm queue is full. This alarm indicates that the alarm module is in the alarm storm state."
        ::= { trapsAlm 12884 }

    -- 1.3.6.1.4.1.2011.2.25.3.40.40.40.12910
    almAcrLockFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: 1588ACR Lock Failure."
        ::= { trapsAlm 12910 }

    -- 1.3.6.1.4.1.2011.2.25.3.40.40.40.12923
    almEthPwrSupplyFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Circuit failure result in no power output or turnoff the power to protect the circuit."
        ::= { trapsAlm 12923 }

    -- 1.3.6.1.4.1.2011.2.25.3.40.40.40.12925
    almImae1Delay NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The transmission delay of the IMA link exceeds the threshold."
        ::= { trapsAlm 12925 }

    -- 1.3.6.1.4.1.2011.2.25.3.40.40.40.12926
    almLanLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: LAN Loss of carrier signal."
        ::= { trapsAlm 12926 }

    -- 1.3.6.1.4.1.2011.2.25.3.40.40.40.12928
    almEthAutoLinkDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Automatic link down of Ethernet port."
        ::= { trapsAlm 12928 }

    -- 1.3.6.1.4.1.2011.2.25.3.40.40.40.12963
    almTimeNoTraceMode NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Time having no source to follow."
        ::= { trapsAlm 12963 }

    -- 1.3.6.1.4.1.2011.2.25.3.40.40.40.12964
    almTimeLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Time source loss of signal."
        ::= { trapsAlm 12964 }

    -- 1.3.6.1.4.1.2011.2.25.3.40.40.40.12972
    almExtTimeLoc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The external clock source is lost."
        ::= { trapsAlm 12972 }

    -- 1.3.6.1.4.1.2011.2.25.3.40.40.40.12989
    almRadioFadingMarginInsuff NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The fading margin is insufficient."
        ::= { trapsAlm 12989 }

    -- 1.3.6.1.4.1.2011.2.25.3.40.40.40.12994
    almGspTnnlDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Tunnel Down."
        ::= { trapsAlm 12994 }

    -- 1.3.6.1.4.1.2011.2.25.3.40.40.40.12996
    almGspIsisNbAuthErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ISIS Neighbor Authentication err."
        ::= { trapsAlm 12996 }

    -- 1.3.6.1.4.1.2011.2.25.3.40.40.40.12997
    almGspRsvpNbDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: RSVP Neighbor Down."
        ::= { trapsAlm 12997 }

    -- 1.3.6.1.4.1.2011.2.25.3.40.40.40.12998
    almGspRsvpNbAuthErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: RSVP Neighbor Authentication err."
        ::= { trapsAlm 12998 }

    -- 1.3.6.1.4.1.2011.2.25.3.40.40.40.13047
    almPassWordNeedChange NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The default user's default password must be changed to reduce risks."
        ::= { trapsAlm 13047 }

    -- 1.3.6.1.4.1.2011.2.25.3.40.40.40.13048
    almErpsInProtection NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Indicates that a node on the EPRS ring is faulty."
        ::= { trapsAlm 13048 }

    -- 1.3.6.1.4.1.2011.2.25.3.40.40.40.13049
    almComExtEccFull NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Number of TCP connections between NEs running the automatically extended ECC protocol exceeding the system limit ."
        ::= { trapsAlm 13049 }

    -- 1.3.6.1.4.1.2011.2.25.3.40.40.40.13050
    almAMDownShift NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: AM modulation downshift."
        ::= { trapsAlm 13050 }

    -- 1.3.6.1.4.1.2011.2.25.3.40.40.40.13064
    almMultiRplOwner NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: More than one RPL_OWNER alarm"
        ::= { trapsAlm 13064 }

    -- 1.3.6.1.4.1.2011.2.25.3.40.40.40.13069
    almRadioRslBeyondTh NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The ODU threshold exceeds the threshold."
        ::= { trapsAlm 13069 }

    -- 1.3.6.1.4.1.2011.2.25.3.40.40.40.13075
    almAtmpwLospktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Number of lost packets over the threshold in a certain period"
        ::= { trapsAlm 13075 }

    -- 1.3.6.1.4.1.2011.2.25.3.40.40.40.13076
    almAtmpwMisorderpktExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Number of disorder packets over the threshold in a certain period"
        ::= { trapsAlm 13076 }

    -- 1.3.6.1.4.1.2011.2.25.3.40.40.40.13078
    almCespwRemoteLospkt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Remote loss packet of CES PW"
        ::= { trapsAlm 13078 }

    -- 1.3.6.1.4.1.2011.2.25.3.40.40.40.13077
    almAtmpwUnknowncellExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Number of unknown cells over the threshold in a certain period."
        ::= { trapsAlm 13077 }

    -- 1.3.6.1.4.1.2011.2.25.3.40.40.40.13080
    almCespwOppositeRai NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The opposite station has a remote alarm indication."
        ::= { trapsAlm 13080 }

    -- 1.3.6.1.4.1.2011.2.25.3.40.40.40.13081
    almCespwOppositeAcfault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The opposite station has an attachment circuit fault."
        ::= { trapsAlm 13081 }

    -- 1.3.6.1.4.1.2011.2.25.3.40.40.40.13087
    almMplsTunnelOamFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Tunnel OAM protocol negotiation failure."
        ::= { trapsAlm 13087 }

    -- 1.3.6.1.4.1.2011.2.25.3.40.40.40.13090
    almCpuBusy NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: CPU BUSY."
        ::= { trapsAlm 13090 }

    -- 1.3.6.1.4.1.2011.2.25.3.40.40.40.13091
    almMplsPwLocv NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Pw loss of connectivity verification."
        ::= { trapsAlm 13091 }

    -- 1.3.6.1.4.1.2011.2.25.3.40.40.40.13092
    almMplsPwExcess NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Excessive pw terminal source identifications (TTSIs) received."
        ::= { trapsAlm 13092 }

    -- 1.3.6.1.4.1.2011.2.25.3.40.40.40.13093
    almMplsPwMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Mismatched pw terminal source identifications (TTSIs)."
        ::= { trapsAlm 13093 }

    -- 1.3.6.1.4.1.2011.2.25.3.40.40.40.13094
    almMplsPwMismerge NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Incorrect merging of PW terminal source identifications (TTSIs)."
        ::= { trapsAlm 13094 }

    -- 1.3.6.1.4.1.2011.2.25.3.40.40.40.13095
    almMplsPwUnknown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Unknown pw defect in the MPLS network."
        ::= { trapsAlm 13095 }

    -- 1.3.6.1.4.1.2011.2.25.3.40.40.40.13096
    almMplsPwBdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Pw backward defect indication."
        ::= { trapsAlm 13096 }

    -- 1.3.6.1.4.1.2011.2.25.3.40.40.40.13097
    almMplsPwSD NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Pw signal degrade."
        ::= { trapsAlm 13097 }

    -- 1.3.6.1.4.1.2011.2.25.3.40.40.40.13098
    almMplsPwSF NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Pw signal fail."
        ::= { trapsAlm 13098 }

    -- 1.3.6.1.4.1.2011.2.25.3.40.40.40.13099
    almPwapsTypeMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Mismatch of APS Protection Types."
        ::= { trapsAlm 13099 }

    -- 1.3.6.1.4.1.2011.2.25.3.40.40.40.13100
    almPwapsPathMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Mismatch of APS working/protection paths."
        ::= { trapsAlm 13100 }

    -- 1.3.6.1.4.1.2011.2.25.3.40.40.40.13101
    almPwapsSwitchFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Protection switching failure."
        ::= { trapsAlm 13101 }

    -- 1.3.6.1.4.1.2011.2.25.3.40.40.40.13102
    almPwapsLost NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: APS frame lost."
        ::= { trapsAlm 13102 }

    -- 1.3.6.1.4.1.2011.2.25.3.40.40.40.13105
    almImaTxclkMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The transmit clock modes of an IMA group are inconsistent at both ends."
        ::= { trapsAlm 13105 }

    -- 1.3.6.1.4.1.2011.2.25.3.40.40.40.13107
    almPwNoTraffic NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "When no traffic is received, this alarm is reported."
        ::= { trapsAlm 13107 }

    -- 1.3.6.1.4.1.2011.2.25.3.40.40.40.13108
    almLagBwMM NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Bandwidth inconsistency in the LAG group."
        ::= { trapsAlm 13108 }

    -- 1.3.6.1.4.1.2011.2.25.3.40.40.40.13110
    almDcnSizeOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: DCN Size Over."
        ::= { trapsAlm 13110 }

    -- 1.3.6.1.4.1.2011.2.25.3.40.40.40.13111
    almDcnLinkOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The number of DCN OSPF neighbors excesses the  suggested threshold."
        ::= { trapsAlm 13111 }

    -- 1.3.6.1.4.1.2011.2.25.3.40.40.40.13115
    almLptCfgCloseport NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: LPT closed access port."
        ::= { trapsAlm 13115 }

    -- 1.3.6.1.4.1.2011.2.25.3.40.40.40.13122
    almLcsMisMatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm indicates that, in the protection group, the license capacity of the boards differs from each other."
        ::= { trapsAlm 13122 }

    -- 1.3.6.1.4.1.2011.2.25.3.40.40.40.13123
    almFanAging NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Fan aging."
        ::= { trapsAlm 13123 }

    -- 1.3.6.1.4.1.2011.2.25.3.40.40.40.13125
    almNtpSyncFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: NTP Synchronization Failure."
        ::= { trapsAlm 13125 }

    -- 1.3.6.1.4.1.2011.2.25.3.40.40.40.13135
    almMplsPwOamfail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Indicates a PW OAM protocol negotiation failure."
        ::= { trapsAlm 13135 }

    -- 1.3.6.1.4.1.2011.2.25.3.40.40.40.13144
    almLcsFileNotExist NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No license file."
        ::= { trapsAlm 13144 }

    -- 1.3.6.1.4.1.2011.2.25.3.40.40.40.13145
    almLcsExpired NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: License expiredLicense."
        ::= { trapsAlm 13145 }

    -- 1.3.6.1.4.1.2011.2.25.3.40.40.40.13146
    almLcsDaysOfGrace NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The license has expired and is within the keepalive period of 60 days."
        ::= { trapsAlm 13146 }

    -- 1.3.6.1.4.1.2011.2.25.3.40.40.40.13147
    almCesK1K2M NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: K1K2 Mismatch."
        ::= { trapsAlm 13147 }

    -- 1.3.6.1.4.1.2011.2.25.3.40.40.40.13148
    almCesK2M NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: K2 Mismatch."
        ::= { trapsAlm 13148 }

    -- 1.3.6.1.4.1.2011.2.25.3.40.40.40.13149
    almCesApsIndi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: APS state indication."
        ::= { trapsAlm 13149 }

    -- 1.3.6.1.4.1.2011.2.25.3.40.40.40.13154
    almOdcDoorOpen NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The cabinet door is open."
        ::= { trapsAlm 13154 }

    -- 1.3.6.1.4.1.2011.2.25.3.40.40.40.13155
    almOdcSurgeProtectionFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: A lightning-protection alarm is reported."
        ::= { trapsAlm 13155 }

    -- 1.3.6.1.4.1.2011.2.25.3.40.40.40.13156
    almOdcSmokeOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Smoke is detected in the cabinet."
        ::= { trapsAlm 13156 }

    -- 1.3.6.1.4.1.2011.2.25.3.40.40.40.13157
    almOdcWaterAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Water enters the cabinet."
        ::= { trapsAlm 13157 }

    -- 1.3.6.1.4.1.2011.2.25.3.40.40.40.13158
    almOdcLoadPwrdown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Power-down occurs in the load."
        ::= { trapsAlm 13158 }

    -- 1.3.6.1.4.1.2011.2.25.3.40.40.40.13159
    almOdcBatteryPwrDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The battery is powered down."
        ::= { trapsAlm 13159 }

    -- 1.3.6.1.4.1.2011.2.25.3.40.40.40.13160
    almOdcBatteryCurrentAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The storage battery is discharged unevenly."
        ::= { trapsAlm 13160 }

    -- 1.3.6.1.4.1.2011.2.25.3.40.40.40.13161
    almOdcFanFailed NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The fan is not installed."
        ::= { trapsAlm 13161 }

    -- 1.3.6.1.4.1.2011.2.25.3.40.40.40.13162
    almOdcTecAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The TEC does not exist."
        ::= { trapsAlm 13162 }

    -- 1.3.6.1.4.1.2011.2.25.3.40.40.40.13163
    almOdcPowerFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The power module of the board works incorrectly."
        ::= { trapsAlm 13163 }

    -- 1.3.6.1.4.1.2011.2.25.3.40.40.40.13164
    almOdcHumiAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: A humidity alarm is generated."
        ::= { trapsAlm 13164 }

    -- 1.3.6.1.4.1.2011.2.25.3.40.40.40.13165
    almOdcMdlAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: An alarm is generated on the power module."
        ::= { trapsAlm 13165 }

    -- 1.3.6.1.4.1.2011.2.25.3.40.40.40.13166
    almOdcTempAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: A temperature alarm is generated."
        ::= { trapsAlm 13166 }

    -- 1.3.6.1.4.1.2011.2.25.3.40.40.40.13169
    almSecRadiusFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Excessive failures in radius authentication."
        ::= { trapsAlm 13169 }

    -- 1.3.6.1.4.1.2011.2.25.3.40.40.40.13173
    almCesApsManualStop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: CES APS protocol manually stopped."
        ::= { trapsAlm 13173 }

    -- 1.3.6.1.4.1.2011.2.25.3.40.40.40.13182
    almMplsPwFdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: FDI packets are received, indicating a fault in the server PW."
        ::= { trapsAlm 13182 }

    -- 1.3.6.1.4.1.2011.2.25.3.40.40.40.13183
    almMwCfgMisMatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Radio link configuration failure."
        ::= { trapsAlm 13183 }

    -- 1.3.6.1.4.1.2011.2.25.3.40.40.40.13187
    almLicenseDiff NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Inconsistent license capacity."
        ::= { trapsAlm 13187 }

    -- 1.3.6.1.4.1.2011.2.25.3.40.40.40.13188
    almPtpTimeStampAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: PTP time stamp anomaly."
        ::= { trapsAlm 13188 }

    -- 1.3.6.1.4.1.2011.2.25.3.40.40.40.13194
    almPtpSourceSwitch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: PTP time source switching alarm."
        ::= { trapsAlm 13194 }

    -- 1.3.6.1.4.1.2011.2.25.3.40.40.40.13195
    almClkLockFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Clock lock failure alarm."
        ::= { trapsAlm 13195 }

    -- 1.3.6.1.4.1.2011.2.25.3.40.40.40.13196
    almTimeLockFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Time lock failure alarm."
        ::= { trapsAlm 13196 }

    -- 1.3.6.1.4.1.2011.2.25.3.40.40.40.13277
    almCesAcrLockAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Lockout anomaly of CES ACR service clock."
        ::= { trapsAlm 13277 }

    -- 1.3.6.1.4.1.2011.2.25.3.40.40.40.13281
    almEthCfmFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:ETH OAM 1AG protocol negotiating failed."
        ::= { trapsAlm 13281 }

    -- 1.3.6.1.4.1.2011.2.25.3.40.40.40.13283
    almLdpPeerDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The connection status of the LDP peer is not Operational."
        ::= { trapsAlm 13283 }

    -- 1.3.6.1.4.1.2011.2.25.3.40.40.40.13284
    almBdtempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Board temperature sensor failure."
        ::= { trapsAlm 13284 }

    -- 1.3.6.1.4.1.2011.2.25.3.40.40.40.13285
    almEnvtempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Ambient temperature sensor failure."
        ::= { trapsAlm 13285 }

    -- 1.3.6.1.4.1.2011.2.25.3.40.40.40.13286
    almOut1tempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Air outlet temperature sensor failure."
        ::= { trapsAlm 13286 }

    -- 1.3.6.1.4.1.2011.2.25.3.40.40.40.13287
    almIntempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Air inlet temperature sensor failure."
        ::= { trapsAlm 13287 }

    -- 1.3.6.1.4.1.2011.2.25.3.40.40.40.13288
    almOut2tempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of the temperature sensor of the external cycling air inlet."
        ::= { trapsAlm 13288 }

    -- 1.3.6.1.4.1.2011.2.25.3.40.40.40.13289
    almBat1tempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of the temperature sensor in battery group 1."
        ::= { trapsAlm 13289 }

    -- 1.3.6.1.4.1.2011.2.25.3.40.40.40.13290
    almEnvhumSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Ambient humidity sensor failure."
        ::= { trapsAlm 13290 }

    -- 1.3.6.1.4.1.2011.2.25.3.40.40.40.13291
    almEnvtemp1SensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of the sensor for ambient temperature 1."
        ::= { trapsAlm 13291 }

    -- 1.3.6.1.4.1.2011.2.25.3.40.40.40.13292
    almEnvtemp2SensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of the sensor for ambient temperature 2."
        ::= { trapsAlm 13292 }

    -- 1.3.6.1.4.1.2011.2.25.3.40.40.40.13293
    almBat2tempSensorFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of the temperature sensor in battery group 2."
        ::= { trapsAlm 13293 }

    -- 1.3.6.1.4.1.2011.2.25.3.40.40.40.13294
    almMwE1Lost NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is reported when the modulation scheme is downshifted or the E1 bandwidth is decreased."
        ::= { trapsAlm 13294 }

    -- 1.3.6.1.4.1.2011.2.25.3.40.40.40.13295
    almMwContWave NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is reported when continuous waves are enabled on the IF board (IF1, IFU2, IFX2, ISU2, or ISX2)."
        ::= { trapsAlm 13295 }

    -- 1.3.6.1.4.1.2011.2.25.3.40.40.40.13303
    almIsisLspOverload NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The ISIS LSP at this node is overloaded. Therefore, information that this LSP carries is incomplete."
        ::= { trapsAlm 13303 }

    -- 1.3.6.1.4.1.2011.2.25.3.40.40.40.13307
    almL3vpnTunnelDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: L3VPN-Bound Tunnel Interruption."
        ::= { trapsAlm 13307 }

    -- 1.3.6.1.4.1.2011.2.25.3.40.40.40.13374
    almPortQueueDropOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Packets dropped in port queue congestion exceeding the threshold."
        ::= { trapsAlm 13374 }

    -- 1.3.6.1.4.1.2011.2.25.3.40.40.40.13377
    almTunnelApsDegraded NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The unused tunnel in a protect group is faulty."
        ::= { trapsAlm 13377 }

    -- 1.3.6.1.4.1.2011.2.25.3.40.40.40.13382
    almPgPrtDegraded NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Downgrade of Protection Group."
        ::= { trapsAlm 13382 }

    -- 1.3.6.1.4.1.2011.2.25.3.40.40.40.13383
    almPgLinkFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Protection Group Link Failure."
        ::= { trapsAlm 13383 }

    -- 1.3.6.1.4.1.2011.2.25.3.40.40.40.13384
    almMwAmTest NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: AM Test Status."
        ::= { trapsAlm 13384 }

    -- 1.3.6.1.4.1.2011.2.25.3.40.40.40.13388
    almMplsTunnelLck NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The server layer of MPLS Tunnel locked signal."
        ::= { trapsAlm 13388 }

    -- 1.3.6.1.4.1.2011.2.25.3.40.40.40.13389
    almMplsPwLck NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm occurs when pw receives a LCK frame."
        ::= { trapsAlm 13389 }

    -- 1.3.6.1.4.1.2011.2.25.3.40.40.40.13390
    almMplsPwAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "MPLS Pw Alarm Indication Signal."
        ::= { trapsAlm 13390 }

    -- 1.3.6.1.4.1.2011.2.25.3.40.40.40.13391
    almMplsTunnelLock NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm occurs when administrator set lock at a specific tunnel."
        ::= { trapsAlm 13391 }

    -- 1.3.6.1.4.1.2011.2.25.3.40.40.40.13392
    almMplsPwLock NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm occurs when administrator set lock at a specific PW."
        ::= { trapsAlm 13392 }

    -- 1.3.6.1.4.1.2011.2.25.3.40.40.40.13393
    almMplsTunnelUnexpmeg NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "MPLS Tunnel Unexpected MEG."
        ::= { trapsAlm 13393 }

    -- 1.3.6.1.4.1.2011.2.25.3.40.40.40.13394
    almMplsTunnelUnexpmep NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "MPLS Tunnel Unexpected MEP."
        ::= { trapsAlm 13394 }

    -- 1.3.6.1.4.1.2011.2.25.3.40.40.40.13395
    almMplsTunnelUnexpper NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "MPLS Tunnel Unexpected Period."
        ::= { trapsAlm 13395 }

    -- 1.3.6.1.4.1.2011.2.25.3.40.40.40.13396
    almMplsTunnelRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "MPLS Pw Remote Defect Indication."
        ::= { trapsAlm 13396 }

    -- 1.3.6.1.4.1.2011.2.25.3.40.40.40.13397
    almMplsTunnelAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "MPLS Tunnel Alarm Indication Signal."
        ::= { trapsAlm 13397 }

    -- 1.3.6.1.4.1.2011.2.25.3.40.40.40.13398
    almMplsPwUnexpmeg NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: MPLS PW Unexpected MEG."
        ::= { trapsAlm 13398 }

    -- 1.3.6.1.4.1.2011.2.25.3.40.40.40.13399
    almMplsPwUnexpmep NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: MPLS Pw Unexpected MEPID."
        ::= { trapsAlm 13399 }

    -- 1.3.6.1.4.1.2011.2.25.3.40.40.40.13400
    almMplsPwUnexpper NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: MPLS Pw Unexpected Period."
        ::= { trapsAlm 13400 }

    -- 1.3.6.1.4.1.2011.2.25.3.40.40.40.13401
    almMPlsPwRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: MPLS Pw Remote Defect Indication."
        ::= { trapsAlm 13401 }

    -- 1.3.6.1.4.1.2011.2.25.3.40.40.40.13402
    almMplsPwCsf NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Received a CSF OAM packet, indicates the far-end client detect a faulty."
        ::= { trapsAlm 13402 }

    -- 1.3.6.1.4.1.2011.2.25.3.40.40.40.13403
    almMplsSectLocv NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Section loss of continuity."
        ::= { trapsAlm 13403 }

    -- 1.3.6.1.4.1.2011.2.25.3.40.40.40.13404
    almMplsSectOamFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: the source and sink nodes of a Section fail to negotiate on the OAM protocol."
        ::= { trapsAlm 13404 }

    -- 1.3.6.1.4.1.2011.2.25.3.40.40.40.13405
    almMplsSectUnexpmeg NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Section Unexpected MEG."
        ::= { trapsAlm 13405 }

    -- 1.3.6.1.4.1.2011.2.25.3.40.40.40.13406
    almMplsSectUnexpmep NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Section Unexpected MEP."
        ::= { trapsAlm 13406 }

    -- 1.3.6.1.4.1.2011.2.25.3.40.40.40.13407
    almMplsSectUnexpper NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Section Unexpected Period."
        ::= { trapsAlm 13407 }

    -- 1.3.6.1.4.1.2011.2.25.3.40.40.40.13408
    almMplsSectRdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Section Remote Defect Indication."
        ::= { trapsAlm 13408 }

    -- 1.3.6.1.4.1.2011.2.25.3.40.40.40.13409
    almMplsSectSd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: the Section signal is degraded."
        ::= { trapsAlm 13409 }

    -- 1.3.6.1.4.1.2011.2.25.3.40.40.40.13410
    almMplsSectSf NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: the Section signal is severely degraded."
        ::= { trapsAlm 13410 }

    -- 1.3.6.1.4.1.2011.2.25.3.40.40.40.13411
    almMplsSectLock NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Administratinve locking of section layer."
        ::= { trapsAlm 13411 }

    -- 1.3.6.1.4.1.2011.2.25.3.40.40.40.13416
    almSrvShutDownLd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Indicats the service shutdown for detecting loop on the network. With the service restarted, the alarm disappears."
        ::= { trapsAlm 13416 }

    -- 1.3.6.1.4.1.2011.2.25.3.40.40.40.13417
    almPortExcTraffic NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Indicats the traffic utilization at the Ethernet port over the threshold. When the received or transmitted traffic exceeds the expected traffic, this alarm occurs."
        ::= { trapsAlm 13417 }

    -- 1.3.6.1.4.1.2011.2.25.3.40.40.40.13418
    almDropratioOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Indicats the ratio of the packet discarded on some performance object over the threshold. When the discarded traffic exceeds the expected traffic, this alarm occurs."
        ::= { trapsAlm 13418 }

    -- 1.3.6.1.4.1.2011.2.25.3.40.40.40.13422
    almPlaCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: PLA Configuration Mismatch."
        ::= { trapsAlm 13422 }

    -- 1.3.6.1.4.1.2011.2.25.3.40.40.40.13433
    almDot1xRsNoresponse NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No Response from the RADIUS Server for 802.1X Authentication."
        ::= { trapsAlm 13433 }

    -- 1.3.6.1.4.1.2011.2.25.3.40.40.40.13440
    almDot1xUsernumOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Number of Users Authenticated by 802.1X Exceeds the Threshold."
        ::= { trapsAlm 13440 }

    -- 1.3.6.1.4.1.2011.2.25.3.40.40.40.13550
    almDot1xPrNoresponse NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No Response from the Proxy for 802.1X Authentication."
        ::= { trapsAlm 13550 }

    -- 1.3.6.1.4.1.2011.2.25.3.40.40.40.13551
    almDot1xPrUserOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Number of Concurrent Users Authenticated by 802.1X Proxy Exceeds the Threshold."
        ::= { trapsAlm 13551 }

    -- 1.3.6.1.4.1.2011.2.25.3.40.40.40.13444
    almMacExtExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Bit error threshold-crossing detected at MAC layer."
        ::= { trapsAlm 13444 }

    -- 1.3.6.1.4.1.2011.2.25.3.40.40.40.13478
    almEthCfmAis NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Received an AIS OAM packet, indicates that the ETH at service level is faulty."
        ::= { trapsAlm 13478 }

    -- 1.3.6.1.4.1.2011.2.25.3.40.40.40.13484
    almUsbProcessFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure to recover data from or back up data to a USB disk."
        ::= { trapsAlm 13484 }

    -- 1.3.6.1.4.1.2011.2.25.3.40.40.40.13485
    almNbUnReachable NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Access neighbor NE failed."
        ::= { trapsAlm 13485 }

    -- 1.3.6.1.4.1.2011.2.25.3.40.40.40.13479
    almUniptpSrcNegoFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Unicast PTP packet negotiation fails."
        ::= { trapsAlm 13479 }

    -- 1.3.6.1.4.1.2011.2.25.3.40.40.40.13480
    almUniptpSrcLoss NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The unicast PTP clock source fails."
        ::= { trapsAlm 13480 }

    -- 1.3.6.1.4.1.2011.2.25.3.40.40.40.13481
    almUniptpSrcSwitch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Switching occurs in the unicast PTP clock source."
        ::= { trapsAlm 13481 }
		
    -- 1.3.6.1.4.1.2011.2.25.3.40.40.40.13486
    almBwutilizationOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Bandwidth utilization over the threshold."
        ::= { trapsAlm 13486 }

    -- 1.3.6.1.4.1.2011.2.25.3.40.40.40.13502
    almDbmsDelete NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The NE database is deleted."
        ::= { trapsAlm 13502 }

    -- 1.3.6.1.4.1.2011.2.25.3.40.40.40.13506
    almLaserCheckErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm indicates that the current optical module has a write/read error."
        ::= { trapsAlm 13506 }

    -- 1.3.6.1.4.1.2011.2.25.3.40.40.40.13507
    almTunnelApsOutage NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Outage of APS Tunnel Protection Group."
        ::= { trapsAlm 13507 }

    -- 1.3.6.1.4.1.2011.2.25.3.40.40.40.13508
    almPwApsDegraded NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Downgrade of APS PW Protection Group."
        ::= { trapsAlm 13508 }

    -- 1.3.6.1.4.1.2011.2.25.3.40.40.40.13509
    almPwApsOutage NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Outage of APS PW Protection Group."
        ::= { trapsAlm 13509 }

    -- 1.3.6.1.4.1.2011.2.25.3.40.40.40.13513
    almNeIPConfusion NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: NEIP CONFUSION."
        ::= { trapsAlm 13513 }

    -- 1.3.6.1.4.1.2011.2.25.3.40.40.40.13514
    almSslCertNoEnc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Certificate file of SSL is not encrypted."
        ::= { trapsAlm 13514 }

    -- 1.3.6.1.4.1.2011.2.25.3.40.40.40.13533
    almNbCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The configuration are mismatch in the two neighboring NEs."
        ::= { trapsAlm 13533 }

    -- 1.3.6.1.4.1.2011.2.25.3.40.40.40.13538
    almPlaMemberDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: PLA group member faulty."
        ::= { trapsAlm 13538 }

    -- 1.3.6.1.4.1.2011.2.25.3.40.40.40.13539
    almPlaDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: PLA faulty."
        ::= { trapsAlm 13539 }

    -- 1.3.6.1.4.1.2011.2.25.3.40.40.40.13545
    almSubnetRtConflict NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Subnetwork route conflict."
        ::= { trapsAlm 13545 }

    -- 1.3.6.1.4.1.2011.2.25.3.40.40.40.13552
    almElanSmacFlapping NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Flapping of source MAC addresses of E-LAN services."
        ::= { trapsAlm 13552 }

    -- 1.3.6.1.4.1.2011.2.25.3.40.40.40.13557
    almPatchBdExclude NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Exclusion of a patch package board."
        ::= { trapsAlm 13557 }

    -- 1.3.6.1.4.1.2011.2.25.3.40.40.40.13558
    almPatchBdMatchFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Patch package matching failure."
        ::= { trapsAlm 13558 }

    -- 1.3.6.1.4.1.2011.2.25.3.40.40.40.13560
    almISISADJACENCYCHANGE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ISIS adjacency state change."
        ::= { trapsAlm 13560 }

    -- 1.3.6.1.4.1.2011.2.25.3.40.40.40.13561
    almBGPBACKTRANSITION NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The BGP connection is interrupted.."
        ::= { trapsAlm 13561 }

    -- 1.3.6.1.4.1.2011.2.25.3.40.40.40.13562
    almL3vTrapThreExceed NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Number of prefixes contained in the VPN exceeding the upper threshold."
        ::= { trapsAlm 13562 }

    -- 1.3.6.1.4.1.2011.2.25.3.40.40.40.13563
    almL3vTrapVrfDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: All VPN interfaces being down."
        ::= { trapsAlm 13563 }

    -- 1.3.6.1.4.1.2011.2.25.3.40.40.40.13564
    almVersionNotsupport NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Not supported by the current version."
        ::= { trapsAlm 13564 }

    -- 1.3.6.1.4.1.2011.2.25.3.40.40.40.13619
    almRtTblLack NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Insufficient routing table resources."
        ::= { trapsAlm 13619 }

    -- 1.3.6.1.4.1.2011.2.25.3.40.40.40.13645
    almIpfpmLossRatioExce NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: IPFPM packet loss rate exceeding the upper threshold."
        ::= { trapsAlm 13645 }

    -- 1.3.6.1.4.1.2011.2.25.3.40.40.40.13646
    almIpfpmOneDelayExce NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: One-way delay of IPFPM exceeding the upper threshold."
        ::= { trapsAlm 13646 }

    -- 1.3.6.1.4.1.2011.2.25.3.40.40.40.13647
    almIpfpmTwoDelayExce NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Two-way delay of IPFPM exceeding the upper threshold."
        ::= { trapsAlm 13647 }

    -- 1.3.6.1.4.1.2011.2.25.3.40.40.40.13663
    almOspfNbrStateChange NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: OSPF Neighbor Status Changes."
        ::= { trapsAlm 13663 }

    -- 1.3.6.1.4.1.2011.2.25.3.40.40.40.13668
    almIpfpmInstTlpErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is generated when an instance fails to add TLP because of insufficient ACL resources."
        ::= { trapsAlm 13668 }

    -- 1.3.6.1.4.1.2011.2.25.3.40.40.40.13669
    almPlaMemberDownExt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: A member in a PLA group is unavailable."
        ::= { trapsAlm 13669 }

    -- 1.3.6.1.4.1.2011.2.25.3.40.40.40.13673
    almSwdlBdMatchFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The SWDL_BD_MATCH_FAIL is an alarm indicating that a board fails to match the board software."
        ::= { trapsAlm 13673 }

    -- 1.3.6.1.4.1.2011.2.25.3.40.40.40.13689
    almArpFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ARP learning failure."
        ::= { trapsAlm 13689 }

    -- 1.3.6.1.4.1.2011.2.25.3.40.40.40.13692
    almRfusdDelayUnequal NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: RFUSD Failed to Provide Main or Diversity Signals with Required Delay Compensation."
        ::= { trapsAlm 13692 }

    -- 1.3.6.1.4.1.2011.2.25.3.40.40.40.13700
    almMplsLdpSessionDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: LDP Session Down."
        ::= { trapsAlm 13700 }

    -- 1.3.6.1.4.1.2011.2.25.3.40.40.40.13701
    almMplsLspTblLack NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The resources of the MPLS LSP table are insufficient."
        ::= { trapsAlm 13701 }

    -- 1.3.6.1.4.1.2011.2.25.3.40.40.40.13704
    almQueueResLack NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The queue lacks resources on the board where the LAG resides."
        ::= { trapsAlm 13704 }

    -- 1.3.6.1.4.1.2011.2.25.3.40.40.40.13705
    almCompressMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The device receives an unrecognized header compression hash conflict ID."
        ::= { trapsAlm 13705 }

    -- 1.3.6.1.4.1.2011.2.25.3.40.40.40.13719
    almLcsTrialPeriod NOTIFICATION-TYPE
        OBJECTS{ rptEvtNumber, rptAlmName, rptEvtNtfcnCde, rptEvtState, rptEvtStartTime, rptEvtEndTime, rptEvtSrvEff, rptEvtObjType, rptEvtPara }
        STATUS current
        DESCRIPTION
            "The current NE is within the license trial period that lasts for 90 days."
        ::= { trapsAlm 13719 }

    -- 1.3.6.1.4.1.2011.2.25.3.40.40.40.13734
    almAesMacErr NOTIFICATION-TYPE
        OBJECTS{ rptEvtNumber, rptAlmName, rptEvtNtfcnCde, rptEvtState, rptEvtStartTime, rptEvtEndTime, rptEvtSrvEff, rptEvtObjType, rptEvtPara }
        STATUS current
        DESCRIPTION
            "AES message authentication code error."
        ::= { trapsAlm 13734 }

    -- 1.3.6.1.4.1.2011.2.25.3.40.40.40.13736
    almReflectorIpCnflct NOTIFICATION-TYPE
        OBJECTS{ rptEvtNumber, rptAlmName, rptEvtNtfcnCde, rptEvtState, rptEvtStartTime, rptEvtEndTime, rptEvtSrvEff, rptEvtObjType, rptEvtPara }
        STATUS current
        DESCRIPTION
            "The simulated IP address of the reflector is the same as the IP address of another node in the network."
        ::= { trapsAlm 13736 }

    -- 1.3.6.1.4.1.2011.2.25.3.40.40.40.13744
    almPwdEncryptRisk NOTIFICATION-TYPE
        OBJECTS{ rptEvtNumber, rptAlmName, rptEvtNtfcnCde, rptEvtState, rptEvtStartTime, rptEvtEndTime, rptEvtSrvEff, rptEvtObjType, rptEvtPara }
        STATUS current
        DESCRIPTION
            "This alarm is generated if the user password encryption mode is MD5 or SHA256 when a user logs in, changes the password, or adds another user."
        ::= { trapsAlm 13744 }

    -- 1.3.6.1.4.1.2011.2.25.3.40.40.40.13745
    almUsbFileUnsec NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The NE on which the USB flash drive is installed is insecure."
        ::= { trapsAlm 13745 }

    -- 1.3.6.1.4.1.2011.2.25.3.40.40.40.13746
    almProPktFlooding NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Rates of protocol packets received by a device exceed the upper rate threshold for 30 consecutive seconds."
        ::= { trapsAlm 13746 }

    -- 1.3.6.1.4.1.2011.2.25.3.40.40.40.13759
    almSslCertDamaged NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: User-defined SSL certificate file damaged."
        ::= { trapsAlm 13759 }

    -- 1.3.6.1.4.1.2011.2.25.3.40.40.40.13762
    almArpSpoof NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ARP spoof."
        ::= { trapsAlm 13762 }

    -- 1.3.6.1.4.1.2011.2.25.3.40.40.40.13774
    almProStatAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Abnormal Protocal Status."
        ::= { trapsAlm 13774 }

    -- 1.3.6.1.4.1.2011.2.25.3.40.40.40.13775
    almIgspEntriesExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Threshold-crossing for IGMP snooping multicast entries."
        ::= { trapsAlm 13775 }

    -- 1.3.6.1.4.1.2011.2.25.3.40.40.40.13779
    almSslCertToExpire NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "This alarm is generated when the SSL certificate file is going to expire two months later."
        ::= { trapsAlm 13779 }

    -- 1.3.6.1.4.1.2011.2.25.3.40.40.40.13810
    almPortBerSd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Port signal degraded"
        ::= { trapsAlm 13810 }

    -- 1.3.6.1.4.1.2011.2.25.3.40.40.40.13891
    almServOverFwdCapa NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is generated when the total service packet traffic exceeds the hardware forwarding capability."
        ::= { trapsAlm 13891 }

    -- 1.3.6.1.4.1.2011.2.25.3.40.40.40.13895
    almNvVportDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm indicates a connection error between an AP UNI port and a master virtual port and as a result the services on the master virtual port are interrupted."
        ::= { trapsAlm 13895 }

    -- 1.3.6.1.4.1.2011.2.25.3.40.40.40.13907
    almFlowExcLcs NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The transmitted traffic exceeds the limitation specified by the license."
        ::= { trapsAlm 13907 }

    -- 1.3.6.1.4.1.2011.2.25.3.40.40.40.13916
    almMwFecExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Microwave FEC BER exceeding the threshold."
        ::= { trapsAlm 13916 }

    -- 1.3.6.1.4.1.2011.2.25.3.40.40.40.13930
    almPlaPktErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Error occurs when a PLA group generates packets"
        ::= { trapsAlm 13930 }

    -- 1.3.6.1.4.1.2011.2.25.3.40.40.40.13933
    almBrdcastRatioOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is generated if the ratio of broadcast and multicast packets to all packets exceeds the threshold."
        ::= { trapsAlm 13933 }

    -- 1.3.6.1.4.1.2011.2.25.3.40.40.40.13937
    almMimoLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is generated if the loss of MIMO signal."
        ::= { trapsAlm 13937 }

    -- 1.3.6.1.4.1.2011.2.25.3.40.40.40.13938
    almMimoLineMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is generated if the connection error of MIMO line."
        ::= { trapsAlm 13938 }

    -- 1.3.6.1.4.1.2011.2.25.3.40.40.40.13948
    almSoftwareUncommit NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Decoupling the board software is not authorized. Obtain the authorization first."
        ::= { trapsAlm 13948 }

    -- 1.3.6.1.4.1.2011.2.25.3.40.40.40.13960
    almKmcKeySyncFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: the KMC key fails to be in sync with APPs."
        ::= { trapsAlm 13960 }

    -- 1.3.6.1.4.1.2011.2.25.3.40.40.40.63509
    almLaserShut NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Board laser shutdown"
        ::= { trapsAlm 63509 }

    -- 1.3.6.1.4.1.2011.2.25.3.40.40.40.63537
    almHardNonSupport NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is reported when the hardware does not support the configuration delivered by the SCC board."
        ::= { trapsAlm 63537 }

    -- 1.3.6.1.4.1.2011.2.25.3.40.40.40.63538
    almVcatLoa NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The VCAT_LOA is an alarm indicating that the delay of the virtual concatenation is over long. This alarm occurs when the delay time of the timeslots bound to a VC trunk exceeds the time allowed by the virtual concatenation delay. The time allowed by the virtual concatenation delay depends on different board types."
        ::= { trapsAlm 63538 }

    -- 1.3.6.1.4.1.2011.2.25.3.40.40.40.63554
    almAlmLFA NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The LFA is an alarm indicating the loss of E1 basic frame alignment. This alarm indicates that the E1 double frame is failed in basic frame delimitation and that the delimitation synchronous status is lost."
        ::= { trapsAlm 63554 }

    -- 1.3.6.1.4.1.2011.2.25.3.40.40.40.63555
    almDdnLfa NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The DDN_LFA is an alarm indicating the loss of frame alignment in the PDH framed E1 services on the electrical interface side. When the electrical interface side fails to receive the frame alignment signals in the framed E1 services, the DDN_LFA alarm is reported."
        ::= { trapsAlm 63555 }

    -- 1.3.6.1.4.1.2011.2.25.3.40.40.40.63558
    almAlmLMFA NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The LMFA is an alarm indicating the loss of E1 multiframe alignment. This alarm indicates that the E1 CRC-4 frame is failed in multiframe delimitation and that the delimitation synchronous status is lost."
        ::= { trapsAlm 63558 }

    -- 1.3.6.1.4.1.2011.2.25.3.40.40.40.63563
    almAlmRMFA NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "The RMFA is an alarm that the framing E1/T1 multiframe notification event occurs. If the framing E1/T1 signals occur in consecutive Z (Z is from two through five) CAS multiframe cycles, the RMFA alarm is reported when all the CAS multiframe mutual-notification bits of the input signals are set to 1."
        ::= { trapsAlm 63563 }

    -- 1.3.6.1.4.1.2011.2.25.3.40.40.40.63575
    almFcsErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The FCS_ERR is an alarm indicating the FCS check error. When there is an error in the frame check sequence (FCS) check performed for the GFP frames received, this alarm occurs."
        ::= { trapsAlm 63575 }

    -- 1.3.6.1.4.1.2011.2.25.3.40.40.40.63577
    almB3ExcVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: B3 bit errors in the lower order path VC-3 crosses the threshold of B3_EXC."
        ::= { trapsAlm 63577 }

    -- 1.3.6.1.4.1.2011.2.25.3.40.40.40.63579
    almB3SdVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: B3 bit errors in the lower order path VC-3 crosses the threshold of B3_SD."
        ::= { trapsAlm 63579 }

    -- 1.3.6.1.4.1.2011.2.25.3.40.40.40.63584
    almVcatlomVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The VCAT_LOM_VC12 is an alarm indicating the loss of the virtual concatenation multiframe in the VC-12 path. This alarm occurs when the system detects that the multiframe indicator (MFI) field in the K4 byte of the VC-12 timeslot is illegal."
        ::= { trapsAlm 63584 }

    -- 1.3.6.1.4.1.2011.2.25.3.40.40.40.63585
    almVcatLomVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The VCAT_LOM_VC3 is an alarm indicating the loss of the virtual concatenation multiframe in the VC-3 path. This alarm occurs when the system detects that the multiframe indicator (MFI) field in the H4 byte of the VC-3 timeslot is illegal."
        ::= { trapsAlm 63585 }

    -- 1.3.6.1.4.1.2011.2.25.3.40.40.40.63587
    almVCATSQMVC12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The VCAT_SQM_VC12 is an alarm indicating the sequence mismatch of the virtual concatenation in the VC-12 path. This alarm occurs when the serial numbers of members in the virtual concatenation at the VC-12 level mismatch."
        ::= { trapsAlm 63587 }

    -- 1.3.6.1.4.1.2011.2.25.3.40.40.40.63588
    almVCATSQMVC3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The VCAT_SQM_VC3 is an alarm indicating the sequence mismatch of the virtual concatenation in the VC-3 path. This alarm occurs when the serial numbers of members in the virtual concatenation at the VC-3 level mismatch."
        ::= { trapsAlm 63588 }

    -- 1.3.6.1.4.1.2011.2.25.3.40.40.40.63590
    almLpRdiVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_RDI_VC12 is a remote defect indication alarm in the lower order path. If a board has detected that bit 8 of the V5 byte in the VC-12 lower order path is 1, the LP_RDI_VC12 alarm is reported."
        ::= { trapsAlm 63590 }

    -- 1.3.6.1.4.1.2011.2.25.3.40.40.40.63591
    almLpRdiVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_RDI_VC3 is a remote defect indication alarm in the lower order path. If a board has detected that bit 5 of the G1 byte in the VC-3 lower order path is 1, the LP_RDI_VC3 alarm is reported."
        ::= { trapsAlm 63591 }

    -- 1.3.6.1.4.1.2011.2.25.3.40.40.40.63592
    almLpReiVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_REI_VC12 is a remote error indication alarm in the lower order path. If a board has detected that bit 3 of the V5 byte is 1, the LP_REI_VC12 alarm is reported."
        ::= { trapsAlm 63592 }

    -- 1.3.6.1.4.1.2011.2.25.3.40.40.40.63593
    almLpReiVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_REI_VC3 is a remote error indication alarm in the lower order path. If a board has detected a 1 in any of (bit1,bit2,bit3,bit4) of the G1 byte, the LP_REI_VC3 alarm is reported."
        ::= { trapsAlm 63593 }

    -- 1.3.6.1.4.1.2011.2.25.3.40.40.40.63594
    almLpSlmVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_SLM_VC12 is a signal label mismatch alarm in the VC-12 lower order path. If a board has detected that the signal label mismatch event occurs in the V5 byte, the LP_SLM_VC12 alarm is reported."
        ::= { trapsAlm 63594 }

    -- 1.3.6.1.4.1.2011.2.25.3.40.40.40.63595
    almLpSlmVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_SLM_VC3 is a signal label mismatch alarm in the VC-3 lower order path. If a board has detected that the signal label mismatch event occurs in the C2 byte, the LP_SLM_VC3 alarm is reported."
        ::= { trapsAlm 63595 }

    -- 1.3.6.1.4.1.2011.2.25.3.40.40.40.63596
    almLpTimVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_TIM_VC12 is a trace identifier mismatch alarm in the VC-12 lower order path. If a board has detected that the J2 byte does not match, the LP_TIM_VC12 alarm is reported."
        ::= { trapsAlm 63596 }

    -- 1.3.6.1.4.1.2011.2.25.3.40.40.40.63597
    almLpTimVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_TIM_VC3 is a trace identifier mismatch alarm in the VC-3 lower order path. If a board has detected that the J1 byte does not match, the LP_TIM_VC3 alarm is reported."
        ::= { trapsAlm 63597 }

    -- 1.3.6.1.4.1.2011.2.25.3.40.40.40.63598
    almLpUneqVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_UNEQ_VC12 is an alarm indicating no payload is equipped in the lower order path. If a board has detected that the signal label in the V5 byte is 0, the LP_UNEQ_VC12 alarm is reported."
        ::= { trapsAlm 63598 }

    -- 1.3.6.1.4.1.2011.2.25.3.40.40.40.63599
    almLpUneqVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LP_UNEQ_VC3 is an alarm indicating no payload is equipped in the lower order path. If a board has detected that the signal label in the C2 byte is 0, the LP_UNEQ_VC3 alarm is reported."
        ::= { trapsAlm 63599 }

    -- 1.3.6.1.4.1.2011.2.25.3.40.40.40.63600
    almTuAisVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The TU_AIS_VC12 is a TU alarm indication signal in the VC-12 lower order path. TU alarm indication is the VC-12 path AIS. If a board has detected that the TU path is all '1's, the TU_AIS_VC12 alarm is reported."
        ::= { trapsAlm 63600 }

    -- 1.3.6.1.4.1.2011.2.25.3.40.40.40.63601
    almTuAisVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The TU_AIS_VC3 is a TU alarm indication signal in the VC-3 lower order path. TU alarm indication is the VC-3 path AIS. If a board has detected that the TU path is all '1's, the TU_AIS_VC3 alarm is reported."
        ::= { trapsAlm 63601 }

    -- 1.3.6.1.4.1.2011.2.25.3.40.40.40.63602
    almTuLopVc12 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The TU_LOP_VC12 is an alarm indicating the loss of TU pointer in the VC-12 lower order path. If a board has detected that the TU-PTR value is an invalid pointer or NDF reversion in eight consecutive frames, the TU_LOP_VC12 alarm is reported."
        ::= { trapsAlm 63602 }

    -- 1.3.6.1.4.1.2011.2.25.3.40.40.40.63603
    almTuLopVc3 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The TU_LOP_VC3 is an alarm indicating the loss of TU pointer in the VC-3 lower order path. If a board has detected that the TU-PTR value is an invalid pointer or NDF reversion in eight consecutive frames, the TU_LOP_VC3 alarm is reported."
        ::= { trapsAlm 63603 }

    -- 1.3.6.1.4.1.2011.2.25.3.40.40.40.63614
    almAlmImaLif NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ALM_IMA_LIF."
        ::= { trapsAlm 63614 }

    -- 1.3.6.1.4.1.2011.2.25.3.40.40.40.63615
    almAlmImaLods NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ALM_IMA_LODS."
        ::= { trapsAlm 63615 }

    -- 1.3.6.1.4.1.2011.2.25.3.40.40.40.63616
    almAlmImaRfi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ALM_IMA_RFI."
        ::= { trapsAlm 63616 }

    -- 1.3.6.1.4.1.2011.2.25.3.40.40.40.63617
    almAlmImaReTxUnusable NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ALM_IMA_RE_TX_UNUSABLE."
        ::= { trapsAlm 63617 }

    -- 1.3.6.1.4.1.2011.2.25.3.40.40.40.63618
    almAlmImaReRxUnusable NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: ALM_IMA_RE_RX_UNUSABLE."
        ::= { trapsAlm 63618 }

    -- 1.3.6.1.4.1.2011.2.25.3.40.40.40.63622
    almAlmE1Rai NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: E1 Remote Alam Indicator."
        ::= { trapsAlm 63622 }

    -- 1.3.6.1.4.1.2011.2.25.3.40.40.40.63629
    almPortModuleOffline NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: No optical or electrical module is in position when the port is enabled."
        ::= { trapsAlm 63629 }

    -- 1.3.6.1.4.1.2011.2.25.3.40.40.40.63635
    almThunderAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Thunder protection circuit failure alarm. The alarm occurs when the board detects a lightning circuit failure."
        ::= { trapsAlm 63635 }

    -- 1.3.6.1.4.1.2011.2.25.3.40.40.40.63638
    almGfpDlfd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The ALM_GFP_dLFD is an alarm indicating GFP loss of frame delineation. When GFP frames are detected out of synchronization, this alarm occurs."
        ::= { trapsAlm 63638 }

    -- 1.3.6.1.4.1.2011.2.25.3.40.40.40.63639
    almGfpDcsf NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The ALM_GFP_dCSF is an alarm indicating GFP loss of client signal. When the source end cannot receive the client signal, it sends the management frame to the sink end. When the sink end receives the management frame, this alarm occurs."
        ::= { trapsAlm 63639 }

    -- 1.3.6.1.4.1.2011.2.25.3.40.40.40.63644
    almLaserModErrEx NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Laser Mode Error."
        ::= { trapsAlm 63644 }

    -- 1.3.6.1.4.1.2011.2.25.3.40.40.40.63646
    almLcasFop NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Failure of LCAS protocol."
        ::= { trapsAlm 63646 }

    -- 1.3.6.1.4.1.2011.2.25.3.40.40.40.63647
    almLcasPlct NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LCAS_PLCT is an alarm indicating partial loss of capacity in the LCAS transmit direction. When the LCAS function of the VCTRUNK is enabled, in the transmit direction, the number of paths that carry load is less than the number of paths configured and is not zero."
        ::= { trapsAlm 63647 }

    -- 1.3.6.1.4.1.2011.2.25.3.40.40.40.63648
    almLcasTlct NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LCAS_TLCT is an alarm indicating total loss of capacity in the LCAS transmit direction. When the LCAS function of the VCTRUNK is enabled, in the transmit direction, the number of paths that carry load is zero, whereas the number of paths configured is not zero."
        ::= { trapsAlm 63648 }

    -- 1.3.6.1.4.1.2011.2.25.3.40.40.40.63649
    almLcasPlcr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LCAS_PLCR is an alarm indicating partial loss of capacity in the LCAS receive direction. When the LCAS function of the VCTRUNK is enabled, in the receive direction, the number of paths that carry load is less than the number of paths configured and is not zero."
        ::= { trapsAlm 63649 }

    -- 1.3.6.1.4.1.2011.2.25.3.40.40.40.63650
    almLcasTlcr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LCAS_TLCR is an alarm indicating the total loss of capacity in the LCAS receive direction. When the LCAS function of the VCTRUNK is enabled, in the receive direction, the number of paths that carry load is zero, whereas the number of paths configured is not zero."
        ::= { trapsAlm 63650 }

    -- 1.3.6.1.4.1.2011.2.25.3.40.40.40.63651
    almLcasFopt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LCAS_FOPT is an alarm indicating the failure of the LCAS protocol in the transmit direction. When the source end of the LCAS module detects abnormalities, the LCAS negotiation is unavailable or incorrect and this alarm occurs."
        ::= { trapsAlm 63651 }

    -- 1.3.6.1.4.1.2011.2.25.3.40.40.40.63652
    almLcasFopr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The LCAS_FOPR is an alarm indicating the failure of the LCAS protocol in the receive direction. When the sink end of the LCAS module detects abnormalities, the LCAS negotiation is unavailable or incorrect and this alarm occurs."
        ::= { trapsAlm 63652 }

    -- 1.3.6.1.4.1.2011.2.25.3.40.40.40.63656
    almLptIneffect NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: LPT function failure."
        ::= { trapsAlm 63656 }

    -- 1.3.6.1.4.1.2011.2.25.3.40.40.40.12295
    almDownT1Ais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: 1.5M down signal alarm indication."
        ::= { trapsAlm 12295 }

    -- 1.3.6.1.4.1.2011.2.25.3.40.40.40.130
    almUpT1Ais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: 1.5M up signal alarm indication."
        ::= { trapsAlm 130 }

    -- 1.3.6.1.4.1.2011.2.25.3.40.40.40.60
    almLsrCoolAlm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Cooling current of the laser over threshold"
        ::= { trapsAlm 60 }

    -- 1.3.6.1.4.1.2011.2.25.3.40.40.40.63
    almOutPwrHigh NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Output optical power too high"
        ::= { trapsAlm 63 }

    -- 1.3.6.1.4.1.2011.2.25.3.40.40.40.120
    almPs NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Protection switch indication"
        ::= { trapsAlm 120 }

    -- 1.3.6.1.4.1.2011.2.25.3.40.40.40.147
    almCfgVerify NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:configuration not verify"
        ::= { trapsAlm 147 }

    -- 1.3.6.1.4.1.2011.2.25.3.40.40.40.65528
    almNeDCNMode NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The device is working under DCN mode."
        ::= { trapsAlm 65528 }

    -- 1.3.6.1.4.1.2011.2.25.3.40.40.40.63578
    almB3ExcVc4 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:B3 bit errors in the VC-4 path crosses the threshold"
        ::= { trapsAlm 63578 }

    -- 1.3.6.1.4.1.2011.2.25.3.40.40.40.63580
    almB3SdVc4 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:B3 bit errors in the VC-4 path crosses the threshold"
        ::= { trapsAlm 63580 }

    -- 1.3.6.1.4.1.2011.2.25.3.40.40.40.63586
    almVcatLomVc4 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:VCAT_LOM_VC4"
        ::= { trapsAlm 63586 }

    -- 1.3.6.1.4.1.2011.2.25.3.40.40.40.63589
    almVcatSqmVc4 NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:VCAT_SQM_VC4"
        ::= { trapsAlm 63589 }

    -- 1.3.6.1.4.1.2011.2.25.3.40.40.40.63640
    almAlmGfpdssf NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:GFP Loss of Client Character Synchronization"
        ::= { trapsAlm 63640 }

    -- 1.3.6.1.4.1.2011.2.25.3.40.40.40.260
    almAuCmm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:pointer concatenation mismatch"
        ::= { trapsAlm 260 }

    -- 1.3.6.1.4.1.2011.2.25.3.40.40.40.262
    almWOffline NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Offline of wrench"
        ::= { trapsAlm 262 }

    -- 1.3.6.1.4.1.2011.2.25.3.40.40.40.335
    almBeffecExc NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Bit errors over threshold before FEC"
        ::= { trapsAlm 335 }

    -- 1.3.6.1.4.1.2011.2.25.3.40.40.40.351
    almBdVerNmat NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:BD_VER_NOT_MATCH"
        ::= { trapsAlm 351 }

    -- 1.3.6.1.4.1.2011.2.25.3.40.40.40.366
    almC2Vcais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:C2 byte alarm indication"
        ::= { trapsAlm 366 }

    -- 1.3.6.1.4.1.2011.2.25.3.40.40.40.368
    almC2Pdi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:C2 byte defect indication"
        ::= { trapsAlm 368 }

    -- 1.3.6.1.4.1.2011.2.25.3.40.40.40.374
    almTestStatus NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:TEST_STATUS"
        ::= { trapsAlm 374 }

    -- 1.3.6.1.4.1.2011.2.25.3.40.40.40.390
    almSyncLockoff NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Timing Source in Priority List has been Locked"
        ::= { trapsAlm 390 }

    -- 1.3.6.1.4.1.2011.2.25.3.40.40.40.597
    almChipAbn NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:temperature chip failure"
        ::= { trapsAlm 597 }

    -- 1.3.6.1.4.1.2011.2.25.3.40.40.40.606
    almLaserModuleMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Laser module is mismatch"
        ::= { trapsAlm 606 }

    -- 1.3.6.1.4.1.2011.2.25.3.40.40.40.644
    almWsLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:wayside interface los of signal"
        ::= { trapsAlm 644 }

    -- 1.3.6.1.4.1.2011.2.25.3.40.40.40.12581
    almNoElabel NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:No e-label"
        ::= { trapsAlm 12581 }

    -- 1.3.6.1.4.1.2011.2.25.3.40.40.40.12590
    almXcpIndi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:XCS protection switching indication"
        ::= { trapsAlm 12590 }

    -- 1.3.6.1.4.1.2011.2.25.3.40.40.40.12643
    almPrbsLss NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Loss of PRBS(Pseudo-Random Binary Sequence) signal"
        ::= { trapsAlm 12643 }

    -- 1.3.6.1.4.1.2011.2.25.3.40.40.40.12974
    almProtConnErr NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Misconnected to IFH2"
        ::= { trapsAlm 12974 }

    -- 1.3.6.1.4.1.2011.2.25.3.40.40.40.12918
    almElpsCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The Ethernet linear protection switching (ELPS) configuration at both ends mismatches."
        ::= { trapsAlm 12918 }

    -- 1.3.6.1.4.1.2011.2.25.3.40.40.40.13006
    almE1Ais NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:AIS of E1 frame"
        ::= { trapsAlm 13006 }

    -- 1.3.6.1.4.1.2011.2.25.3.40.40.40.13007
    almE1Lof NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Loss of E1 frame"
        ::= { trapsAlm 13007 }

    -- 1.3.6.1.4.1.2011.2.25.3.40.40.40.13008
    almArpMacMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The mac of static arp is mismatched."
        ::= { trapsAlm 13008 }

    -- 1.3.6.1.4.1.2011.2.25.3.40.40.40.13103
    almMcapsApsidMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:MCAPS APSID MisMatch"
        ::= { trapsAlm 13103 }

    -- 1.3.6.1.4.1.2011.2.25.3.40.40.40.13104
    almMcapsDnipwMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:MCAPS DNI PW MisMatch"
        ::= { trapsAlm 13104 }

    -- 1.3.6.1.4.1.2011.2.25.3.40.40.40.13112
    almMemOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:MEM_OVER"
        ::= { trapsAlm 13112 }

    -- 1.3.6.1.4.1.2011.2.25.3.40.40.40.13113
    almMcspPathLocv NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Loss of Connectivity Verification defect"
        ::= { trapsAlm 13113 }

    -- 1.3.6.1.4.1.2011.2.25.3.40.40.40.13114
    almMclagCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Configuration of MC-LAG Mismatch"
        ::= { trapsAlm 13114 }

    -- 1.3.6.1.4.1.2011.2.25.3.40.40.40.13150
    almCesApsFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:APS protection switching failure"
        ::= { trapsAlm 13150 }

    -- 1.3.6.1.4.1.2011.2.25.3.40.40.40.13152
    almCesLpsUniBiM NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:alarm of mismatch in unidirectional operation and bidirectional operation in msp_linear"
        ::= { trapsAlm 13152 }

    -- 1.3.6.1.4.1.2011.2.25.3.40.40.40.13375
    almPortcarRedpktOver NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Packets marked red in port exceeding the threshold"
        ::= { trapsAlm 13375 }

    -- 1.3.6.1.4.1.2011.2.25.3.40.40.40.13419
    almBdLedtest NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Board LED Flash Test"
        ::= { trapsAlm 13419 }

    -- 1.3.6.1.4.1.2011.2.25.3.40.40.40.13445
    almMringOamLocvW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring loss of connectivity verification"
        ::= { trapsAlm 13445 }

    -- 1.3.6.1.4.1.2011.2.25.3.40.40.40.13451
    almMringOamSdW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring signal degrade"
        ::= { trapsAlm 13451 }

    -- 1.3.6.1.4.1.2011.2.25.3.40.40.40.13452
    almMringOamSfW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring signal fail"
        ::= { trapsAlm 13452 }

    -- 1.3.6.1.4.1.2011.2.25.3.40.40.40.13453
    almMringOamUnexpmegW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring Unexpected MEG"
        ::= { trapsAlm 13453 }

    -- 1.3.6.1.4.1.2011.2.25.3.40.40.40.13454
    almMringOamUnexpmepW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring Unexpected MEP"
        ::= { trapsAlm 13454 }

    -- 1.3.6.1.4.1.2011.2.25.3.40.40.40.13455
    almMringOamUnexpperW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring Unexpected Period"
        ::= { trapsAlm 13455 }

    -- 1.3.6.1.4.1.2011.2.25.3.40.40.40.13456
    almMringOamRdiW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring Remote Defect Indication"
        ::= { trapsAlm 13456 }

    -- 1.3.6.1.4.1.2011.2.25.3.40.40.40.13457
    almMringApsLostW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:West of MPLS Ring APS packet lost"
        ::= { trapsAlm 13457 }

    -- 1.3.6.1.4.1.2011.2.25.3.40.40.40.13458
    almMringApsMismatchW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Far-end west of MPLS Ring APS Error"
        ::= { trapsAlm 13458 }

    -- 1.3.6.1.4.1.2011.2.25.3.40.40.40.13460
    almMringFarSwFailW NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Far-end west of MPLS Ring APS Switch Failure"
        ::= { trapsAlm 13460 }

    -- 1.3.6.1.4.1.2011.2.25.3.40.40.40.13461
    almMringOamLocvE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring loss of connectivity verification"
        ::= { trapsAlm 13461 }

    -- 1.3.6.1.4.1.2011.2.25.3.40.40.40.13467
    almMringOamSdE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring signal degrade"
        ::= { trapsAlm 13467 }

    -- 1.3.6.1.4.1.2011.2.25.3.40.40.40.13468
    almMringOamSfE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring signal fail"
        ::= { trapsAlm 13468 }

    -- 1.3.6.1.4.1.2011.2.25.3.40.40.40.13469
    almMringOamUnexpmegE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring Unexpected MEG"
        ::= { trapsAlm 13469 }

    -- 1.3.6.1.4.1.2011.2.25.3.40.40.40.13470
    almMringOamUnexpmepE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring Unexpected MEP"
        ::= { trapsAlm 13470 }

    -- 1.3.6.1.4.1.2011.2.25.3.40.40.40.13471
    almMringOamUnexpperE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring Unexpected Period"
        ::= { trapsAlm 13471 }

    -- 1.3.6.1.4.1.2011.2.25.3.40.40.40.13472
    almMringOamRdiE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring Remote Defect Indication"
        ::= { trapsAlm 13472 }

    -- 1.3.6.1.4.1.2011.2.25.3.40.40.40.13473
    almMringApsLostE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:East of MPLS Ring APS packet lost"
        ::= { trapsAlm 13473 }

    -- 1.3.6.1.4.1.2011.2.25.3.40.40.40.13474
    almMringApsMismatchE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Far-end east of MPLS Ring APS Error"
        ::= { trapsAlm 13474 }

    -- 1.3.6.1.4.1.2011.2.25.3.40.40.40.13476
    almMringFarSwFailE NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Far-end east of MPLS Ring APS Switch Failure"
        ::= { trapsAlm 13476 }

    -- 1.3.6.1.4.1.2011.2.25.3.40.40.40.13655
    almEthtrunkMemberDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:EHT-TRUNK member unavailable"
        ::= { trapsAlm 13655 }

    -- 1.3.6.1.4.1.2011.2.25.3.40.40.40.13656
    almEthtrunkDown NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:ETH-TRUNK unavailable"
        ::= { trapsAlm 13656 }

    -- 1.3.6.1.4.1.2011.2.25.3.40.40.40.13949
    almFldCfgCloseport NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:IF port data services disabled by FLD"
        ::= { trapsAlm 13949 }

    -- 1.3.6.1.4.1.2011.2.25.3.40.40.40.13951
    almLaserTypeMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Optical module type mismatch"
        ::= { trapsAlm 13951 }

    -- 1.3.6.1.4.1.2011.2.25.3.40.40.40.13983
    almInsuffcntMemSpace NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The space of the memory file system is insufficient."
        ::= { trapsAlm 13983 }

    -- 1.3.6.1.4.1.2011.2.25.3.40.40.40.13984
    almInsuffcntFlshSpace NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The space of the flash file system is insufficient."
        ::= { trapsAlm 13984 }

    -- 1.3.6.1.4.1.2011.2.25.3.40.40.40.13985	
    almStorageFail NOTIFICATION-TYPE
	OBJECTS{ rptEvtNumber,rptAlmName,rptEvtNtfcnCde,rptEvtState,rptEvtStartTime,rptEvtEndTime,rptEvtSrvEff,rptEvtObjType,rptEvtPara }
        STATUS current
        DESCRIPTION
            "Trap of Alarm:There is an error in the storage."
        ::= { trapsAlm  13985}

    -- 1.3.6.1.4.1.2011.2.25.3.40.40.40.14002
    almIsisLspSeqExceed NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The LSP sequence number has exceeded the upper threshold value."
        ::= { trapsAlm 14002 }

    -- 1.3.6.1.4.1.2011.2.25.3.40.40.40.14003
    almIsisSeqReachMax NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The LSP sequence number has reached the maximum value."
        ::= { trapsAlm 14003 }

    -- 1.3.6.1.4.1.2011.2.25.3.40.40.40.14007
    almDeviceAuthFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Device authentication failure."
        ::= { trapsAlm 14007 }

    -- 1.3.6.1.4.1.2011.2.25.3.40.40.40.14035
    almErpsBlock NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Indicates the blocked port on the EPRS ring when protection switching occurs (under non-idle state)."
        ::= { trapsAlm 14035 }	

    -- 1.3.6.1.4.1.2011.2.25.3.40.40.40.14051
    almPwrAcFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The AC power fails."
        ::= { trapsAlm 14051 }

    -- 1.3.6.1.4.1.2011.2.25.3.40.40.40.14052
    almPwrAcAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The PWR_AC_ALARM is an alarm indicating that the AC voltage is beyond the normal range."
        ::= { trapsAlm 14052 }

    -- 1.3.6.1.4.1.2011.2.25.3.40.40.40.14053
    almPwrDcAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The PWR_DC_ALARM is an alarm indicating that the DC voltage."
        ::= { trapsAlm 14053 }

    -- 1.3.6.1.4.1.2011.2.25.3.40.40.40.14054
    almPwrSurgeAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:AC surge protective device (SPD) is faulty."
        ::= { trapsAlm 14054 }

    -- 1.3.6.1.4.1.2011.2.25.3.40.40.40.14055
    almPwrSolarProt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated when the Solar locks out due to output."
        ::= { trapsAlm 14055 }

    -- 1.3.6.1.4.1.2011.2.25.3.40.40.40.14056
    almPwrSloarFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated when the system detects that the input voltage of each PVDU module is lower than 20 V for 24 hours."
        ::= { trapsAlm 14056 }

    -- 1.3.6.1.4.1.2011.2.25.3.40.40.40.14066
    almPwrTmpovrProt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated if any ESMU battery is undertemperature and the metal oxide semiconductor is disconnected."
        ::= { trapsAlm 14066 }

    -- 1.3.6.1.4.1.2011.2.25.3.40.40.40.14067
    almPwrAcModProt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The AC module has no output."
        ::= { trapsAlm 14067 }

    -- 1.3.6.1.4.1.2011.2.25.3.40.40.40.14068
    almPwrCommFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated in case of a failure to communicate with all."
        ::= { trapsAlm 14068 }

    -- 1.3.6.1.4.1.2011.2.25.3.40.40.40.14057
    almPwrUpgradeFalled NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Module upgrade failure."
        ::= { trapsAlm 14057 }

    -- 1.3.6.1.4.1.2011.2.25.3.40.40.40.14058
    almPwrOutputProt NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:AC/DC output protection."
        ::= { trapsAlm 14058 }

    -- 1.3.6.1.4.1.2011.2.25.3.40.40.40.14072
    almPwrLlvdAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The alarm indicating that the voltage is below the powerdown voltage."
        ::= { trapsAlm 14072 }

    -- 1.3.6.1.4.1.2011.2.25.3.40.40.40.14069
    almPwrHardFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated in case of an AC module fault, 24 V AC module fault, or 48 V DC module fault."
        ::= { trapsAlm 14069 }

    -- 1.3.6.1.4.1.2011.2.25.3.40.40.40.14059
    almBatHardFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The battery hardware is faulty."
        ::= { trapsAlm 14059 }

    -- 1.3.6.1.4.1.2011.2.25.3.40.40.40.14060
    almBatProtAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated by following reasons:when the battery temperature is low enough and then disconnectes."
        ::= { trapsAlm 14060 }

    -- 1.3.6.1.4.1.2011.2.25.3.40.40.40.14070
    almBatAddrConflict NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:If multiple ESMU devices have the same hardware address DIP switch setting, the SMU generates an Address Conflict alarm."
        ::= { trapsAlm 14070 }

    -- 1.3.6.1.4.1.2011.2.25.3.40.40.40.14061
    almBatOverdischarge NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated if battery discharging current exceeds the upper."
        ::= { trapsAlm 14061 }

    -- 1.3.6.1.4.1.2011.2.25.3.40.40.40.14062
    almBatOvercharge NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated if battery charging current exceeds the upper."
        ::= { trapsAlm 14062 }

    -- 1.3.6.1.4.1.2011.2.25.3.40.40.40.14063
    almBatTempAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The alarm indicating that the battery temperature is beyond the normal."
        ::= { trapsAlm 14063 }

    -- 1.3.6.1.4.1.2011.2.25.3.40.40.40.14064
    almBatMissing NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated when no battery is detected."
        ::= { trapsAlm 14064 }

    -- 1.3.6.1.4.1.2011.2.25.3.40.40.40.14065
    almBatSohLow NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The SOH is equal to or less than the SOH self-load value."
        ::= { trapsAlm 14065 }

    -- 1.3.6.1.4.1.2011.2.25.3.40.40.40.14071
    almBatSohWarning NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The SOH is equal or less than the SOH sub-health value."
        ::= { trapsAlm 14071 }

    -- 1.3.6.1.4.1.2011.2.25.3.40.40.40.14075
    almDevDoorOpen NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The cabinet door is open."
        ::= { trapsAlm 14075 }

    -- 1.3.6.1.4.1.2011.2.25.3.40.40.40.14041
    almPatchOpTimeout NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Patch package operation timeout."
        ::= { trapsAlm 14041 }

    -- 1.3.6.1.4.1.2011.2.25.3.40.40.40.14042
    almPatchInitFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated when the patch initialization fails."
        ::= { trapsAlm 14042 }

    -- 1.3.6.1.4.1.2011.2.25.3.40.40.40.14077
    almGpsmodLockFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The clock of the GPS module fails to lock satellite signals"
        ::= { trapsAlm 14077 }

    -- 1.3.6.1.4.1.2011.2.25.3.40.40.40.14078
    almGpsmodInvalid NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The GPS module fails"
        ::= { trapsAlm 14078 }

    -- 1.3.6.1.4.1.2011.2.25.3.40.40.40.14082
    almBatFanAlarm NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated when the patch initialization fails."
        ::= { trapsAlm 14082 }

    -- 1.3.6.1.4.1.2011.2.25.3.40.40.40.14084
    almSepPortFault NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:SEP port fault"
        ::= { trapsAlm 14084 }

    -- 1.3.6.1.4.1.2011.2.25.3.40.40.40.14085
    almErpsCfmFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The MEP bound to an ERPS instance fails"
        ::= { trapsAlm 14085 }
		
    -- 1.3.6.1.4.1.2011.2.25.3.40.40.40.14088
    almPatchMatchNoStart NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The system control board does not launch a board patch match for specific reasons"
        ::= { trapsAlm 14088 }

    -- 1.3.6.1.4.1.2011.2.25.3.40.40.40.14102
    almDcnChannelBiterror NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The Bit-ERROR of the DCN channel"
        ::= { trapsAlm 14102 }		

    -- 1.3.6.1.4.1.2011.2.25.3.40.40.40.14147
    almDcncfgNotCommit NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The configured DCN subnet ID has not been committed."
        ::= { trapsAlm 14147 }
	
    -- 1.3.6.1.4.1.2011.2.25.3.40.40.40.14141
    almLptAuthFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is generated when LPT authentication fails"
        ::= { trapsAlm 14141 }	

    -- 1.3.6.1.4.1.2011.2.25.3.40.40.40.14150
    almPingLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The destination IP address is unreachable."
        ::= { trapsAlm 14150 }	
		
    -- 1.3.6.1.4.1.2011.2.25.3.40.40.40.14151
    almPingArpMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The MAC addresses in the static and dynamic ARP entries conflict with each other."
        ::= { trapsAlm 14151 }	
		
    -- 1.3.6.1.4.1.2011.2.25.3.40.40.40.14164
    almErpsNotComplete NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The alarm indicates that configuration of the EPRS ring is not complete"
        ::= { trapsAlm 14164 }
	
    -- 1.3.6.1.4.1.2011.2.25.3.40.40.40.14149
    almSrvLoopLd NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is reported when a loop is detected. This alarm is cleared after the loop is removed"
        ::= { trapsAlm 14149 }

    -- 1.3.6.1.4.1.2011.2.25.3.40.40.40.14172
    almDhcpFreeIpUseUp NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: This alarm is reported when the DHCP server fails to allocate IP addresses because the available IP addresses have been used up."
        ::= { trapsAlm 14172 }

    -- 1.3.6.1.4.1.2011.2.25.3.40.40.40.14174
    almApsStatusIndi NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:The APS_STATUS_INDI alarm indicates the APS status"
        ::= { trapsAlm 14174 }

    -- 1.3.6.1.4.1.2011.2.25.3.40.40.40.14255
    almDbUnsave NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:This alarm is reported when configuration persistency occurs in the database in some scenarios."
        ::= { trapsAlm 14255 }

    -- 1.3.6.1.4.1.2011.2.25.3.40.40.40.14262
    almAccessCtrlDisabled NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: Access control is disabled."
        ::= { trapsAlm 14262 }

    -- 1.3.6.1.4.1.2011.2.25.3.40.40.40.14284
    almPtpTimeAdjustOff NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:PTP time synchronization is disabled."
        ::= { trapsAlm 14284 }

    -- 1.3.6.1.4.1.2011.2.25.3.40.40.40.14285
    almGpsLos NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: There is no signal received from the GPS on this device."
        ::= { trapsAlm 14285 }

    -- 1.3.6.1.4.1.2011.2.25.3.40.40.40.14382	
    almCaCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The configuration of the members in the CA group is inconsistent, or the CA group configuration of the two cascade NEs is inconsistent."
        ::= { trapsAlm 14382 }

    -- 1.3.6.1.4.1.2011.2.25.3.40.40.40.14407	
    almBdFileUnsecured NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: The file may be unsecured."
        ::= { trapsAlm 14407 }

    -- 1.3.6.1.4.1.2011.2.25.3.40.40.40.14408	
    almComboPortCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm: One cascading port is configured in a working group (for example, a CA group), but the other cascading port that is actually connected is not in the working group."
        ::= { trapsAlm 14408 }

    -- 1.3.6.1.4.1.2011.2.25.3.40.40.40.14459	
    almEthCfgMismatch NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:Ethernet port configurations are inconsistent."
        ::= { trapsAlm 14459 }
	
	-- 1.3.6.1.4.1.2011.2.25.3.40.40.40.14400
    almErpsHeartDetectFail NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:ERPS heartbeat detection timeout alarm."
        ::= { trapsAlm 14400 }
		
	-- 1.3.6.1.4.1.2011.2.25.3.40.40.40.14581
    almIpv4PrefixExceed NOTIFICATION-TYPE
        OBJECTS{ rptEvtNumber,rptAlmName,rptEvtNtfcnCde,rptEvtState,rptEvtStartTime,rptEvtEndTime,rptEvtSrvEff,rptEvtObjType,rptEvtPara }
        STATUS current
        DESCRIPTION
            "Trap of Alarm:IPv4 Route Prefix Count Exceeding Limit."
        ::= { trapsAlm 14581 }
END
