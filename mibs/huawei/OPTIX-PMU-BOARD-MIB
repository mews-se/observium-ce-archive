-- OPTIX-PMU-BOARD-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PMU-BOARD-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        optixLogBoardId,optixLogSubCardId
            FROM OPTIX-BOARD-MANAGE-MIB
        ;

    optixPMUBoard MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This MIB describes thePMU boardconfigurations."
        REVISION "201204170000Z"
        DESCRIPTION
            "The initial revision of this MIB module."
        REVISION "201204170000Z"
        DESCRIPTION
            "The initial revision of this MIB module."
        ::={ optixProvisionEqpt 35 }

    -- 1.3.6.1.4.1.2011.2.25.4.30.35.1
    optixPMU OBJECT IDENTIFIER ::= { optixPMUBoard 1 }

    -- 1.3.6.1.4.1.2011.2.25.4.30.35.1.1
    optixPMUTable OBJECT-TYPE
        SYNTAX SEQUENCE OF OptixPMUEntry
        MAX-ACCESS not-accessible
        STATUS current
        DESCRIPTION
            "This table describes the PMU board configurations."
        ::= { optixPMU 1 }

    -- 1.3.6.1.4.1.2011.2.25.4.30.35.1.1.1
    optixPMUEntry OBJECT-TYPE
        SYNTAX OptixPMUEntry
        MAX-ACCESS not-accessible
        STATUS current
        DESCRIPTION
            "Thisentry describes the PMU board configurations."
        INDEX{ optixLogBoardId,optixLogSubCardId }
        ::= { optixPMUTable 1 }

    OptixPMUEntry ::=
        SEQUENCE {
            optixPMUAcHighthr
                OCTET STRING,
            optixPMUAcLowthr
                OCTET STRING,
            optixPMUDCHighthr
                OCTET STRING,
            optixPMUDCLowthr
                OCTET STRING,
            optixPMUEvolt
                OCTET STRING,
            optixPMUFvolt
                OCTET STRING,
            optixPMULoadDownState
                INTEGER,
            optixPMULoadDownVolt
                OCTET STRING,
            optixPMUBtDownState
                INTEGER,
            optixPMUBtDownVolt
                OCTET STRING,
            optixPMUTempEnvHighThr
                OCTET STRING,
            optixPMUTempEnvLowThr
                OCTET STRING,
            optixPMUHumEnvHighThr
                OCTET STRING,
            optixPMUHumEnvLowThr
                OCTET STRING,
            optixPMUParasPSUNum
                Unsigned32,
            optixPMULimitFactor
                OCTET STRING,
            optixPMUChargeTime
                Unsigned32,
            optixPMUCompensateFactor
                Unsigned32,
            optixPMUCtrlState
                INTEGER,
            optixPMUChargeState
                INTEGER,
            optixPMUCurrentLimit
                INTEGER,
            optixPMUCtrlModeODC
                INTEGER,
            optixPMUChargeMode
                INTEGER,
            optixPMUPowerDownState
                INTEGER,
            optixPMUPsuNum
                Unsigned32,
            optixPMUEnvironHumidity
                OCTET STRING,
            optixPMUDcVolt
                OCTET STRING,
            optixPMULoadCurrent
                OCTET STRING,
            optixPMUBatteryCurrent1
                OCTET STRING,
            optixPMUBatteryCurrent2
                OCTET STRING,
            optixPMUAcVolt
                OCTET STRING,
            optixPMUHtempDownEnable
                INTEGER,
            optixPMUHighTempthre
                OCTET STRING
        }

    -- 1.3.6.1.4.1.2011.2.25.4.30.35.1.1.1.1
    optixPMUAcHighthr OBJECT-TYPE
        SYNTAX OCTET STRING
        MAX-ACCESS read-write
        STATUS current
        DESCRIPTION
            "This object indicates the upper thresholdfor the PMU AC voltage alarms."
        ::= { optixPMUEntry 1 }

    -- 1.3.6.1.4.1.2011.2.25.4.30.35.1.1.1.2
    optixPMUAcLowthr OBJECT-TYPE
        SYNTAX OCTET STRING
        MAX-ACCESS read-write
        STATUS current
        DESCRIPTION
            "This object indicates the lower threshold for the PMU AC voltage alarms."
        ::= { optixPMUEntry 2 }

    -- 1.3.6.1.4.1.2011.2.25.4.30.35.1.1.1.3
    optixPMUDCHighthr OBJECT-TYPE
        SYNTAX OCTET STRING
        MAX-ACCESS read-write
        STATUS current
        DESCRIPTION
            "This object indicates the upper threshold for the PMU DC voltage alarms."
        ::= { optixPMUEntry 3 }

    -- 1.3.6.1.4.1.2011.2.25.4.30.35.1.1.1.4
    optixPMUDCLowthr OBJECT-TYPE
        SYNTAX OCTET STRING
        MAX-ACCESS read-write
        STATUS current
        DESCRIPTION
            "This object indicates the lower threshold for the PMU DC voltage alarms."
        ::= { optixPMUEntry 4 }

    -- 1.3.6.1.4.1.2011.2.25.4.30.35.1.1.1.5
    optixPMUEvolt OBJECT-TYPE
        SYNTAX OCTET STRING
        MAX-ACCESS read-write
        STATUS current
        DESCRIPTION
            "This object indicates the even charging PMU voltage."
        ::= { optixPMUEntry 5 }

    -- 1.3.6.1.4.1.2011.2.25.4.30.35.1.1.1.6
    optixPMUFvolt OBJECT-TYPE
        SYNTAX OCTET STRING
        MAX-ACCESS read-write
        STATUS current
        DESCRIPTION
            "This object indicates the floating charging PMU voltage."
        ::= { optixPMUEntry 6 }

    -- 1.3.6.1.4.1.2011.2.25.4.30.35.1.1.1.7
    optixPMULoadDownState OBJECT-TYPE
        SYNTAX INTEGER
        {
            enable(1),
            disable(0)
        }
        MAX-ACCESS read-write
        STATUS current
        DESCRIPTION
            "This object indicates the enable status of the load power-off function. 0: disable, 1: enable"
        ::= { optixPMUEntry 7 }

    -- 1.3.6.1.4.1.2011.2.25.4.30.35.1.1.1.8
    optixPMULoadDownVolt OBJECT-TYPE
        SYNTAX OCTET STRING
        MAX-ACCESS read-write
        STATUS current
        DESCRIPTION
            "This object indicates the threshold of PMU load power-off voltage. 0: disable, 1: enable"
        ::= { optixPMUEntry 8 }

    -- 1.3.6.1.4.1.2011.2.25.4.30.35.1.1.1.9
    optixPMUBtDownState OBJECT-TYPE
        SYNTAX INTEGER
        {
            enable(1),
            disable(0)
        }
        MAX-ACCESS read-write
        STATUS current
        DESCRIPTION
            "This object indicates the enable status of the load power-off PMU battery group."
        ::= { optixPMUEntry 9 }

    -- 1.3.6.1.4.1.2011.2.25.4.30.35.1.1.1.10
    optixPMUBtDownVolt OBJECT-TYPE
        SYNTAX OCTET STRING
        MAX-ACCESS read-write
        STATUS current
        DESCRIPTION
            "This object indicates the threshold of PMUbattery group power-off voltage."
        ::= { optixPMUEntry 10 }

    -- 1.3.6.1.4.1.2011.2.25.4.30.35.1.1.1.11
    optixPMUTempEnvHighThr OBJECT-TYPE
        SYNTAX OCTET STRING
        MAX-ACCESS read-write
        STATUS current
        DESCRIPTION
            "This object indicates the upper threshold of the PMU ambient temperature."
        ::= { optixPMUEntry 11 }

    -- 1.3.6.1.4.1.2011.2.25.4.30.35.1.1.1.12
    optixPMUTempEnvLowThr OBJECT-TYPE
        SYNTAX OCTET STRING
        MAX-ACCESS read-write
        STATUS current
        DESCRIPTION
            "This object indicates the lower threshold of the PMU ambient temperature."
        ::= { optixPMUEntry 12 }

    -- 1.3.6.1.4.1.2011.2.25.4.30.35.1.1.1.13
    optixPMUHumEnvHighThr OBJECT-TYPE
        SYNTAX OCTET STRING
        MAX-ACCESS read-write
        STATUS current
        DESCRIPTION
            "This object indicates the upper threshold of the PMU ambient humidity."
        ::= { optixPMUEntry 13 }

    -- 1.3.6.1.4.1.2011.2.25.4.30.35.1.1.1.14
    optixPMUHumEnvLowThr OBJECT-TYPE
        SYNTAX OCTET STRING
        MAX-ACCESS read-write
        STATUS current
        DESCRIPTION
            "This object indicates thelower threshold of the PMU ambient humidity."
        ::= { optixPMUEntry 14 }

    -- 1.3.6.1.4.1.2011.2.25.4.30.35.1.1.1.15
    optixPMUParasPSUNum OBJECT-TYPE
        SYNTAX Unsigned32
        MAX-ACCESS read-write
        STATUS current
        DESCRIPTION
            "This object indicates the PMU number of power module."
        ::= { optixPMUEntry 15 }

    -- 1.3.6.1.4.1.2011.2.25.4.30.35.1.1.1.16
    optixPMULimitFactor OBJECT-TYPE
        SYNTAX OCTET STRING
        MAX-ACCESS read-write
        STATUS current
        DESCRIPTION
            "This object indicates the limit factor of battary."
        ::= { optixPMUEntry 16 }

    -- 1.3.6.1.4.1.2011.2.25.4.30.35.1.1.1.17
    optixPMUChargeTime OBJECT-TYPE
        SYNTAX Unsigned32
        MAX-ACCESS read-write
        STATUS current
        DESCRIPTION
            "This object indicates the time of charge battary."
        ::= { optixPMUEntry 17 }

    -- 1.3.6.1.4.1.2011.2.25.4.30.35.1.1.1.18
    optixPMUCompensateFactor OBJECT-TYPE
        SYNTAX Unsigned32
        MAX-ACCESS read-write
        STATUS current
        DESCRIPTION
            "This parameter specifies the battary temp compensatefactor"
        ::= { optixPMUEntry 18 }

    -- 1.3.6.1.4.1.2011.2.25.4.30.35.1.1.1.19
    optixPMUCtrlState OBJECT-TYPE
        SYNTAX INTEGER
        {
            accessory(85),
            main(170)
        }
        MAX-ACCESS read-write
        STATUS current
        DESCRIPTION
            "This parameter specifies ctrl state of PMU"
        ::= { optixPMUEntry 19 }

    -- 1.3.6.1.4.1.2011.2.25.4.30.35.1.1.1.20
    optixPMUChargeState OBJECT-TYPE
        SYNTAX INTEGER
        {
            forceEven(0),
            float(85),
            even(170),
            discharge(255)
        }
        MAX-ACCESS read-write
        STATUS current
        DESCRIPTION
            "This parameter specifies charge state of PMU"
        ::= { optixPMUEntry 20 }

    -- 1.3.6.1.4.1.2011.2.25.4.30.35.1.1.1.21
    optixPMUCurrentLimit OBJECT-TYPE
        SYNTAX INTEGER
        {
            disable(0),
            enable(1)
        }
        MAX-ACCESS read-only
        STATUS current
        DESCRIPTION
            "This object indicates the stat of limit current of charge battery"
        ::= { optixPMUEntry 21 }

    -- 1.3.6.1.4.1.2011.2.25.4.30.35.1.1.1.22
    optixPMUCtrlModeODC OBJECT-TYPE
        SYNTAX INTEGER
        {
            accessory(85),
            main(170)
        }
        MAX-ACCESS read-only
        STATUS current
        DESCRIPTION
            "This object indicates the ctrl state of charged battery"
        ::= { optixPMUEntry 22 }

    -- 1.3.6.1.4.1.2011.2.25.4.30.35.1.1.1.23
    optixPMUChargeMode OBJECT-TYPE
        SYNTAX INTEGER
        {
            forceEven(0),
            float(85),
            even(170),
            discharge(255)
        }
        MAX-ACCESS read-only
        STATUS current
        DESCRIPTION
            "This object indicates the state of PMU charge mode"
        ::= { optixPMUEntry 23 }

    -- 1.3.6.1.4.1.2011.2.25.4.30.35.1.1.1.24
    optixPMUPowerDownState OBJECT-TYPE
        SYNTAX INTEGER
        {
            disable(0),
            enable(1)
        }
        MAX-ACCESS read-only
        STATUS current
        DESCRIPTION
            "This object indicates the state of power down"
        ::= { optixPMUEntry 24 }

    -- 1.3.6.1.4.1.2011.2.25.4.30.35.1.1.1.25
    optixPMUPsuNum OBJECT-TYPE
        SYNTAX Unsigned32
        MAX-ACCESS read-only
        STATUS current
        DESCRIPTION
            "This object indicates the number of PSU"
        ::= { optixPMUEntry 25 }

    -- 1.3.6.1.4.1.2011.2.25.4.30.35.1.1.1.26
    optixPMUEnvironHumidity OBJECT-TYPE
        SYNTAX OCTET STRING
        MAX-ACCESS read-only
        STATUS current
        DESCRIPTION
            "This object indicates the environmental Humidity"
        ::= { optixPMUEntry 26 }

    -- 1.3.6.1.4.1.2011.2.25.4.30.35.1.1.1.27
    optixPMUDcVolt OBJECT-TYPE
        SYNTAX OCTET STRING
        MAX-ACCESS read-only
        STATUS current
        DESCRIPTION
            "This object indicates the DC voltage."
        ::= { optixPMUEntry 27 }

    -- 1.3.6.1.4.1.2011.2.25.4.30.35.1.1.1.28
    optixPMULoadCurrent OBJECT-TYPE
        SYNTAX OCTET STRING
        MAX-ACCESS read-only
        STATUS current
        DESCRIPTION
            "This object indicates the load current."
        ::= { optixPMUEntry 28 }

    -- 1.3.6.1.4.1.2011.2.25.4.30.35.1.1.1.29
    optixPMUBatteryCurrent1 OBJECT-TYPE
        SYNTAX OCTET STRING
        MAX-ACCESS read-only
        STATUS current
        DESCRIPTION
            "This object indicates the current of battery1."
        ::= { optixPMUEntry 29 }

    -- 1.3.6.1.4.1.2011.2.25.4.30.35.1.1.1.30
    optixPMUBatteryCurrent2 OBJECT-TYPE
        SYNTAX OCTET STRING
        MAX-ACCESS read-only
        STATUS current
        DESCRIPTION
            "This object indicates the current of battery2."
        ::= { optixPMUEntry 30 }

    -- 1.3.6.1.4.1.2011.2.25.4.30.35.1.1.1.31
    optixPMUAcVolt OBJECT-TYPE
        SYNTAX OCTET STRING
        MAX-ACCESS read-only
        STATUS current
        DESCRIPTION
            "This object indicates the AC voltage."
        ::= { optixPMUEntry 31 }

    -- 1.3.6.1.4.1.2011.2.25.4.30.35.1.1.1.32
    optixPMUHtempDownEnable OBJECT-TYPE
        SYNTAX INTEGER
        {
            disable(0),
            enable(1),
            auto(2)
        }
        MAX-ACCESS read-write
        STATUS current
        DESCRIPTION
            "This object indicates the enable status of temp down para."
        ::= { optixPMUEntry 32 }

    -- 1.3.6.1.4.1.2011.2.25.4.30.35.1.1.1.33
    optixPMUHighTempthre OBJECT-TYPE
        SYNTAX OCTET STRING
        MAX-ACCESS read-write
        STATUS current
        DESCRIPTION
            "This object indicates the para of temp down."
        ::= { optixPMUEntry 33 }

    -- 1.3.6.1.4.1.2011.2.25.4.30.35.1.2
    optixPMUBatteryTable OBJECT-TYPE
        SYNTAX SEQUENCE OF OptixPMUBatteryEntry
        MAX-ACCESS not-accessible
        STATUS current
        DESCRIPTION
            "This table contains basic battery information of PMU"
        ::= { optixPMU 2 }

    -- 1.3.6.1.4.1.2011.2.25.4.30.35.1.2.1
    optixPMUBatteryEntry OBJECT-TYPE
        SYNTAX OptixPMUBatteryEntry
        MAX-ACCESS not-accessible
        STATUS current
        DESCRIPTION
            "This Entry containins basic battery information of PMU"
        INDEX{ optixLogBoardId,optixLogSubCardId,optixPMUBatteryNum }
        ::= { optixPMUBatteryTable 1 }

    OptixPMUBatteryEntry ::=
        SEQUENCE {
            optixPMUBatteryNum
                Unsigned32,
            optixPMUBatteryCapacity
                Unsigned32,
            optixPMUBatteryTemp
                OCTET STRING,
            optixPMUBatteryHighTh
                OCTET STRING,
            optixPMUBatteryLowTh
                OCTET STRING
        }

    -- 1.3.6.1.4.1.2011.2.25.4.30.35.1.2.1.1
    optixPMUBatteryNum OBJECT-TYPE
        SYNTAX Unsigned32
        MAX-ACCESS not-accessible
        STATUS current
        DESCRIPTION
            "This parameter specifies the PMU index"
        ::= { optixPMUBatteryEntry 1 }

    -- 1.3.6.1.4.1.2011.2.25.4.30.35.1.2.1.2
    optixPMUBatteryCapacity OBJECT-TYPE
        SYNTAX Unsigned32
        MAX-ACCESS read-write
        STATUS current
        DESCRIPTION
            "This parameter specifies the capacity of battery"
        ::= { optixPMUBatteryEntry 2 }

    -- 1.3.6.1.4.1.2011.2.25.4.30.35.1.2.1.3
    optixPMUBatteryTemp OBJECT-TYPE
        SYNTAX OCTET STRING
        MAX-ACCESS read-only
        STATUS current
        DESCRIPTION
            "This object indicates the temperature of battery"
        ::= { optixPMUBatteryEntry 3 }

    -- 1.3.6.1.4.1.2011.2.25.4.30.35.1.2.1.4
    optixPMUBatteryHighTh OBJECT-TYPE
        SYNTAX OCTET STRING
        MAX-ACCESS read-write
        STATUS current
        DESCRIPTION
            "This parameter specifies the high tempth of bid sbid"
        ::= { optixPMUBatteryEntry 4 }

    -- 1.3.6.1.4.1.2011.2.25.4.30.35.1.2.1.5
    optixPMUBatteryLowTh OBJECT-TYPE
        SYNTAX OCTET STRING
        MAX-ACCESS read-write
        STATUS current
        DESCRIPTION
            "This parameter specifies the low tempth of bid sbid"
        ::= { optixPMUBatteryEntry 5 }

    -- 1.3.6.1.4.1.2011.2.25.4.30.35.1.3
    optixPMUEnTempTable OBJECT-TYPE
        SYNTAX SEQUENCE OF OptixPMUEnTempEntry
        MAX-ACCESS not-accessible
        STATUS current
        DESCRIPTION
            "this tabel indicates the environmental temperature"
        ::= { optixPMU 3 }

    -- 1.3.6.1.4.1.2011.2.25.4.30.35.1.3.1
    optixPMUEnTempEntry OBJECT-TYPE
        SYNTAX OptixPMUEnTempEntry
        MAX-ACCESS not-accessible
        STATUS current
        DESCRIPTION
            "This Entry indicates environmental temperature"
        INDEX{ optixLogBoardId,optixLogSubCardId,optixPMUEnTempEnvNum }
        ::= { optixPMUEnTempTable 1 }

    OptixPMUEnTempEntry ::=
        SEQUENCE {
            optixPMUEnTempEnvNum
                Unsigned32,
            optixPMUEnvironTem
                OCTET STRING
        }

    -- 1.3.6.1.4.1.2011.2.25.4.30.35.1.3.1.1
    optixPMUEnTempEnvNum OBJECT-TYPE
        SYNTAX Unsigned32
        MAX-ACCESS not-accessible
        STATUS current
        DESCRIPTION
            "This object indicates the index of optixPMUEnTempTable."
        ::= { optixPMUEnTempEntry 1 }

    -- 1.3.6.1.4.1.2011.2.25.4.30.35.1.3.1.2
    optixPMUEnvironTem OBJECT-TYPE
        SYNTAX OCTET STRING
        MAX-ACCESS read-only
        STATUS current
        DESCRIPTION
            "This object indicates the environmental temperature."
        ::= { optixPMUEnTempEntry 2 }

END
