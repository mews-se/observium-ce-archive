-- OPTIX-PKT-SDHALM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-SDHALM-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY
            FROM SNMPv2-SMI
        optixPktSdhPortId
            FROM OPTIX-PKT-SDHOH-MIB
        optixLogBoardId,optixLogSubCardId
            FROM OPTIX-BOARD-MANAGE-MIB
        ;

    optixPktSdhAlmClksw MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the port configuration information of sdh alarm"
        REVISION "201204200000Z"
        DESCRIPTION
            "The initial revision of this MIB module1."
        ::={ optixProvisionPtn 33 }

    -- 1.3.6.1.4.1.2011.2.25.4.50.33.1
    optixPktSdhAlmClkswGroup OBJECT IDENTIFIER ::= { optixPktSdhAlmClksw 1 }

    -- 1.3.6.1.4.1.2011.2.25.4.50.33.1.1
    optixPktSdhB1B2B3Table OBJECT-TYPE
        SYNTAX SEQUENCE OF OptixPktSdhB1B2B3Entry
        MAX-ACCESS not-accessible
        STATUS current
        DESCRIPTION
            "This table describes the threshold-crossing/deterioration configurations of B1/B2/B3 bit errors."
        ::= { optixPktSdhAlmClkswGroup 1 }

    -- 1.3.6.1.4.1.2011.2.25.4.50.33.1.1.1
    optixPktSdhB1B2B3Entry OBJECT-TYPE
        SYNTAX OptixPktSdhB1B2B3Entry
        MAX-ACCESS not-accessible
        STATUS current
        DESCRIPTION
            "This entry describes the threshold-crossing/deterioration configurations of B1/B2/B3 bit errors."
        INDEX{ optixLogBoardId,optixLogSubCardId,optixPktSdhPortId,optixPktSdhB1B2B3THType }
        ::= { optixPktSdhB1B2B3Table 1 }

    OptixPktSdhB1B2B3Entry ::=
        SEQUENCE {
            optixPktSdhB1B2B3THType
                INTEGER,
            optixPktSdhB1B2B3EXECTH
                Unsigned32,
            optixPktSdhB1B2B3SDTH
                Unsigned32
        }

    -- 1.3.6.1.4.1.2011.2.25.4.50.33.1.1.1.1
    optixPktSdhB1B2B3THType OBJECT-TYPE
        SYNTAX INTEGER
        {
            b1th(1),
            b2th(2),
            b3th(3),
            bip2th(5),
            b3iec(6)
        }
        MAX-ACCESS not-accessible
        STATUS current
        DESCRIPTION
            "This object indicates the threshold type of B1/B2/B3 bit errors. 1: b1th, 2: b2th, 3: b3th, 5: bip2th, 6: b3iec"
        ::= { optixPktSdhB1B2B3Entry 1 }

    -- 1.3.6.1.4.1.2011.2.25.4.50.33.1.1.1.2
    optixPktSdhB1B2B3EXECTH OBJECT-TYPE
        SYNTAX Unsigned32
        MAX-ACCESS read-write
        STATUS current
        DESCRIPTION
            "This object indicates the threshold-crossing levelof B1/B2/B3 bit errors. 1: 1.0E-9, 2: 1.0E-8, 3: 1.0E-7, 4: 1.0E-6, 5: 1.0E-5, 6: 1.0E-4, 7: 1.0E-3. The default value is 3 (1.0E-7)."
        ::= { optixPktSdhB1B2B3Entry 2 }

    -- 1.3.6.1.4.1.2011.2.25.4.50.33.1.1.1.3
    optixPktSdhB1B2B3SDTH OBJECT-TYPE
        SYNTAX Unsigned32
        MAX-ACCESS read-write
        STATUS current
        DESCRIPTION
            "This object indicates the performance deterioration threshold level of B1/B2/B3 bit errors. 1: 1.0E-9, 2: 1.0E-8, 3: 1.0E-7, 4: 1.0E-6, 5: 1.0E-5, 6: 1.0E-4, 7: 1.0E-3. The default value is 6 (1.0E-4)."
        ::= { optixPktSdhB1B2B3Entry 3 }

    -- 1.3.6.1.4.1.2011.2.25.4.50.33.1.2
    optixPktSdhAlmClkswTable OBJECT-TYPE
        SYNTAX SEQUENCE OF OptixPktSdhAlmClkswEntry
        MAX-ACCESS not-accessible
        STATUS current
        DESCRIPTION
            "This table describes the configurations on whether MS AIS and B2 EXC trigger a clock switching."
        ::= { optixPktSdhAlmClkswGroup 2 }

    -- 1.3.6.1.4.1.2011.2.25.4.50.33.1.2.1
    optixPktSdhAlmClkswEntry OBJECT-TYPE
        SYNTAX OptixPktSdhAlmClkswEntry
        MAX-ACCESS not-accessible
        STATUS current
        DESCRIPTION
            "This entry describes the configurations to whether MS AIS and B2 EXC trigger a clock switching."
        INDEX{ optixLogBoardId,optixLogSubCardId,optixPktSdhPortId,optixPktSdhAlmClkswEid }
        ::= { optixPktSdhAlmClkswTable 1 }

    OptixPktSdhAlmClkswEntry ::=
        SEQUENCE {
            optixPktSdhAlmClkswEid
                INTEGER,
            optixPktSdhAlmClkswEnable
                INTEGER
        }

    -- 1.3.6.1.4.1.2011.2.25.4.50.33.1.2.1.1
    optixPktSdhAlmClkswEid OBJECT-TYPE
        SYNTAX INTEGER
        {
            msais(33),
            b2exc(35)
        }
        MAX-ACCESS not-accessible
        STATUS current
        DESCRIPTION
            "This object indicates the alarm ID. 33: msais, 35: b2exc"
        ::= { optixPktSdhAlmClkswEntry 1 }

    -- 1.3.6.1.4.1.2011.2.25.4.50.33.1.2.1.2
    optixPktSdhAlmClkswEnable OBJECT-TYPE
        SYNTAX INTEGER
        {
            enable(1),
            disable(0)
        }
        MAX-ACCESS read-write
        STATUS current
        DESCRIPTION
            "This object indicates the enable status of the clock switching. 0: disable, 1: enable"
        ::= { optixPktSdhAlmClkswEntry 2 }

    -- 1.3.6.1.4.1.2011.2.25.4.50.33.1.3
    optixPktSdhAlm2Table OBJECT-TYPE
        SYNTAX SEQUENCE OF OptixPktSdhAlm2Entry
        MAX-ACCESS not-accessible
        STATUS current
        DESCRIPTION
            "This table describes the configurations on whether AIS when alarm."
        ::= { optixPktSdhAlmClkswGroup 3 }

    -- 1.3.6.1.4.1.2011.2.25.4.50.33.1.3.1
    optixPktSdhAlm2Entry OBJECT-TYPE
        SYNTAX OptixPktSdhAlm2Entry
        MAX-ACCESS not-accessible
        STATUS current
        DESCRIPTION
            "This entry describes the configurations on whether AIS when alarm."
        INDEX{ optixLogBoardId,optixLogSubCardId,optixPktSdhPortId,optixPktSdhAlm2Eid }
        ::= { optixPktSdhAlm2Table 1 }

    OptixPktSdhAlm2Entry ::=
        SEQUENCE {
            optixPktSdhAlm2Eid
                INTEGER,
            optixPktSdhAlm2AisEnable
                INTEGER
        }

    -- 1.3.6.1.4.1.2011.2.25.4.50.33.1.3.1.1
    optixPktSdhAlm2Eid OBJECT-TYPE
        SYNTAX INTEGER
        {
            snmp0(0),
            b1sd(175),
            b1exc(12),
            b2sd(36),
            b2exc(35),
            b3sd(70),
            b3exc(71),
            roof(5),
            msais(33),
            hptim(76),
            hpslm(77),
            hpuneq(75),
            hplom(81),
            auais(72),
            tcltc(352),
            tcuneq(353),
            tcincais(354),
            tctim(357),
            rlos(1),
            rlof(8),
            aulop(66),
            lptim(91),
            lpuneq(90),
            lpslm(92),
            bipexc(183),
            bipsd(182),
            linkerr(261),
            lpslmvc12(63594),
            lptimvc12(63596),
            lpuneqvc12(63598)
        }
        MAX-ACCESS not-accessible
        STATUS current
        DESCRIPTION
            "This object indicates the alarm ID. 0: snmp0, 175: b1sd, 12: b1exc, 36: b2sd, 35: b2exc, 70: b3sd, 71: b3exc, 5: roof, 33: msais, 76: hptim, 77: hpslm, 75: hpuneq, 81: hplom, 72: auais, 352: tcltc, 353: tcuneq, 354: tcincais, 357: tctim, 1: rlos, 8: rlof, 66: aulop, 91: lptim, 90: lpuneq, 92: lpslm, 183: bipexc, 182: bipsd, 261: linkerr, 63594: lpslmvc12, 63596: lptimvc12, 63598: lpuneqvc12"
        ::= { optixPktSdhAlm2Entry 1 }

    -- 1.3.6.1.4.1.2011.2.25.4.50.33.1.3.1.2
    optixPktSdhAlm2AisEnable OBJECT-TYPE
        SYNTAX INTEGER
        {
            enable(1),
            disable(0)
        }
        MAX-ACCESS read-write
        STATUS current
        DESCRIPTION
            "This object indicates the ais enable status of the alarm. 0: disable, 1: enable"
        ::= { optixPktSdhAlm2Entry 2 }

    -- 1.3.6.1.4.1.2011.2.25.4.50.33.1.4
    optixPktSdhPortAlmAisTable OBJECT-TYPE
        SYNTAX SEQUENCE OF OptixPktSdhPortAlmAisEntry
        MAX-ACCESS not-accessible
        STATUS current
        DESCRIPTION
            "This table describes whether the TU_AIS alarm is inserted."
        ::= { optixPktSdhAlmClkswGroup 4 }

    -- 1.3.6.1.4.1.2011.2.25.4.50.33.1.4.1
    optixPktSdhPortAlmAisEntry OBJECT-TYPE
        SYNTAX OptixPktSdhPortAlmAisEntry
        MAX-ACCESS not-accessible
        STATUS current
        DESCRIPTION
            "This entry describes whether the TU_AIS alarm is inserted."
        INDEX{ optixLogBoardId,optixLogSubCardId,optixPktSdhPortId }
        ::= { optixPktSdhPortAlmAisTable 1 }

    OptixPktSdhPortAlmAisEntry ::=
        SEQUENCE {
            optixPktSdhPortAlmAisEn
                INTEGER
        }

    -- 1.3.6.1.4.1.2011.2.25.4.50.33.1.4.1.1
    optixPktSdhPortAlmAisEn OBJECT-TYPE
        SYNTAX INTEGER
        {
            enable(1),
            disable(0)
        }
        MAX-ACCESS read-write
        STATUS current
        DESCRIPTION
            "This object indicates the AIS enable status of the TU_AIS alarm. 0: disable, 1: enable"
        ::= { optixPktSdhPortAlmAisEntry 1 }

END
