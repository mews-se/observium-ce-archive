-- OPTIX-PW-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PW-MIB DEFINITIONS ::= BEGIN
    IMPORTS
        OBJECT-GROUP,MODULE-COMPLIANCE
            FROM SNMPv2-CONF
        MODULE-IDENTITY,OBJECT-TYPE,Unsigned32,Integer32,IpAddress,NOTIFICATION-TYPE
            FROM SNMPv2-SMI
        RowStatus
            FROM SNMPv2-TC
        optixProvisionPtn
            FROM OPTIX-OID-MIB
        ;

    optixPWMod MODULE-IDENTITY
        LAST-UPDATED "201204100000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and manage MPLS PWs. The PWE3 is a Layer 2 service bearer technology that emulates the basic behaviors and characteristics of services such as ATM/IMA, Ethernet, and TDM on a packet switched network (PSN).Aided by the PWE3 technology, conventional networks can be connectedto a PSN. Therefore, resource sharing and network scaling can be achieved."
        REVISION "201204100000Z"
        DESCRIPTION
            "Initial version of this MIB module"
        ::={ optixProvisionPtn 6 }

    -- 1.3.6.1.4.1.2011.2.25.4.50.6.1
    optixPWObject OBJECT IDENTIFIER ::= { optixPWMod 1 }

    -- 1.3.6.1.4.1.2011.2.25.4.50.6.1.1
    optixNeTPId OBJECT-TYPE
        SYNTAX Unsigned32(1..65535)
        MAX-ACCESS read-write
        STATUS current
        DESCRIPTION
            "When ETH services are carried through Ethernet tagged PWs, service VLAN must be added before the service payloads. This object is used tospecify theTP ID of the VLAN."
        DEFVAL{ 34984 }
        ::= { optixPWObject 1 }

    -- 1.3.6.1.4.1.2011.2.25.4.50.6.1.2
    optixStaticUcEthPWTable OBJECT-TYPE
        SYNTAX SEQUENCE OF OptixStaticUcEthPWEntry
        MAX-ACCESS not-accessible
        STATUS current
        DESCRIPTION
            "This table implements the configurations of static unicast ETH PWs, including the PW type, label, tunnels carried on the PW, CW, VCCV, and applied VLAN."
        ::= { optixPWObject 2 }

    -- 1.3.6.1.4.1.2011.2.25.4.50.6.1.2.1
    optixStaticUcEthPWEntry OBJECT-TYPE
        SYNTAX OptixStaticUcEthPWEntry
        MAX-ACCESS not-accessible
        STATUS current
        DESCRIPTION
            "This entry indicates the parameter table of the static unicast ETH PWs."
        INDEX{ optixEthPWIndex }
        ::= { optixStaticUcEthPWTable 1 }

    OptixStaticUcEthPWEntry ::=
        SEQUENCE {
            optixEthPWIndex
                Unsigned32,
            optixEthPWtype
                INTEGER,
            optixEthPWId
                Unsigned32,
            optixEthPWDirection
                INTEGER,
            optixEthPWPosition
                INTEGER,
            optixEthPWInLabel
                Unsigned32,
            optixEthPWOutLabel
                Unsigned32,
            optixEthPWPeerIp
                IpAddress,
            optixEthPWTunnelIndex
                Unsigned32,
            optixEthPWVccvctrlChnlType
                INTEGER,
            optixEthPWVccvCheckType
                INTEGER,
            optixEthPWCtrlWord
                INTEGER,
            optixEthPWExp
                Unsigned32,
            optixEthPWLspMode
                INTEGER,
            optixEthPWEnable
                INTEGER,
            optixEthPWIngressIdBoundEgrTnl
                IpAddress,
            optixEthPWEgressIdBoundEgrTnl
                IpAddress,
            optixEthPWTunnelIdBoundEgrTnl
                Unsigned32,
            optixEthPWEncapsulateVlanId
                Unsigned32,
            optixEthPWCheckRet
                INTEGER,
            optixEthPWSrvType
                INTEGER,
            optixEthPWSrvIndex
                Unsigned32,
            optixEthPWSrvID
                Unsigned32,
            optixEthPWLocalState
                Unsigned32,
            optixEthPWRemoteState
                Unsigned32,
            optixEthPWState
                Unsigned32,
            optixEthPWRowStatus
                RowStatus
        }

    -- 1.3.6.1.4.1.2011.2.25.4.50.6.1.2.1.1
    optixEthPWIndex OBJECT-TYPE
        SYNTAX Unsigned32
        MAX-ACCESS not-accessible
        STATUS current
        DESCRIPTION
            "This object indicates the PW index, ranging from 1 to 0x00ffffff,0 means auto."
        ::= { optixStaticUcEthPWEntry 1 }

    -- 1.3.6.1.4.1.2011.2.25.4.50.6.1.2.1.2
    optixEthPWtype OBJECT-TYPE
        SYNTAX INTEGER
        {
            ethtag(4),
            ethraw(5)
        }
        MAX-ACCESS read-create
        STATUS current
        DESCRIPTION
            "This object indcates the PW type. 0x0004: eth-tag 0x0005: eth-raw"
        ::= { optixStaticUcEthPWEntry 2 }

    -- 1.3.6.1.4.1.2011.2.25.4.50.6.1.2.1.3
    optixEthPWId OBJECT-TYPE
        SYNTAX Unsigned32
        MAX-ACCESS read-create
        STATUS current
        DESCRIPTION
            "This object indicates the PW ID."
        ::= { optixStaticUcEthPWEntry 3 }

    -- 1.3.6.1.4.1.2011.2.25.4.50.6.1.2.1.4
    optixEthPWDirection OBJECT-TYPE
        SYNTAX INTEGER
        {
            uni(2),
            bi(1)
        }
        MAX-ACCESS read-create
        STATUS current
        DESCRIPTION
            "This object indicates the PW direction. 1: bi 2: uni"
        DEFVAL{ 1 }
        ::= { optixStaticUcEthPWEntry 4 }

    -- 1.3.6.1.4.1.2011.2.25.4.50.6.1.2.1.5
    optixEthPWPosition OBJECT-TYPE
        SYNTAX INTEGER
        {
            null(0),
            ingress(1),
            egress(2)
        }
        MAX-ACCESS read-create
        STATUS current
        DESCRIPTION
            "This object indicates the node location. 0: null 1: ingress 2: egress"
        DEFVAL{ 0 }
        ::= { optixStaticUcEthPWEntry 5 }

    -- 1.3.6.1.4.1.2011.2.25.4.50.6.1.2.1.6
    optixEthPWInLabel OBJECT-TYPE
        SYNTAX Unsigned32
        MAX-ACCESS read-create
        STATUS current
        DESCRIPTION
            "This object indicates the ingress label."
        ::= { optixStaticUcEthPWEntry 6 }

    -- 1.3.6.1.4.1.2011.2.25.4.50.6.1.2.1.7
    optixEthPWOutLabel OBJECT-TYPE
        SYNTAX Unsigned32
        MAX-ACCESS read-create
        STATUS current
        DESCRIPTION
            "This object indicates the egress label."
        ::= { optixStaticUcEthPWEntry 7 }

    -- 1.3.6.1.4.1.2011.2.25.4.50.6.1.2.1.8
    optixEthPWPeerIp OBJECT-TYPE
        SYNTAX IpAddress
        MAX-ACCESS read-create
        STATUS current
        DESCRIPTION
            "This object indicates the peer IP address."
        ::= { optixStaticUcEthPWEntry 8 }

    -- 1.3.6.1.4.1.2011.2.25.4.50.6.1.2.1.9
    optixEthPWTunnelIndex OBJECT-TYPE
        SYNTAX Unsigned32
        MAX-ACCESS read-create
        STATUS current
        DESCRIPTION
            "This object indicates the index to the tunnel carried through the PW."
        ::= { optixStaticUcEthPWEntry 9 }

    -- 1.3.6.1.4.1.2011.2.25.4.50.6.1.2.1.10
    optixEthPWVccvctrlChnlType OBJECT-TYPE
        SYNTAX INTEGER
        {
            none(0),
            cw(1),
            alertlabel(2),
            cwaltlb(4)
        }
        MAX-ACCESS read-create
        STATUS current
        DESCRIPTION
            "This object indicates the control channel type. 0: none 1: cw 2: alertlabel 3: cwaltlb 4: ttl"
        ::= { optixStaticUcEthPWEntry 10 }

    -- 1.3.6.1.4.1.2011.2.25.4.50.6.1.2.1.11
    optixEthPWVccvCheckType OBJECT-TYPE
        SYNTAX INTEGER
        {
            none(0),
            ping(1),
            bfd(2),
            pingbfd(3)
        }
        MAX-ACCESS read-create
        STATUS current
        DESCRIPTION
            "This object indicates the verification mode. 0: none 1: ping 2: bfd 3 :pingbfd"
        ::= { optixStaticUcEthPWEntry 11 }

    -- 1.3.6.1.4.1.2011.2.25.4.50.6.1.2.1.12
    optixEthPWCtrlWord OBJECT-TYPE
        SYNTAX INTEGER
        {
            notuse(1),
            fstuse(2),
            mstuse(3)
        }
        MAX-ACCESS read-create
        STATUS current
        DESCRIPTION
            "This object indicates the usage policy of the control word. 1: not-use 2: frt-use 3: mst-use"
        DEFVAL{ 2 }
        ::= { optixStaticUcEthPWEntry 12 }

    -- 1.3.6.1.4.1.2011.2.25.4.50.6.1.2.1.13
    optixEthPWExp OBJECT-TYPE
        SYNTAX Unsigned32(0..7|255)
        MAX-ACCESS read-create
        STATUS current
        DESCRIPTION
            "This object indicates the EXP value. (Only upstream EXPs are supported.) Valid values:0-7. 0xff: The EXP value is invalid."
        DEFVAL{ 255 }
        ::= { optixStaticUcEthPWEntry 13 }

    -- 1.3.6.1.4.1.2011.2.25.4.50.6.1.2.1.14
    optixEthPWLspMode OBJECT-TYPE
        SYNTAX INTEGER
        {
            uniform(1),
            pipe(2),
            none(255)
        }
        MAX-ACCESS read-create
        STATUS current
        DESCRIPTION
            "This object indicates the LSP mode.(Only the downstreamLSP is supported.) 1: uniform 2: pipe 255: none (The LSP mode is invalid upstream.)"
        DEFVAL{ 1 }
        ::= { optixStaticUcEthPWEntry 14 }

    -- 1.3.6.1.4.1.2011.2.25.4.50.6.1.2.1.15
    optixEthPWEnable OBJECT-TYPE
        SYNTAX INTEGER
        {
            disable(0),
            enable(1)
        }
        MAX-ACCESS read-create
        STATUS current
        DESCRIPTION
            "This object indicates the enable status of the PW. 0: disable 1: enable"
        DEFVAL{ 1 }
        ::= { optixStaticUcEthPWEntry 15 }

    -- 1.3.6.1.4.1.2011.2.25.4.50.6.1.2.1.16
    optixEthPWIngressIdBoundEgrTnl OBJECT-TYPE
        SYNTAX IpAddress
        MAX-ACCESS read-create
        STATUS current
        DESCRIPTION
            "This object indicates the source node ID of the bound egress tunnel."
        DEFVAL{ 0 }
        ::= { optixStaticUcEthPWEntry 16 }

    -- 1.3.6.1.4.1.2011.2.25.4.50.6.1.2.1.17
    optixEthPWEgressIdBoundEgrTnl OBJECT-TYPE
        SYNTAX IpAddress
        MAX-ACCESS read-create
        STATUS current
        DESCRIPTION
            "This object indicates the sink node ID of the bound egress tunnel."
        DEFVAL{ 0 }
        ::= { optixStaticUcEthPWEntry 17 }

    -- 1.3.6.1.4.1.2011.2.25.4.50.6.1.2.1.18
    optixEthPWTunnelIdBoundEgrTnl OBJECT-TYPE
        SYNTAX Unsigned32
        MAX-ACCESS read-create
        STATUS current
        DESCRIPTION
            "This object idnicates the bound egress tunnel ID."
        DEFVAL{ 0 }
        ::= { optixStaticUcEthPWEntry 18 }

    -- 1.3.6.1.4.1.2011.2.25.4.50.6.1.2.1.19
    optixEthPWEncapsulateVlanId OBJECT-TYPE
        SYNTAX Unsigned32(1..4094|65535)
        MAX-ACCESS read-create
        STATUS current
        DESCRIPTION
            "When ETH services are carried through Ethernet tagged PWs, service VLAN must be added before the service payloads. This object is used to specify the VLAN ID.Valid values: 1-4095. 0xffff: The VLAN ID is not specified."
        DEFVAL{ 65535 }
        ::= { optixStaticUcEthPWEntry 19 }

    -- 1.3.6.1.4.1.2011.2.25.4.50.6.1.2.1.20
    optixEthPWCheckRet OBJECT-TYPE
        SYNTAX INTEGER
        {
            normal(0),
            abnormal(1)
        }
        MAX-ACCESS read-only
        STATUS current
        DESCRIPTION
            "This object indicates the PW check result."
        ::= { optixStaticUcEthPWEntry 20 }

    -- 1.3.6.1.4.1.2011.2.25.4.50.6.1.2.1.21
    optixEthPWSrvType OBJECT-TYPE
        SYNTAX INTEGER
        {
            ces(1),
            atmPwe3(2),
            eLine(3),
            eLan(4),
            eAggr(5),
            eTree(6),
            mirror(7),
            msPw(8),
            ptp1588(9),
            top(10)
        }
        MAX-ACCESS read-only
        STATUS current
        DESCRIPTION
            "This object indicates the type of the service carried by the PW."
        ::= { optixStaticUcEthPWEntry 21 }

    -- 1.3.6.1.4.1.2011.2.25.4.50.6.1.2.1.22
    optixEthPWSrvIndex OBJECT-TYPE
        SYNTAX Unsigned32
        MAX-ACCESS read-only
        STATUS current
        DESCRIPTION
            "This object indicates the index to the service carried by the PW."
        ::= { optixStaticUcEthPWEntry 22 }

    -- 1.3.6.1.4.1.2011.2.25.4.50.6.1.2.1.23
    optixEthPWSrvID OBJECT-TYPE
        SYNTAX Unsigned32
        MAX-ACCESS read-only
        STATUS current
        DESCRIPTION
            "This object indicates the ID of the service carried by the PW."
        ::= { optixStaticUcEthPWEntry 23 }

    -- 1.3.6.1.4.1.2011.2.25.4.50.6.1.2.1.24
    optixEthPWLocalState OBJECT-TYPE
        SYNTAX Unsigned32
        MAX-ACCESS read-only
        STATUS current
        DESCRIPTION
            "This object indicates the local state of the PW."
        ::= { optixStaticUcEthPWEntry 24 }

    -- 1.3.6.1.4.1.2011.2.25.4.50.6.1.2.1.25
    optixEthPWRemoteState OBJECT-TYPE
        SYNTAX Unsigned32
        MAX-ACCESS read-only
        STATUS current
        DESCRIPTION
            "This object indicates the remote state of the PW."
        ::= { optixStaticUcEthPWEntry 25 }

    -- 1.3.6.1.4.1.2011.2.25.4.50.6.1.2.1.26
    optixEthPWState OBJECT-TYPE
        SYNTAX Unsigned32
        MAX-ACCESS read-only
        STATUS current
        DESCRIPTION
            "This object indicates the PW state."
        ::= { optixStaticUcEthPWEntry 26 }

    -- 1.3.6.1.4.1.2011.2.25.4.50.6.1.2.1.255
    optixEthPWRowStatus OBJECT-TYPE
        SYNTAX RowStatus
        MAX-ACCESS read-create
        STATUS current
        DESCRIPTION
            "This object indicates the row status. 1: active 4: createAndGo 6: destroy"
        ::= { optixStaticUcEthPWEntry 255 }

    -- 1.3.6.1.4.1.2011.2.25.4.50.6.1.3
    optixStaticUcAtmPWTable OBJECT-TYPE
        SYNTAX SEQUENCE OF OptixStaticUcAtmPWEntry
        MAX-ACCESS not-accessible
        STATUS current
        DESCRIPTION
            "This table implements the configurations of static unicastATM PWs, including PW type, label, tunnels carried on the PW, CW, VCCV, and ATM concatenation."
        ::= { optixPWObject 3 }

    -- 1.3.6.1.4.1.2011.2.25.4.50.6.1.3.1
    optixStaticUcAtmPWEntry OBJECT-TYPE
        SYNTAX OptixStaticUcAtmPWEntry
        MAX-ACCESS not-accessible
        STATUS current
        DESCRIPTION
            "This entry indicates the parameter table of the static unicastATM PWs."
        INDEX{ optixAtmPWIndex }
        ::= { optixStaticUcAtmPWTable 1 }

    OptixStaticUcAtmPWEntry ::=
        SEQUENCE {
            optixAtmPWIndex
                Unsigned32,
            optixAtmPWtype
                INTEGER,
            optixAtmPWId
                Unsigned32,
            optixAtmPWDirection
                INTEGER,
            optixAtmPWPosition
                INTEGER,
            optixAtmPWInLabel
                Unsigned32,
            optixAtmPWOutLabel
                Unsigned32,
            optixAtmPWPeerIp
                IpAddress,
            optixAtmPWTunnelIndex
                Unsigned32,
            optixAtmPWVccvctrlChnlType
                INTEGER,
            optixAtmPWVccvCheckType
                INTEGER,
            optixAtmPWCtrlWord
                INTEGER,
            optixAtmPWExp
                Unsigned32,
            optixAtmPWLspMode
                INTEGER,
            optixAtmPWEnable
                INTEGER,
            optixAtmPWIngressIdBoundEgrTnl
                IpAddress,
            optixAtmPWEgressIdBoundEgrTnl
                IpAddress,
            optixAtmPWTunnelIdBoundEgrTnl
                Unsigned32,
            optixAtmPWMaxCellNum
                Unsigned32,
            optixAtmPWMaxLoadTime
                Unsigned32,
            optixAtmPWCheckRet
                INTEGER,
            optixAtmPWSrvType
                INTEGER,
            optixAtmPWSrvIndex
                Unsigned32,
            optixAtmPWSrvID
                Unsigned32,
            optixAtmPWLocalState
                Unsigned32,
            optixAtmPWRemoteState
                Unsigned32,
            optixAtmPWState
                Unsigned32,
            optixAtmPWRowStatus
                RowStatus
        }

    -- 1.3.6.1.4.1.2011.2.25.4.50.6.1.3.1.1
    optixAtmPWIndex OBJECT-TYPE
        SYNTAX Unsigned32
        MAX-ACCESS not-accessible
        STATUS current
        DESCRIPTION
            "This object indicates the PW index, ranging from 1 to 0x00ffffff."
        ::= { optixStaticUcAtmPWEntry 1 }

    -- 1.3.6.1.4.1.2011.2.25.4.50.6.1.3.1.2
    optixAtmPWtype OBJECT-TYPE
        SYNTAX INTEGER
        {
            atmtrans(3),
            atmnto1vcc(9),
            atmnto1vpc(10),
            atm1to1vcc(12),
            atm1to1vpc(13)
        }
        MAX-ACCESS read-create
        STATUS current
        DESCRIPTION
            "This object indcates the PW type. 0x0003: atm-trans 0x0009: atm-nto1-vcc 0x000A: atm-nto1-vpc 0x000C: atm-1to1-vcc 0x000D: atm-1to1-vpc"
        ::= { optixStaticUcAtmPWEntry 2 }

    -- 1.3.6.1.4.1.2011.2.25.4.50.6.1.3.1.3
    optixAtmPWId OBJECT-TYPE
        SYNTAX Unsigned32
        MAX-ACCESS read-create
        STATUS current
        DESCRIPTION
            "This object indicates the PW ID."
        ::= { optixStaticUcAtmPWEntry 3 }

    -- 1.3.6.1.4.1.2011.2.25.4.50.6.1.3.1.4
    optixAtmPWDirection OBJECT-TYPE
        SYNTAX INTEGER
        {
            uni(2),
            bi(1)
        }
        MAX-ACCESS read-create
        STATUS current
        DESCRIPTION
            "This object indicates the PW direction. 1: bi 2: uni"
        DEFVAL{ 1 }
        ::= { optixStaticUcAtmPWEntry 4 }

    -- 1.3.6.1.4.1.2011.2.25.4.50.6.1.3.1.5
    optixAtmPWPosition OBJECT-TYPE
        SYNTAX INTEGER
        {
            null(0),
            ingress(1),
            egress(2)
        }
        MAX-ACCESS read-create
        STATUS current
        DESCRIPTION
            "This object indicates the node location. 0: null 1: ingress 2: egress"
        DEFVAL{ 0 }
        ::= { optixStaticUcAtmPWEntry 5 }

    -- 1.3.6.1.4.1.2011.2.25.4.50.6.1.3.1.6
    optixAtmPWInLabel OBJECT-TYPE
        SYNTAX Unsigned32
        MAX-ACCESS read-create
        STATUS current
        DESCRIPTION
            "This object indicates the ingress label."
        ::= { optixStaticUcAtmPWEntry 6 }

    -- 1.3.6.1.4.1.2011.2.25.4.50.6.1.3.1.7
    optixAtmPWOutLabel OBJECT-TYPE
        SYNTAX Unsigned32
        MAX-ACCESS read-create
        STATUS current
        DESCRIPTION
            "This object indicates the egress label."
        ::= { optixStaticUcAtmPWEntry 7 }

    -- 1.3.6.1.4.1.2011.2.25.4.50.6.1.3.1.8
    optixAtmPWPeerIp OBJECT-TYPE
        SYNTAX IpAddress
        MAX-ACCESS read-create
        STATUS current
        DESCRIPTION
            "This object indicates the peer IP address."
        ::= { optixStaticUcAtmPWEntry 8 }

    -- 1.3.6.1.4.1.2011.2.25.4.50.6.1.3.1.9
    optixAtmPWTunnelIndex OBJECT-TYPE
        SYNTAX Unsigned32
        MAX-ACCESS read-create
        STATUS current
        DESCRIPTION
            "This object indicates the index to the tunnel carried through the PW."
        ::= { optixStaticUcAtmPWEntry 9 }

    -- 1.3.6.1.4.1.2011.2.25.4.50.6.1.3.1.10
    optixAtmPWVccvctrlChnlType OBJECT-TYPE
        SYNTAX INTEGER
        {
            none(0),
            cw(1),
            alertlabel(2),
            ttl(3)
        }
        MAX-ACCESS read-create
        STATUS current
        DESCRIPTION
            "This object indicates the control channel type. 0: none 1: cw 2: alertlabel 4: ttl"
        DEFVAL{ 1 }
        ::= { optixStaticUcAtmPWEntry 10 }

    -- 1.3.6.1.4.1.2011.2.25.4.50.6.1.3.1.11
    optixAtmPWVccvCheckType OBJECT-TYPE
        SYNTAX INTEGER
        {
            none(0),
            ping(1),
            bfd(2)
        }
        MAX-ACCESS read-create
        STATUS current
        DESCRIPTION
            "This object indicates the verification mode. 0: none 1: ping 2: bfd"
        DEFVAL{ 1 }
        ::= { optixStaticUcAtmPWEntry 11 }

    -- 1.3.6.1.4.1.2011.2.25.4.50.6.1.3.1.12
    optixAtmPWCtrlWord OBJECT-TYPE
        SYNTAX INTEGER
        {
            notuse(1),
            fstuse(2),
            mstuse(3)
        }
        MAX-ACCESS read-create
        STATUS current
        DESCRIPTION
            "This object indicates the usage policy of the control word. 1: not-use 2: frt-use 3: mst-use"
        DEFVAL{ 2 }
        ::= { optixStaticUcAtmPWEntry 12 }

    -- 1.3.6.1.4.1.2011.2.25.4.50.6.1.3.1.13
    optixAtmPWExp OBJECT-TYPE
        SYNTAX Unsigned32(0..7|255)
        MAX-ACCESS read-create
        STATUS current
        DESCRIPTION
            "This object indicates the EXP value. (Only upstream EXPs are supported.) Valid values:0-7. 0xff: none"
        DEFVAL{ 255 }
        ::= { optixStaticUcAtmPWEntry 13 }

    -- 1.3.6.1.4.1.2011.2.25.4.50.6.1.3.1.14
    optixAtmPWLspMode OBJECT-TYPE
        SYNTAX INTEGER
        {
            uniform(1),
            pipe(2),
            none(255)
        }
        MAX-ACCESS read-create
        STATUS current
        DESCRIPTION
            "This object indicates the LSP mode.(Only the downstream LSPis supported.) 1: uniform 2: pipe 255: none (The LSP mode is invalid upstream.)"
        ::= { optixStaticUcAtmPWEntry 14 }

    -- 1.3.6.1.4.1.2011.2.25.4.50.6.1.3.1.15
    optixAtmPWEnable OBJECT-TYPE
        SYNTAX INTEGER
        {
            disable(0),
            enable(1)
        }
        MAX-ACCESS read-create
        STATUS current
        DESCRIPTION
            "This object indicates the enable status of the PW. 0: disable 1: enable"
        DEFVAL{ 1 }
        ::= { optixStaticUcAtmPWEntry 15 }

    -- 1.3.6.1.4.1.2011.2.25.4.50.6.1.3.1.16
    optixAtmPWIngressIdBoundEgrTnl OBJECT-TYPE
        SYNTAX IpAddress
        MAX-ACCESS read-create
        STATUS current
        DESCRIPTION
            "This object indicates the source node ID of the bound egress tunnel."
        DEFVAL{ 0 }
        ::= { optixStaticUcAtmPWEntry 16 }

    -- 1.3.6.1.4.1.2011.2.25.4.50.6.1.3.1.17
    optixAtmPWEgressIdBoundEgrTnl OBJECT-TYPE
        SYNTAX IpAddress
        MAX-ACCESS read-create
        STATUS current
        DESCRIPTION
            "This object indicates the sink node ID of the bound egress tunnel."
        DEFVAL{ 0 }
        ::= { optixStaticUcAtmPWEntry 17 }

    -- 1.3.6.1.4.1.2011.2.25.4.50.6.1.3.1.18
    optixAtmPWTunnelIdBoundEgrTnl OBJECT-TYPE
        SYNTAX Unsigned32
        MAX-ACCESS read-create
        STATUS current
        DESCRIPTION
            "Thisobject indicates the bound egress tunnel ID."
        DEFVAL{ 0 }
        ::= { optixStaticUcAtmPWEntry 18 }

    -- 1.3.6.1.4.1.2011.2.25.4.50.6.1.3.1.19
    optixAtmPWMaxCellNum OBJECT-TYPE
        SYNTAX Unsigned32(1..31)
        MAX-ACCESS read-create
        STATUS current
        DESCRIPTION
            "This object indicates the maximum number of concatenate ATM cells. Valid values range from 1 to 31. 1: The ATM concatenation is disabled."
        ::= { optixStaticUcAtmPWEntry 19 }

    -- 1.3.6.1.4.1.2011.2.25.4.50.6.1.3.1.20
    optixAtmPWMaxLoadTime OBJECT-TYPE
        SYNTAX Unsigned32(0|10..50000)
        MAX-ACCESS read-create
        STATUS current
        DESCRIPTION
            "This object indicates the longest waiting time for ATM concatenation. Valid values:100-50000. 0: The ATM concatenation is disabled. Unit:us; step: 100."
        ::= { optixStaticUcAtmPWEntry 20 }

    -- 1.3.6.1.4.1.2011.2.25.4.50.6.1.3.1.21
    optixAtmPWCheckRet OBJECT-TYPE
        SYNTAX INTEGER
        {
            normal(0),
            abnormal(1)
        }
        MAX-ACCESS read-only
        STATUS current
        DESCRIPTION
            "This object indicates the PW check result."
        ::= { optixStaticUcAtmPWEntry 21 }

    -- 1.3.6.1.4.1.2011.2.25.4.50.6.1.3.1.22
    optixAtmPWSrvType OBJECT-TYPE
        SYNTAX INTEGER
        {
            ces(1),
            atmPwe3(2),
            eLine(3),
            eLan(4),
            eAggr(5),
            eTree(6),
            mirror(7),
            msPw(8),
            ptp1588(9),
            top(10)
        }
        MAX-ACCESS read-only
        STATUS current
        DESCRIPTION
            "This object indicates the type of the service carried by the PW."
        ::= { optixStaticUcAtmPWEntry 22 }

    -- 1.3.6.1.4.1.2011.2.25.4.50.6.1.3.1.23
    optixAtmPWSrvIndex OBJECT-TYPE
        SYNTAX Unsigned32
        MAX-ACCESS read-only
        STATUS current
        DESCRIPTION
            "This object indicates the index to the service carried by the PW."
        ::= { optixStaticUcAtmPWEntry 23 }

    -- 1.3.6.1.4.1.2011.2.25.4.50.6.1.3.1.24
    optixAtmPWSrvID OBJECT-TYPE
        SYNTAX Unsigned32
        MAX-ACCESS read-only
        STATUS current
        DESCRIPTION
            "This object indicates the ID of the service carried by the PW."
        ::= { optixStaticUcAtmPWEntry 24 }

    -- 1.3.6.1.4.1.2011.2.25.4.50.6.1.3.1.25
    optixAtmPWLocalState OBJECT-TYPE
        SYNTAX Unsigned32
        MAX-ACCESS read-only
        STATUS current
        DESCRIPTION
            "This object indicates the local state of the PW."
        ::= { optixStaticUcAtmPWEntry 25 }

    -- 1.3.6.1.4.1.2011.2.25.4.50.6.1.3.1.26
    optixAtmPWRemoteState OBJECT-TYPE
        SYNTAX Unsigned32
        MAX-ACCESS read-only
        STATUS current
        DESCRIPTION
            "This object indicates the remote state of the PW."
        ::= { optixStaticUcAtmPWEntry 26 }

    -- 1.3.6.1.4.1.2011.2.25.4.50.6.1.3.1.27
    optixAtmPWState OBJECT-TYPE
        SYNTAX Unsigned32
        MAX-ACCESS read-only
        STATUS current
        DESCRIPTION
            "This object indicates the PW state."
        ::= { optixStaticUcAtmPWEntry 27 }

    -- 1.3.6.1.4.1.2011.2.25.4.50.6.1.3.1.255
    optixAtmPWRowStatus OBJECT-TYPE
        SYNTAX RowStatus
        MAX-ACCESS read-create
        STATUS current
        DESCRIPTION
            "This object indicates the row status. 1: active 4: createAndGo 6: destroy"
        ::= { optixStaticUcAtmPWEntry 255 }

    -- 1.3.6.1.4.1.2011.2.25.4.50.6.1.4
    optixStaticUcCesPWTable OBJECT-TYPE
        SYNTAX SEQUENCE OF OptixStaticUcCesPWEntry
        MAX-ACCESS not-accessible
        STATUS current
        DESCRIPTION
            "This table implements the PW configurations of the static unicast CES service. These configurations include thePW type, label, tunnels carried by the PW, CW, VCCV, SDH emulation level, enable status of the RTP header, packet loading time, and jitter buffer time."
        ::= { optixPWObject 4 }

    -- 1.3.6.1.4.1.2011.2.25.4.50.6.1.4.1
    optixStaticUcCesPWEntry OBJECT-TYPE
        SYNTAX OptixStaticUcCesPWEntry
        MAX-ACCESS not-accessible
        STATUS current
        DESCRIPTION
            "This entry indicates the parameter table of the static unicast CES PWs."
        INDEX{ optixCesPWIndex }
        ::= { optixStaticUcCesPWTable 1 }

    OptixStaticUcCesPWEntry ::=
        SEQUENCE {
            optixCesPWIndex
                Unsigned32,
            optixPCesPWtype
                INTEGER,
            optixCesPWId
                Unsigned32,
            optixCesPWDirection
                INTEGER,
            optixCesPWPosition
                INTEGER,
            optixCesPWInLabel
                Unsigned32,
            optixCesPWOutLabel
                Unsigned32,
            optixCesPWPeerIp
                IpAddress,
            optixCesPWTunnelIndex
                Unsigned32,
            optixCesPWVccvctrlChnlType
                INTEGER,
            optixCesPWVccvCheckType
                INTEGER,
            optixCesPWCtrlWord
                INTEGER,
            optixCesPWExp
                Unsigned32,
            optixCesPWLspMode
                INTEGER,
            optixCesPWEnable
                INTEGER,
            optixCesPWIngressIdBoundEgrTnl
                IpAddress,
            optixCesPWEgressIdBoundEgrTnl
                IpAddress,
            optixCesPWTunnelIdBoundEgrTnl
                Unsigned32,
            optixCesPWRtpHead
                INTEGER,
            optixCesPWLoadTime
                Unsigned32,
            optixCesPWJitterTime
                Unsigned32,
            optixCesPWEmulLevel
                INTEGER,
            optixCesPWPathNum
                Unsigned32,
            optixCesPWSNMode
                INTEGER,
            optixCesPWLMREnable
                INTEGER,
            optixCesPWInRbit
                Unsigned32,
            optixCesPWOutRbit
                Unsigned32,
            optixCesPWCheckRet
                INTEGER,
            optixCesPWSrvType
                INTEGER,
            optixCesPWSrvIndex
                Unsigned32,
            optixCesPWSrvID
                Unsigned32,
            optixCesPWLocalState
                Unsigned32,
            optixCesPWRemoteState
                Unsigned32,
            optixCesPWState
                Unsigned32,
            optixCesPWRowStatus
                RowStatus
        }

    -- 1.3.6.1.4.1.2011.2.25.4.50.6.1.4.1.1
    optixCesPWIndex OBJECT-TYPE
        SYNTAX Unsigned32
        MAX-ACCESS not-accessible
        STATUS current
        DESCRIPTION
            "This object indicates the PW index, ranging from 1 to 0x00ffffff."
        ::= { optixStaticUcCesPWEntry 1 }

    -- 1.3.6.1.4.1.2011.2.25.4.50.6.1.4.1.2
    optixPCesPWtype OBJECT-TYPE
        SYNTAX INTEGER
        {
            satop(17),
            cesopsn(21),
            cep(16)
        }
        MAX-ACCESS read-create
        STATUS current
        DESCRIPTION
            "This object indcates the PW type. 0x0011: satop-e1 0x0015: cesopsn 0x0010: cep"
        ::= { optixStaticUcCesPWEntry 2 }

    -- 1.3.6.1.4.1.2011.2.25.4.50.6.1.4.1.3
    optixCesPWId OBJECT-TYPE
        SYNTAX Unsigned32
        MAX-ACCESS read-create
        STATUS current
        DESCRIPTION
            "This object indicates the PW ID."
        ::= { optixStaticUcCesPWEntry 3 }

    -- 1.3.6.1.4.1.2011.2.25.4.50.6.1.4.1.4
    optixCesPWDirection OBJECT-TYPE
        SYNTAX INTEGER
        {
            uni(2),
            bi(1)
        }
        MAX-ACCESS read-create
        STATUS current
        DESCRIPTION
            "This object indicates the PW direction. 1: bi 2: uni}"
        DEFVAL{ 1 }
        ::= { optixStaticUcCesPWEntry 4 }

    -- 1.3.6.1.4.1.2011.2.25.4.50.6.1.4.1.5
    optixCesPWPosition OBJECT-TYPE
        SYNTAX INTEGER
        {
            null(0),
            ingress(1),
            egress(2)
        }
        MAX-ACCESS read-create
        STATUS current
        DESCRIPTION
            "This object indicates the node location. 0: null 1: ingress 2: egress"
        DEFVAL{ 0 }
        ::= { optixStaticUcCesPWEntry 5 }

    -- 1.3.6.1.4.1.2011.2.25.4.50.6.1.4.1.6
    optixCesPWInLabel OBJECT-TYPE
        SYNTAX Unsigned32
        MAX-ACCESS read-create
        STATUS current
        DESCRIPTION
            "This object indicates the ingress label."
        ::= { optixStaticUcCesPWEntry 6 }

    -- 1.3.6.1.4.1.2011.2.25.4.50.6.1.4.1.7
    optixCesPWOutLabel OBJECT-TYPE
        SYNTAX Unsigned32
        MAX-ACCESS read-create
        STATUS current
        DESCRIPTION
            "This object indicates the egress label."
        ::= { optixStaticUcCesPWEntry 7 }

    -- 1.3.6.1.4.1.2011.2.25.4.50.6.1.4.1.8
    optixCesPWPeerIp OBJECT-TYPE
        SYNTAX IpAddress
        MAX-ACCESS read-create
        STATUS current
        DESCRIPTION
            "This object indicates the peer IP address."
        ::= { optixStaticUcCesPWEntry 8 }

    -- 1.3.6.1.4.1.2011.2.25.4.50.6.1.4.1.9
    optixCesPWTunnelIndex OBJECT-TYPE
        SYNTAX Unsigned32
        MAX-ACCESS read-create
        STATUS current
        DESCRIPTION
            "This object indicates the index to the tunnel carried through the PW."
        ::= { optixStaticUcCesPWEntry 9 }

    -- 1.3.6.1.4.1.2011.2.25.4.50.6.1.4.1.10
    optixCesPWVccvctrlChnlType OBJECT-TYPE
        SYNTAX INTEGER
        {
            none(0),
            cw(1),
            alertlabel(2),
            ttl(3),
            cwaltlb(4)
        }
        MAX-ACCESS read-create
        STATUS current
        DESCRIPTION
            "This object indicates the control channel type. 0: none 1: cw 2: alertlabel 3: cwaltlb 4: ttl"
        ::= { optixStaticUcCesPWEntry 10 }

    -- 1.3.6.1.4.1.2011.2.25.4.50.6.1.4.1.11
    optixCesPWVccvCheckType OBJECT-TYPE
        SYNTAX INTEGER
        {
            none(0),
            ping(1),
            bfd(2),
            pingbfd(3)
        }
        MAX-ACCESS read-create
        STATUS current
        DESCRIPTION
            "This object indicates the verification mode. 0: none 1: ping 2: bfd 3 :pingbfd"
        ::= { optixStaticUcCesPWEntry 11 }

    -- 1.3.6.1.4.1.2011.2.25.4.50.6.1.4.1.12
    optixCesPWCtrlWord OBJECT-TYPE
        SYNTAX INTEGER
        {
            notuse(1),
            fstuse(2),
            mstuse(3)
        }
        MAX-ACCESS read-create
        STATUS current
        DESCRIPTION
            "This object indicates the usage policy of the control word. 1: not-use 2: frt-use 3: mst-use"
        DEFVAL{ 2 }
        ::= { optixStaticUcCesPWEntry 12 }

    -- 1.3.6.1.4.1.2011.2.25.4.50.6.1.4.1.13
    optixCesPWExp OBJECT-TYPE
        SYNTAX Unsigned32(0..7|255)
        MAX-ACCESS read-create
        STATUS current
        DESCRIPTION
            "This object indicates the EXP value. (Only upstream EXPs are supported.) Valid values:0-7. 0xff: none"
        DEFVAL{ 255 }
        ::= { optixStaticUcCesPWEntry 13 }

    -- 1.3.6.1.4.1.2011.2.25.4.50.6.1.4.1.14
    optixCesPWLspMode OBJECT-TYPE
        SYNTAX INTEGER
        {
            uniform(1),
            pipe(2),
            none(255)
        }
        MAX-ACCESS read-create
        STATUS current
        DESCRIPTION
            "This object indicates the LSP mode.(Only the downstream LSP is supported.) 1: uniform 2: pipe 255: none (the LSP mode is invalid upstream.)"
        DEFVAL{ 1 }
        ::= { optixStaticUcCesPWEntry 14 }

    -- 1.3.6.1.4.1.2011.2.25.4.50.6.1.4.1.15
    optixCesPWEnable OBJECT-TYPE
        SYNTAX INTEGER
        {
            disable(0),
            enable(1)
        }
        MAX-ACCESS read-create
        STATUS current
        DESCRIPTION
            "This object indicates the enable status of the PW. 0: disable 1: enable"
        DEFVAL{ 1 }
        ::= { optixStaticUcCesPWEntry 15 }

    -- 1.3.6.1.4.1.2011.2.25.4.50.6.1.4.1.16
    optixCesPWIngressIdBoundEgrTnl OBJECT-TYPE
        SYNTAX IpAddress
        MAX-ACCESS read-create
        STATUS current
        DESCRIPTION
            "This object indicates the source node ID of the bound egress tunnel."
        DEFVAL{ 0 }
        ::= { optixStaticUcCesPWEntry 16 }

    -- 1.3.6.1.4.1.2011.2.25.4.50.6.1.4.1.17
    optixCesPWEgressIdBoundEgrTnl OBJECT-TYPE
        SYNTAX IpAddress
        MAX-ACCESS read-create
        STATUS current
        DESCRIPTION
            "This object indicates the sink node ID of the bound egress tunnel."
        DEFVAL{ 0 }
        ::= { optixStaticUcCesPWEntry 17 }

    -- 1.3.6.1.4.1.2011.2.25.4.50.6.1.4.1.18
    optixCesPWTunnelIdBoundEgrTnl OBJECT-TYPE
        SYNTAX Unsigned32
        MAX-ACCESS read-create
        STATUS current
        DESCRIPTION
            "This object indicates the bound egress tunnel ID."
        DEFVAL{ 0 }
        ::= { optixStaticUcCesPWEntry 18 }

    -- 1.3.6.1.4.1.2011.2.25.4.50.6.1.4.1.19
    optixCesPWRtpHead OBJECT-TYPE
        SYNTAX INTEGER
        {
            disable(0),
            ablehwrtp(1),
            enablestdrtp(2)
        }
        MAX-ACCESS read-create
        STATUS current
        DESCRIPTION
            "This object indicates the enable status of the RTP header encapsulation. 0: disable 1: enablehwrtp 2: enablestdrtp"
        DEFVAL{ 0 }
        ::= { optixStaticUcCesPWEntry 19 }

    -- 1.3.6.1.4.1.2011.2.25.4.50.6.1.4.1.20
    optixCesPWLoadTime OBJECT-TYPE
        SYNTAX Unsigned32(125..5000)
        MAX-ACCESS read-create
        STATUS current
        DESCRIPTION
            "This object indicates the packet loading time. Valid values: 125-5000 us; step: 125"
        DEFVAL{ 1000 }
        ::= { optixStaticUcCesPWEntry 20 }

    -- 1.3.6.1.4.1.2011.2.25.4.50.6.1.4.1.21
    optixCesPWJitterTime OBJECT-TYPE
        SYNTAX Unsigned32(125..64000)
        MAX-ACCESS read-create
        STATUS current
        DESCRIPTION
            "This object indicates the jitter buffer time. Valid values: 125-64000 us; step: 125"
        DEFVAL{ 8000 }
        ::= { optixStaticUcCesPWEntry 21 }

    -- 1.3.6.1.4.1.2011.2.25.4.50.6.1.4.1.22
    optixCesPWEmulLevel OBJECT-TYPE
        SYNTAX INTEGER
        {
            vc12(1),
            vc11(2),
            vc4(3),
            triplicatevc3(4)
        }
        MAX-ACCESS read-create
        STATUS current
        DESCRIPTION
            "This object indicates the CES emulation level. 1: vc12 2: vc11 3: vc4 4: vc4 (3 x vc3)"
        DEFVAL{ 1 }
        ::= { optixStaticUcCesPWEntry 22 }

    -- 1.3.6.1.4.1.2011.2.25.4.50.6.1.4.1.23
    optixCesPWPathNum OBJECT-TYPE
        SYNTAX Unsigned32(1..32)
        MAX-ACCESS read-create
        STATUS current
        DESCRIPTION
            "This object indicates the number of valid timeslots/channels. E1: 1-32; T1: 1-24; VC4: 1; VC4 (3 x VC3):3"
        DEFVAL{ 32 }
        ::= { optixStaticUcCesPWEntry 23 }

    -- 1.3.6.1.4.1.2011.2.25.4.50.6.1.4.1.24
    optixCesPWSNMode OBJECT-TYPE
        SYNTAX INTEGER
        {
            stdmode(0),
            hwmode(1)
        }
        MAX-ACCESS read-create
        STATUS current
        DESCRIPTION
            "This object indicates the serial-number mode. 0: stdmode; valid values range from 0 to 65535 and restart from 0. 1: hwmode; valid values range form 0 to 65535 and restart from 1."
        DEFVAL{ 1 }
        ::= { optixStaticUcCesPWEntry 24 }

    -- 1.3.6.1.4.1.2011.2.25.4.50.6.1.4.1.25
    optixCesPWLMREnable OBJECT-TYPE
        SYNTAX INTEGER
        {
            disable(0),
            enable(1)
        }
        MAX-ACCESS read-create
        STATUS current
        DESCRIPTION
            "This object indicates the processing status of the L, M, and R bits. 0: disable 1: enable"
        DEFVAL{ 0 }
        ::= { optixStaticUcCesPWEntry 25 }

    -- 1.3.6.1.4.1.2011.2.25.4.50.6.1.4.1.26
    optixCesPWInRbit OBJECT-TYPE
        SYNTAX Unsigned32(1..65535)
        MAX-ACCESS read-create
        STATUS current
        DESCRIPTION
            "This object indicates the threshold for entering the R bit insertion status. Valid values: 1-65535."
        DEFVAL{ 100 }
        ::= { optixStaticUcCesPWEntry 26 }

    -- 1.3.6.1.4.1.2011.2.25.4.50.6.1.4.1.27
    optixCesPWOutRbit OBJECT-TYPE
        SYNTAX Unsigned32(1..65535)
        MAX-ACCESS read-create
        STATUS current
        DESCRIPTION
            "Thisobject indicates the threshold forexiting the R bit insertion status. Valid values: 1-65535."
        DEFVAL{ 5 }
        ::= { optixStaticUcCesPWEntry 27 }

    -- 1.3.6.1.4.1.2011.2.25.4.50.6.1.4.1.28
    optixCesPWCheckRet OBJECT-TYPE
        SYNTAX INTEGER
        {
            normal(0),
            abnormal(1)
        }
        MAX-ACCESS read-only
        STATUS current
        DESCRIPTION
            "This object indicates the PW check result."
        ::= { optixStaticUcCesPWEntry 28 }

    -- 1.3.6.1.4.1.2011.2.25.4.50.6.1.4.1.29
    optixCesPWSrvType OBJECT-TYPE
        SYNTAX INTEGER
        {
            ces(1),
            atmPwe3(2),
            eLine(3),
            eLan(4),
            eAggr(5),
            eTree(6),
            mirror(7),
            msPw(8),
            ptp1588(9),
            top(10)
        }
        MAX-ACCESS read-only
        STATUS current
        DESCRIPTION
            "This object indicates the type of the service carried by the PW."
        ::= { optixStaticUcCesPWEntry 29 }

    -- 1.3.6.1.4.1.2011.2.25.4.50.6.1.4.1.30
    optixCesPWSrvIndex OBJECT-TYPE
        SYNTAX Unsigned32
        MAX-ACCESS read-only
        STATUS current
        DESCRIPTION
            "This object indicates the index to the service carried by the PW."
        ::= { optixStaticUcCesPWEntry 30 }

    -- 1.3.6.1.4.1.2011.2.25.4.50.6.1.4.1.31
    optixCesPWSrvID OBJECT-TYPE
        SYNTAX Unsigned32
        MAX-ACCESS read-only
        STATUS current
        DESCRIPTION
            "This object indicates the ID of the service carried by the PW."
        ::= { optixStaticUcCesPWEntry 31 }

    -- 1.3.6.1.4.1.2011.2.25.4.50.6.1.4.1.32
    optixCesPWLocalState OBJECT-TYPE
        SYNTAX Unsigned32
        MAX-ACCESS read-only
        STATUS current
        DESCRIPTION
            "This object indicates the local state of the PW."
        ::= { optixStaticUcCesPWEntry 32 }

    -- 1.3.6.1.4.1.2011.2.25.4.50.6.1.4.1.33
    optixCesPWRemoteState OBJECT-TYPE
        SYNTAX Unsigned32
        MAX-ACCESS read-only
        STATUS current
        DESCRIPTION
            "This object indicates the remote state of the PW."
        ::= { optixStaticUcCesPWEntry 33 }

    -- 1.3.6.1.4.1.2011.2.25.4.50.6.1.4.1.34
    optixCesPWState OBJECT-TYPE
        SYNTAX Unsigned32
        MAX-ACCESS read-only
        STATUS current
        DESCRIPTION
            "This object indicates the PW state."
        ::= { optixStaticUcCesPWEntry 34 }

    -- 1.3.6.1.4.1.2011.2.25.4.50.6.1.4.1.255
    optixCesPWRowStatus OBJECT-TYPE
        SYNTAX RowStatus
        MAX-ACCESS read-create
        STATUS current
        DESCRIPTION
            "This object indicates the row status. 1: active 4: createAndGo 6: destroy"
        ::= { optixStaticUcCesPWEntry 255 }

    -- 1.3.6.1.4.1.2011.2.25.4.50.6.1.5
    optixPWCrossTable OBJECT-TYPE
        SYNTAX SEQUENCE OF OptixPWCrossEntry
        MAX-ACCESS not-accessible
        STATUS current
        DESCRIPTION
            "This table is used to query the actual PW cross-connect and forwarding paths. One PW has two cross-connections, forward and backward."
        ::= { optixPWObject 5 }

    -- 1.3.6.1.4.1.2011.2.25.4.50.6.1.5.1
    optixPWCrossEntry OBJECT-TYPE
        SYNTAX OptixPWCrossEntry
        MAX-ACCESS not-accessible
        STATUS current
        DESCRIPTION
            "This entry is used to query the parameter table for actual PW cross-connections."
        INDEX{ optixPWIndex,optixPWCrossdirection }
        ::= { optixPWCrossTable 1 }

    OptixPWCrossEntry ::=
        SEQUENCE {
            optixPWIndex
                Unsigned32,
            optixPWCrossdirection
                INTEGER,
            optixPWCrossType
                INTEGER,
            optixPWCrossPWId
                Unsigned32,
            optixPWCrossPWGroupId
                Unsigned32,
            optixPWCrossPeerIp
                IpAddress,
            optixPWCrossSingalType
                INTEGER,
            optixPWCrossPosition
                INTEGER,
            optixPWCrossCtrlWord
                INTEGER,
            optixPWCrossVccvctrlChnlType
                INTEGER,
            optixPWCrossVccvCheckType
                INTEGER,
            optixPWCrossInLabel
                Unsigned32,
            optixPWCrossOutLabel
                Unsigned32,
            optixPWCrossTunnelIngressId
                IpAddress,
            optixPWCrossTunnelEgressId
                IpAddress,
            optixPWCrossTunnelId
                Unsigned32,
            optixPWCrossTunnelType
                INTEGER,
            optixPWCrossActiveStaus
                INTEGER
        }

    -- 1.3.6.1.4.1.2011.2.25.4.50.6.1.5.1.1
    optixPWIndex OBJECT-TYPE
        SYNTAX Unsigned32(1..16777215)
        MAX-ACCESS not-accessible
        STATUS current
        DESCRIPTION
            "This object indicates the PW index, ranging from 1 to 0x00ffffff."
        ::= { optixPWCrossEntry 1 }

    -- 1.3.6.1.4.1.2011.2.25.4.50.6.1.5.1.2
    optixPWCrossdirection OBJECT-TYPE
        SYNTAX INTEGER
        {
            posit(1),
            minus(2)
        }
        MAX-ACCESS not-accessible
        STATUS current
        DESCRIPTION
            "This object indicates the cross-connect direction. 1: forward 2: backward"
        ::= { optixPWCrossEntry 2 }

    -- 1.3.6.1.4.1.2011.2.25.4.50.6.1.5.1.4
    optixPWCrossType OBJECT-TYPE
        SYNTAX INTEGER
        {
            ethtag(4),
            ethraw(5),
            atmtrans(3),
            atmnto1vcc(9),
            atmnto1vpc(10),
            atm1to1vcc(12),
            atm1to1vpc(13),
            satop(17),
            cesopsn(21),
            cep(16),
            ip(4097)
        }
        MAX-ACCESS read-only
        STATUS current
        DESCRIPTION
            "This object indcates the PW type. 0x0003: atm-trans 0x0004: eth-tag 0x0005: eth-raw 0x0009: atm-nto1-vcc 0x000A: atm-nto1-vpc 0x000C: atm-1to1-vcc 0x000D: atm-1to1-vpc 0x0011: satop-e1 0x0015: cesopsn 0x0010: cep 0x1001: ip"
        ::= { optixPWCrossEntry 4 }

    -- 1.3.6.1.4.1.2011.2.25.4.50.6.1.5.1.5
    optixPWCrossPWId OBJECT-TYPE
        SYNTAX Unsigned32
        MAX-ACCESS read-only
        STATUS current
        DESCRIPTION
            "This object indicates the PW ID."
        ::= { optixPWCrossEntry 5 }

    -- 1.3.6.1.4.1.2011.2.25.4.50.6.1.5.1.6
    optixPWCrossPWGroupId OBJECT-TYPE
        SYNTAX Unsigned32
        MAX-ACCESS read-only
        STATUS current
        DESCRIPTION
            "This object indicates the group ID."
        ::= { optixPWCrossEntry 6 }

    -- 1.3.6.1.4.1.2011.2.25.4.50.6.1.5.1.7
    optixPWCrossPeerIp OBJECT-TYPE
        SYNTAX IpAddress
        MAX-ACCESS read-only
        STATUS current
        DESCRIPTION
            "This object indicates the peer IP address."
        ::= { optixPWCrossEntry 7 }

    -- 1.3.6.1.4.1.2011.2.25.4.50.6.1.5.1.8
    optixPWCrossSingalType OBJECT-TYPE
        SYNTAX INTEGER
        {
            static(1),
            ldp(2)
        }
        MAX-ACCESS read-only
        STATUS current
        DESCRIPTION
            "This object indicates the signaling type. 1: static; 2: dynamic LDP"
        ::= { optixPWCrossEntry 8 }

    -- 1.3.6.1.4.1.2011.2.25.4.50.6.1.5.1.9
    optixPWCrossPosition OBJECT-TYPE
        SYNTAX INTEGER
        {
            null(0),
            ingress(1),
            egress(2)
        }
        MAX-ACCESS read-only
        STATUS current
        DESCRIPTION
            "This object indicates the node location. 0: null, 1: ingress, 2: egress"
        ::= { optixPWCrossEntry 9 }

    -- 1.3.6.1.4.1.2011.2.25.4.50.6.1.5.1.10
    optixPWCrossCtrlWord OBJECT-TYPE
        SYNTAX INTEGER
        {
            notuse(1),
            fstuse(2),
            mstuse(3)
        }
        MAX-ACCESS read-only
        STATUS current
        DESCRIPTION
            "This object indicates the control word type. 1: notuse, 2: fstuse, 3: mstuse"
        ::= { optixPWCrossEntry 10 }

    -- 1.3.6.1.4.1.2011.2.25.4.50.6.1.5.1.11
    optixPWCrossVccvctrlChnlType OBJECT-TYPE
        SYNTAX INTEGER
        {
            none(0),
            cw(1),
            alertlabel(2),
            ttl(3)
        }
        MAX-ACCESS read-only
        STATUS current
        DESCRIPTION
            "This object indicates the VCCV control channel type. 0: none, 1: cw, 2: alertlabel, 3: ttl"
        ::= { optixPWCrossEntry 11 }

    -- 1.3.6.1.4.1.2011.2.25.4.50.6.1.5.1.12
    optixPWCrossVccvCheckType OBJECT-TYPE
        SYNTAX INTEGER
        {
            none(0),
            ping(1),
            bfd(2)
        }
        MAX-ACCESS read-only
        STATUS current
        DESCRIPTION
            "This object indicates the VCCV verification mode. 0: none, 1: ping, 2: bfd"
        ::= { optixPWCrossEntry 12 }

    -- 1.3.6.1.4.1.2011.2.25.4.50.6.1.5.1.13
    optixPWCrossInLabel OBJECT-TYPE
        SYNTAX Unsigned32
        MAX-ACCESS read-only
        STATUS current
        DESCRIPTION
            "This object indicates the ingress label. The forward cross-connection value is 0xffffffff."
        ::= { optixPWCrossEntry 13 }

    -- 1.3.6.1.4.1.2011.2.25.4.50.6.1.5.1.14
    optixPWCrossOutLabel OBJECT-TYPE
        SYNTAX Unsigned32
        MAX-ACCESS read-only
        STATUS current
        DESCRIPTION
            "This object indicates the ingress label. The backward cross-connection value is 0xffffffff."
        ::= { optixPWCrossEntry 14 }

    -- 1.3.6.1.4.1.2011.2.25.4.50.6.1.5.1.15
    optixPWCrossTunnelIngressId OBJECT-TYPE
        SYNTAX IpAddress
        MAX-ACCESS read-only
        STATUS current
        DESCRIPTION
            "This object indicates the ingress tunnel ID to which the PW belongs."
        ::= { optixPWCrossEntry 15 }

    -- 1.3.6.1.4.1.2011.2.25.4.50.6.1.5.1.16
    optixPWCrossTunnelEgressId OBJECT-TYPE
        SYNTAX IpAddress
        MAX-ACCESS read-only
        STATUS current
        DESCRIPTION
            "This object indicates the egress tunnel ID to which the PW belongs."
        ::= { optixPWCrossEntry 16 }

    -- 1.3.6.1.4.1.2011.2.25.4.50.6.1.5.1.17
    optixPWCrossTunnelId OBJECT-TYPE
        SYNTAX Unsigned32
        MAX-ACCESS read-only
        STATUS current
        DESCRIPTION
            "This object indicates the tunnel ID to which the PW belongs."
        ::= { optixPWCrossEntry 17 }

    -- 1.3.6.1.4.1.2011.2.25.4.50.6.1.5.1.18
    optixPWCrossTunnelType OBJECT-TYPE
        SYNTAX INTEGER
        {
            mpls(0),
            pbt(1),
            ip(2),
            gre(3)
        }
        MAX-ACCESS read-only
        STATUS current
        DESCRIPTION
            "This object indicates the type of the tunnel to which the PW belongs. 0: mpls 1: pbt 2: ip 3: gre"
        ::= { optixPWCrossEntry 18 }

    -- 1.3.6.1.4.1.2011.2.25.4.50.6.1.5.1.19
    optixPWCrossActiveStaus OBJECT-TYPE
        SYNTAX INTEGER
        {
            noactive(0),
            active(1)
        }
        MAX-ACCESS read-only
        STATUS current
        DESCRIPTION
            "This object indicates the activation status of the PW cross-connection. 0: deactive 1: active"
        ::= { optixPWCrossEntry 19 }

    -- 1.3.6.1.4.1.2011.2.25.4.50.6.1.6
    optixDynLdpPWTable OBJECT-TYPE
        SYNTAX SEQUENCE OF OptixDynLdpPWEntry
        MAX-ACCESS not-accessible
        STATUS current
        DESCRIPTION
            "This table implements the configurations of a dynamic PW."
        ::= { optixPWObject 6 }

    -- 1.3.6.1.4.1.2011.2.25.4.50.6.1.6.1
    optixDynLdpPWEntry OBJECT-TYPE
        SYNTAX OptixDynLdpPWEntry
        MAX-ACCESS not-accessible
        STATUS current
        DESCRIPTION
            "This node describes an entity of the dynamic PW parameter table."
        INDEX{ optixDynLdpPWIndex }
        ::= { optixDynLdpPWTable 1 }

    OptixDynLdpPWEntry ::=
        SEQUENCE {
            optixDynLdpPWIndex
                Unsigned32,
            optixDynLdpPWtype
                INTEGER,
            optixDynLdpPWId
                Unsigned32,
            optixDynLdpPWDirection
                INTEGER,
            optixDynLdpPWPosition
                INTEGER,
            optixDynLdpPWInLabel
                Unsigned32,
            optixDynLdpPWOutLabel
                Unsigned32,
            optixDynLdpPWPeerIp
                IpAddress,
            optixDynLdpPWTunnelIndex
                Unsigned32,
            optixDynLdpPWCWEn
                INTEGER,
            optixDynLdpPWCCType
                INTEGER,
            optixDynLdpPWCVType
                INTEGER,
            optixDynLdpPWATMCellNum
                Unsigned32,
            optixDynLdpPWCESRTP
                INTEGER,
            optixDynLdpPWErrCode
                Unsigned32,
            optixDynLdpPWRowStatus
                RowStatus
        }

    -- 1.3.6.1.4.1.2011.2.25.4.50.6.1.6.1.1
    optixDynLdpPWIndex OBJECT-TYPE
        SYNTAX Unsigned32
        MAX-ACCESS not-accessible
        STATUS current
        DESCRIPTION
            "This object describes the index of a dynamic PW."
        ::= { optixDynLdpPWEntry 1 }

    -- 1.3.6.1.4.1.2011.2.25.4.50.6.1.6.1.2
    optixDynLdpPWtype OBJECT-TYPE
        SYNTAX INTEGER
        {
            ethraw(5),
            ethtag(4),
            atmtrans(3),
            atmnto1vcc(9),
            atmnto1vpc(10),
            atm1to1vcc(12),
            atm1to1vpc(13),
            satope1(17),
            cesopsnbas(21)
        }
        MAX-ACCESS read-create
        STATUS current
        DESCRIPTION
            "This object describes the type of a dynamic PW."
        ::= { optixDynLdpPWEntry 2 }

    -- 1.3.6.1.4.1.2011.2.25.4.50.6.1.6.1.3
    optixDynLdpPWId OBJECT-TYPE
        SYNTAX Unsigned32
        MAX-ACCESS read-create
        STATUS current
        DESCRIPTION
            "This object describes the ID of a dynamic PW."
        ::= { optixDynLdpPWEntry 3 }

    -- 1.3.6.1.4.1.2011.2.25.4.50.6.1.6.1.4
    optixDynLdpPWDirection OBJECT-TYPE
        SYNTAX INTEGER
        {
            uni(2),
            bi(1)
        }
        MAX-ACCESS read-create
        STATUS current
        DESCRIPTION
            "This object describes the direction of a dynamic PW."
        ::= { optixDynLdpPWEntry 4 }

    -- 1.3.6.1.4.1.2011.2.25.4.50.6.1.6.1.5
    optixDynLdpPWPosition OBJECT-TYPE
        SYNTAX INTEGER
        {
            null(0),
            ingress(1),
            egress(2)
        }
        MAX-ACCESS read-create
        STATUS current
        DESCRIPTION
            "This object describes the node location of a dynamic PW. 0: null 1: ingress 2: egress"
        ::= { optixDynLdpPWEntry 5 }

    -- 1.3.6.1.4.1.2011.2.25.4.50.6.1.6.1.6
    optixDynLdpPWInLabel OBJECT-TYPE
        SYNTAX Unsigned32
        MAX-ACCESS read-only
        STATUS current
        DESCRIPTION
            "This object describes the ingress label of a dynamic PW."
        ::= { optixDynLdpPWEntry 6 }

    -- 1.3.6.1.4.1.2011.2.25.4.50.6.1.6.1.7
    optixDynLdpPWOutLabel OBJECT-TYPE
        SYNTAX Unsigned32
        MAX-ACCESS read-only
        STATUS current
        DESCRIPTION
            "This object describes the egress label of a dynamic PW."
        ::= { optixDynLdpPWEntry 7 }

    -- 1.3.6.1.4.1.2011.2.25.4.50.6.1.6.1.8
    optixDynLdpPWPeerIp OBJECT-TYPE
        SYNTAX IpAddress
        MAX-ACCESS read-create
        STATUS current
        DESCRIPTION
            "This object describes the peer IP address of a dynamic PW."
        ::= { optixDynLdpPWEntry 8 }

    -- 1.3.6.1.4.1.2011.2.25.4.50.6.1.6.1.9
    optixDynLdpPWTunnelIndex OBJECT-TYPE
        SYNTAX Unsigned32
        MAX-ACCESS read-create
        STATUS current
        DESCRIPTION
            "This object describes the index to the tunnel carried over the PW."
        ::= { optixDynLdpPWEntry 9 }

    -- 1.3.6.1.4.1.2011.2.25.4.50.6.1.6.1.10
    optixDynLdpPWCWEn OBJECT-TYPE
        SYNTAX INTEGER
        {
            disable(0),
            enable(1)
        }
        MAX-ACCESS read-only
        STATUS current
        DESCRIPTION
            "This object describes whether to enable the control word of the VCCV."
        ::= { optixDynLdpPWEntry 10 }

    -- 1.3.6.1.4.1.2011.2.25.4.50.6.1.6.1.11
    optixDynLdpPWCCType OBJECT-TYPE
        SYNTAX INTEGER
        {
            none(0),
            cw(1),
            altlb(2),
            ttl(3),
            cwaltlb(4)
        }
        MAX-ACCESS read-only
        STATUS current
        DESCRIPTION
            "This object describes the control channel type of the VCCV."
        ::= { optixDynLdpPWEntry 11 }

    -- 1.3.6.1.4.1.2011.2.25.4.50.6.1.6.1.12
    optixDynLdpPWCVType OBJECT-TYPE
        SYNTAX INTEGER
        {
            none(0),
            ping(1),
            bfd(2),
            pingbfd(3)
        }
        MAX-ACCESS read-only
        STATUS current
        DESCRIPTION
            "This object describes the check mode of the VCCV."
        ::= { optixDynLdpPWEntry 12 }

    -- 1.3.6.1.4.1.2011.2.25.4.50.6.1.6.1.13
    optixDynLdpPWATMCellNum OBJECT-TYPE
        SYNTAX Unsigned32
        MAX-ACCESS read-only
        STATUS current
        DESCRIPTION
            "This object describes the actual number of cascaded ATM cells of a dynamic PW."
        ::= { optixDynLdpPWEntry 13 }

    -- 1.3.6.1.4.1.2011.2.25.4.50.6.1.6.1.14
    optixDynLdpPWCESRTP OBJECT-TYPE
        SYNTAX INTEGER
        {
            disable(0),
            enablehwrtp(1),
            enablestdrtp(2)
        }
        MAX-ACCESS read-only
        STATUS current
        DESCRIPTION
            "This object describes whether the RTP header encapsulation is enabled on a dynamic PW."
        ::= { optixDynLdpPWEntry 14 }

    -- 1.3.6.1.4.1.2011.2.25.4.50.6.1.6.1.15
    optixDynLdpPWErrCode OBJECT-TYPE
        SYNTAX Unsigned32
        MAX-ACCESS read-only
        STATUS current
        DESCRIPTION
            "This object describes the error code of a dynamic pw. 57385:MTU negotiation failure between local end and remote end, 57386:Control word mode negotiation failure between local end and remote end, 57387:RTP enable/disable negotiation failure between local end and remote end, 57388:Payload size negotiation failure between local end and remote end, 57389:Bit rate negotiation failure between local end and remote end, 57390:PW GR restoration failure, 57391:PW cancellation message received from remote end, 58347:The PW status is down because the session status is down, 58348:The PW status is down because the AC status is down, 58349:The PW status is down because the tunnel status is down, 58350:The PW status is down because the remote status is down"
        ::= { optixDynLdpPWEntry 15 }

    -- 1.3.6.1.4.1.2011.2.25.4.50.6.1.6.1.255
    optixDynLdpPWRowStatus OBJECT-TYPE
        SYNTAX RowStatus
        MAX-ACCESS read-create
        STATUS current
        DESCRIPTION
            "This object describes the row status. 1: active 4: createAndGo 6: destroy."
        ::= { optixDynLdpPWEntry 255 }

    -- 1.3.6.1.4.1.2011.2.25.4.50.6.1.7
    optixDynPWBFDTable OBJECT-TYPE
        SYNTAX SEQUENCE OF OptixDynPWBFDEntry
        MAX-ACCESS not-accessible
        STATUS current
        DESCRIPTION
            "This table implements the configurations of a BFD session for dynamic PWs."
        ::= { optixPWObject 7 }

    -- 1.3.6.1.4.1.2011.2.25.4.50.6.1.7.1
    optixDynPWBFDEntry OBJECT-TYPE
        SYNTAX OptixDynPWBFDEntry
        MAX-ACCESS not-accessible
        STATUS current
        DESCRIPTION
            "This entry describes an entity of the BFD session parameter table."
        INDEX{ optixDynLdpPWIndex }
        ::= { optixDynPWBFDTable 1 }

    OptixDynPWBFDEntry ::=
        SEQUENCE {
            optixDynPWBFDSessionName
                OCTET STRING,
            optixDynPWBFDLocalMark
                Unsigned32,
            optixDynPWBFDRemoteMark
                Unsigned32,
            optixDynPWBFDPeerIP
                IpAddress,
            optixDynPWBFDAutoCalc
                Unsigned32,
            optixDynPWBFDTTL
                Unsigned32,
            optixDynPWBFDSessionType
                Unsigned32,
            optixDynPWBFDMinRxInterval
                Unsigned32,
            optixDynPWBFDMinTxInterval
                Unsigned32,
            optixDynPWBFDMultiplier
                Unsigned32,
            optixDynPWBFDTosExp
                Unsigned32,
            optixDynPWBFDWtr
                Unsigned32,
            optixDynPWBFDShutdown
                INTEGER,
            optixDynPWBFDState
                Unsigned32,
            optixDynPWBFDRowStatus
                RowStatus
        }

    -- 1.3.6.1.4.1.2011.2.25.4.50.6.1.7.1.1
    optixDynPWBFDSessionName OBJECT-TYPE
        SYNTAX OCTET STRING
        MAX-ACCESS read-create
        STATUS current
        DESCRIPTION
            "This object describes the name of a BFD session."
        ::= { optixDynPWBFDEntry 1 }

    -- 1.3.6.1.4.1.2011.2.25.4.50.6.1.7.1.2
    optixDynPWBFDLocalMark OBJECT-TYPE
        SYNTAX Unsigned32
        MAX-ACCESS read-create
        STATUS current
        DESCRIPTION
            "This object describes the local label of a BFD session."
        ::= { optixDynPWBFDEntry 2 }

    -- 1.3.6.1.4.1.2011.2.25.4.50.6.1.7.1.3
    optixDynPWBFDRemoteMark OBJECT-TYPE
        SYNTAX Unsigned32
        MAX-ACCESS read-create
        STATUS current
        DESCRIPTION
            "This object describes the remote label of a BFD session."
        ::= { optixDynPWBFDEntry 3 }

    -- 1.3.6.1.4.1.2011.2.25.4.50.6.1.7.1.4
    optixDynPWBFDPeerIP OBJECT-TYPE
        SYNTAX IpAddress
        MAX-ACCESS read-create
        STATUS current
        DESCRIPTION
            "This object describes the sink IP address of a BFD session."
        ::= { optixDynPWBFDEntry 4 }

    -- 1.3.6.1.4.1.2011.2.25.4.50.6.1.7.1.5
    optixDynPWBFDAutoCalc OBJECT-TYPE
        SYNTAX Unsigned32
        MAX-ACCESS read-create
        STATUS current
        DESCRIPTION
            "This object describes whether the auto calculation of the number of PW hops is enabled."
        ::= { optixDynPWBFDEntry 5 }

    -- 1.3.6.1.4.1.2011.2.25.4.50.6.1.7.1.6
    optixDynPWBFDTTL OBJECT-TYPE
        SYNTAX Unsigned32
        MAX-ACCESS read-create
        STATUS current
        DESCRIPTION
            "This object describes the number of PW hops detected in a BFD session."
        ::= { optixDynPWBFDEntry 6 }

    -- 1.3.6.1.4.1.2011.2.25.4.50.6.1.7.1.7
    optixDynPWBFDSessionType OBJECT-TYPE
        SYNTAX Unsigned32
        MAX-ACCESS read-only
        STATUS current
        DESCRIPTION
            "This object describes the type of a BFD session."
        ::= { optixDynPWBFDEntry 7 }

    -- 1.3.6.1.4.1.2011.2.25.4.50.6.1.7.1.8
    optixDynPWBFDMinRxInterval OBJECT-TYPE
        SYNTAX Unsigned32
        MAX-ACCESS read-create
        STATUS current
        DESCRIPTION
            "This object describes the minimum interval expected by the NE to receive BFD packets."
        ::= { optixDynPWBFDEntry 8 }

    -- 1.3.6.1.4.1.2011.2.25.4.50.6.1.7.1.9
    optixDynPWBFDMinTxInterval OBJECT-TYPE
        SYNTAX Unsigned32
        MAX-ACCESS read-create
        STATUS current
        DESCRIPTION
            "This object describes the minimum interval expected by the NE to transmit BFD packets."
        ::= { optixDynPWBFDEntry 9 }

    -- 1.3.6.1.4.1.2011.2.25.4.50.6.1.7.1.10
    optixDynPWBFDMultiplier OBJECT-TYPE
        SYNTAX Unsigned32
        MAX-ACCESS read-create
        STATUS current
        DESCRIPTION
            "This object describes the local detection multiplier for the BFD session."
        ::= { optixDynPWBFDEntry 10 }

    -- 1.3.6.1.4.1.2011.2.25.4.50.6.1.7.1.11
    optixDynPWBFDTosExp OBJECT-TYPE
        SYNTAX Unsigned32
        MAX-ACCESS read-create
        STATUS current
        DESCRIPTION
            "This object describes the priority of a BFD packet."
        ::= { optixDynPWBFDEntry 11 }

    -- 1.3.6.1.4.1.2011.2.25.4.50.6.1.7.1.12
    optixDynPWBFDWtr OBJECT-TYPE
        SYNTAX Unsigned32
        MAX-ACCESS read-create
        STATUS current
        DESCRIPTION
            "This object describes the wait-to-recovery time for the BFD session."
        ::= { optixDynPWBFDEntry 12 }

    -- 1.3.6.1.4.1.2011.2.25.4.50.6.1.7.1.13
    optixDynPWBFDShutdown OBJECT-TYPE
        SYNTAX INTEGER
        {
            on(1),
            off(2)
        }
        MAX-ACCESS read-create
        STATUS current
        DESCRIPTION
            "This object describes the BFD session testing status."
        ::= { optixDynPWBFDEntry 13 }

    -- 1.3.6.1.4.1.2011.2.25.4.50.6.1.7.1.14
    optixDynPWBFDState OBJECT-TYPE
        SYNTAX Unsigned32
        MAX-ACCESS read-only
        STATUS current
        DESCRIPTION
            "This object describes the status of a BFD session."
        ::= { optixDynPWBFDEntry 14 }

    -- 1.3.6.1.4.1.2011.2.25.4.50.6.1.7.1.255
    optixDynPWBFDRowStatus OBJECT-TYPE
        SYNTAX RowStatus
        MAX-ACCESS read-create
        STATUS current
        DESCRIPTION
            "This object describes the row status. 1: active 4: createAndGo 6: destroy"
        ::= { optixDynPWBFDEntry 255 }

    -- 1.3.6.1.4.1.2011.2.25.4.50.6.1.8
    optixDynPWREDDYTable OBJECT-TYPE
        SYNTAX SEQUENCE OF OptixDynPWREDDYEntry
        MAX-ACCESS not-accessible
        STATUS current
        DESCRIPTION
            "This table implements the configurations of a redundancy group for dynamic PWs."
        ::= { optixPWObject 8 }

    -- 1.3.6.1.4.1.2011.2.25.4.50.6.1.8.1
    optixDynPWREDDYEntry OBJECT-TYPE
        SYNTAX OptixDynPWREDDYEntry
        MAX-ACCESS not-accessible
        STATUS current
        DESCRIPTION
            "This entry describes the parameter table of a redundancy group."
        INDEX{ optixDynPWREDDYIndex }
        ::= { optixDynPWREDDYTable 1 }

    OptixDynPWREDDYEntry ::=
        SEQUENCE {
            optixDynPWREDDYIndex
                Unsigned32,
            optixDynPWREDDYProtectType
                INTEGER,
            optixDynPWREDDYMem1PW
                Unsigned32,
            optixDynPWREDDYPW1State
                INTEGER,
            optixDynPWREDDYMem2PW
                Unsigned32,
            optixDynPWREDDYPW2State
                INTEGER,
            optixDynPWREDDYMode
                INTEGER,
            optixDynPWREDDYDualRecv
                INTEGER,
            optixDynPWREDDYReroute
                INTEGER,
            optixDynPWREDDYDelayTime
                Unsigned32,
            optixDynPWREDDYRowStatus
                RowStatus
        }

    -- 1.3.6.1.4.1.2011.2.25.4.50.6.1.8.1.1
    optixDynPWREDDYIndex OBJECT-TYPE
        SYNTAX Unsigned32
        MAX-ACCESS not-accessible
        STATUS current
        DESCRIPTION
            "This object describes the index of a PW redundancy group."
        ::= { optixDynPWREDDYEntry 1 }

    -- 1.3.6.1.4.1.2011.2.25.4.50.6.1.8.1.2
    optixDynPWREDDYProtectType OBJECT-TYPE
        SYNTAX INTEGER
        {
            oneplusone(1),
            onetoone(2),
            bfdfrr1to1(3)
        }
        MAX-ACCESS read-create
        STATUS current
        DESCRIPTION
            "This object describes the protection type of a PW redundancy group."
        ::= { optixDynPWREDDYEntry 2 }

    -- 1.3.6.1.4.1.2011.2.25.4.50.6.1.8.1.3
    optixDynPWREDDYMem1PW OBJECT-TYPE
        SYNTAX Unsigned32
        MAX-ACCESS read-create
        STATUS current
        DESCRIPTION
            "This object describes the PW1, a member of the PW redundancy group."
        ::= { optixDynPWREDDYEntry 3 }

    -- 1.3.6.1.4.1.2011.2.25.4.50.6.1.8.1.4
    optixDynPWREDDYPW1State OBJECT-TYPE
        SYNTAX INTEGER
        {
            forwarding(0),
            unforwarding(1)
        }
        MAX-ACCESS read-only
        STATUS current
        DESCRIPTION
            "This node describes the forwarding status of PW1, a member of the PW redundancy group."
        ::= { optixDynPWREDDYEntry 4 }

    -- 1.3.6.1.4.1.2011.2.25.4.50.6.1.8.1.5
    optixDynPWREDDYMem2PW OBJECT-TYPE
        SYNTAX Unsigned32
        MAX-ACCESS read-create
        STATUS current
        DESCRIPTION
            "This object describes PW2, another member of the PW redundancy group."
        ::= { optixDynPWREDDYEntry 5 }

    -- 1.3.6.1.4.1.2011.2.25.4.50.6.1.8.1.6
    optixDynPWREDDYPW2State OBJECT-TYPE
        SYNTAX INTEGER
        {
            forwarding(0),
            unforwarding(1)
        }
        MAX-ACCESS read-only
        STATUS current
        DESCRIPTION
            "This node describes the forwarding status of PW2, another member of the PW redundancy protection group."
        ::= { optixDynPWREDDYEntry 6 }

    -- 1.3.6.1.4.1.2011.2.25.4.50.6.1.8.1.7
    optixDynPWREDDYMode OBJECT-TYPE
        SYNTAX INTEGER
        {
            master(0),
            independent(1)
        }
        MAX-ACCESS read-create
        STATUS current
        DESCRIPTION
            "This object describes the mode of a PW redundancy group."
        ::= { optixDynPWREDDYEntry 7 }

    -- 1.3.6.1.4.1.2011.2.25.4.50.6.1.8.1.8
    optixDynPWREDDYDualRecv OBJECT-TYPE
        SYNTAX INTEGER
        {
            disable(0),
            enable(1)
        }
        MAX-ACCESS read-create
        STATUS current
        DESCRIPTION
            "This object describes the dual receiving mode of a PW redundancy group."
        ::= { optixDynPWREDDYEntry 8 }

    -- 1.3.6.1.4.1.2011.2.25.4.50.6.1.8.1.9
    optixDynPWREDDYReroute OBJECT-TYPE
        SYNTAX INTEGER
        {
            delay(1),
            never(2),
            immediately(3)
        }
        MAX-ACCESS read-create
        STATUS current
        DESCRIPTION
            "This object describes the PW switchback policy mode."
        ::= { optixDynPWREDDYEntry 9 }

    -- 1.3.6.1.4.1.2011.2.25.4.50.6.1.8.1.10
    optixDynPWREDDYDelayTime OBJECT-TYPE
        SYNTAX Unsigned32
        MAX-ACCESS read-create
        STATUS current
        DESCRIPTION
            "This object describes switchback delay time of a PW redundancy group."
        ::= { optixDynPWREDDYEntry 10 }

    -- 1.3.6.1.4.1.2011.2.25.4.50.6.1.8.1.255
    optixDynPWREDDYRowStatus OBJECT-TYPE
        SYNTAX RowStatus
        MAX-ACCESS read-create
        STATUS current
        DESCRIPTION
            "This object describes the row status. 1: active 4: createAndGo 6: destroy"
        ::= { optixDynPWREDDYEntry 255 }

    -- 1.3.6.1.4.1.2011.2.25.4.50.6.2
    optixMsPWObject OBJECT IDENTIFIER ::= { optixPWMod 2 }

    -- 1.3.6.1.4.1.2011.2.25.4.50.6.2.1
    optixMsPWTable OBJECT-TYPE
        SYNTAX SEQUENCE OF OptixMsPWEntry
        MAX-ACCESS not-accessible
        STATUS current
        DESCRIPTION
            "This table implements the configurations of MS-PWs, including the last/next segment PW index, name, MTU, types of services carried on the PW."
        ::= { optixMsPWObject 1 }

    -- 1.3.6.1.4.1.2011.2.25.4.50.6.2.1.1
    optixMsPWEntry OBJECT-TYPE
        SYNTAX OptixMsPWEntry
        MAX-ACCESS not-accessible
        STATUS current
        DESCRIPTION
            "This entry indicates the MS PW parameter table."
        INDEX{ optixMsPWIndex }
        ::= { optixMsPWTable 1 }

    OptixMsPWEntry ::=
        SEQUENCE {
            optixMsPWIndex
                Unsigned32,
            optixMsPWid
                Unsigned32,
            optixMsPWForePwIndex
                Unsigned32,
            optixMsPWBackPwIndex
                Unsigned32,
            optixMsPWMtu
                Unsigned32,
            optixMsPWName
                OCTET STRING,
            optixMsPWServiceType
                INTEGER,
            optixMsPWForePwLocalState
                Unsigned32,
            optixMsPWForePwRemoteState
                Unsigned32,
            optixMsPWForePwState
                Unsigned32,
            optixMsPWBackPwLocalState
                Unsigned32,
            optixMsPWBackPwRemoteState
                Unsigned32,
            optixMsPWBackPwState
                Unsigned32,
            optixMsPWRowStatus
                RowStatus
        }

    -- 1.3.6.1.4.1.2011.2.25.4.50.6.2.1.1.1
    optixMsPWIndex OBJECT-TYPE
        SYNTAX Unsigned32
        MAX-ACCESS not-accessible
        STATUS current
        DESCRIPTION
            "This object indicates the MS-PW index."
        ::= { optixMsPWEntry 1 }

    -- 1.3.6.1.4.1.2011.2.25.4.50.6.2.1.1.2
    optixMsPWid OBJECT-TYPE
        SYNTAX Unsigned32
        MAX-ACCESS read-create
        STATUS current
        DESCRIPTION
            "This object indicates the MS-PW ID."
        ::= { optixMsPWEntry 2 }

    -- 1.3.6.1.4.1.2011.2.25.4.50.6.2.1.1.3
    optixMsPWForePwIndex OBJECT-TYPE
        SYNTAX Unsigned32
        MAX-ACCESS read-create
        STATUS current
        DESCRIPTION
            "This object indicates the last segment PW index."
        ::= { optixMsPWEntry 3 }

    -- 1.3.6.1.4.1.2011.2.25.4.50.6.2.1.1.4
    optixMsPWBackPwIndex OBJECT-TYPE
        SYNTAX Unsigned32
        MAX-ACCESS read-create
        STATUS current
        DESCRIPTION
            "This object indicates thenext segment PW index."
        ::= { optixMsPWEntry 4 }

    -- 1.3.6.1.4.1.2011.2.25.4.50.6.2.1.1.5
    optixMsPWMtu OBJECT-TYPE
        SYNTAX Unsigned32(46..9000)
        MAX-ACCESS read-create
        STATUS current
        DESCRIPTION
            "This object indicates the MTU. If the last and next segment PWs are of ETH service type, the value ranges from 46-9000. Default value: 1500. If the last and next segment PWs are of ATM or CES service type. The value is 0xffff."
        DEFVAL{ 1500 }
        ::= { optixMsPWEntry 5 }

    -- 1.3.6.1.4.1.2011.2.25.4.50.6.2.1.1.6
    optixMsPWName OBJECT-TYPE
        SYNTAX OCTET STRING(SIZE(0..64))
        MAX-ACCESS read-create
        STATUS current
        DESCRIPTION
            "This object indicates the MS-PW name, which is a character string, supporting a maximum of 64 bytes. No default value is configured. The name could be null, space, and chinese characters."
        ::= { optixMsPWEntry 6 }

    -- 1.3.6.1.4.1.2011.2.25.4.50.6.2.1.1.7
    optixMsPWServiceType OBJECT-TYPE
        SYNTAX INTEGER
        {
            ces(1),
            atm(2),
            eth(3),
            ptp(4),
            top(5),
            ip(6),
            sohcep(7),
            nosohcep(8)
        }
        MAX-ACCESS read-create
        STATUS current
        DESCRIPTION
            "This object indicates the service type. 1: ces 2: atm 3: eth 4: ptp 5: top 6: ip 7: soh-cep 8: nosoh-cep"
        ::= { optixMsPWEntry 7 }

    -- 1.3.6.1.4.1.2011.2.25.4.50.6.2.1.1.8
    optixMsPWForePwLocalState OBJECT-TYPE
        SYNTAX Unsigned32
        MAX-ACCESS read-only
        STATUS current
        DESCRIPTION
            "This object indicates the local state of fore pw."
        ::= { optixMsPWEntry 8 }

    -- 1.3.6.1.4.1.2011.2.25.4.50.6.2.1.1.9
    optixMsPWForePwRemoteState OBJECT-TYPE
        SYNTAX Unsigned32
        MAX-ACCESS read-only
        STATUS current
        DESCRIPTION
            "This object indicates the remote state of fore pw."
        ::= { optixMsPWEntry 9 }

    -- 1.3.6.1.4.1.2011.2.25.4.50.6.2.1.1.10
    optixMsPWForePwState OBJECT-TYPE
        SYNTAX Unsigned32
        MAX-ACCESS read-only
        STATUS current
        DESCRIPTION
            "This object indicates the state of fore PW."
        ::= { optixMsPWEntry 10 }

    -- 1.3.6.1.4.1.2011.2.25.4.50.6.2.1.1.11
    optixMsPWBackPwLocalState OBJECT-TYPE
        SYNTAX Unsigned32
        MAX-ACCESS read-only
        STATUS current
        DESCRIPTION
            "This object indicates the local state of back PW"
        ::= { optixMsPWEntry 11 }

    -- 1.3.6.1.4.1.2011.2.25.4.50.6.2.1.1.12
    optixMsPWBackPwRemoteState OBJECT-TYPE
        SYNTAX Unsigned32
        MAX-ACCESS read-only
        STATUS current
        DESCRIPTION
            "This object indicates the remote state of back pw."
        ::= { optixMsPWEntry 12 }

    -- 1.3.6.1.4.1.2011.2.25.4.50.6.2.1.1.13
    optixMsPWBackPwState OBJECT-TYPE
        SYNTAX Unsigned32
        MAX-ACCESS read-only
        STATUS current
        DESCRIPTION
            "This object indicates the state of back pw."
        ::= { optixMsPWEntry 13 }

    -- 1.3.6.1.4.1.2011.2.25.4.50.6.2.1.1.255
    optixMsPWRowStatus OBJECT-TYPE
        SYNTAX RowStatus
        MAX-ACCESS read-create
        STATUS current
        DESCRIPTION
            "This object indicates the row status. 1: active 4: createAndGo 6: destroy"
        ::= { optixMsPWEntry 255 }

    -- 1.3.6.1.4.1.2011.2.25.4.50.6.2.2
    optixMsPWCrossTable OBJECT-TYPE
        SYNTAX SEQUENCE OF OptixMsPWCrossEntry
        MAX-ACCESS not-accessible
        STATUS current
        DESCRIPTION
            "This table is used to query the actual MS-PW cross-connect and forwarding paths and the cross-connection information of the last and next segment PWs are returned."
        ::= { optixMsPWObject 2 }

    -- 1.3.6.1.4.1.2011.2.25.4.50.6.2.2.1
    optixMsPWCrossEntry OBJECT-TYPE
        SYNTAX OptixMsPWCrossEntry
        MAX-ACCESS not-accessible
        STATUS current
        DESCRIPTION
            "This entry is used to query the parameter table for actual MS-PW cross-connections."
        INDEX{ optixMsPWCrossIndex }
        ::= { optixMsPWCrossTable 1 }

    OptixMsPWCrossEntry ::=
        SEQUENCE {
            optixMsPWCrossIndex
                Unsigned32,
            optixMsPWCrossForePWXCId
                Unsigned32,
            optixMsPWCrossForePWType
                INTEGER,
            optixMsPWCrossForePWId
                Unsigned32,
            optixMsPWCrossForePWInlabel
                Unsigned32,
            optixMsPWCrossBackPWOutlabel
                Unsigned32,
            optixMsPWCrossBackPWTnlIngressId
                IpAddress,
            optixMsPWCrossBackPWTnlEgressId
                IpAddress,
            optixMsPWCrossBackPWTnlId
                Unsigned32,
            optixMsPWCrossBackPWTunnelType
                INTEGER,
            optixMsPWCrossForePWActiveStaus
                INTEGER,
            optixMsPWCrossBackPWXCId
                Unsigned32,
            optixMsPWCrossBackPWType
                INTEGER,
            optixMsPWCrossBackPWId
                Unsigned32,
            optixMsPWCrossBackPWInlabel
                Unsigned32,
            optixMsPWCrossForePWOutlabel
                Unsigned32,
            optixMsPWCrossForePWTnlIngressId
                IpAddress,
            optixMsPWCrossForePWTnlEgressId
                IpAddress,
            optixMsPWCrossForePWTnlId
                Unsigned32,
            optixMsPWCrossForePWTunnelType
                INTEGER,
            optixMsPWCrossBackPWActiveStaus
                INTEGER
        }

    -- 1.3.6.1.4.1.2011.2.25.4.50.6.2.2.1.1
    optixMsPWCrossIndex OBJECT-TYPE
        SYNTAX Unsigned32
        MAX-ACCESS not-accessible
        STATUS current
        DESCRIPTION
            "This object indicates the MS-PW index, ranging from 1 to 0x00ffffff."
        ::= { optixMsPWCrossEntry 1 }

    -- 1.3.6.1.4.1.2011.2.25.4.50.6.2.2.1.2
    optixMsPWCrossForePWXCId OBJECT-TYPE
        SYNTAX Unsigned32
        MAX-ACCESS read-only
        STATUS current
        DESCRIPTION
            "This object indicates the ID of the cross-connection between the last segment and the next segment PWs."
        ::= { optixMsPWCrossEntry 2 }

    -- 1.3.6.1.4.1.2011.2.25.4.50.6.2.2.1.3
    optixMsPWCrossForePWType OBJECT-TYPE
        SYNTAX INTEGER
        {
            ethtag(4),
            ethraw(5),
            atmtrans(3),
            atmnto1vcc(9),
            atmnto1vpc(10),
            atm1to1vcc(12),
            atm1to1vpc(13),
            satop(17),
            cesopsn(21),
            cep(16),
            ip(4097)
        }
        MAX-ACCESS read-only
        STATUS current
        DESCRIPTION
            "This object indicates the last segment PW type. 4: ethtag, 5: ethraw, 3: atmtrans, 9: atmnto1vcc, 10: atmnto1vpc, 12: atm1to1vcc, 13: atm1to1vpc, 17: satop, 21: cesopsn, 16: cep, 4097: ip"
        ::= { optixMsPWCrossEntry 3 }

    -- 1.3.6.1.4.1.2011.2.25.4.50.6.2.2.1.4
    optixMsPWCrossForePWId OBJECT-TYPE
        SYNTAX Unsigned32
        MAX-ACCESS read-only
        STATUS current
        DESCRIPTION
            "This object indicates the last segment PW ID."
        ::= { optixMsPWCrossEntry 4 }

    -- 1.3.6.1.4.1.2011.2.25.4.50.6.2.2.1.5
    optixMsPWCrossForePWInlabel OBJECT-TYPE
        SYNTAX Unsigned32
        MAX-ACCESS read-only
        STATUS current
        DESCRIPTION
            "This object indicates the ingress label of the last segment PW."
        ::= { optixMsPWCrossEntry 5 }

    -- 1.3.6.1.4.1.2011.2.25.4.50.6.2.2.1.6
    optixMsPWCrossBackPWOutlabel OBJECT-TYPE
        SYNTAX Unsigned32
        MAX-ACCESS read-only
        STATUS current
        DESCRIPTION
            "This object indicates the egress label of the last segment PW."
        ::= { optixMsPWCrossEntry 6 }

    -- 1.3.6.1.4.1.2011.2.25.4.50.6.2.2.1.7
    optixMsPWCrossBackPWTnlIngressId OBJECT-TYPE
        SYNTAX IpAddress
        MAX-ACCESS read-only
        STATUS current
        DESCRIPTION
            "This object indicates the ingress tunnel ID of the last segment PW."
        ::= { optixMsPWCrossEntry 7 }

    -- 1.3.6.1.4.1.2011.2.25.4.50.6.2.2.1.8
    optixMsPWCrossBackPWTnlEgressId OBJECT-TYPE
        SYNTAX IpAddress
        MAX-ACCESS read-only
        STATUS current
        DESCRIPTION
            "This object indicates the egress tunnel ID of the last segment PW."
        ::= { optixMsPWCrossEntry 8 }

    -- 1.3.6.1.4.1.2011.2.25.4.50.6.2.2.1.9
    optixMsPWCrossBackPWTnlId OBJECT-TYPE
        SYNTAX Unsigned32
        MAX-ACCESS read-only
        STATUS current
        DESCRIPTION
            "This object indicates the tunnel ID of the last segment PW."
        ::= { optixMsPWCrossEntry 9 }

    -- 1.3.6.1.4.1.2011.2.25.4.50.6.2.2.1.10
    optixMsPWCrossBackPWTunnelType OBJECT-TYPE
        SYNTAX INTEGER
        {
            mpls(0),
            pbt(1),
            ip(2),
            gre(3)
        }
        MAX-ACCESS read-only
        STATUS current
        DESCRIPTION
            "This object indicates the tunnel type of the last segment PW. 0: mpls, 1: pbt, 2: ip, 3: gre"
        ::= { optixMsPWCrossEntry 10 }

    -- 1.3.6.1.4.1.2011.2.25.4.50.6.2.2.1.11
    optixMsPWCrossForePWActiveStaus OBJECT-TYPE
        SYNTAX INTEGER
        {
            noactive(0),
            active(1)
        }
        MAX-ACCESS read-only
        STATUS current
        DESCRIPTION
            "This object indicates the activation status of the cross-connection between the last segment and the next segment PWs. 0: noactive, 1: active"
        ::= { optixMsPWCrossEntry 11 }

    -- 1.3.6.1.4.1.2011.2.25.4.50.6.2.2.1.12
    optixMsPWCrossBackPWXCId OBJECT-TYPE
        SYNTAX Unsigned32
        MAX-ACCESS read-only
        STATUS current
        DESCRIPTION
            "This object indicates the ID of the cross-connection between the next segment and thelast segment PWs."
        ::= { optixMsPWCrossEntry 12 }

    -- 1.3.6.1.4.1.2011.2.25.4.50.6.2.2.1.13
    optixMsPWCrossBackPWType OBJECT-TYPE
        SYNTAX INTEGER
        {
            ethtag(4),
            ethraw(5),
            atmtrans(3),
            atmnto1vcc(9),
            atmnto1vpc(10),
            atm1to1vcc(12),
            atm1to1vpc(13),
            satop(17),
            cesopsn(21),
            cep(16),
            ip(4097)
        }
        MAX-ACCESS read-only
        STATUS current
        DESCRIPTION
            "This object indicates thenext segment PW type. 4: ethtag, 5: ethraw, 3: atmtrans, 9: atmnto1vcc, 10: atmnto1vpc, 12: atm1to1vcc, 13: atm1to1vpc, 17: satop, 21: cesopsn, 16: cep, 4097: ip"
        ::= { optixMsPWCrossEntry 13 }

    -- 1.3.6.1.4.1.2011.2.25.4.50.6.2.2.1.14
    optixMsPWCrossBackPWId OBJECT-TYPE
        SYNTAX Unsigned32
        MAX-ACCESS read-only
        STATUS current
        DESCRIPTION
            "This object indicates the next segment PW ID."
        ::= { optixMsPWCrossEntry 14 }

    -- 1.3.6.1.4.1.2011.2.25.4.50.6.2.2.1.15
    optixMsPWCrossBackPWInlabel OBJECT-TYPE
        SYNTAX Unsigned32
        MAX-ACCESS read-only
        STATUS current
        DESCRIPTION
            "This object indicates the ingress label of thenext segment PW."
        ::= { optixMsPWCrossEntry 15 }

    -- 1.3.6.1.4.1.2011.2.25.4.50.6.2.2.1.16
    optixMsPWCrossForePWOutlabel OBJECT-TYPE
        SYNTAX Unsigned32
        MAX-ACCESS read-only
        STATUS current
        DESCRIPTION
            "This object indicates the egress label of the last segment PW."
        ::= { optixMsPWCrossEntry 16 }

    -- 1.3.6.1.4.1.2011.2.25.4.50.6.2.2.1.17
    optixMsPWCrossForePWTnlIngressId OBJECT-TYPE
        SYNTAX IpAddress
        MAX-ACCESS read-only
        STATUS current
        DESCRIPTION
            "This object indicates the ingress tunnel ID of the last segment PW."
        ::= { optixMsPWCrossEntry 17 }

    -- 1.3.6.1.4.1.2011.2.25.4.50.6.2.2.1.18
    optixMsPWCrossForePWTnlEgressId OBJECT-TYPE
        SYNTAX IpAddress
        MAX-ACCESS read-only
        STATUS current
        DESCRIPTION
            "This object indicates the egress tunnel ID of the last segment PW."
        ::= { optixMsPWCrossEntry 18 }

    -- 1.3.6.1.4.1.2011.2.25.4.50.6.2.2.1.19
    optixMsPWCrossForePWTnlId OBJECT-TYPE
        SYNTAX Unsigned32
        MAX-ACCESS read-only
        STATUS current
        DESCRIPTION
            "This object indicates the tunnel ID of the last segment PW."
        ::= { optixMsPWCrossEntry 19 }

    -- 1.3.6.1.4.1.2011.2.25.4.50.6.2.2.1.20
    optixMsPWCrossForePWTunnelType OBJECT-TYPE
        SYNTAX INTEGER
        {
            mpls(0),
            pbt(1),
            ip(2),
            gre(3)
        }
        MAX-ACCESS read-only
        STATUS current
        DESCRIPTION
            "This object indicates the tunnel type of the last segment PW. 0: mpls, 1: pbt, 2: ip, 3: gre"
        ::= { optixMsPWCrossEntry 20 }

    -- 1.3.6.1.4.1.2011.2.25.4.50.6.2.2.1.21
    optixMsPWCrossBackPWActiveStaus OBJECT-TYPE
        SYNTAX INTEGER
        {
            noactive(0),
            active(1)
        }
        MAX-ACCESS read-only
        STATUS current
        DESCRIPTION
            "This object indicates the activation status of the cross-connection between thenext segment and the last segment PWs. 0: noactive, 1: active"
        ::= { optixMsPWCrossEntry 21 }

    -- 1.3.6.1.4.1.2011.2.25.4.50.6.5
    optixPWTrapGroup OBJECT IDENTIFIER ::= { optixPWMod 5 }

    -- 1.3.6.1.4.1.2011.2.25.4.50.6.5.1
    optixPWTrapMember OBJECT IDENTIFIER ::= { optixPWTrapGroup 1 }

    -- 1.3.6.1.4.1.2011.2.25.4.50.6.5.1.1
    optixPWTrapPWPingIndex OBJECT-TYPE
        SYNTAX Unsigned32
        MAX-ACCESS accessible-for-notify
        STATUS current
        DESCRIPTION
            "This object indicates the index to the PW initiating PW ping."
        ::= { optixPWTrapMember 1 }

    -- 1.3.6.1.4.1.2011.2.25.4.50.6.5.1.2
    optixPWTrapRspLSRIP OBJECT-TYPE
        SYNTAX OCTET STRING
        MAX-ACCESS accessible-for-notify
        STATUS current
        DESCRIPTION
            "This object indicates the IP address of the response LSR."
        ::= { optixPWTrapMember 2 }

    -- 1.3.6.1.4.1.2011.2.25.4.50.6.5.1.3
    optixPWTrapPKTLen OBJECT-TYPE
        SYNTAX Unsigned32
        MAX-ACCESS accessible-for-notify
        STATUS current
        DESCRIPTION
            "This object indicates the number of bytes in the sent packet."
        ::= { optixPWTrapMember 3 }

    -- 1.3.6.1.4.1.2011.2.25.4.50.6.5.1.4
    optixPWTrapSEQNumber OBJECT-TYPE
        SYNTAX Unsigned32
        MAX-ACCESS accessible-for-notify
        STATUS current
        DESCRIPTION
            "This object indicates the sequence number of the response packet."
        ::= { optixPWTrapMember 4 }

    -- 1.3.6.1.4.1.2011.2.25.4.50.6.5.1.5
    optixPWTrapDelay OBJECT-TYPE
        SYNTAX Unsigned32
        MAX-ACCESS accessible-for-notify
        STATUS current
        DESCRIPTION
            "This object indicates the delay. (unit: us)"
        ::= { optixPWTrapMember 5 }

    -- 1.3.6.1.4.1.2011.2.25.4.50.6.5.1.6
    optixPWTrapTTL OBJECT-TYPE
        SYNTAX Unsigned32
        MAX-ACCESS accessible-for-notify
        STATUS current
        DESCRIPTION
            "This object indicates the TTL of the sent packet."
        ::= { optixPWTrapMember 6 }

    -- 1.3.6.1.4.1.2011.2.25.4.50.6.5.1.7
    optixPWTrapRetCode OBJECT-TYPE
        SYNTAX INTEGER
        {
            noReturn(0),
            errorRequest(1),
            unknownTLV(2),
            egress(3),
            noMappingFEC(4),
            mapMismatch(5),
            unknownUpInterface(6),
            reserved(7),
            labelSwitch(8),
            labelSwitchNoMPLSForward(9),
            noLabelMapping(10),
            noLabelEntry(11),
            procUnloadInterface(12),
            endPingCmd(13)
        }
        MAX-ACCESS accessible-for-notify
        STATUS current
        DESCRIPTION
            "This object indicates the return code. (0: No return code; 1: An error request is received; 2: Unknown TLVs are received; 3: An egress for an LSP is available; 4: The replying router has no mapping for the FEC at stack-depth; 5: Mismatch with the downstream mapping occurs; 6: Unknown upstream interfaces are found; 7: Reserved; 8: Label switching at stack-depth; 9: Label switching but no MPLS forwarding at stack-depth; 10: Mapping for this FEC is not the given label at stack-depth; 11: No label entry at stack-depth; 12: Protocol not associated with the interface at FEC stack-depth; 13: Premature termination of ping due to label stack shrinking to a single label."
        ::= { optixPWTrapMember 7 }

    -- 1.3.6.1.4.1.2011.2.25.4.50.6.5.1.8
    optixPWTrapSubCode OBJECT-TYPE
        SYNTAX Unsigned32
        MAX-ACCESS accessible-for-notify
        STATUS current
        DESCRIPTION
            "This object indicates the return subcode."
        ::= { optixPWTrapMember 8 }

    -- 1.3.6.1.4.1.2011.2.25.4.50.6.5.1.9
    optixPWTrapListId OBJECT-TYPE
        SYNTAX Unsigned32
        MAX-ACCESS accessible-for-notify
        STATUS current
        DESCRIPTION
            "This object indicates the sequence number."
        ::= { optixPWTrapMember 9 }

    -- 1.3.6.1.4.1.2011.2.25.4.50.6.5.1.10
    optixPWTrapTXNumber OBJECT-TYPE
        SYNTAX Unsigned32
        MAX-ACCESS accessible-for-notify
        STATUS current
        DESCRIPTION
            "This object indicates the number of sent packets."
        ::= { optixPWTrapMember 10 }

    -- 1.3.6.1.4.1.2011.2.25.4.50.6.5.1.11
    optixPWTrapRXNumber OBJECT-TYPE
        SYNTAX Unsigned32
        MAX-ACCESS accessible-for-notify
        STATUS current
        DESCRIPTION
            "This object indicates the number of received packets."
        ::= { optixPWTrapMember 11 }

    -- 1.3.6.1.4.1.2011.2.25.4.50.6.5.1.12
    optixPWTrapLoseRate OBJECT-TYPE
        SYNTAX Unsigned32
        MAX-ACCESS accessible-for-notify
        STATUS current
        DESCRIPTION
            "This object indicates the packet loss rate."
        ::= { optixPWTrapMember 12 }

    -- 1.3.6.1.4.1.2011.2.25.4.50.6.5.1.13
    optixPWTrapMinDelay OBJECT-TYPE
        SYNTAX Unsigned32
        MAX-ACCESS accessible-for-notify
        STATUS current
        DESCRIPTION
            "This object indicates the minimum delay. (unit: us)"
        ::= { optixPWTrapMember 13 }

    -- 1.3.6.1.4.1.2011.2.25.4.50.6.5.1.14
    optixPWTrapMaxDelay OBJECT-TYPE
        SYNTAX Unsigned32
        MAX-ACCESS accessible-for-notify
        STATUS current
        DESCRIPTION
            "This object indicates the maximum delay. (unit: us)"
        ::= { optixPWTrapMember 14 }

    -- 1.3.6.1.4.1.2011.2.25.4.50.6.5.1.15
    optixPWTrapAverDelay OBJECT-TYPE
        SYNTAX Unsigned32
        MAX-ACCESS accessible-for-notify
        STATUS current
        DESCRIPTION
            "This object indicates the average delay. (unit: us)"
        ::= { optixPWTrapMember 15 }

    -- 1.3.6.1.4.1.2011.2.25.4.50.6.5.1.16
    optixPWTrapTraceRoutePWIndex OBJECT-TYPE
        SYNTAX Unsigned32
        MAX-ACCESS accessible-for-notify
        STATUS current
        DESCRIPTION
            "This object indicates the index to the PW initiating TraceRoute."
        ::= { optixPWTrapMember 16 }

    -- 1.3.6.1.4.1.2011.2.25.4.50.6.5.1.17
    optixPWTrapReplierIP OBJECT-TYPE
        SYNTAX OCTET STRING
        MAX-ACCESS accessible-for-notify
        STATUS current
        DESCRIPTION
            "This object indicates the IP address of the response node."
        ::= { optixPWTrapMember 17 }

    -- 1.3.6.1.4.1.2011.2.25.4.50.6.5.1.18
    optixPWTrapMPLSTraceType OBJECT-TYPE
        SYNTAX INTEGER
        {
            stpe(1),
            spe(2),
            ttpe(3)
        }
        MAX-ACCESS accessible-for-notify
        STATUS current
        DESCRIPTION
            "This object indicates the type of response node."
        ::= { optixPWTrapMember 18 }

    -- 1.3.6.1.4.1.2011.2.25.4.50.6.5.1.19
    optixPWTrapDownStreamIP OBJECT-TYPE
        SYNTAX OCTET STRING
        MAX-ACCESS accessible-for-notify
        STATUS current
        DESCRIPTION
            "This object indicates the IP address of the downstream node."
        ::= { optixPWTrapMember 19 }

    -- 1.3.6.1.4.1.2011.2.25.4.50.6.5.1.20
    optixPWTrapDownStreamLabel OBJECT-TYPE
        SYNTAX Unsigned32
        MAX-ACCESS accessible-for-notify
        STATUS current
        DESCRIPTION
            "This object indicates the label of the downstream node."
        ::= { optixPWTrapMember 20 }

    -- 1.3.6.1.4.1.2011.2.25.4.50.6.5.1.21
    optixPWTrapSourceIP OBJECT-TYPE
        SYNTAX OCTET STRING
        MAX-ACCESS accessible-for-notify
        STATUS current
        DESCRIPTION
            "This object indicates the source IP address."
        ::= { optixPWTrapMember 21 }

    -- 1.3.6.1.4.1.2011.2.25.4.50.6.5.1.22
    optixTrapDynLdpPWIndex OBJECT-TYPE
        SYNTAX Unsigned32
        MAX-ACCESS accessible-for-notify
        STATUS current
        DESCRIPTION
            "This object describes the index of a dynamic PW."
        ::= { optixPWTrapMember 22 }

    -- 1.3.6.1.4.1.2011.2.25.4.50.6.5.1.23
    optixTrapDynLdpPWLocalState OBJECT-TYPE
        SYNTAX Unsigned32
        MAX-ACCESS accessible-for-notify
        STATUS current
        DESCRIPTION
            "This object describes the local state of a dynamic PW."
        ::= { optixPWTrapMember 23 }

    -- 1.3.6.1.4.1.2011.2.25.4.50.6.5.1.24
    optixTrapDynLdpPWRemoteState OBJECT-TYPE
        SYNTAX Unsigned32
        MAX-ACCESS accessible-for-notify
        STATUS current
        DESCRIPTION
            "This object describes the remote state of a dynamic PW."
        ::= { optixPWTrapMember 24 }

    -- 1.3.6.1.4.1.2011.2.25.4.50.6.5.1.25
    optixTrapDynLdpPWState OBJECT-TYPE
        SYNTAX Unsigned32
        MAX-ACCESS accessible-for-notify
        STATUS current
        DESCRIPTION
            "This object describes the state of a dynamic PW."
        ::= { optixPWTrapMember 25 }

    -- 1.3.6.1.4.1.2011.2.25.4.50.6.5.1.26
    optixTrapDynPWRdyIndex OBJECT-TYPE
        SYNTAX Unsigned32
        MAX-ACCESS accessible-for-notify
        STATUS current
        DESCRIPTION
            "This object describes the index of a PW redundancy group."
        ::= { optixPWTrapMember 26 }

    -- 1.3.6.1.4.1.2011.2.25.4.50.6.5.1.27
    optixTrapDynPWRdyPW1Id OBJECT-TYPE
        SYNTAX Unsigned32
        MAX-ACCESS accessible-for-notify
        STATUS current
        DESCRIPTION
            "This object describes PW1, a member of the PW redundant group."
        ::= { optixPWTrapMember 27 }

    -- 1.3.6.1.4.1.2011.2.25.4.50.6.5.1.28
    optixTrapDynPWRdyPW1Fwd OBJECT-TYPE
        SYNTAX INTEGER
        {
            forwarding(0),
            unforwarding(1)
        }
        MAX-ACCESS accessible-for-notify
        STATUS current
        DESCRIPTION
            "This node describes the forwarding status of PW1, a member of the PW redundancy group."
        ::= { optixPWTrapMember 28 }

    -- 1.3.6.1.4.1.2011.2.25.4.50.6.5.1.29
    optixTrapDynPWRdyPW2Id OBJECT-TYPE
        SYNTAX Unsigned32
        MAX-ACCESS accessible-for-notify
        STATUS current
        DESCRIPTION
            "This object describes the PW2, another member of the PW redundancy group."
        ::= { optixPWTrapMember 29 }

    -- 1.3.6.1.4.1.2011.2.25.4.50.6.5.1.30
    optixTrapDynPWRdyPW2Fwd OBJECT-TYPE
        SYNTAX INTEGER
        {
            forwarding(0),
            unforwarding(1)
        }
        MAX-ACCESS accessible-for-notify
        STATUS current
        DESCRIPTION
            "This node describes the forwarding status of PW2, another member of the PW redundancy group."
        ::= { optixPWTrapMember 30 }

    -- 1.3.6.1.4.1.2011.2.25.4.50.6.5.1.31
    optixPWTrapSaltusNum OBJECT-TYPE
        SYNTAX Unsigned32
        MAX-ACCESS accessible-for-notify
        STATUS current
        DESCRIPTION
            "This object indicates the number of payload bit changes."
        ::= { optixPWTrapMember 31 }

    -- 1.3.6.1.4.1.2011.2.25.4.50.6.5.1.32
    optixPWTrapSaltusBit OBJECT-TYPE
        SYNTAX Unsigned32
        MAX-ACCESS accessible-for-notify
        STATUS current
        DESCRIPTION
            "This object indicates the payload change bit."
        ::= { optixPWTrapMember 32 }

    -- 1.3.6.1.4.1.2011.2.25.4.50.6.5.1.33
    optixPWTrapChangeNum OBJECT-TYPE
        SYNTAX Unsigned32
        MAX-ACCESS accessible-for-notify
        STATUS current
        DESCRIPTION
            "This object indicates the total number of payload change packets."
        ::= { optixPWTrapMember 33 }

    -- 1.3.6.1.4.1.2011.2.25.4.50.6.5.1.34
    optixPWTrapPWPingType OBJECT-TYPE
        SYNTAX INTEGER
        {
            pwping(6)
        }
        MAX-ACCESS accessible-for-notify
        STATUS current
        DESCRIPTION
            "This object indicates the ping type."
        ::= { optixPWTrapMember 34 }

    -- 1.3.6.1.4.1.2011.2.25.4.50.6.5.2
    optixPWTrap OBJECT IDENTIFIER ::= { optixPWTrapGroup 2 }

    -- 1.3.6.1.4.1.2011.2.25.4.50.6.5.2.1
    optixPWPingRSPTrap NOTIFICATION-TYPE
        OBJECTS{ optixPWTrapPWPingIndex,optixPWTrapRspLSRIP,optixPWTrapPKTLen,optixPWTrapSEQNumber,optixPWTrapDelay,optixPWTrapTTL,optixPWTrapRetCode,optixPWTrapSubCode }
        STATUS current
        DESCRIPTION
            "This object is used to report the PW ping response event."
        ::= { optixPWTrap 1 }

    -- 1.3.6.1.4.1.2011.2.25.4.50.6.5.2.2
    optixPWPingOverTimeTrap NOTIFICATION-TYPE
        OBJECTS{ optixPWTrapPWPingIndex,optixPWTrapListId }
        STATUS current
        DESCRIPTION
            "This objectis used to report the PW ping response timeout event."
        ::= { optixPWTrap 2 }

    -- 1.3.6.1.4.1.2011.2.25.4.50.6.5.2.3
    optixPWPingStatisticTrap NOTIFICATION-TYPE
        OBJECTS{ optixPWTrapPWPingIndex,optixPWTrapTXNumber,optixPWTrapRXNumber,optixPWTrapLoseRate,optixPWTrapMinDelay,optixPWTrapMaxDelay,optixPWTrapAverDelay }
        STATUS current
        DESCRIPTION
            "This object is used to report the PW ping statistics result event."
        ::= { optixPWTrap 3 }

    -- 1.3.6.1.4.1.2011.2.25.4.50.6.5.2.4
    optixPWTraceRouteResponseTrap NOTIFICATION-TYPE
        OBJECTS{ optixPWTrapTraceRoutePWIndex,optixPWTrapReplierIP,optixPWTrapDelay,optixPWTrapMPLSTraceType,optixPWTrapDownStreamIP,optixPWTrapDownStreamLabel,optixPWTrapTTL,optixPWTrapRetCode }
        STATUS current
        DESCRIPTION
            "This object is used to report the PW traceroute response event."
        ::= { optixPWTrap 4 }

    -- 1.3.6.1.4.1.2011.2.25.4.50.6.5.2.5
    optixPWTraceRouteEndTrap NOTIFICATION-TYPE
        OBJECTS{ optixPWTrapTraceRoutePWIndex }
        STATUS current
        DESCRIPTION
            "This object is used to report the PW traceroute end event."
        ::= { optixPWTrap 5 }

    -- 1.3.6.1.4.1.2011.2.25.4.50.6.5.2.6
    optixPWTraceRouteOverTimeTrap NOTIFICATION-TYPE
        OBJECTS{ optixPWTrapTraceRoutePWIndex,optixPWTrapTTL }
        STATUS current
        DESCRIPTION
            "This object is used to report the PW traceroute response timeout event."
        ::= { optixPWTrap 6 }

    -- 1.3.6.1.4.1.2011.2.25.4.50.6.5.2.7
    optixPWNoReplyPingRSPTrap NOTIFICATION-TYPE
        OBJECTS{ optixPWTrapPWPingIndex,optixPWTrapTTL,optixPWTrapSourceIP }
        STATUS current
        DESCRIPTION
            "This object is used to report the PW ping event in no-reply mode."
        ::= { optixPWTrap 7 }

    -- 1.3.6.1.4.1.2011.2.25.4.50.6.5.2.8
    optixPWNoReplyTrcrtRSPTrap NOTIFICATION-TYPE
        OBJECTS{ optixPWTrapPWPingIndex,optixPWTrapTTL,optixPWTrapSourceIP }
        STATUS current
        DESCRIPTION
            "This object is used to report the PW TRACEROUTE event in no-reply mode."
        ::= { optixPWTrap 8 }

    -- 1.3.6.1.4.1.2011.2.25.4.50.6.5.2.9
    optixDynLdpPWStateTrap NOTIFICATION-TYPE
        OBJECTS{ optixTrapDynLdpPWIndex,optixTrapDynLdpPWLocalState,optixTrapDynLdpPWRemoteState,optixTrapDynLdpPWState }
        STATUS current
        DESCRIPTION
            "This object is used to report the PW TRACEROUTE event in no-reply mode."
        ::= { optixPWTrap 9 }

    -- 1.3.6.1.4.1.2011.2.25.4.50.6.5.2.10
    optixDynPWREDDYSWTrap NOTIFICATION-TYPE
        OBJECTS{ optixTrapDynPWRdyIndex,optixTrapDynPWRdyPW1Id,optixTrapDynPWRdyPW1Fwd,optixTrapDynPWRdyPW2Id,optixTrapDynPWRdyPW2Fwd }
        STATUS current
        DESCRIPTION
            "This object is used to report the PW TRACEROUTE event in no-reply mode."
        ::= { optixPWTrap 10 }

END
