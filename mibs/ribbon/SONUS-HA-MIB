-- Generated by
-- confdc ++emit-mib db64/sonusHaPort.mib ++oid sonusCommonSoftwarePlatformServicesMIBs.10 ++top sonusHaPortMIB ++prefix Sonus ++module SONUS-HA-MIB -f /sonus/p4/ws/release/sbx5000_V08.02.00R002/hornet/dist/fxs/common/SNMP-FRAMEWORK-MIB.fxs /sonus/p4/ws/release/sbx5000_V08.02.00R002/hornet/dist/fxs/common/SNMP-TARGET-MIB.fxs /sonus/p4/ws/release/sbx5000_V08.02.00R002/hornet/dist/fxs/common/SNMPv2-TC.fxs /sonus/p4/ws/release/sbx5000_V08.02.00R002/hornet/dist/fxs/common/ietf-inet-types.fxs /sonus/p4/ws/release/sbx5000_V08.02.00R002/hornet/dist/fxs/common/ietf-yang-types.fxs /sonus/p4/ws/release/sbx5000_V08.02.00R002/hornet/dist/fxs/common/sonusHornetTc.fxs /sonus/p4/ws/release/sbx5000_V08.02.00R002/hornet/dist/fxs/common/sonusTc.fxs ++ db64/sonusHaPort.fxs
-- 2020-03-09 23:54:42
-- Namespace: http://sonusnet.com/ns/mibs/SONUS-HA-MIB/1.0

SONUS-HA-MIB DEFINITIONS ::= BEGIN
IMPORTS
    sonusCommonSoftwarePlatformServicesMIBs FROM SONUS-SMI
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

sonusHaPortMIB MODULE-IDENTITY
    LAST-UPDATED "201212310000Z"
    ORGANIZATION "Ribbon Communications, Inc."
    CONTACT-INFO "Customer Support        
                  Ribbon Communications, Inc. 
                  4 Technology Park Drive 
                  Westford, MA 01886      
                  USA                     
                                          
                  Tel: 978-614-8100       
                  Fax: 978-614-8609"
    DESCRIPTION "The MIB Module for High Availability Port Management."
    REVISION "201212310000Z"
    DESCRIPTION "Auto generated MIB."
    ::= { sonusCommonSoftwarePlatformServicesMIBs 10 }

InetAddressIP ::= TEXTUAL-CONVENTION
    STATUS      current
    DESCRIPTION "confd:inetAddressIP"
    SYNTAX      OCTET STRING (SIZE (4|16))

String ::= TEXTUAL-CONVENTION
    DISPLAY-HINT "1t"
    STATUS      current
    DESCRIPTION "xs:string"
    SYNTAX      OCTET STRING

SonusNifOnOrOff ::= TEXTUAL-CONVENTION
    STATUS      current
    DESCRIPTION ""
    SYNTAX      INTEGER {on(1),off(2)}

SonusNifNegotiatedSpeedType ::= TEXTUAL-CONVENTION
    STATUS      current
    DESCRIPTION ""
    SYNTAX      INTEGER {speed10Mbps(1),speed100Mbps(2),speed1000Mbps(3),unknown(4),speed10Gbps(5)}

OosReasonType ::= TEXTUAL-CONVENTION
    STATUS      current
    DESCRIPTION ""
    SYNTAX      INTEGER {na(1),noSignal(4),noRemoteResponse(5)}

SonusNifDuplexModeType ::= TEXTUAL-CONVENTION
    STATUS      current
    DESCRIPTION ""
    SYNTAX      INTEGER {half(1),full(2)}

SonusNifTypeType ::= TEXTUAL-CONVENTION
    STATUS      current
    DESCRIPTION ""
    SYNTAX      INTEGER {bondingDevice(1),ethernetPort(2)}

-- Configuration and status for the HA ethernet ports.
-- tagpath /highAvailabilityPort
sonusHighAvailabilityPort OBJECT IDENTIFIER ::= { sonusHaPortMIB 1 }

-- tagpath /highAvailabilityPort/status
sonusHighAvailabilityPortStatusTable OBJECT-TYPE
    SYNTAX      SEQUENCE OF SonusHighAvailabilityPortStatusEntry
    MAX-ACCESS  not-accessible
    STATUS      current
    DESCRIPTION ""
    ::= { sonusHighAvailabilityPort 1 }

-- tagpath /highAvailabilityPort/status
sonusHighAvailabilityPortStatusEntry OBJECT-TYPE
    SYNTAX      SonusHighAvailabilityPortStatusEntry
    MAX-ACCESS  not-accessible
    STATUS      current
    DESCRIPTION ""
    INDEX { sonusHighAvailabilityPortStatusCeName, sonusHighAvailabilityPortStatusPortName }
        ::= { sonusHighAvailabilityPortStatusTable 1 }

SonusHighAvailabilityPortStatusEntry ::=
    SEQUENCE {
        sonusHighAvailabilityPortStatusCeName String,
        sonusHighAvailabilityPortStatusPortName String,
        sonusHighAvailabilityPortStatusMacAddress String,
        sonusHighAvailabilityPortStatusIpAddress InetAddressIP,
        sonusHighAvailabilityPortStatusNegotiatedSpeed SonusNifNegotiatedSpeedType,
        sonusHighAvailabilityPortStatusOosReason OosReasonType
    }

-- tagpath /highAvailabilityPort/status/ceName
sonusHighAvailabilityPortStatusCeName OBJECT-TYPE
    SYNTAX      String (SIZE (0 .. 255))
    MAX-ACCESS  not-accessible
    STATUS      current
    DESCRIPTION "
The host name is this server.
"
    ::= { sonusHighAvailabilityPortStatusEntry 1 }

-- tagpath /highAvailabilityPort/status/portName
sonusHighAvailabilityPortStatusPortName OBJECT-TYPE
    SYNTAX      String (SIZE (0 .. 23))
    MAX-ACCESS  not-accessible
    STATUS      current
    DESCRIPTION "
The name of the port.
"
    ::= { sonusHighAvailabilityPortStatusEntry 2 }

-- tagpath /highAvailabilityPort/status/macAddress
sonusHighAvailabilityPortStatusMacAddress OBJECT-TYPE
    SYNTAX      String (SIZE (0 .. 255))
    MAX-ACCESS  read-only
    STATUS      current
    DESCRIPTION "
The MAC address of this port.
"
    ::= { sonusHighAvailabilityPortStatusEntry 3 }

-- tagpath /highAvailabilityPort/status/ipAddress
sonusHighAvailabilityPortStatusIpAddress OBJECT-TYPE
    SYNTAX      InetAddressIP
    MAX-ACCESS  read-only
    STATUS      current
    DESCRIPTION "
The IP address of this port.
"
    ::= { sonusHighAvailabilityPortStatusEntry 4 }

-- tagpath /highAvailabilityPort/status/negotiatedSpeed
sonusHighAvailabilityPortStatusNegotiatedSpeed OBJECT-TYPE
    SYNTAX      SonusNifNegotiatedSpeedType
    MAX-ACCESS  read-only
    STATUS      current
    DESCRIPTION "
The negotiated speed of this port.
"
    ::= { sonusHighAvailabilityPortStatusEntry 5 }

-- tagpath /highAvailabilityPort/status/oosReason
sonusHighAvailabilityPortStatusOosReason OBJECT-TYPE
    SYNTAX      OosReasonType
    MAX-ACCESS  read-only
    STATUS      current
    DESCRIPTION "
The reason this port is out of service.
"
    ::= { sonusHighAvailabilityPortStatusEntry 6 }

-- tagpath /highAvailabilityPort/statistics
sonusHighAvailabilityPortStatisticsTable OBJECT-TYPE
    SYNTAX      SEQUENCE OF SonusHighAvailabilityPortStatisticsEntry
    MAX-ACCESS  not-accessible
    STATUS      current
    DESCRIPTION ""
    ::= { sonusHighAvailabilityPort 2 }

-- tagpath /highAvailabilityPort/statistics
sonusHighAvailabilityPortStatisticsEntry OBJECT-TYPE
    SYNTAX      SonusHighAvailabilityPortStatisticsEntry
    MAX-ACCESS  not-accessible
    STATUS      current
    DESCRIPTION ""
    INDEX { sonusHighAvailabilityPortStatisticsCeName, sonusHighAvailabilityPortStatisticsPortName }
        ::= { sonusHighAvailabilityPortStatisticsTable 1 }

SonusHighAvailabilityPortStatisticsEntry ::=
    SEQUENCE {
        sonusHighAvailabilityPortStatisticsCeName String,
        sonusHighAvailabilityPortStatisticsPortName String,
        sonusHighAvailabilityPortStatisticsPacketTx Counter64,
        sonusHighAvailabilityPortStatisticsByteTx Counter64,
        sonusHighAvailabilityPortStatisticsErrTx Counter32,
        sonusHighAvailabilityPortStatisticsPacketRx Counter64,
        sonusHighAvailabilityPortStatisticsByteRx Counter64,
        sonusHighAvailabilityPortStatisticsCrcErrRx Counter32,
        sonusHighAvailabilityPortStatisticsOverErrRx Counter32,
        sonusHighAvailabilityPortStatisticsNoBufCntRx Counter32,
        sonusHighAvailabilityPortStatisticsAllocRxBufFailRx Counter32
    }

-- tagpath /highAvailabilityPort/statistics/ceName
sonusHighAvailabilityPortStatisticsCeName OBJECT-TYPE
    SYNTAX      String (SIZE (0 .. 255))
    MAX-ACCESS  not-accessible
    STATUS      current
    DESCRIPTION "
The host name is this server.
"
    ::= { sonusHighAvailabilityPortStatisticsEntry 1 }

-- tagpath /highAvailabilityPort/statistics/portName
sonusHighAvailabilityPortStatisticsPortName OBJECT-TYPE
    SYNTAX      String (SIZE (0 .. 23))
    MAX-ACCESS  not-accessible
    STATUS      current
    DESCRIPTION "
The name of the port.
"
    ::= { sonusHighAvailabilityPortStatisticsEntry 2 }

-- tagpath /highAvailabilityPort/statistics/packetTx
sonusHighAvailabilityPortStatisticsPacketTx OBJECT-TYPE
    SYNTAX      Counter64
    MAX-ACCESS  read-only
    STATUS      current
    DESCRIPTION "
The number of packets transmitted.
"
    ::= { sonusHighAvailabilityPortStatisticsEntry 3 }

-- tagpath /highAvailabilityPort/statistics/byteTx
sonusHighAvailabilityPortStatisticsByteTx OBJECT-TYPE
    SYNTAX      Counter64
    MAX-ACCESS  read-only
    STATUS      current
    DESCRIPTION "
The number of bytes transmitted.
"
    ::= { sonusHighAvailabilityPortStatisticsEntry 4 }

-- tagpath /highAvailabilityPort/statistics/errTx
sonusHighAvailabilityPortStatisticsErrTx OBJECT-TYPE
    SYNTAX      Counter32
    MAX-ACCESS  read-only
    STATUS      current
    DESCRIPTION "
The number of transmit errors.
"
    ::= { sonusHighAvailabilityPortStatisticsEntry 5 }

-- tagpath /highAvailabilityPort/statistics/packetRx
sonusHighAvailabilityPortStatisticsPacketRx OBJECT-TYPE
    SYNTAX      Counter64
    MAX-ACCESS  read-only
    STATUS      current
    DESCRIPTION "
The number of packets received.
"
    ::= { sonusHighAvailabilityPortStatisticsEntry 6 }

-- tagpath /highAvailabilityPort/statistics/byteRx
sonusHighAvailabilityPortStatisticsByteRx OBJECT-TYPE
    SYNTAX      Counter64
    MAX-ACCESS  read-only
    STATUS      current
    DESCRIPTION "
The number of bytes received.
"
    ::= { sonusHighAvailabilityPortStatisticsEntry 7 }

-- tagpath /highAvailabilityPort/statistics/crcErrRx
sonusHighAvailabilityPortStatisticsCrcErrRx OBJECT-TYPE
    SYNTAX      Counter32
    MAX-ACCESS  read-only
    STATUS      current
    DESCRIPTION "
The number of receive CRC errors.
"
    ::= { sonusHighAvailabilityPortStatisticsEntry 8 }

-- tagpath /highAvailabilityPort/statistics/overErrRx
sonusHighAvailabilityPortStatisticsOverErrRx OBJECT-TYPE
    SYNTAX      Counter32
    MAX-ACCESS  read-only
    STATUS      current
    DESCRIPTION "
The number of receive overrun errors.
"
    ::= { sonusHighAvailabilityPortStatisticsEntry 9 }

-- tagpath /highAvailabilityPort/statistics/noBufCntRx
sonusHighAvailabilityPortStatisticsNoBufCntRx OBJECT-TYPE
    SYNTAX      Counter32
    MAX-ACCESS  read-only
    STATUS      current
    DESCRIPTION "
The number of receive no buffer errors.
"
    ::= { sonusHighAvailabilityPortStatisticsEntry 10 }

-- tagpath /highAvailabilityPort/statistics/allocRxBufFailRx
sonusHighAvailabilityPortStatisticsAllocRxBufFailRx OBJECT-TYPE
    SYNTAX      Counter32
    MAX-ACCESS  read-only
    STATUS      current
    DESCRIPTION "
The number of receive buffer allocation errors.
"
    ::= { sonusHighAvailabilityPortStatisticsEntry 11 }

END
