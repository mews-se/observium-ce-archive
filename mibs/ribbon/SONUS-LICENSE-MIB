-- Generated by
-- confdc ++emit-mib db64/sonusLicense.mib ++oid sonusCommonSoftwarePlatformServicesMIBs.16 ++top sonusLicenseMIB ++prefix Sonus ++module SONUS-LICENSE-MIB -f /sonus/p4/ws/release/sbx5000_V08.02.00R002/hornet/dist/fxs/common/SNMP-FRAMEWORK-MIB.fxs /sonus/p4/ws/release/sbx5000_V08.02.00R002/hornet/dist/fxs/common/SNMP-TARGET-MIB.fxs /sonus/p4/ws/release/sbx5000_V08.02.00R002/hornet/dist/fxs/common/SNMPv2-TC.fxs /sonus/p4/ws/release/sbx5000_V08.02.00R002/hornet/dist/fxs/common/ietf-inet-types.fxs /sonus/p4/ws/release/sbx5000_V08.02.00R002/hornet/dist/fxs/common/ietf-yang-types.fxs /sonus/p4/ws/release/sbx5000_V08.02.00R002/hornet/dist/fxs/common/sonusHornetTc.fxs /sonus/p4/ws/release/sbx5000_V08.02.00R002/hornet/dist/fxs/common/sonusTc.fxs ++ db64/sonusLicense.fxs
-- 2020-03-09 23:54:42
-- Namespace: http://sonusnet.com/ns/mibs/SONUS-LICENSE-MIB/1.0

SONUS-LICENSE-MIB DEFINITIONS ::= BEGIN
IMPORTS
    sonusCommonSoftwarePlatformServicesMIBs FROM SONUS-SMI
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

sonusLicenseMIB MODULE-IDENTITY
    LAST-UPDATED "201212310000Z"
    ORGANIZATION "Ribbon Communications, Inc."
    CONTACT-INFO "Customer Support        
                  Ribbon Communications, Inc. 
                  4 Technology Park Drive 
                  Westford, MA 01886      
                  USA                     
                                          
                  Tel: 978-614-8100       
                  Fax: 978-614-8609"
    DESCRIPTION "The MIB module for Sonus License."
    REVISION "201212310000Z"
    DESCRIPTION "Auto generated MIB."
    ::= { sonusCommonSoftwarePlatformServicesMIBs 16 }

String ::= TEXTUAL-CONVENTION
    DISPLAY-HINT "1t"
    STATUS      current
    DESCRIPTION "xs:string"
    SYNTAX      OCTET STRING

AuthSignatureType ::= TEXTUAL-CONVENTION
    DISPLAY-HINT "1t"
    STATUS      current
    DESCRIPTION ""
    SYNTAX      OCTET STRING (SIZE (0 .. 500))

HashType ::= TEXTUAL-CONVENTION
    DISPLAY-HINT "1t"
    STATUS      current
    DESCRIPTION ""
    SYNTAX      OCTET STRING (SIZE (0 .. 40))

SonusFeatureType ::= TEXTUAL-CONVENTION
    STATUS      current
    DESCRIPTION ""
    SYNTAX      INTEGER {onoff(1),counted(2)}

LicenseBundleString ::= TEXTUAL-CONVENTION
    DISPLAY-HINT "1t"
    STATUS      current
    DESCRIPTION ""
    SYNTAX      OCTET STRING (SIZE (0 .. 20000))

SonusLicenseBundleType ::= TEXTUAL-CONVENTION
    STATUS      current
    DESCRIPTION ""
    SYNTAX      INTEGER {nodeLocked(0),legacy(1),local(2),domain(3)}

-- tagpath /license
sonusLicense OBJECT IDENTIFIER ::= { sonusLicenseMIB 1 }

-- tagpath /license/bundle
sonusLicenseBundleTable OBJECT-TYPE
    SYNTAX      SEQUENCE OF SonusLicenseBundleEntry
    MAX-ACCESS  not-accessible
    STATUS      current
    DESCRIPTION "
The license bundle.
"
    ::= { sonusLicense 1 }

-- tagpath /license/bundle
sonusLicenseBundleEntry OBJECT-TYPE
    SYNTAX      SonusLicenseBundleEntry
    MAX-ACCESS  not-accessible
    STATUS      current
    DESCRIPTION ""
    INDEX { IMPLIED sonusLicenseBundleBundleName }
        ::= { sonusLicenseBundleTable 1 }

SonusLicenseBundleEntry ::=
    SEQUENCE {
        sonusLicenseBundleBundleName String,
        sonusLicenseBundleBundleString LicenseBundleString,
        sonusLicenseBundleRowstatus RowStatus,
        sonusLicenseBundleBundleType SonusLicenseBundleType,
        sonusLicenseBundleInstallDate DateAndTime
    }

-- tagpath /license/bundle/bundleName
sonusLicenseBundleBundleName OBJECT-TYPE
    SYNTAX      String (SIZE (0 .. 23))
    MAX-ACCESS  not-accessible
    STATUS      current
    DESCRIPTION "
This indicates the license identifier for license bundle.
"
    ::= { sonusLicenseBundleEntry 1 }

-- tagpath /license/bundle/bundleString
sonusLicenseBundleBundleString OBJECT-TYPE
    SYNTAX      LicenseBundleString
    MAX-ACCESS  read-create
    STATUS      current
    DESCRIPTION "
This object indicates the license bundle XML string.
"
    ::= { sonusLicenseBundleEntry 2 }

-- tagpath /license/bundle/rowstatus
sonusLicenseBundleRowstatus OBJECT-TYPE
    SYNTAX      RowStatus
    MAX-ACCESS  read-create
    STATUS      current
    DESCRIPTION ""
    ::= { sonusLicenseBundleEntry 3 }

-- tagpath /license/bundle/bundleType
sonusLicenseBundleBundleType OBJECT-TYPE
    SYNTAX      SonusLicenseBundleType
    MAX-ACCESS  read-create
    STATUS      current
    DESCRIPTION "
This indicates the license type of the bundle string
"
    DEFVAL { nodeLocked }
    ::= { sonusLicenseBundleEntry 4 }

-- tagpath /license/bundle/installDate
sonusLicenseBundleInstallDate OBJECT-TYPE
    SYNTAX      DateAndTime
    MAX-ACCESS  read-create
    STATUS      current
    DESCRIPTION "
This date the license was installed
"
    ::= { sonusLicenseBundleEntry 5 }

-- tagpath /license/licenseFeaturesInfo
sonusLicenseLicenseFeaturesInfoTable OBJECT-TYPE
    SYNTAX      SEQUENCE OF SonusLicenseLicenseFeaturesInfoEntry
    MAX-ACCESS  not-accessible
    STATUS      current
    DESCRIPTION "
The features allowed  by this application
"
    ::= { sonusLicense 2 }

-- tagpath /license/licenseFeaturesInfo
sonusLicenseLicenseFeaturesInfoEntry OBJECT-TYPE
    SYNTAX      SonusLicenseLicenseFeaturesInfoEntry
    MAX-ACCESS  not-accessible
    STATUS      current
    DESCRIPTION ""
    INDEX { sonusLicenseLicenseFeaturesInfoFeatureName }
        ::= { sonusLicenseLicenseFeaturesInfoTable 1 }

SonusLicenseLicenseFeaturesInfoEntry ::=
    SEQUENCE {
        sonusLicenseLicenseFeaturesInfoFeatureName String,
        sonusLicenseLicenseFeaturesInfoFeatureType SonusFeatureType
    }

-- tagpath /license/licenseFeaturesInfo/featureName
sonusLicenseLicenseFeaturesInfoFeatureName OBJECT-TYPE
    SYNTAX      String (SIZE (0 .. 23))
    MAX-ACCESS  not-accessible
    STATUS      current
    DESCRIPTION "
This indicates feature name
"
    ::= { sonusLicenseLicenseFeaturesInfoEntry 1 }

-- tagpath /license/licenseFeaturesInfo/featureType
sonusLicenseLicenseFeaturesInfoFeatureType OBJECT-TYPE
    SYNTAX      SonusFeatureType
    MAX-ACCESS  read-write
    STATUS      current
    DESCRIPTION "
The type of license
"
    ::= { sonusLicenseLicenseFeaturesInfoEntry 2 }

END
