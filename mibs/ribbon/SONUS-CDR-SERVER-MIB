-- Generated by
-- confdc ++emit-mib db64/sonusCdrServer.mib ++oid sonusCommonSoftwarePlatformServicesMIBs.17 ++top sonusCdrServerMIB ++prefix Sonus ++module SONUS-CDR-SERVER-MIB -f /sonus/p4/ws/release/sbx5000_V08.02.00R002/hornet/dist/fxs/common/SNMP-FRAMEWORK-MIB.fxs /sonus/p4/ws/release/sbx5000_V08.02.00R002/hornet/dist/fxs/common/SNMP-TARGET-MIB.fxs /sonus/p4/ws/release/sbx5000_V08.02.00R002/hornet/dist/fxs/common/SNMPv2-TC.fxs /sonus/p4/ws/release/sbx5000_V08.02.00R002/hornet/dist/fxs/common/ietf-inet-types.fxs /sonus/p4/ws/release/sbx5000_V08.02.00R002/hornet/dist/fxs/common/ietf-yang-types.fxs /sonus/p4/ws/release/sbx5000_V08.02.00R002/hornet/dist/fxs/common/sonusHornetTc.fxs /sonus/p4/ws/release/sbx5000_V08.02.00R002/hornet/dist/fxs/common/sonusTc.fxs ++ db64/sonusCdrServer.fxs
-- 2020-03-09 23:54:42
-- Namespace: http://sonusnet.com/ns/mibs/SONUS-CDR-SERVER-MIB/1.0

SONUS-CDR-SERVER-MIB DEFINITIONS ::= BEGIN
IMPORTS
    sonusCommonSoftwarePlatformServicesMIBs FROM SONUS-SMI
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

sonusCdrServerMIB MODULE-IDENTITY
    LAST-UPDATED "201212310000Z"
    ORGANIZATION "Ribbon Communications, Inc."
    CONTACT-INFO "Customer Support        
                  Ribbon Communications, Inc. 
                  4 Technology Park Drive 
                  Westford, MA 01886      
                  USA                     
                                          
                  Tel: 978-614-8100       
                  Fax: 978-614-8609"
    DESCRIPTION "Configuration for external CDR servers."
    REVISION "201212310000Z"
    DESCRIPTION "Auto generated MIB."
    ::= { sonusCommonSoftwarePlatformServicesMIBs 17 }

UnsignedShort ::= TEXTUAL-CONVENTION
    DISPLAY-HINT "d"
    STATUS      current
    DESCRIPTION "xs:unsignedShort"
    SYNTAX      Unsigned32 (0 .. 65535)

ConfdString ::= TEXTUAL-CONVENTION
    DISPLAY-HINT "1t"
    STATUS      current
    DESCRIPTION "xs: and confd: types mapped to strings"
    SYNTAX      OCTET STRING

InetAddressIP ::= TEXTUAL-CONVENTION
    STATUS      current
    DESCRIPTION "confd:inetAddressIP"
    SYNTAX      OCTET STRING (SIZE (4|16))

String ::= TEXTUAL-CONVENTION
    DISPLAY-HINT "1t"
    STATUS      current
    DESCRIPTION "xs:string"
    SYNTAX      OCTET STRING

SonusCdrServerTypeXferState ::= TEXTUAL-CONVENTION
    STATUS      current
    DESCRIPTION "
Server state
"
    SYNTAX      INTEGER {idle(0),started(1),connecting(2),transferring(3),failed(4),done(5)}

SonusAccountingOutOfServiceReason ::= TEXTUAL-CONVENTION
    STATUS      current
    DESCRIPTION "
The reason why Sonus Acccounting is out of Service
"
    SYNTAX      INTEGER {configchange(1),eventloggingerror(2)}

SonusCdrServerConnectionTimeoutType ::= TEXTUAL-CONVENTION
    STATUS      current
    DESCRIPTION "
Enter a value between in the range (15..120)
"
    SYNTAX      Integer32 (15 .. 120)

SonusCdrServerTypePasswdStr ::= TEXTUAL-CONVENTION
    DISPLAY-HINT "1t"
    STATUS      current
    DESCRIPTION "
Enter encrypted string password data
"
    SYNTAX      OCTET STRING

SonusCdrServerPublicKey ::= TEXTUAL-CONVENTION
    DISPLAY-HINT "1t"
    STATUS      current
    DESCRIPTION "
Enter public key of CDR server
"
    SYNTAX      OCTET STRING (SIZE (0 .. 2048))

SonusCdrServerTypeState ::= TEXTUAL-CONVENTION
    STATUS      current
    DESCRIPTION "
Server state
"
    SYNTAX      INTEGER {active(1),standby(2)}

SonusCdrServerBufferSizeType ::= TEXTUAL-CONVENTION
    STATUS      current
    DESCRIPTION "
Enter a value between in the range (4..1024)
"
    SYNTAX      Integer32 (4 .. 1024)

SonusCdrServerTypeName ::= TEXTUAL-CONVENTION
    DISPLAY-HINT "1t"
    STATUS      current
    DESCRIPTION "
Enter string character data
"
    SYNTAX      OCTET STRING (SIZE (0 .. 255))

SonusCdrServerTimeoutType ::= TEXTUAL-CONVENTION
    STATUS      current
    DESCRIPTION "
Enter a value between in the range (15..600)
"
    SYNTAX      Integer32 (15 .. 600)

SonusCdrServerTypeType ::= TEXTUAL-CONVENTION
    STATUS      current
    DESCRIPTION "
One of primary or secondary
"
    SYNTAX      INTEGER {primary(1),secondary(2)}

-- Configuration for external CDR servers.
-- tagpath /cdrServer
sonusCdrServer OBJECT IDENTIFIER ::= { sonusCdrServerMIB 1 }

-- tagpath /cdrServer/admin
sonusCdrServerAdminTable OBJECT-TYPE
    SYNTAX      SEQUENCE OF SonusCdrServerAdminEntry
    MAX-ACCESS  not-accessible
    STATUS      obsolete
    DESCRIPTION "
CDR server admin
"
    ::= { sonusCdrServer 1 }

-- tagpath /cdrServer/admin
sonusCdrServerAdminEntry OBJECT-TYPE
    SYNTAX      SonusCdrServerAdminEntry
    MAX-ACCESS  not-accessible
    STATUS      obsolete
    DESCRIPTION ""
    INDEX { sonusCdrServerAdminType }
        ::= { sonusCdrServerAdminTable 1 }

SonusCdrServerAdminEntry ::=
    SEQUENCE {
        sonusCdrServerAdminType SonusCdrServerTypeType,
        sonusCdrServerAdminIpAddress InetAddressIP,
        sonusCdrServerAdminUsername SonusCdrServerTypeName,
        sonusCdrServerAdminPassword SonusCdrServerTypePasswdStr,
        sonusCdrServerAdminPath SonusCdrServerTypeName,
        sonusCdrServerAdminFilePrefix SonusCdrServerTypeName,
        sonusCdrServerAdminConnectionTimeout SonusCdrServerConnectionTimeoutType,
        sonusCdrServerAdminTransferTimeout SonusCdrServerTimeoutType,
        sonusCdrServerAdminRowstatus RowStatus,
        sonusCdrServerAdminBufferSize SonusCdrServerBufferSizeType,
        sonusCdrServerAdminCdrPort UnsignedShort,
        sonusCdrServerAdminUseSshKeyFile INTEGER
    }

-- tagpath /cdrServer/admin/type
sonusCdrServerAdminType OBJECT-TYPE
    SYNTAX      SonusCdrServerTypeType
    MAX-ACCESS  not-accessible
    STATUS      obsolete
    DESCRIPTION "
Server type - either primary of secondary.
"
    ::= { sonusCdrServerAdminEntry 1 }

-- tagpath /cdrServer/admin/ipAddress
sonusCdrServerAdminIpAddress OBJECT-TYPE
    SYNTAX      InetAddressIP
    MAX-ACCESS  read-create
    STATUS      obsolete
    DESCRIPTION "
The IP address of the server
"
    ::= { sonusCdrServerAdminEntry 2 }

-- tagpath /cdrServer/admin/username
sonusCdrServerAdminUsername OBJECT-TYPE
    SYNTAX      SonusCdrServerTypeName
    MAX-ACCESS  read-create
    STATUS      obsolete
    DESCRIPTION "
The username on the remote server
"
    ::= { sonusCdrServerAdminEntry 3 }

-- tagpath /cdrServer/admin/password
sonusCdrServerAdminPassword OBJECT-TYPE
    SYNTAX      SonusCdrServerTypePasswdStr
    MAX-ACCESS  read-create
    STATUS      obsolete
    DESCRIPTION "
The password on the remote server
"
    ::= { sonusCdrServerAdminEntry 4 }

-- tagpath /cdrServer/admin/path
sonusCdrServerAdminPath OBJECT-TYPE
    SYNTAX      SonusCdrServerTypeName
    MAX-ACCESS  read-create
    STATUS      obsolete
    DESCRIPTION "
The path on the remote server
"
    ::= { sonusCdrServerAdminEntry 5 }

-- tagpath /cdrServer/admin/filePrefix
sonusCdrServerAdminFilePrefix OBJECT-TYPE
    SYNTAX      SonusCdrServerTypeName
    MAX-ACCESS  read-create
    STATUS      obsolete
    DESCRIPTION "
The remote file prefix that will be appended with a datestamp
"
    ::= { sonusCdrServerAdminEntry 6 }

-- tagpath /cdrServer/admin/connectionTimeout
sonusCdrServerAdminConnectionTimeout OBJECT-TYPE
    SYNTAX      SonusCdrServerConnectionTimeoutType
    MAX-ACCESS  read-create
    STATUS      obsolete
    DESCRIPTION "
The time to wait before timing out the connect operation
"
    DEFVAL { 30 }
    ::= { sonusCdrServerAdminEntry 7 }

-- tagpath /cdrServer/admin/transferTimeout
sonusCdrServerAdminTransferTimeout OBJECT-TYPE
    SYNTAX      SonusCdrServerTimeoutType
    MAX-ACCESS  read-create
    STATUS      obsolete
    DESCRIPTION "
The time to wait before timing out the file transfer
"
    DEFVAL { 120 }
    ::= { sonusCdrServerAdminEntry 8 }

-- tagpath /cdrServer/admin/rowstatus
sonusCdrServerAdminRowstatus OBJECT-TYPE
    SYNTAX      RowStatus
    MAX-ACCESS  read-create
    STATUS      obsolete
    DESCRIPTION ""
    ::= { sonusCdrServerAdminEntry 9 }

-- tagpath /cdrServer/admin/bufferSize
sonusCdrServerAdminBufferSize OBJECT-TYPE
    SYNTAX      SonusCdrServerBufferSizeType
    MAX-ACCESS  read-create
    STATUS      obsolete
    DESCRIPTION "
The size of data to send to sftp server. Some servers may not handle large sizes.
"
    DEFVAL { 1024 }
    ::= { sonusCdrServerAdminEntry 10 }

-- tagpath /cdrServer/admin/cdrPort
sonusCdrServerAdminCdrPort OBJECT-TYPE
    SYNTAX      UnsignedShort (1 .. 65535)
    MAX-ACCESS  read-create
    STATUS      obsolete
    DESCRIPTION "
The ssh port of the remote server.
"
    ::= { sonusCdrServerAdminEntry 11 }

-- tagpath /cdrServer/admin/useSshKeyFile
sonusCdrServerAdminUseSshKeyFile OBJECT-TYPE
    SYNTAX      INTEGER {disable(0),enable(1)}
    MAX-ACCESS  read-create
    STATUS      obsolete
    DESCRIPTION "
use ssh public key for authentication on the remote server.
"
    ::= { sonusCdrServerAdminEntry 12 }

-- tagpath /cdrServer/status
sonusCdrServerStatusTable OBJECT-TYPE
    SYNTAX      SEQUENCE OF SonusCdrServerStatusEntry
    MAX-ACCESS  not-accessible
    STATUS      current
    DESCRIPTION "
CDR server status
"
    ::= { sonusCdrServer 2 }

-- tagpath /cdrServer/status
sonusCdrServerStatusEntry OBJECT-TYPE
    SYNTAX      SonusCdrServerStatusEntry
    MAX-ACCESS  not-accessible
    STATUS      current
    DESCRIPTION ""
    INDEX { sonusCdrServerStatusType }
        ::= { sonusCdrServerStatusTable 1 }

SonusCdrServerStatusEntry ::=
    SEQUENCE {
        sonusCdrServerStatusType SonusCdrServerTypeType,
        sonusCdrServerStatusState SonusCdrServerTypeState,
        sonusCdrServerStatusProgress SonusCdrServerTypeXferState,
        sonusCdrServerStatusSuccessfulTransfers Counter32,
        sonusCdrServerStatusFailedTransfers Counter32,
        sonusCdrServerStatusPendingTransfers Counter32
    }

-- tagpath /cdrServer/status/type
sonusCdrServerStatusType OBJECT-TYPE
    SYNTAX      SonusCdrServerTypeType
    MAX-ACCESS  not-accessible
    STATUS      current
    DESCRIPTION "
Server type - either primary of secondary.
"
    ::= { sonusCdrServerStatusEntry 1 }

-- tagpath /cdrServer/status/state
sonusCdrServerStatusState OBJECT-TYPE
    SYNTAX      SonusCdrServerTypeState
    MAX-ACCESS  read-only
    STATUS      current
    DESCRIPTION "
The type of the event log.  Each type has separate
configuration parameters and logs to a separate file.
"
    ::= { sonusCdrServerStatusEntry 2 }

-- tagpath /cdrServer/status/progress
sonusCdrServerStatusProgress OBJECT-TYPE
    SYNTAX      SonusCdrServerTypeXferState
    MAX-ACCESS  read-only
    STATUS      current
    DESCRIPTION "
Indicator that a transfer is in progress.
"
    ::= { sonusCdrServerStatusEntry 3 }

-- tagpath /cdrServer/status/successfulTransfers
sonusCdrServerStatusSuccessfulTransfers OBJECT-TYPE
    SYNTAX      Counter32
    MAX-ACCESS  read-only
    STATUS      current
    DESCRIPTION "
Count of the number of files successfully transferred.
"
    ::= { sonusCdrServerStatusEntry 4 }

-- tagpath /cdrServer/status/failedTransfers
sonusCdrServerStatusFailedTransfers OBJECT-TYPE
    SYNTAX      Counter32
    MAX-ACCESS  read-only
    STATUS      current
    DESCRIPTION "
Count of the number of failed transfers.
"
    ::= { sonusCdrServerStatusEntry 5 }

-- tagpath /cdrServer/status/pendingTransfers
sonusCdrServerStatusPendingTransfers OBJECT-TYPE
    SYNTAX      Counter32
    MAX-ACCESS  read-only
    STATUS      current
    DESCRIPTION "
Count the nmber of pending transfers.
"
    ::= { sonusCdrServerStatusEntry 6 }

END
