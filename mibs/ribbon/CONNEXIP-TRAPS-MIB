-- Sonus Networks, Inc.
--
-- ConnexIp traps.
--

	CONNEXIP-TRAPS-MIB

		DEFINITIONS ::= BEGIN

        IMPORTS
            MODULE-IDENTITY, OBJECT-TYPE, Unsigned32, Integer32, NOTIFICATION-TYPE
                FROM SNMPv2-SMI
			DisplayString 
				FROM SNMPv2-TC
			OBJECT-GROUP, NOTIFICATION-GROUP
				FROM SNMPv2-CONF
			sonusCspsNotificationMIBs
				FROM SONUS-SMI
			sonusServerID, 
			sonusAlarmNodeID, 
			sonusAlarmLevel, 
			sonusAlarmSequenceId, 
			sonusAlarmTime,
			sonusAlarmDescription
				FROM SONUS-COMMON-TRAP-MIB;

        sonusConnexIpTrapsMIB MODULE-IDENTITY
			LAST-UPDATED "200807110000Z" -- Fri Jul  11 14:10:11 EST 2008
            ORGANIZATION "Sonus Networks, Inc."
            CONTACT-INFO
               "   Customer Support    
                   Sonus Networks, Inc.
                   4 Technology Park Drive
                   Westford, MA 01886
                   USA

                   Tel: 978-614-8100
                   Fax: 978-614-8609"
            DESCRIPTION
               "The MIB Module for ConnexIp Traps."
			REVISION "200807110000Z" -- Fri Jul  11 14:10:11 EST 2008
            DESCRIPTION
               "Last revision."
            ::= { sonusCspsNotificationMIBs 4 }


sonusConnexIpTraps OBJECT IDENTIFIER ::= { sonusConnexIpTrapsMIB 1 }


sonusConnexIpSystemServicesMIBNotifications OBJECT IDENTIFIER ::= { sonusConnexIpTraps 1 }
sonusConnexIpSystemServicesMIBNotificationsPrefix  OBJECT IDENTIFIER ::= { sonusConnexIpSystemServicesMIBNotifications 0 }
sonusConnexIpSystemServicesMIBNotificationsObjects OBJECT IDENTIFIER ::= { sonusConnexIpSystemServicesMIBNotifications 1 }


sonusConnexIpSystemCEPowerSupplyFailureNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemPowerSupplyId
               }
    STATUS       current
    DESCRIPTION
                "This trap indicates that a power supply of the server failed."
    ::= { sonusConnexIpSystemServicesMIBNotificationsPrefix 1 }

sonusConnexIpSystemCEPowerSupplyNormalNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemPowerSupplyId
               }
    STATUS       current
    DESCRIPTION
                "This trap indicates that a power supply of the server is normal."
    ::= { sonusConnexIpSystemServicesMIBNotificationsPrefix 2 }

sonusConnexIpSystemCEPowerSupplyUnitRemovedNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemPowerSupplyId
               }
    STATUS       current
    DESCRIPTION
                "This trap indicates that a power supply unit of the server is removed."
    ::= { sonusConnexIpSystemServicesMIBNotificationsPrefix 3 }

sonusConnexIpSystemCEPowerSupplyUnitInsertedNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemPowerSupplyId
               }
    STATUS       current
    DESCRIPTION
                "This trap indicates that a power supply unit of the server is inserted."
    ::= { sonusConnexIpSystemServicesMIBNotificationsPrefix 4 }

sonusConnexIpSystemCEFanNormalNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemFanId,
                 sonusConnexIpSystemFanSpeed
               }
    STATUS       current
    DESCRIPTION
                "This trap indicates that a fan of the server is operating normal."
    ::= { sonusConnexIpSystemServicesMIBNotificationsPrefix 5 }

sonusConnexIpSystemCEFanFailureNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemFanId,
                 sonusConnexIpSystemFanSpeed
               }
    STATUS       current
    DESCRIPTION
                "This trap indicates that a fan of the server is failed."
    ::= { sonusConnexIpSystemServicesMIBNotificationsPrefix 6 }

sonusConnexIpSystemCEFanAbsentNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemFanId
               }
    STATUS       current
    DESCRIPTION
                "This trap indicates that a fan of the server is removed (absent)."
    ::= { sonusConnexIpSystemServicesMIBNotificationsPrefix 7 }

sonusConnexIpSystemCEFanPresentNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName,
                 sonusConnexIpSystemFanId
               }
    STATUS       current
    DESCRIPTION
                "This trap indicates that a fan of the server is inserted (present)."
    ::= { sonusConnexIpSystemServicesMIBNotificationsPrefix 8 }

sonusConnexIpSystemCEMultipleFanAbsentNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName
               }
    STATUS       current
    DESCRIPTION
                "This trap indicates that two or more fans of the server are removed (absent)."
    ::= { sonusConnexIpSystemServicesMIBNotificationsPrefix 9 }

sonusConnexIpSystemCEMultipleFanPresentNotification NOTIFICATION-TYPE
    OBJECTS    { 
                 sonusAlarmNodeID,
                 sonusAlarmLevel,
                 sonusAlarmSequenceId,
                 sonusAlarmTime,
                 sonusAlarmDescription,
                 sonusConnexIpSystemAdminName,
                 sonusConnexIpSystemServerName
               }
    STATUS       current
    DESCRIPTION
                "This trap indicates that at least two fans of the server are present."
    ::= { sonusConnexIpSystemServicesMIBNotificationsPrefix 10 }

sonusConnexIpSystemCECardInsertedNotification NOTIFICATION-TYPE
    OBJECTS    { 
                 sonusAlarmNodeID,
                 sonusAlarmLevel,
                 sonusAlarmSequenceId,
                 sonusAlarmTime,
                 sonusAlarmDescription,
                 sonusConnexIpSystemServerName,
                 sonusConnexIpSlotNum,
                 sonusConnexIpCardType,
                 sonusConnexIpCardAdminState
               }
    STATUS       current
    DESCRIPTION
                "This trap indicates that a card is inserted into a specified slot on the server."
    ::= { sonusConnexIpSystemServicesMIBNotificationsPrefix 11 }

sonusConnexIpSystemCECardRemovedNotification NOTIFICATION-TYPE
    OBJECTS    { 
                 sonusAlarmNodeID,
                 sonusAlarmLevel,
                 sonusAlarmSequenceId,
                 sonusAlarmTime,
                 sonusAlarmDescription,
                 sonusConnexIpSystemServerName,
                 sonusConnexIpSlotNum,
                 sonusConnexIpCardType,
                 sonusConnexIpCardAdminState
               }
    STATUS       current
    DESCRIPTION
                "This trap indicates that a card is removed from a specified slot on the server."
    ::= { sonusConnexIpSystemServicesMIBNotificationsPrefix 12 }

sonusConnexIpSystemCESlotEnabledNotification NOTIFICATION-TYPE
    OBJECTS    { 
                 sonusAlarmNodeID,
                 sonusAlarmLevel,
                 sonusAlarmSequenceId,
                 sonusAlarmTime,
                 sonusAlarmDescription,
                 sonusConnexIpSystemServerName,
                 sonusConnexIpSlotNum,
                 sonusConnexIpCardType
               }
    STATUS       current
    DESCRIPTION
                "This trap indicates that a specified slot on the server is enabled."
    ::= { sonusConnexIpSystemServicesMIBNotificationsPrefix 13 }

sonusConnexIpSystemCESlotDisabledNotification NOTIFICATION-TYPE
    OBJECTS    { 
                 sonusAlarmNodeID,
                 sonusAlarmLevel,
                 sonusAlarmSequenceId,
                 sonusAlarmTime,
                 sonusAlarmDescription,
                 sonusConnexIpSystemServerName,
                 sonusConnexIpSlotNum,
                 sonusConnexIpCardType,
                 sonusConnexIpCleanupType,
                 sonusConnexIpDryupTime
               }
    STATUS       current
    DESCRIPTION
                "This trap indicates that a specified slot on the server is disabled."
    ::= { sonusConnexIpSystemServicesMIBNotificationsPrefix 14 }

sonusConnexIpSystemCESlotDryupNotification NOTIFICATION-TYPE
    OBJECTS    {
                 sonusAlarmNodeID,
                 sonusAlarmLevel,
                 sonusAlarmSequenceId,
                 sonusAlarmTime,
                 sonusAlarmDescription,
                 sonusConnexIpSystemServerName,
                 sonusConnexIpSlotNum,
                 sonusConnexIpCardType
               }   
    STATUS       current
    DESCRIPTION
                "This trap indicates that a specified slot on the server is going to dryup mode."
    ::= { sonusConnexIpSystemServicesMIBNotificationsPrefix 15 }



sonusConnexIpSystemCESlotMismatchNotification NOTIFICATION-TYPE
    OBJECTS    {
                 sonusAlarmNodeID,
                 sonusAlarmLevel,
                 sonusAlarmSequenceId,
                 sonusAlarmTime,
                 sonusAlarmDescription,
                 sonusConnexIpSystemServerName,
                 sonusConnexIpSlotNum
               }   
    STATUS       current
    DESCRIPTION
                "This trap indicates that a specified slot on the server is mismatched with peer server."
    ::= { sonusConnexIpSystemServicesMIBNotificationsPrefix 16 }


sonusConnexIpSystemCESlotMismatchClearNotification NOTIFICATION-TYPE
    OBJECTS    {
                 sonusAlarmNodeID,
                 sonusAlarmLevel,
                 sonusAlarmSequenceId,
                 sonusAlarmTime,
                 sonusAlarmDescription,
                 sonusConnexIpSystemServerName,
                 sonusConnexIpSlotNum
               }   
    STATUS       current
    DESCRIPTION
                "This trap indicates that a specified slot on the server mismatch with peer server is cleared ."
    ::= { sonusConnexIpSystemServicesMIBNotificationsPrefix 17 }

sonusConnexIpSystemCESlotLockNotification NOTIFICATION-TYPE
    OBJECTS    {
                 sonusAlarmNodeID,
                 sonusAlarmLevel,
                 sonusAlarmSequenceId,
                 sonusAlarmTime,
                 sonusAlarmDescription,
                 sonusConnexIpSystemServerName,
                 sonusConnexIpSlotNum
               }   
    STATUS       current
    DESCRIPTION
                "This trap indicates that a specified slot on the server is locked due to mismatch with peer server, system admin dspMismatchAction set to preserve redunndancy."
    ::= { sonusConnexIpSystemServicesMIBNotificationsPrefix 18 }

sonusConnexIpSystemCESlotLockClearNotification NOTIFICATION-TYPE
    OBJECTS    {
                 sonusAlarmNodeID,
                 sonusAlarmLevel,
                 sonusAlarmSequenceId,
                 sonusAlarmTime,
                 sonusAlarmDescription,
                 sonusConnexIpSystemServerName,
                 sonusConnexIpSlotNum
               }   
    STATUS       current
    DESCRIPTION
                "This trap indicates that a specified slot on the server lockout is cleared."
    ::= { sonusConnexIpSystemServicesMIBNotificationsPrefix 19 }

sonusConnexIpSystemCESlotFailedNotification NOTIFICATION-TYPE
    OBJECTS    {
                 sonusAlarmNodeID,
                 sonusAlarmLevel,
                 sonusAlarmSequenceId,
                 sonusAlarmTime,
                 sonusAlarmDescription,
                 sonusConnexIpSystemServerName,
                 sonusConnexIpSlotNum
               }   
    STATUS       current
    DESCRIPTION
                "This trap indicates that a specified slot on the server load/boot failed on 3 or more consecutive attempts. Module should be disabled, replaced and re-enabled in order to be returned to service."
    ::= { sonusConnexIpSystemServicesMIBNotificationsPrefix 20 }



    -- ADD NEW TRAPS HERE FOR THIS GROUP

sonusConnexIpSystemServerName OBJECT-TYPE
    SYNTAX      DisplayString
    MAX-ACCESS  read-only
    STATUS      current
    DESCRIPTION "
            The unique identifier assigned to this card or server.
          "
    ::= {sonusConnexIpSystemServicesMIBNotificationsObjects  1 }

sonusConnexIpSystemPowerSupplyId OBJECT-TYPE
    SYNTAX      DisplayString
    MAX-ACCESS  read-only
    STATUS      current
    DESCRIPTION "
           The name of the power supply (/SYS/VPS)
        "
    ::= { sonusConnexIpSystemServicesMIBNotificationsObjects 2 }

sonusConnexIpSystemFanId OBJECT-TYPE
    SYNTAX      DisplayString
    MAX-ACCESS  read-only
    STATUS      current
    DESCRIPTION "
           The name of the fan (usually /FT0/F0/ /FT0/F1/ etc).

        "
    ::= {sonusConnexIpSystemServicesMIBNotificationsObjects 3 }

sonusConnexIpSystemFanSpeed OBJECT-TYPE
    SYNTAX      Integer32
    MAX-ACCESS  read-only
    STATUS      current
    DESCRIPTION "
           Fan speed (in rpm)
        "
    ::= { sonusConnexIpSystemServicesMIBNotificationsObjects 4 }

sonusConnexIpSystemAdminName OBJECT-TYPE
    SYNTAX      DisplayString
    MAX-ACCESS  read-only
    STATUS      current
    DESCRIPTION "
            Name of the system
        "
    ::= { sonusConnexIpSystemServicesMIBNotificationsObjects 5 }

sonusConnexIpSlotNum OBJECT-TYPE
    SYNTAX      Integer32
    MAX-ACCESS  read-only
    STATUS      current
    DESCRIPTION "
            Slot number
        "
    ::= { sonusConnexIpSystemServicesMIBNotificationsObjects 6 }

sonusConnexIpCardType OBJECT-TYPE
    SYNTAX      DisplayString
    MAX-ACCESS  read-only
    STATUS      current
    DESCRIPTION "
            Card type
        "
    ::= { sonusConnexIpSystemServicesMIBNotificationsObjects 7 }

sonusConnexIpCardAdminState OBJECT-TYPE
         	SYNTAX       INTEGER { disabled(1), enabled(2) } 
			MAX-ACCESS  read-only
			STATUS  current
			DESCRIPTION "
                   Admin state of the card
				"
            ::= { sonusConnexIpSystemServicesMIBNotificationsObjects 8 }

sonusConnexIpCleanupType OBJECT-TYPE
         	SYNTAX       INTEGER { graceful(1), forced(2) } 
			MAX-ACCESS  read-only
			STATUS  current
			DESCRIPTION "
                   Cleanup type on disabling a slot
				"
            ::= { sonusConnexIpSystemServicesMIBNotificationsObjects 9 }

sonusConnexIpDryupTime OBJECT-TYPE
         	SYNTAX       INTEGER 
			MAX-ACCESS  read-only
			STATUS  current
			DESCRIPTION "
                   Dryup time allowed on disabling a slot
				"
            ::= { sonusConnexIpSystemServicesMIBNotificationsObjects 10 }

END
