-- Generated by
-- confdc ++emit-mib db64/sonusGen2Profiles.mib ++oid sonusCommonSoftwarePlatformServicesMIBs.11 ++top sonusGen2ProfilesMIB ++prefix Sonus ++module SONUS-GEN2-PROFILES-MIB -f /sonus/p4/ws/release/sbx5000_V08.02.00R002/hornet/dist/fxs/common/PerfHist-TC-MIB.fxs /sonus/p4/ws/release/sbx5000_V08.02.00R002/hornet/dist/fxs/common/SNMP-FRAMEWORK-MIB.fxs /sonus/p4/ws/release/sbx5000_V08.02.00R002/hornet/dist/fxs/common/SNMP-TARGET-MIB.fxs /sonus/p4/ws/release/sbx5000_V08.02.00R002/hornet/dist/fxs/common/SNMPv2-TC.fxs /sonus/p4/ws/release/sbx5000_V08.02.00R002/hornet/dist/fxs/common/ietf-inet-types.fxs /sonus/p4/ws/release/sbx5000_V08.02.00R002/hornet/dist/fxs/common/ietf-yang-types.fxs /sonus/p4/ws/release/sbx5000_V08.02.00R002/hornet/dist/fxs/common/sonusHornetTc.fxs /sonus/p4/ws/release/sbx5000_V08.02.00R002/hornet/dist/fxs/common/sonusTc.fxs ++ db64/sonusGen2Profiles.fxs
-- 2020-03-09 23:54:42
-- Namespace: http://sonusnet.com/ns/mibs/SONUS-GEN2-PROFILES-MIB/1.0

SONUS-GEN2-PROFILES-MIB DEFINITIONS ::= BEGIN
IMPORTS
    sonusCommonSoftwarePlatformServicesMIBs FROM SONUS-SMI
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

sonusGen2ProfilesMIB MODULE-IDENTITY
    LAST-UPDATED "201212310000Z"
    ORGANIZATION "Ribbon Communications, Inc."
    CONTACT-INFO "Customer Support        
                  Ribbon Communications, Inc. 
                  4 Technology Park Drive 
                  Westford, MA 01886      
                  USA                     
                                          
                  Tel: 978-614-8100       
                  Fax: 978-614-8609"
    DESCRIPTION "The MIB Module for Characteristic Management."
    REVISION "201212310000Z"
    DESCRIPTION "Auto generated MIB."
    ::= { sonusCommonSoftwarePlatformServicesMIBs 11 }

String ::= TEXTUAL-CONVENTION
    DISPLAY-HINT "1t"
    STATUS      current
    DESCRIPTION "xs:string"
    SYNTAX      OCTET STRING

SonusNodeCoreDumpCountLimitType ::= TEXTUAL-CONVENTION
    STATUS      current
    DESCRIPTION "
Number of coredumps allowed on harddisk per process. Minimum 1, Maximum 10.
"
    SYNTAX      Integer32 (1 .. 10)

SonusNodeCoreDumpLevelType ::= TEXTUAL-CONVENTION
    STATUS      current
    DESCRIPTION ""
    SYNTAX      INTEGER {disabled(1),normal(2),sensitive(3)}

SonusNodeCoreDumpSpaceLimitType ::= TEXTUAL-CONVENTION
    STATUS      current
    DESCRIPTION "
Coredump disk space limit in GigaBytes. Minimum 1, Maximum 20.
"
    SYNTAX      Integer32 (1 .. 20)

-- Profiles of configuration shared by multiple objects.
-- tagpath /profiles
sonusProfiles OBJECT IDENTIFIER ::= { sonusGen2ProfilesMIB 1 }

-- System-level profiles.
-- tagpath /profiles/system
sonusProfilesSystem OBJECT IDENTIFIER ::= { sonusProfiles 1 }

-- tagpath /profiles/system/coredumpProfile
sonusProfilesSystemCoredumpProfileTable OBJECT-TYPE
    SYNTAX      SEQUENCE OF SonusProfilesSystemCoredumpProfileEntry
    MAX-ACCESS  not-accessible
    STATUS      obsolete
    DESCRIPTION "
Coredump settings applicable to server(s)
"
    ::= { sonusProfilesSystem 1 }

-- tagpath /profiles/system/coredumpProfile
sonusProfilesSystemCoredumpProfileEntry OBJECT-TYPE
    SYNTAX      SonusProfilesSystemCoredumpProfileEntry
    MAX-ACCESS  not-accessible
    STATUS      obsolete
    DESCRIPTION ""
    INDEX { sonusProfilesSystemCoredumpProfileName }
        ::= { sonusProfilesSystemCoredumpProfileTable 1 }

SonusProfilesSystemCoredumpProfileEntry ::=
    SEQUENCE {
        sonusProfilesSystemCoredumpProfileName String,
        sonusProfilesSystemCoredumpProfileCoredumpLevel SonusNodeCoreDumpLevelType,
        sonusProfilesSystemCoredumpProfileCoredumpPath String,
        sonusProfilesSystemCoredumpProfileCoredumpSpaceLimit SonusNodeCoreDumpSpaceLimitType,
        sonusProfilesSystemCoredumpProfileCoredumpCountLimit SonusNodeCoreDumpCountLimitType,
        sonusProfilesSystemCoredumpProfileRowstatus RowStatus
    }

-- tagpath /profiles/system/coredumpProfile/name
sonusProfilesSystemCoredumpProfileName OBJECT-TYPE
    SYNTAX      String (SIZE (0 .. 23))
    MAX-ACCESS  not-accessible
    STATUS      obsolete
    DESCRIPTION "
The name of the profile.
"
    ::= { sonusProfilesSystemCoredumpProfileEntry 1 }

-- tagpath /profiles/system/coredumpProfile/coredumpLevel
sonusProfilesSystemCoredumpProfileCoredumpLevel OBJECT-TYPE
    SYNTAX      SonusNodeCoreDumpLevelType
    MAX-ACCESS  read-create
    STATUS      obsolete
    DESCRIPTION "
Sensitivity level for coredumping.
"
    DEFVAL { normal }
    ::= { sonusProfilesSystemCoredumpProfileEntry 2 }

-- tagpath /profiles/system/coredumpProfile/coredumpPath
sonusProfilesSystemCoredumpProfileCoredumpPath OBJECT-TYPE
    SYNTAX      String (SIZE (0 .. 255))
    MAX-ACCESS  read-create
    STATUS      obsolete
    DESCRIPTION "
The path of the coredump.
"
    ::= { sonusProfilesSystemCoredumpProfileEntry 3 }

-- tagpath /profiles/system/coredumpProfile/coredumpSpaceLimit
sonusProfilesSystemCoredumpProfileCoredumpSpaceLimit OBJECT-TYPE
    SYNTAX      SonusNodeCoreDumpSpaceLimitType
    MAX-ACCESS  read-create
    STATUS      obsolete
    DESCRIPTION "
Coredump disk space limit per server (in GigaBytes).
"
    DEFVAL { 6 }
    ::= { sonusProfilesSystemCoredumpProfileEntry 4 }

-- tagpath /profiles/system/coredumpProfile/coredumpCountLimit
sonusProfilesSystemCoredumpProfileCoredumpCountLimit OBJECT-TYPE
    SYNTAX      SonusNodeCoreDumpCountLimitType
    MAX-ACCESS  read-create
    STATUS      obsolete
    DESCRIPTION "
Number of coredumps allowed on disk (per process).
"
    DEFVAL { 3 }
    ::= { sonusProfilesSystemCoredumpProfileEntry 5 }

-- tagpath /profiles/system/coredumpProfile/rowstatus
sonusProfilesSystemCoredumpProfileRowstatus OBJECT-TYPE
    SYNTAX      RowStatus
    MAX-ACCESS  read-create
    STATUS      obsolete
    DESCRIPTION ""
    ::= { sonusProfilesSystemCoredumpProfileEntry 6 }

END
