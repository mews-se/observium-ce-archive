-- Generated by
-- confdc ++emit-mib db64/sonusSystem.mib ++oid sonusCommonSoftwarePlatformServicesMIBs.5 ++top sonusSystemMIB ++prefix Sonus ++module SONUS-SYSTEM-MIB -f /sonus/p4/ws/release/sbx5000_V08.02.00R002/hornet/dist/fxs/common/PerfHist-TC-MIB.fxs /sonus/p4/ws/release/sbx5000_V08.02.00R002/hornet/dist/fxs/common/SNMP-FRAMEWORK-MIB.fxs /sonus/p4/ws/release/sbx5000_V08.02.00R002/hornet/dist/fxs/common/SNMP-TARGET-MIB.fxs /sonus/p4/ws/release/sbx5000_V08.02.00R002/hornet/dist/fxs/common/SNMPv2-TC.fxs /sonus/p4/ws/release/sbx5000_V08.02.00R002/hornet/dist/fxs/common/ietf-inet-types.fxs /sonus/p4/ws/release/sbx5000_V08.02.00R002/hornet/dist/fxs/common/ietf-yang-types.fxs /sonus/p4/ws/release/sbx5000_V08.02.00R002/hornet/dist/fxs/common/sonusGen2Profiles.fxs /sonus/p4/ws/release/sbx5000_V08.02.00R002/hornet/dist/fxs/common/sonusHornetTc.fxs /sonus/p4/ws/release/sbx5000_V08.02.00R002/hornet/dist/fxs/common/sonusLicense.fxs /sonus/p4/ws/release/sbx5000_V08.02.00R002/hornet/dist/fxs/common/sonusTc.fxs ++ db64/sonusSystem.fxs
-- 2020-03-09 23:54:42
-- Namespace: http://sonusnet.com/ns/mibs/SONUS-SYSTEM-MIB/1.0

SONUS-SYSTEM-MIB DEFINITIONS ::= BEGIN
IMPORTS
    sonusCommonSoftwarePlatformServicesMIBs FROM SONUS-SMI
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    Ipv6Address
        FROM IPV6-TC
;

sonusSystemMIB MODULE-IDENTITY
    LAST-UPDATED "201603230000Z"
    ORGANIZATION "Ribbon Communications, Inc."
    CONTACT-INFO "Customer Support        
                  Ribbon Communications, Inc. 
                  4 Technology Park Drive 
                  Westford, MA 01886      
                  USA                     
                                          
                  Tel: 978-614-8100       
                  Fax: 978-614-8609"
    DESCRIPTION "The MIB Module for Node Management."
    REVISION "201603230000Z"
    DESCRIPTION "Auto generated MIB."
    ::= { sonusCommonSoftwarePlatformServicesMIBs 5 }

Short ::= TEXTUAL-CONVENTION
    DISPLAY-HINT "d"
    STATUS      current
    DESCRIPTION "xs:short"
    SYNTAX      Integer32 (-32768 .. 32767)

UnsignedShort ::= TEXTUAL-CONVENTION
    DISPLAY-HINT "d"
    STATUS      current
    DESCRIPTION "xs:unsignedShort"
    SYNTAX      Unsigned32 (0 .. 65535)

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

HexList ::= TEXTUAL-CONVENTION
    DISPLAY-HINT "1x:"
    STATUS      current
    DESCRIPTION "confd:hexList"
    SYNTAX      OCTET STRING

SonusBlockCountType ::= TEXTUAL-CONVENTION
    STATUS      current
    DESCRIPTION "
          The blockCount type.  Range 5 to 256000 
      "
    SYNTAX      Unsigned32 (5 .. 256000)

AlphaNumericRestrictionType ::= TEXTUAL-CONVENTION
    STATUS      current
    DESCRIPTION "
The minimum number of characters in a particular class.
Enter value in range of 0-16
"
    SYNTAX      Unsigned32 (0 .. 16)

SonusCoreDumpType ::= TEXTUAL-CONVENTION
    STATUS      current
    DESCRIPTION "
Full or partial core dump process set.
"
    SYNTAX      INTEGER {full(0),partial(1)}

SonusNodeStatMgmtStatusType ::= TEXTUAL-CONVENTION
    STATUS      current
    DESCRIPTION ""
    SYNTAX      INTEGER {manageable(1),softwareUpgradeInProgress(2),softwareUpgradeFailed(3)}

SonusNodeUpgradeType ::= TEXTUAL-CONVENTION
    STATUS      current
    DESCRIPTION ""
    SYNTAX      INTEGER {normal(1),forced(2)}

SonusSearchString ::= TEXTUAL-CONVENTION
    DISPLAY-HINT "1t"
    STATUS      current
    DESCRIPTION "
        Input Search String.
      "
    SYNTAX      OCTET STRING (SIZE (0 .. 128))

SonusFacTimeOut ::= TEXTUAL-CONVENTION
    DISPLAY-HINT "d"
    STATUS      current
    DESCRIPTION "Global configurable for the fault record aging timeout.  Range 15 to 60 Min."
    SYNTAX      Integer32 (15 .. 60)

PasswordHashType ::= TEXTUAL-CONVENTION
    DISPLAY-HINT "1t"
    STATUS      current
    DESCRIPTION ""
    SYNTAX      OCTET STRING (SIZE (0 .. 128))

SonusAdSyncStatusType ::= TEXTUAL-CONVENTION
    STATUS      current
    DESCRIPTION ""
    SYNTAX      INTEGER {neverSynced(0),syncInProgress(1),syncCompleted(2),syncFailed(3),syncAccepted(4),syncRejected(5)}

SonusPasswordExpiryWarningPeriodType ::= TEXTUAL-CONVENTION
    STATUS      current
    DESCRIPTION "
Password expiry warning period in days.
Enter value in range of 3-14
"
    SYNTAX      Unsigned32 (3 .. 14)

SonusRevisionType ::= TEXTUAL-CONVENTION
    DISPLAY-HINT "d"
    STATUS      current
    DESCRIPTION ""
    SYNTAX      Integer32 (-32768 .. 32767)

OutOfMemoryCoredumpThresholdValueType ::= TEXTUAL-CONVENTION
    STATUS      current
    DESCRIPTION "
          Enter 'disabled' or a value in the range of (75..91)
        "
    SYNTAX      Integer32 (75 .. 91)

SonusAccountAgingPeriodType ::= TEXTUAL-CONVENTION
    STATUS      current
    DESCRIPTION "
Account aging period in days.
Enter value in range of 30-180
"
    SYNTAX      Unsigned32 (30 .. 180)

SonusNodeSrvrLastRestartReasonType ::= TEXTUAL-CONVENTION
    STATUS      current
    DESCRIPTION ""
    SYNTAX      INTEGER {unknown(1),systemRestart(2),systemSoftReset(3),serverRestart(4),serverSoftReset(5),switchover(6),processAbnormalTermination(7),softwareUpgradeOrRevert(8),managementPortDown(9)}

SonusPersonalityType ::= TEXTUAL-CONVENTION
    STATUS      current
    DESCRIPTION "personality type of the server"
    SYNTAX      INTEGER {isbc(1),ssbc(2),msbc(3),mrfp(4),slb(5)}

SonusSyncStatusType ::= TEXTUAL-CONVENTION
    STATUS      current
    DESCRIPTION ""
    SYNTAX      INTEGER {unknown(0),inSync(1),outOfSync(2),inProgress(3),notApplicable(4)}

SonusDspSlotIndex ::= TEXTUAL-CONVENTION
    STATUS      current
    DESCRIPTION "
The index for a DSP slot.
"
    SYNTAX      Unsigned32 (1 .. 4)

SonusNodeSrvrPktPortSpeed ::= TEXTUAL-CONVENTION
    STATUS      current
    DESCRIPTION "
Packet port speed setting
"
    SYNTAX      INTEGER {speed1Gbps(0),speed10Gbps(1)}

OutOfMemoryCoredumpThresholdDisabledType ::= TEXTUAL-CONVENTION
    DISPLAY-HINT "1t"
    STATUS      current
    DESCRIPTION "
          Enter 'disabled' or a value in the range of (75..91)
        "
    SYNTAX      OCTET STRING

SonusNodeSrvrRole ::= TEXTUAL-CONVENTION
    STATUS      current
    DESCRIPTION ""
    SYNTAX      INTEGER {primary(1),secondary(2)}

DaughterBoardOperationalStatus ::= TEXTUAL-CONVENTION
    STATUS      current
    DESCRIPTION ""
    SYNTAX      INTEGER {enabled(1),disabled(2),dryup(3),locked(4),loading(5),failed(6)}

FailedPasswordAttemptType ::= TEXTUAL-CONVENTION
    STATUS      current
    DESCRIPTION "
Allowed wrong password attempts.
Enter value in range of 1-10
"
    SYNTAX      Integer32 (1 .. 10)

MacAddressStatusType ::= TEXTUAL-CONVENTION
    STATUS      current
    DESCRIPTION "
Status of MAC address in macAddressStatus table .
"
    SYNTAX      INTEGER {free(1),used(2)}

OutOfMemoryCoredumpThresholdType ::= TEXTUAL-CONVENTION
    DISPLAY-HINT "1t"
    STATUS      current
    DESCRIPTION "
The threshold for taking coredumps when memory utilization increases
"
    SYNTAX      OCTET STRING

SonusDspDryupTime ::= TEXTUAL-CONVENTION
    STATUS      current
    DESCRIPTION "
Dryup time limits for DSPs in minutes.
"
    SYNTAX      Unsigned32 (0 .. 60)

SonusLeaderElectType ::= TEXTUAL-CONVENTION
    STATUS      current
    DESCRIPTION "
Leader election enumeration. CurrentValue indicates no change required for this parameter.
"
    SYNTAX      INTEGER {currentValue(0),standard(1),enhanced(2)}

SonusNodeVersionCheckType ::= TEXTUAL-CONVENTION
    STATUS      current
    DESCRIPTION ""
    SYNTAX      INTEGER {perform(1),skip(2)}

SonusOSAccountAgingPeriodType ::= TEXTUAL-CONVENTION
    STATUS      current
    DESCRIPTION "
Account aging period in days.
Enter value in range of 7-712
"
    SYNTAX      Unsigned32 (7 .. 712)

AccountUnlockTime ::= TEXTUAL-CONVENTION
    STATUS      current
    DESCRIPTION "
Auto unlock time value (in secs).
Enter value in range of 30-5400
"
    SYNTAX      Integer32 (30 .. 5400)

SonusBondMonitorType ::= TEXTUAL-CONVENTION
    STATUS      current
    DESCRIPTION "
Bond port monitoring  enumeration. CurrentValue indicates no change required for this parameter.
"
    SYNTAX      INTEGER {currentValue(0),direct-connect(1),network-connect(2)}

SonusNodeCeLicenseStatusType ::= TEXTUAL-CONVENTION
    STATUS      current
    DESCRIPTION ""
    SYNTAX      INTEGER {dualCe(1),singleCe(2)}

SonusNodeSwitchoverType ::= TEXTUAL-CONVENTION
    STATUS      current
    DESCRIPTION ""
    SYNTAX      INTEGER {normal(1),forced(2)}

SonusSystemHaModeType ::= TEXTUAL-CONVENTION
    STATUS      current
    DESCRIPTION "
SBC HA mode type.
"
    SYNTAX      INTEGER {haMode1to1(1),haModeNto1(2)}

SonusNodeServerLiveSoftwareUpgradeStatusType ::= TEXTUAL-CONVENTION
    STATUS      current
    DESCRIPTION ""
    SYNTAX      INTEGER {none(1),pendingUpgrade(2),upgrading(3),upgraded(4),pendingRevert(5),reverting(6),reverted(7),revertingOnError(8),committed(9)}

SonusNodeSrvrAdmnActionType ::= TEXTUAL-CONVENTION
    STATUS      current
    DESCRIPTION ""
    SYNTAX      INTEGER {dryUp(1),force(2),undefined(3)}

SonusNodeSrvrStatSwVersionType ::= TEXTUAL-CONVENTION
    DISPLAY-HINT "1t"
    STATUS      current
    DESCRIPTION ""
    SYNTAX      OCTET STRING (SIZE (0 .. 255))

SonusId ::= TEXTUAL-CONVENTION
    STATUS      current
    DESCRIPTION ""
    SYNTAX      INTEGER {all(1),activeConfigAndActivePolicy(2),activeAndStandbyPolicy(3)}

CoredumpCountLimitType ::= TEXTUAL-CONVENTION
    DISPLAY-HINT "d"
    STATUS      current
    DESCRIPTION "
Number of out of memory coredumps allowed on a node. Minimum 1, Maximum 10.
"
    SYNTAX      Unsigned32 (1 .. 10)

MinDiffWithOldPasswdType ::= TEXTUAL-CONVENTION
    STATUS      current
    DESCRIPTION "
The minimum difference between the new and old password.
Enter value in range of 1-8
"
    SYNTAX      Unsigned32 (1 .. 8)

PasswordType ::= TEXTUAL-CONVENTION
    DISPLAY-HINT "1t"
    STATUS      current
    DESCRIPTION ""
    SYNTAX      OCTET STRING (SIZE (0 .. 32))

SonusMaxSessionsType ::= TEXTUAL-CONVENTION
    STATUS      current
    DESCRIPTION "
Enter value in range of 1-5
"
    SYNTAX      Integer32 (1 .. 5)

SonusNodeShelfStatSerialNumberType ::= TEXTUAL-CONVENTION
    DISPLAY-HINT "1t"
    STATUS      current
    DESCRIPTION ""
    SYNTAX      OCTET STRING (SIZE (0 .. 255))

SonusNodeSrvrAdmnDryupLimitType ::= TEXTUAL-CONVENTION
    STATUS      current
    DESCRIPTION ""
    SYNTAX      Integer32 (0 .. 65535)

SonusNodeSrvrStatPartNumType ::= TEXTUAL-CONVENTION
    DISPLAY-HINT "1t"
    STATUS      current
    DESCRIPTION ""
    SYNTAX      OCTET STRING (SIZE (0 .. 255))

SonusNodeSrvrSyncStatusType ::= TEXTUAL-CONVENTION
    STATUS      current
    DESCRIPTION ""
    SYNTAX      INTEGER {syncInProgress(1),syncCompleted(2),unprotected(3),unprotectedRunningStandby(4)}

SonusNodeSyncStatusType ::= TEXTUAL-CONVENTION
    STATUS      current
    DESCRIPTION ""
    SYNTAX      INTEGER {synchronizingSource(1),synchronizingDestination(2),synchronized(3),unprotected(4),unknown(5),standyRepartitionInprogress(6),forceSwitchoverforRepartition(7),preParingforForcedSwitchover(8)}

BannerString ::= TEXTUAL-CONVENTION
    DISPLAY-HINT "1t"
    STATUS      current
    DESCRIPTION "
This data type is used to model textual information taken
from the NVT ASCII character set.  This type is similar to
SonusLongName, but can be null.  It is a replacement for
xs:string and xsd:string, since all strings must have a
maxLength specified.
"
    SYNTAX      OCTET STRING (SIZE (0 .. 1600))

LicenseBundleString ::= TEXTUAL-CONVENTION
    DISPLAY-HINT "1t"
    STATUS      current
    DESCRIPTION ""
    SYNTAX      OCTET STRING (SIZE (0 .. 12288))

OperationType ::= TEXTUAL-CONVENTION
    STATUS      current
    DESCRIPTION ""
    SYNTAX      INTEGER {lock(1),unlock(2)}

SonusDspDisableCleanupType ::= TEXTUAL-CONVENTION
    STATUS      current
    DESCRIPTION ""
    SYNTAX      INTEGER {graceful(1),forced(2)}

SonusNodeDiskStatusType ::= TEXTUAL-CONVENTION
    STATUS      current
    DESCRIPTION ""
    SYNTAX      INTEGER {online(1),missing(2),failed(3),unknown(4)}

SonusNodeSrvrStatMfgDateType ::= TEXTUAL-CONVENTION
    DISPLAY-HINT "1t"
    STATUS      current
    DESCRIPTION ""
    SYNTAX      OCTET STRING (SIZE (0 .. 255))

SonusConfigSyncStatus ::= TEXTUAL-CONVENTION
    STATUS      current
    DESCRIPTION ""
    SYNTAX      INTEGER {success(1),failure(2)}

SonusAdSearchResult ::= TEXTUAL-CONVENTION
    STATUS      current
    DESCRIPTION ""
    SYNTAX      INTEGER {notFound(0),found(1)}

SonusDetailedStatusType ::= TEXTUAL-CONVENTION
    DISPLAY-HINT "1t"
    STATUS      current
    DESCRIPTION ""
    SYNTAX      OCTET STRING (SIZE (0 .. 4096))

SonusNodeIntegrityCheckType ::= TEXTUAL-CONVENTION
    STATUS      current
    DESCRIPTION ""
    SYNTAX      INTEGER {perform(1),skip(2)}

SonusSessionType ::= TEXTUAL-CONVENTION
    STATUS      current
    DESCRIPTION "
The number of management session.
Enter value in range of 1-32
"
    SYNTAX      Integer32 (1 .. 32)

SonusSshMaxAuthTriesType ::= TEXTUAL-CONVENTION
    STATUS      current
    DESCRIPTION "
Enter value in range of 2-6
"
    SYNTAX      Integer32 (2 .. 6)

SonusTimeIntervalType ::= TEXTUAL-CONVENTION
    STATUS      current
    DESCRIPTION "
This type defines the range of the timer interval in minutes
that can be used by the configuration management for activities
such as to measure the statistics of certain resources.
"
    SYNTAX      Unsigned32 (5 .. 60)

SonusMaxCountTypeUnlimited ::= TEXTUAL-CONVENTION
    DISPLAY-HINT "1t"
    STATUS      current
    DESCRIPTION "
        Enter 'unlimited' or value in range of (2..1000000).
      "
    SYNTAX      OCTET STRING

SonusNodeLiveSoftwareUpgradeReasonType ::= TEXTUAL-CONVENTION
    STATUS      current
    DESCRIPTION ""
    SYNTAX      INTEGER {none(0),successfulCompletion(1),initTimeout(2),userInitiated(3),fileUnavailable(4),timeout(5),unexpectedSwitchover(6),internalError(7),failedToRemoveOldPackage(8),failedToInstallNewPackage(9),failedToStartApplication(10),userReset(11)}

SonusNodeLiveSoftwareUpgradeStatusType ::= TEXTUAL-CONVENTION
    STATUS      current
    DESCRIPTION ""
    SYNTAX      INTEGER {idle(1),upgradingStandby(2),upgradingActive(3),restartingStandby(4),upgradeDone(5),revertingStandby(6),revertingActive(7),revertDone(8),upgradeStopped(9),validatingCmd(10),reverting(11),standbyModelChange(12),activeModelChange(13),standbyRevertModelChange(14),activeRevertModelChange(15),waitRedundSyncComplete(16),upgrading(17)}

SonusNodeSrvrStatPartNumRevType ::= TEXTUAL-CONVENTION
    DISPLAY-HINT "1t"
    STATUS      current
    DESCRIPTION ""
    SYNTAX      OCTET STRING (SIZE (0 .. 255))

SonusSearchResponseString ::= TEXTUAL-CONVENTION
    DISPLAY-HINT "1t"
    STATUS      current
    DESCRIPTION "
      "
    SYNTAX      OCTET STRING (SIZE (0 .. 128))

SonusDspMismatchAction ::= TEXTUAL-CONVENTION
    STATUS      current
    DESCRIPTION ""
    SYNTAX      INTEGER {preserveRedundancy(1),preserveCapacity(2)}

MaxRepeatCountType ::= TEXTUAL-CONVENTION
    STATUS      current
    DESCRIPTION "
The maximum number of consecutive repeating character.
Enter value in range of 3-16
"
    SYNTAX      Unsigned32 (3 .. 16)

MinPasswordLengthType ::= TEXTUAL-CONVENTION
    STATUS      current
    DESCRIPTION "
The minimum number of characters in a password.
Enter value in range of 8-24
"
    SYNTAX      Unsigned32 (8 .. 24)

SonusAllowOldVersionType ::= TEXTUAL-CONVENTION
    STATUS      current
    DESCRIPTION ""
    SYNTAX      INTEGER {yes(1),no(2)}

SonusMaxCountType ::= TEXTUAL-CONVENTION
    DISPLAY-HINT "1t"
    STATUS      current
    DESCRIPTION "
          The maximum license count allowed
      "
    SYNTAX      OCTET STRING

SonusMinCountType ::= TEXTUAL-CONVENTION
    STATUS      current
    DESCRIPTION "
          The mininum license count allowed.  Range 1 to 256000
      "
    SYNTAX      Unsigned32 (1 .. 256000)

SonusPasswordAgingPeriodType ::= TEXTUAL-CONVENTION
    STATUS      current
    DESCRIPTION "
Password validity period in days.
Enter value in range of 1-365
"
    SYNTAX      Unsigned32 (1 .. 365)

SonusMaxCountTypeVal ::= TEXTUAL-CONVENTION
    STATUS      current
    DESCRIPTION "
        Enter 'unlimited' or value in range of (2..1000000).
      "
    SYNTAX      Integer32 (2 .. 1000000)

SonusConfigStoreType ::= TEXTUAL-CONVENTION
    STATUS      current
    DESCRIPTION "Defines the type of external cloud object store service used for configuration file save/retrieve"
    SYNTAX      INTEGER {ems(1),swift(2)}

SonusNodeSrvrStatModeType ::= TEXTUAL-CONVENTION
    STATUS      current
    DESCRIPTION ""
    SYNTAX      INTEGER {unknown(1),standby(2),active(3),switchoverPending(4)}

SonusNodeSrvrStatUserNameType ::= TEXTUAL-CONVENTION
    DISPLAY-HINT "1t"
    STATUS      current
    DESCRIPTION ""
    SYNTAX      OCTET STRING (SIZE (0 .. 255))

SonusNodeSrvrStatViewNameType ::= TEXTUAL-CONVENTION
    DISPLAY-HINT "1t"
    STATUS      current
    DESCRIPTION ""
    SYNTAX      OCTET STRING (SIZE (0 .. 255))

SonusNumberOfPastIntervalsType ::= TEXTUAL-CONVENTION
    STATUS      current
    DESCRIPTION "
This type defines the range of the number of past interval
that can be configured for retrieving the statistics data.
"
    SYNTAX      Unsigned32 (1 .. 12)

SonusSystemIdleTimeoutType ::= TEXTUAL-CONVENTION
    STATUS      current
    DESCRIPTION "
Timeout is in minutes from 1 to 120.
"
    SYNTAX      Integer32 (1 .. 120)

DiskNumberType ::= TEXTUAL-CONVENTION
    STATUS      current
    DESCRIPTION "
The index for a disk, 0 through 3.
"
    SYNTAX      Unsigned32 (0 .. 3)

PasswordHistoryDepthType ::= TEXTUAL-CONVENTION
    STATUS      current
    DESCRIPTION "
The number of passwords to be stored in history.
Enter value in range of 0-24
"
    SYNTAX      Unsigned32 (0 .. 24)

RaidDiskNumberType ::= TEXTUAL-CONVENTION
    STATUS      current
    DESCRIPTION "
The index for a disk (0 or 1).
"
    SYNTAX      Unsigned32 (0 .. 1)

SonusLicenseAdminStateType ::= TEXTUAL-CONVENTION
    STATUS      current
    DESCRIPTION "Admin state of a license"
    SYNTAX      INTEGER {disabled(1),enabled(2)}

SonusNodeUpgradeStateResetType ::= TEXTUAL-CONVENTION
    STATUS      current
    DESCRIPTION ""
    SYNTAX      INTEGER {normal(1),forced(2)}

SonusSystemManagementIpVersionType ::= TEXTUAL-CONVENTION
    STATUS      current
    DESCRIPTION ""
    SYNTAX      INTEGER {ipv4(1),ipv6(2)}

SonusAdAttributeIndex ::= TEXTUAL-CONVENTION
    STATUS      current
    DESCRIPTION ""
    SYNTAX      INTEGER {adAttribute1(251),adAttribute2(252),adAttribute3(253),adAttribute4(254),adAttribute5(255),adAttribute6(256),adAttribute7(257),adAttribute8(258),adAttribute9(259),adAttribute10(260),adAttribute11(261),adAttribute12(262),adAttribute13(263),adAttribute14(264),adAttribute15(265),adAttribute16(266),adAttribute17(267),adAttribute18(268),adAttribute19(269),adAttribute20(270),adAttribute21(271),adAttribute22(272),adAttribute23(273),adAttribute24(274),adAttribute25(275),adAttribute26(276),adAttribute27(277),adAttribute28(278),adAttribute29(279),adAttribute30(280),adAttribute31(281),adAttribute32(282)}

SonusFacKeyElement ::= TEXTUAL-CONVENTION
    STATUS      current
    DESCRIPTION ""
    SYNTAX      INTEGER {callingParty(4),calledParty(5),callId(6),sourceIp(7),callingNcalledId(8)}

NumberOfProcessesToCoredumpType ::= TEXTUAL-CONVENTION
    STATUS      current
    DESCRIPTION "
The number of processes to take a core dump of when memory utilization is high
"
    SYNTAX      Integer32 (1 .. 5)

SonusNodeSrvrHwType ::= TEXTUAL-CONVENTION
    DISPLAY-HINT "1t"
    STATUS      current
    DESCRIPTION ""
    SYNTAX      OCTET STRING (SIZE (0 .. 255))

SonusNodeSrvrStatSerialNumType ::= TEXTUAL-CONVENTION
    DISPLAY-HINT "1t"
    STATUS      current
    DESCRIPTION ""
    SYNTAX      OCTET STRING (SIZE (0 .. 255))

SonusAccountRemovalPeriodType ::= TEXTUAL-CONVENTION
    STATUS      current
    DESCRIPTION "
Account removal period in days.
Enter value in range of 60-360
"
    SYNTAX      Unsigned32 (60 .. 360)

SonusLicenseServerPriorityType ::= TEXTUAL-CONVENTION
    STATUS      current
    DESCRIPTION "Priority. Range 1 to 4"
    SYNTAX      Integer32 (1 .. 4)

SonusFacThreshold ::= TEXTUAL-CONVENTION
    DISPLAY-HINT "d"
    STATUS      current
    DESCRIPTION "Threshold range for SBC Fault Avalanche Detection and Control.  Range 0 to 999"
    SYNTAX      Integer32 (0 .. 999)

SonusLicenseModeType ::= TEXTUAL-CONVENTION
    STATUS      current
    DESCRIPTION "
The License mode
"
    SYNTAX      INTEGER {nodeLocked(0),domain(3)}

SonusNodeCeRunTimeModeType ::= TEXTUAL-CONVENTION
    STATUS      current
    DESCRIPTION ""
    SYNTAX      INTEGER {dualCe(1),singleCe(2)}

SonusNodeSrvrStatFlashVersionType ::= TEXTUAL-CONVENTION
    DISPLAY-HINT "1t"
    STATUS      current
    DESCRIPTION ""
    SYNTAX      OCTET STRING (SIZE (0 .. 255))

-- System-level configuration.
-- tagpath /system
sonusSystem OBJECT IDENTIFIER ::= { sonusSystemMIB 1 }

-- This indicates if the system is the configurator
-- tagpath /system/configurator
sonusSystemConfigurator OBJECT IDENTIFIER ::= { sonusSystem 41 }

-- tagpath /system/configurator/isConfigurator
sonusSystemConfiguratorIsConfigurator OBJECT-TYPE
    SYNTAX      TruthValue
    MAX-ACCESS  read-only
    STATUS      current
    DESCRIPTION "
This indicates if the system is the configurator.
"
    ::= { sonusSystemConfigurator 1 }

-- tagpath /system/resetLicenseStats
sonusSystemResetLicenseStats OBJECT IDENTIFIER ::= { sonusSystem 49 }

-- The shared key for sharing safenet licenses between active and standby nodes
-- tagpath /system/licenseClusterSharedId
sonusSystemLicenseClusterSharedId OBJECT IDENTIFIER ::= { sonusSystem 38 }

-- tagpath /system/licenseClusterSharedId/sharedId
sonusSystemLicenseClusterSharedIdSharedId OBJECT-TYPE
    SYNTAX      String (SIZE (0 .. 255))
    MAX-ACCESS  read-only
    STATUS      current
    DESCRIPTION "
The shared id.
"
    ::= { sonusSystemLicenseClusterSharedId 1 }

-- The CE license status table describes the state of license information.
-- tagpath /system/licenseStatus
sonusSystemLicenseStatus OBJECT IDENTIFIER ::= { sonusSystem 1 }

-- tagpath /system/licenseStatus/cemode
sonusSystemLicenseStatusCemode OBJECT-TYPE
    SYNTAX      SonusNodeCeLicenseStatusType
    MAX-ACCESS  read-only
    STATUS      current
    DESCRIPTION "
This is the current CE license state.
"
    ::= { sonusSystemLicenseStatus 1 }

-- Live software upgrade status at any given time.
-- tagpath /system/softwareUpgradeStatus
sonusSystemSoftwareUpgradeStatus OBJECT IDENTIFIER ::= { sonusSystem 2 }

-- tagpath /system/softwareUpgradeStatus/state
sonusSystemSoftwareUpgradeStatusState OBJECT-TYPE
    SYNTAX      SonusNodeLiveSoftwareUpgradeStatusType
    MAX-ACCESS  read-only
    STATUS      current
    DESCRIPTION "
This is the current LSWU state.
"
    ::= { sonusSystemSoftwareUpgradeStatus 1 }

-- tagpath /system/softwareUpgradeStatus/previousState
sonusSystemSoftwareUpgradeStatusPreviousState OBJECT-TYPE
    SYNTAX      SonusNodeLiveSoftwareUpgradeStatusType
    MAX-ACCESS  read-only
    STATUS      current
    DESCRIPTION "
This is the previous LSWU state.
"
    ::= { sonusSystemSoftwareUpgradeStatus 2 }

-- tagpath /system/softwareUpgradeStatus/upgradeStartTime
sonusSystemSoftwareUpgradeStatusUpgradeStartTime OBJECT-TYPE
    SYNTAX      String (SIZE (0 .. 255))
    MAX-ACCESS  read-only
    STATUS      current
    DESCRIPTION "
Indicates when the live software upgrade started.
"
    ::= { sonusSystemSoftwareUpgradeStatus 3 }

-- tagpath /system/softwareUpgradeStatus/upgradeCompleteTime
sonusSystemSoftwareUpgradeStatusUpgradeCompleteTime OBJECT-TYPE
    SYNTAX      String (SIZE (0 .. 255))
    MAX-ACCESS  read-only
    STATUS      current
    DESCRIPTION "
Indicates when the live software upgrade completed.
"
    ::= { sonusSystemSoftwareUpgradeStatus 18 }

-- tagpath /system/softwareUpgradeStatus/revertStartTime
sonusSystemSoftwareUpgradeStatusRevertStartTime OBJECT-TYPE
    SYNTAX      String (SIZE (0 .. 255))
    MAX-ACCESS  read-only
    STATUS      deprecated
    DESCRIPTION "
Indicates when the live software upgrade started.
"
    ::= { sonusSystemSoftwareUpgradeStatus 4 }

-- tagpath /system/softwareUpgradeStatus/package
sonusSystemSoftwareUpgradeStatusPackage OBJECT-TYPE
    SYNTAX      String (SIZE (0 .. 255))
    MAX-ACCESS  read-only
    STATUS      current
    DESCRIPTION "
Name of the new package.
"
    ::= { sonusSystemSoftwareUpgradeStatus 5 }

-- tagpath /system/softwareUpgradeStatus/rpmName
sonusSystemSoftwareUpgradeStatusRpmName OBJECT-TYPE
    SYNTAX      String (SIZE (0 .. 255))
    MAX-ACCESS  read-only
    STATUS      deprecated
    DESCRIPTION "
Name of the new rpm used for upgrade.
"
    ::= { sonusSystemSoftwareUpgradeStatus 6 }

-- tagpath /system/softwareUpgradeStatus/upgradeScript
sonusSystemSoftwareUpgradeStatusUpgradeScript OBJECT-TYPE
    SYNTAX      String (SIZE (0 .. 255))
    MAX-ACCESS  read-only
    STATUS      deprecated
    DESCRIPTION "
Script to run to perform upgrade.
"
    ::= { sonusSystemSoftwareUpgradeStatus 8 }

-- tagpath /system/softwareUpgradeStatus/revertScript
sonusSystemSoftwareUpgradeStatusRevertScript OBJECT-TYPE
    SYNTAX      String (SIZE (0 .. 255))
    MAX-ACCESS  read-only
    STATUS      deprecated
    DESCRIPTION "
Script to run to perform revert in case upgrade fails.
"
    ::= { sonusSystemSoftwareUpgradeStatus 9 }

-- tagpath /system/softwareUpgradeStatus/reason
sonusSystemSoftwareUpgradeStatusReason OBJECT-TYPE
    SYNTAX      SonusNodeLiveSoftwareUpgradeReasonType
    MAX-ACCESS  read-only
    STATUS      current
    DESCRIPTION "
Indicates the exit reason for failure of the last software upgrade.
"
    ::= { sonusSystemSoftwareUpgradeStatus 10 }

-- tagpath /system/softwareUpgradeStatus/cemodeAtStart
sonusSystemSoftwareUpgradeStatusCemodeAtStart OBJECT-TYPE
    SYNTAX      SonusNodeCeRunTimeModeType
    MAX-ACCESS  read-only
    STATUS      deprecated
    DESCRIPTION "
CE mode when upgrade started (single/dual).
"
    ::= { sonusSystemSoftwareUpgradeStatus 11 }

-- tagpath /system/softwareUpgradeStatus/oldRelease
sonusSystemSoftwareUpgradeStatusOldRelease OBJECT-TYPE
    SYNTAX      String (SIZE (0 .. 255))
    MAX-ACCESS  read-only
    STATUS      current
    DESCRIPTION "
Software release that was running before upgrade started.
"
    ::= { sonusSystemSoftwareUpgradeStatus 12 }

-- tagpath /system/softwareUpgradeStatus/newRelease
sonusSystemSoftwareUpgradeStatusNewRelease OBJECT-TYPE
    SYNTAX      String (SIZE (0 .. 255))
    MAX-ACCESS  read-only
    STATUS      current
    DESCRIPTION "
Software release to which the upgrade is performed.
"
    ::= { sonusSystemSoftwareUpgradeStatus 13 }

-- tagpath /system/softwareUpgradeStatus/activeCeAtStart
sonusSystemSoftwareUpgradeStatusActiveCeAtStart OBJECT-TYPE
    SYNTAX      String (SIZE (0 .. 255))
    MAX-ACCESS  read-only
    STATUS      deprecated
    DESCRIPTION "
Active CE name when the upgrade started.
"
    ::= { sonusSystemSoftwareUpgradeStatus 14 }

-- tagpath /system/softwareUpgradeStatus/modelChange
sonusSystemSoftwareUpgradeStatusModelChange OBJECT-TYPE
    SYNTAX      TruthValue
    MAX-ACCESS  read-only
    STATUS      deprecated
    DESCRIPTION "
Inidicates if the process model changed as part of this upgrade.
"
    ::= { sonusSystemSoftwareUpgradeStatus 15 }

-- tagpath /system/softwareUpgradeStatus/primaryUpgradeStatus
sonusSystemSoftwareUpgradeStatusPrimaryUpgradeStatus OBJECT-TYPE
    SYNTAX      SonusNodeServerLiveSoftwareUpgradeStatusType
    MAX-ACCESS  read-only
    STATUS      current
    DESCRIPTION "
Indicates the current status of the primary server.
"
    ::= { sonusSystemSoftwareUpgradeStatus 16 }

-- tagpath /system/softwareUpgradeStatus/secondaryUpgradeStatus
sonusSystemSoftwareUpgradeStatusSecondaryUpgradeStatus OBJECT-TYPE
    SYNTAX      SonusNodeServerLiveSoftwareUpgradeStatusType
    MAX-ACCESS  read-only
    STATUS      current
    DESCRIPTION "
Indicates the current status of the secondary server.
"
    ::= { sonusSystemSoftwareUpgradeStatus 17 }

-- The current ID of the last performance statistics written to the database
-- tagpath /system/fileStatisticsStatus
sonusSystemFileStatisticsStatus OBJECT IDENTIFIER ::= { sonusSystem 25 }

-- tagpath /system/fileStatisticsStatus/ID
sonusSystemFileStatisticsStatusID OBJECT-TYPE
    SYNTAX      Counter64
    MAX-ACCESS  read-only
    STATUS      current
    DESCRIPTION "
Identifies the server.
"
    ::= { sonusSystemFileStatisticsStatus 1 }

-- Personality of this instance
-- tagpath /system/sbcPersonalityStatus
sonusSystemSbcPersonalityStatus OBJECT IDENTIFIER ::= { sonusSystem 48 }

-- tagpath /system/sbcPersonalityStatus/role
sonusSystemSbcPersonalityStatusRole OBJECT-TYPE
    SYNTAX      SonusPersonalityType
    MAX-ACCESS  read-only
    STATUS      current
    DESCRIPTION "
Personality type of this instance.
"
    ::= { sonusSystemSbcPersonalityStatus 1 }

-- Parameters used to specify an object store service to upload or download
-- a configuration file.
-- tagpath /system/objectStoreParameters
sonusSystemObjectStoreParameters OBJECT IDENTIFIER ::= { sonusSystem 39 }

-- tagpath /system/objectStoreParameters/objectStoreType
sonusSystemObjectStoreParametersObjectStoreType OBJECT-TYPE
    SYNTAX      SonusConfigStoreType
    MAX-ACCESS  read-only
    STATUS      current
    DESCRIPTION "
The type of object store service.
"
    ::= { sonusSystemObjectStoreParameters 1 }

-- tagpath /system/objectStoreParameters/userName
sonusSystemObjectStoreParametersUserName OBJECT-TYPE
    SYNTAX      String (SIZE (0 .. 255))
    MAX-ACCESS  read-only
    STATUS      current
    DESCRIPTION "
The user name credential needed to access the object store service.
"
    ::= { sonusSystemObjectStoreParameters 2 }

-- tagpath /system/objectStoreParameters/password
sonusSystemObjectStoreParametersPassword OBJECT-TYPE
    SYNTAX      ConfdString
    MAX-ACCESS  read-only
    STATUS      current
    DESCRIPTION "
The password credential needed to access the object store service.
"
    ::= { sonusSystemObjectStoreParameters 3 }

-- tagpath /system/objectStoreParameters/url
sonusSystemObjectStoreParametersUrl OBJECT-TYPE
    SYNTAX      String (SIZE (0 .. 255))
    MAX-ACCESS  read-only
    STATUS      current
    DESCRIPTION "
The url used to access the object store service.
"
    ::= { sonusSystemObjectStoreParameters 4 }

-- Contains whether Nice recording is allowed or not.
-- tagpath /system/niceLicense
sonusSystemNiceLicense OBJECT IDENTIFIER ::= { sonusSystem 52 }

-- tagpath /system/niceLicense/isNiceRecordingAllowed
sonusSystemNiceLicenseIsNiceRecordingAllowed OBJECT-TYPE
    SYNTAX      TruthValue
    MAX-ACCESS  read-only
    STATUS      current
    DESCRIPTION "
if True nice recording is allowed else not.
"
    ::= { sonusSystemNiceLicense 1 }

-- Contains whether PDCS license is allowed or not.
-- tagpath /system/pdcsLicense
sonusSystemPdcsLicense OBJECT IDENTIFIER ::= { sonusSystem 54 }

-- tagpath /system/pdcsLicense/isPDCSAllowed
sonusSystemPdcsLicenseIsPDCSAllowed OBJECT-TYPE
    SYNTAX      TruthValue
    MAX-ACCESS  read-only
    STATUS      current
    DESCRIPTION "
if True PDCS license is allowed else not.
"
    ::= { sonusSystemPdcsLicense 1 }

-- Contains whether SBC-LI license is allowed or not.
-- tagpath /system/sbcliLicense
sonusSystemSbcliLicense OBJECT IDENTIFIER ::= { sonusSystem 55 }

-- tagpath /system/sbcliLicense/isSBCLIAllowed
sonusSystemSbcliLicenseIsSBCLIAllowed OBJECT-TYPE
    SYNTAX      TruthValue
    MAX-ACCESS  read-only
    STATUS      current
    DESCRIPTION "
if True SBC-LI license is allowed else not.
"
    ::= { sonusSystemSbcliLicense 1 }

-- tagpath /system/admin
sonusSystemAdminTable OBJECT-TYPE
    SYNTAX      SEQUENCE OF SonusSystemAdminEntry
    MAX-ACCESS  not-accessible
    STATUS      obsolete
    DESCRIPTION "
Basic configuration (name, location, etc) for the system.
"
    ::= { sonusSystem 3 }

-- tagpath /system/admin
sonusSystemAdminEntry OBJECT-TYPE
    SYNTAX      SonusSystemAdminEntry
    MAX-ACCESS  not-accessible
    STATUS      obsolete
    DESCRIPTION ""
    INDEX { sonusSystemAdminName }
        ::= { sonusSystemAdminTable 1 }

SonusSystemAdminEntry ::=
    SEQUENCE {
        sonusSystemAdminName String,
        sonusSystemAdminLocation String,
        sonusSystemAdminContact String,
        sonusSystemAdminCliIdleTimeout SonusSystemIdleTimeoutType,
        sonusSystemAdminLocalAuthenticationEnabled TruthValue,
        sonusSystemAdminExternalAuthenticationEnabled TruthValue,
        sonusSystemAdminStandbyServerState INTEGER,
        sonusSystemAdminUtilMonitorStatsInterval SonusTimeIntervalType,
        sonusSystemAdminUtilMonitorStatsNumOfPastInterval SonusNumberOfPastIntervalsType,
        sonusSystemAdminManagementIpVersion SonusSystemManagementIpVersionType,
        sonusSystemAdminAuditLogState INTEGER,
        sonusSystemAdminCliSessions SonusSessionType,
        sonusSystemAdminNetconfSessions SonusSessionType,
        sonusSystemAdminPasswordRulesMinimumLength MinPasswordLengthType,
        sonusSystemAdminPasswordRulesMinimumNumberOfUppercaseChars AlphaNumericRestrictionType,
        sonusSystemAdminPasswordRulesMinimumNumberOfLowercaseChars AlphaNumericRestrictionType,
        sonusSystemAdminPasswordRulesMinimumNumberOfDigits AlphaNumericRestrictionType,
        sonusSystemAdminPasswordRulesMinimumNumberOfOtherChars AlphaNumericRestrictionType,
        sonusSystemAdminPasswordRulesPasswordHistoryDepth PasswordHistoryDepthType,
        sonusSystemAdminPasswordRulesMaximumRepeatingCharsCount MaxRepeatCountType,
        sonusSystemAdminCliSetWarningSupport INTEGER,
        sonusSystemAdminRowstatus RowStatus,
        sonusSystemAdminActualSystemName String,
        sonusSystemAdminClusterId String,
        sonusSystemAdminDefaultAccountLocalOnly TruthValue
    }

-- tagpath /system/admin/name
sonusSystemAdminName OBJECT-TYPE
    SYNTAX      String (SIZE (0 .. 255))
    MAX-ACCESS  not-accessible
    STATUS      obsolete
    DESCRIPTION "
Name of the system.
"
    ::= { sonusSystemAdminEntry 1 }

-- tagpath /system/admin/location
sonusSystemAdminLocation OBJECT-TYPE
    SYNTAX      String (SIZE (0 .. 255))
    MAX-ACCESS  read-create
    STATUS      obsolete
    DESCRIPTION "
Physical location of the system.
"
    ::= { sonusSystemAdminEntry 2 }

-- tagpath /system/admin/contact
sonusSystemAdminContact OBJECT-TYPE
    SYNTAX      String (SIZE (0 .. 255))
    MAX-ACCESS  read-create
    STATUS      obsolete
    DESCRIPTION "
Contact information of the system.
"
    ::= { sonusSystemAdminEntry 3 }

-- tagpath /system/admin/cliIdleTimeout
sonusSystemAdminCliIdleTimeout OBJECT-TYPE
    SYNTAX      SonusSystemIdleTimeoutType
    MAX-ACCESS  read-create
    STATUS      obsolete
    DESCRIPTION "
This is the time before the CLI session will be diconnected.
"
    DEFVAL { 30 }
    ::= { sonusSystemAdminEntry 4 }

-- tagpath /system/admin/localAuthenticationEnabled
sonusSystemAdminLocalAuthenticationEnabled OBJECT-TYPE
    SYNTAX      TruthValue
    MAX-ACCESS  read-create
    STATUS      obsolete
    DESCRIPTION "
The confd cli user information stored locally can be used for authentication.
"
    ::= { sonusSystemAdminEntry 5 }

-- tagpath /system/admin/externalAuthenticationEnabled
sonusSystemAdminExternalAuthenticationEnabled OBJECT-TYPE
    SYNTAX      TruthValue
    MAX-ACCESS  read-create
    STATUS      obsolete
    DESCRIPTION "
The confd cli user information stored on remote Radius server used for authentication.
"
    ::= { sonusSystemAdminEntry 6 }

-- tagpath /system/admin/standbyServerState
sonusSystemAdminStandbyServerState OBJECT-TYPE
    SYNTAX      INTEGER {disabled(1),enabled(2)}
    MAX-ACCESS  read-create
    STATUS      obsolete
    DESCRIPTION "
Standby server state indicates if to bring up or not the standby server.
"
    ::= { sonusSystemAdminEntry 9 }

-- tagpath /system/admin/utilMonitorStatsInterval
sonusSystemAdminUtilMonitorStatsInterval OBJECT-TYPE
    SYNTAX      SonusTimeIntervalType
    MAX-ACCESS  read-create
    STATUS      obsolete
    DESCRIPTION "
The time interval for system resource monitoring statistics.
"
    DEFVAL { 15 }
    ::= { sonusSystemAdminEntry 10 }

-- tagpath /system/admin/utilMonitorStatsNumOfPastInterval
sonusSystemAdminUtilMonitorStatsNumOfPastInterval OBJECT-TYPE
    SYNTAX      SonusNumberOfPastIntervalsType
    MAX-ACCESS  read-create
    STATUS      obsolete
    DESCRIPTION "
The number of past intervals saved for system resource monitoring statistics.
"
    DEFVAL { 4 }
    ::= { sonusSystemAdminEntry 11 }

-- tagpath /system/admin/managementIpVersion
sonusSystemAdminManagementIpVersion OBJECT-TYPE
    SYNTAX      SonusSystemManagementIpVersionType
    MAX-ACCESS  read-create
    STATUS      obsolete
    DESCRIPTION "
This is the IP version used by the management application. The management application
will only accept packets using either IPV4 or IPV6 over the managemnt port.
"
    DEFVAL { ipv4 }
    ::= { sonusSystemAdminEntry 12 }

-- tagpath /system/admin/auditLogState
sonusSystemAdminAuditLogState OBJECT-TYPE
    SYNTAX      INTEGER {disabled(1),enabled(2)}
    MAX-ACCESS  read-create
    STATUS      obsolete
    DESCRIPTION "
This enables/disable the management audit log.
"
    ::= { sonusSystemAdminEntry 13 }

-- tagpath /system/admin/cliSessions
sonusSystemAdminCliSessions OBJECT-TYPE
    SYNTAX      SonusSessionType
    MAX-ACCESS  read-create
    STATUS      obsolete
    DESCRIPTION "
The number of active cli sessions allowed.
"
    DEFVAL { 16 }
    ::= { sonusSystemAdminEntry 14 }

-- tagpath /system/admin/netconfSessions
sonusSystemAdminNetconfSessions OBJECT-TYPE
    SYNTAX      SonusSessionType
    MAX-ACCESS  read-create
    STATUS      obsolete
    DESCRIPTION "
The number of active netconf sessions allowed.
"
    DEFVAL { 8 }
    ::= { sonusSystemAdminEntry 15 }

-- tagpath /system/admin/passwordRules/minimumLength
sonusSystemAdminPasswordRulesMinimumLength OBJECT-TYPE
    SYNTAX      MinPasswordLengthType
    MAX-ACCESS  read-create
    STATUS      obsolete
    DESCRIPTION "
Minimum number of characters that should be present in the password.
"
    DEFVAL { 8 }
    ::= { sonusSystemAdminEntry 16 }

-- tagpath /system/admin/passwordRules/minimumNumberOfUppercaseChars
sonusSystemAdminPasswordRulesMinimumNumberOfUppercaseChars OBJECT-TYPE
    SYNTAX      AlphaNumericRestrictionType
    MAX-ACCESS  read-create
    STATUS      obsolete
    DESCRIPTION "
Minimum number of upper case characters that should be present in the password.
"
    DEFVAL { 1 }
    ::= { sonusSystemAdminEntry 17 }

-- tagpath /system/admin/passwordRules/minimumNumberOfLowercaseChars
sonusSystemAdminPasswordRulesMinimumNumberOfLowercaseChars OBJECT-TYPE
    SYNTAX      AlphaNumericRestrictionType
    MAX-ACCESS  read-create
    STATUS      obsolete
    DESCRIPTION "
Minimum number of lower case characters that should be present in the password.
"
    DEFVAL { 1 }
    ::= { sonusSystemAdminEntry 18 }

-- tagpath /system/admin/passwordRules/minimumNumberOfDigits
sonusSystemAdminPasswordRulesMinimumNumberOfDigits OBJECT-TYPE
    SYNTAX      AlphaNumericRestrictionType
    MAX-ACCESS  read-create
    STATUS      obsolete
    DESCRIPTION "
Minimum number of digits that should be present in the password.
"
    DEFVAL { 1 }
    ::= { sonusSystemAdminEntry 19 }

-- tagpath /system/admin/passwordRules/minimumNumberOfOtherChars
sonusSystemAdminPasswordRulesMinimumNumberOfOtherChars OBJECT-TYPE
    SYNTAX      AlphaNumericRestrictionType
    MAX-ACCESS  read-create
    STATUS      obsolete
    DESCRIPTION "
Minimum number of non-alpha-numeric characters that should be present in the password.
"
    DEFVAL { 1 }
    ::= { sonusSystemAdminEntry 20 }

-- tagpath /system/admin/passwordRules/passwordHistoryDepth
sonusSystemAdminPasswordRulesPasswordHistoryDepth OBJECT-TYPE
    SYNTAX      PasswordHistoryDepthType
    MAX-ACCESS  read-create
    STATUS      obsolete
    DESCRIPTION "
The number of latest passwords that should be prevented from re-use.
"
    DEFVAL { 4 }
    ::= { sonusSystemAdminEntry 21 }

-- tagpath /system/admin/passwordRules/maximumRepeatingCharsCount
sonusSystemAdminPasswordRulesMaximumRepeatingCharsCount OBJECT-TYPE
    SYNTAX      MaxRepeatCountType
    MAX-ACCESS  read-create
    STATUS      obsolete
    DESCRIPTION "
Maximum number of consecutive repeatation for any character in the password.
"
    DEFVAL { 3 }
    ::= { sonusSystemAdminEntry 22 }

-- tagpath /system/admin/cliSetWarningSupport
sonusSystemAdminCliSetWarningSupport OBJECT-TYPE
    SYNTAX      INTEGER {disabled(1),enabled(2)}
    MAX-ACCESS  read-create
    STATUS      obsolete
    DESCRIPTION "
Setting to enable/disable warning prompts configured for the set command. This
setting does not modify warnings generated with the request command.
"
    ::= { sonusSystemAdminEntry 23 }

-- tagpath /system/admin/rowstatus
sonusSystemAdminRowstatus OBJECT-TYPE
    SYNTAX      RowStatus
    MAX-ACCESS  read-create
    STATUS      obsolete
    DESCRIPTION ""
    ::= { sonusSystemAdminEntry 24 }

-- tagpath /system/admin/actualSystemName
sonusSystemAdminActualSystemName OBJECT-TYPE
    SYNTAX      String (SIZE (0 .. 255))
    MAX-ACCESS  read-only
    STATUS      obsolete
    DESCRIPTION "
System Name given by user as user/metadata
"
    ::= { sonusSystemAdminEntry 25 }

-- tagpath /system/admin/clusterId
sonusSystemAdminClusterId OBJECT-TYPE
    SYNTAX      String (SIZE (0 .. 255))
    MAX-ACCESS  read-only
    STATUS      obsolete
    DESCRIPTION "
clusterID instance given in userdata
"
    ::= { sonusSystemAdminEntry 26 }

-- tagpath /system/admin/defaultAccountLocalOnly
sonusSystemAdminDefaultAccountLocalOnly OBJECT-TYPE
    SYNTAX      TruthValue
    MAX-ACCESS  read-create
    STATUS      obsolete
    DESCRIPTION "
Default confd cli user admin can only have local authentication.
"
    ::= { sonusSystemAdminEntry 27 }

-- tagpath /system/applications
sonusSystemApplicationsTable OBJECT-TYPE
    SYNTAX      SEQUENCE OF SonusSystemApplicationsEntry
    MAX-ACCESS  not-accessible
    STATUS      obsolete
    DESCRIPTION "
The applications deployed on the system.
"
    ::= { sonusSystem 4 }

-- tagpath /system/applications
sonusSystemApplicationsEntry OBJECT-TYPE
    SYNTAX      SonusSystemApplicationsEntry
    MAX-ACCESS  not-accessible
    STATUS      obsolete
    DESCRIPTION ""
    INDEX { sonusSystemApplicationsName }
        ::= { sonusSystemApplicationsTable 1 }

SonusSystemApplicationsEntry ::=
    SEQUENCE {
        sonusSystemApplicationsName String,
        sonusSystemApplicationsPath String,
        sonusSystemApplicationsRowstatus RowStatus
    }

-- tagpath /system/applications/name
sonusSystemApplicationsName OBJECT-TYPE
    SYNTAX      String (SIZE (0 .. 23))
    MAX-ACCESS  not-accessible
    STATUS      obsolete
    DESCRIPTION "
The name of the application.
"
    ::= { sonusSystemApplicationsEntry 1 }

-- tagpath /system/applications/path
sonusSystemApplicationsPath OBJECT-TYPE
    SYNTAX      String (SIZE (0 .. 255))
    MAX-ACCESS  read-create
    STATUS      obsolete
    DESCRIPTION "
The path of the application.
"
    ::= { sonusSystemApplicationsEntry 2 }

-- tagpath /system/applications/rowstatus
sonusSystemApplicationsRowstatus OBJECT-TYPE
    SYNTAX      RowStatus
    MAX-ACCESS  read-create
    STATUS      obsolete
    DESCRIPTION ""
    ::= { sonusSystemApplicationsEntry 3 }

-- tagpath /system/hardDiskStatus
sonusSystemHardDiskStatusTable OBJECT-TYPE
    SYNTAX      SEQUENCE OF SonusSystemHardDiskStatusEntry
    MAX-ACCESS  not-accessible
    STATUS      current
    DESCRIPTION "
Hard disk status on the server(s).
"
    ::= { sonusSystem 5 }

-- tagpath /system/hardDiskStatus
sonusSystemHardDiskStatusEntry OBJECT-TYPE
    SYNTAX      SonusSystemHardDiskStatusEntry
    MAX-ACCESS  not-accessible
    STATUS      current
    DESCRIPTION ""
    INDEX { sonusSystemHardDiskStatusServerName, sonusSystemHardDiskStatusDiskNumber }
        ::= { sonusSystemHardDiskStatusTable 1 }

SonusSystemHardDiskStatusEntry ::=
    SEQUENCE {
        sonusSystemHardDiskStatusServerName String,
        sonusSystemHardDiskStatusDiskNumber DiskNumberType,
        sonusSystemHardDiskStatusPresent TruthValue,
        sonusSystemHardDiskStatusProductId String,
        sonusSystemHardDiskStatusRevision String,
        sonusSystemHardDiskStatusCapacity String,
        sonusSystemHardDiskStatusDiskStatus SonusNodeDiskStatusType,
        sonusSystemHardDiskStatusSyncStatus SonusNodeSyncStatusType,
        sonusSystemHardDiskStatusSyncCompletion String,
        sonusSystemHardDiskStatusHealthTest String,
        sonusSystemHardDiskStatusDiskLifeRemaining String
    }

-- tagpath /system/hardDiskStatus/serverName
sonusSystemHardDiskStatusServerName OBJECT-TYPE
    SYNTAX      String (SIZE (0 .. 255))
    MAX-ACCESS  not-accessible
    STATUS      current
    DESCRIPTION "
Identifies the server.
"
    ::= { sonusSystemHardDiskStatusEntry 1 }

-- tagpath /system/hardDiskStatus/diskNumber
sonusSystemHardDiskStatusDiskNumber OBJECT-TYPE
    SYNTAX      DiskNumberType
    MAX-ACCESS  not-accessible
    STATUS      current
    DESCRIPTION "
Hard disk number (typically 0 through 3)
"
    ::= { sonusSystemHardDiskStatusEntry 2 }

-- tagpath /system/hardDiskStatus/present
sonusSystemHardDiskStatusPresent OBJECT-TYPE
    SYNTAX      TruthValue
    MAX-ACCESS  read-only
    STATUS      current
    DESCRIPTION "
Indicates if the hard disk exists.
"
    ::= { sonusSystemHardDiskStatusEntry 3 }

-- tagpath /system/hardDiskStatus/productId
sonusSystemHardDiskStatusProductId OBJECT-TYPE
    SYNTAX      String (SIZE (0 .. 255))
    MAX-ACCESS  read-only
    STATUS      current
    DESCRIPTION "
Product ID of the hard disk as assigned by vendor
"
    ::= { sonusSystemHardDiskStatusEntry 4 }

-- tagpath /system/hardDiskStatus/revision
sonusSystemHardDiskStatusRevision OBJECT-TYPE
    SYNTAX      String (SIZE (0 .. 23))
    MAX-ACCESS  read-only
    STATUS      current
    DESCRIPTION "
Revision of the hard disk as assigned by vendor
"
    ::= { sonusSystemHardDiskStatusEntry 5 }

-- tagpath /system/hardDiskStatus/capacity
sonusSystemHardDiskStatusCapacity OBJECT-TYPE
    SYNTAX      String (SIZE (0 .. 23))
    MAX-ACCESS  read-only
    STATUS      current
    DESCRIPTION "
Capacity of the disk
"
    ::= { sonusSystemHardDiskStatusEntry 6 }

-- tagpath /system/hardDiskStatus/diskStatus
sonusSystemHardDiskStatusDiskStatus OBJECT-TYPE
    SYNTAX      SonusNodeDiskStatusType
    MAX-ACCESS  read-only
    STATUS      current
    DESCRIPTION "
Harddisk status that indicates if the disk is online/failed
"
    ::= { sonusSystemHardDiskStatusEntry 7 }

-- tagpath /system/hardDiskStatus/syncStatus
sonusSystemHardDiskStatusSyncStatus OBJECT-TYPE
    SYNTAX      SonusNodeSyncStatusType
    MAX-ACCESS  read-only
    STATUS      obsolete
    DESCRIPTION "
RAID synchrinization status
"
    ::= { sonusSystemHardDiskStatusEntry 8 }

-- tagpath /system/hardDiskStatus/syncCompletion
sonusSystemHardDiskStatusSyncCompletion OBJECT-TYPE
    SYNTAX      String (SIZE (0 .. 23))
    MAX-ACCESS  read-only
    STATUS      obsolete
    DESCRIPTION "
Indicates hard disk sync completion percentage
"
    ::= { sonusSystemHardDiskStatusEntry 9 }

-- tagpath /system/hardDiskStatus/healthTest
sonusSystemHardDiskStatusHealthTest OBJECT-TYPE
    SYNTAX      String (SIZE (0 .. 255))
    MAX-ACCESS  read-only
    STATUS      current
    DESCRIPTION "
Pass or Fail indicating the overall health of the device.
"
    ::= { sonusSystemHardDiskStatusEntry 10 }

-- tagpath /system/hardDiskStatus/diskLifeRemaining
sonusSystemHardDiskStatusDiskLifeRemaining OBJECT-TYPE
    SYNTAX      String (SIZE (0 .. 23))
    MAX-ACCESS  read-only
    STATUS      current
    DESCRIPTION "
A calculated percentage estimating the life remaining of the device or N/A if not supported by the device.
"
    ::= { sonusSystemHardDiskStatusEntry 11 }

-- tagpath /system/hardDiskUsage
sonusSystemHardDiskUsageTable OBJECT-TYPE
    SYNTAX      SEQUENCE OF SonusSystemHardDiskUsageEntry
    MAX-ACCESS  not-accessible
    STATUS      current
    DESCRIPTION "
Hard disk status on the server(s).
"
    ::= { sonusSystem 6 }

-- tagpath /system/hardDiskUsage
sonusSystemHardDiskUsageEntry OBJECT-TYPE
    SYNTAX      SonusSystemHardDiskUsageEntry
    MAX-ACCESS  not-accessible
    STATUS      current
    DESCRIPTION ""
    INDEX { sonusSystemHardDiskUsageServerName, sonusSystemHardDiskUsagePartition }
        ::= { sonusSystemHardDiskUsageTable 1 }

SonusSystemHardDiskUsageEntry ::=
    SEQUENCE {
        sonusSystemHardDiskUsageServerName String,
        sonusSystemHardDiskUsagePartition String,
        sonusSystemHardDiskUsageTotalDiskSpace String,
        sonusSystemHardDiskUsageFreeDiskSpace String,
        sonusSystemHardDiskUsageUsedDiskSpace String,
        sonusSystemHardDiskUsageRole SonusNodeSrvrRole,
        sonusSystemHardDiskUsageSyncStatus SonusNodeSyncStatusType,
        sonusSystemHardDiskUsageSyncCompletion String
    }

-- tagpath /system/hardDiskUsage/serverName
sonusSystemHardDiskUsageServerName OBJECT-TYPE
    SYNTAX      String (SIZE (0 .. 255))
    MAX-ACCESS  not-accessible
    STATUS      current
    DESCRIPTION "
Identifies the server.
"
    ::= { sonusSystemHardDiskUsageEntry 1 }

-- tagpath /system/hardDiskUsage/partition
sonusSystemHardDiskUsagePartition OBJECT-TYPE
    SYNTAX      String (SIZE (0 .. 255))
    MAX-ACCESS  not-accessible
    STATUS      current
    DESCRIPTION "
Name of the hard disk partition
"
    ::= { sonusSystemHardDiskUsageEntry 2 }

-- tagpath /system/hardDiskUsage/totalDiskSpace
sonusSystemHardDiskUsageTotalDiskSpace OBJECT-TYPE
    SYNTAX      String (SIZE (0 .. 23))
    MAX-ACCESS  read-only
    STATUS      current
    DESCRIPTION "
Capacity of the disk (KBytes)
"
    ::= { sonusSystemHardDiskUsageEntry 3 }

-- tagpath /system/hardDiskUsage/freeDiskSpace
sonusSystemHardDiskUsageFreeDiskSpace OBJECT-TYPE
    SYNTAX      String (SIZE (0 .. 23))
    MAX-ACCESS  read-only
    STATUS      current
    DESCRIPTION "
Indicates free hard disk space (KBytes)
"
    ::= { sonusSystemHardDiskUsageEntry 4 }

-- tagpath /system/hardDiskUsage/usedDiskSpace
sonusSystemHardDiskUsageUsedDiskSpace OBJECT-TYPE
    SYNTAX      String (SIZE (0 .. 23))
    MAX-ACCESS  read-only
    STATUS      current
    DESCRIPTION "
Indicates used hard disk (%)
"
    ::= { sonusSystemHardDiskUsageEntry 5 }

-- tagpath /system/hardDiskUsage/role
sonusSystemHardDiskUsageRole OBJECT-TYPE
    SYNTAX      SonusNodeSrvrRole
    MAX-ACCESS  read-only
    STATUS      current
    DESCRIPTION "
Role of the server for the indicated partition
"
    ::= { sonusSystemHardDiskUsageEntry 6 }

-- tagpath /system/hardDiskUsage/syncStatus
sonusSystemHardDiskUsageSyncStatus OBJECT-TYPE
    SYNTAX      SonusNodeSyncStatusType
    MAX-ACCESS  read-only
    STATUS      current
    DESCRIPTION "
Partition's synchronization status with peer server
"
    ::= { sonusSystemHardDiskUsageEntry 7 }

-- tagpath /system/hardDiskUsage/syncCompletion
sonusSystemHardDiskUsageSyncCompletion OBJECT-TYPE
    SYNTAX      String (SIZE (0 .. 23))
    MAX-ACCESS  read-only
    STATUS      current
    DESCRIPTION "
Indicates partition's sync completion percentage
"
    ::= { sonusSystemHardDiskUsageEntry 8 }

-- tagpath /system/fanStatus
sonusSystemFanStatusTable OBJECT-TYPE
    SYNTAX      SEQUENCE OF SonusSystemFanStatusEntry
    MAX-ACCESS  not-accessible
    STATUS      current
    DESCRIPTION "
Fan status on the server(s).
"
    ::= { sonusSystem 7 }

-- tagpath /system/fanStatus
sonusSystemFanStatusEntry OBJECT-TYPE
    SYNTAX      SonusSystemFanStatusEntry
    MAX-ACCESS  not-accessible
    STATUS      current
    DESCRIPTION ""
    INDEX { sonusSystemFanStatusServerName, sonusSystemFanStatusFanId }
        ::= { sonusSystemFanStatusTable 1 }

SonusSystemFanStatusEntry ::=
    SEQUENCE {
        sonusSystemFanStatusServerName String,
        sonusSystemFanStatusFanId String,
        sonusSystemFanStatusSpeed String
    }

-- tagpath /system/fanStatus/serverName
sonusSystemFanStatusServerName OBJECT-TYPE
    SYNTAX      String (SIZE (0 .. 255))
    MAX-ACCESS  not-accessible
    STATUS      current
    DESCRIPTION "
Identifies the server.
"
    ::= { sonusSystemFanStatusEntry 1 }

-- tagpath /system/fanStatus/fanId
sonusSystemFanStatusFanId OBJECT-TYPE
    SYNTAX      String (SIZE (0 .. 255))
    MAX-ACCESS  not-accessible
    STATUS      current
    DESCRIPTION "
The name of the fan (usually /FT0/F0/ /FT0/F1/ etc).
"
    ::= { sonusSystemFanStatusEntry 2 }

-- tagpath /system/fanStatus/speed
sonusSystemFanStatusSpeed OBJECT-TYPE
    SYNTAX      String (SIZE (0 .. 23))
    MAX-ACCESS  read-only
    STATUS      current
    DESCRIPTION "
Indicates the fan speed in RPM.
"
    ::= { sonusSystemFanStatusEntry 3 }

-- tagpath /system/powerSupplyStatus
sonusSystemPowerSupplyStatusTable OBJECT-TYPE
    SYNTAX      SEQUENCE OF SonusSystemPowerSupplyStatusEntry
    MAX-ACCESS  not-accessible
    STATUS      current
    DESCRIPTION "
Power consumption/state of the server.
"
    ::= { sonusSystem 8 }

-- tagpath /system/powerSupplyStatus
sonusSystemPowerSupplyStatusEntry OBJECT-TYPE
    SYNTAX      SonusSystemPowerSupplyStatusEntry
    MAX-ACCESS  not-accessible
    STATUS      current
    DESCRIPTION ""
    INDEX { sonusSystemPowerSupplyStatusServerName, sonusSystemPowerSupplyStatusPowerSupplyId }
        ::= { sonusSystemPowerSupplyStatusTable 1 }

SonusSystemPowerSupplyStatusEntry ::=
    SEQUENCE {
        sonusSystemPowerSupplyStatusServerName String,
        sonusSystemPowerSupplyStatusPowerSupplyId String,
        sonusSystemPowerSupplyStatusPresent TruthValue,
        sonusSystemPowerSupplyStatusProductName String,
        sonusSystemPowerSupplyStatusSerialNum SonusNodeSrvrStatSerialNumType,
        sonusSystemPowerSupplyStatusPartNum SonusNodeSrvrStatPartNumType,
        sonusSystemPowerSupplyStatusManufactureDate SonusNodeSrvrStatMfgDateType,
        sonusSystemPowerSupplyStatusInputPower String,
        sonusSystemPowerSupplyStatusInputVoltage String,
        sonusSystemPowerSupplyStatusInputCurrent String,
        sonusSystemPowerSupplyStatusOutputPower String,
        sonusSystemPowerSupplyStatusOutputVoltage String,
        sonusSystemPowerSupplyStatusOutputCurrent String,
        sonusSystemPowerSupplyStatusAmbientTemperature String,
        sonusSystemPowerSupplyStatusFanSpeed String,
        sonusSystemPowerSupplyStatusPowerFault TruthValue,
        sonusSystemPowerSupplyStatusVoltageFault TruthValue,
        sonusSystemPowerSupplyStatusCurrentFault TruthValue,
        sonusSystemPowerSupplyStatusFanFault TruthValue,
        sonusSystemPowerSupplyStatusTemperatureFault TruthValue
    }

-- tagpath /system/powerSupplyStatus/serverName
sonusSystemPowerSupplyStatusServerName OBJECT-TYPE
    SYNTAX      String (SIZE (0 .. 255))
    MAX-ACCESS  not-accessible
    STATUS      current
    DESCRIPTION "
Identifies the server.
"
    ::= { sonusSystemPowerSupplyStatusEntry 1 }

-- tagpath /system/powerSupplyStatus/powerSupplyId
sonusSystemPowerSupplyStatusPowerSupplyId OBJECT-TYPE
    SYNTAX      String (SIZE (0 .. 23))
    MAX-ACCESS  not-accessible
    STATUS      current
    DESCRIPTION "
The name of the power supply (/SYS/VPS)
"
    ::= { sonusSystemPowerSupplyStatusEntry 2 }

-- tagpath /system/powerSupplyStatus/present
sonusSystemPowerSupplyStatusPresent OBJECT-TYPE
    SYNTAX      TruthValue
    MAX-ACCESS  read-only
    STATUS      current
    DESCRIPTION "
Indicates if the module is present or not.
"
    ::= { sonusSystemPowerSupplyStatusEntry 3 }

-- tagpath /system/powerSupplyStatus/productName
sonusSystemPowerSupplyStatusProductName OBJECT-TYPE
    SYNTAX      String (SIZE (0 .. 255))
    MAX-ACCESS  read-only
    STATUS      current
    DESCRIPTION "
Identifies the name (as given by manufacturer) of power supply module.
"
    ::= { sonusSystemPowerSupplyStatusEntry 4 }

-- tagpath /system/powerSupplyStatus/serialNum
sonusSystemPowerSupplyStatusSerialNum OBJECT-TYPE
    SYNTAX      SonusNodeSrvrStatSerialNumType
    MAX-ACCESS  read-only
    STATUS      current
    DESCRIPTION "
Identifies the serial number of the power supply module.  This is the
serial number assigned to the server module at manufacture.
"
    ::= { sonusSystemPowerSupplyStatusEntry 5 }

-- tagpath /system/powerSupplyStatus/partNum
sonusSystemPowerSupplyStatusPartNum OBJECT-TYPE
    SYNTAX      SonusNodeSrvrStatPartNumType
    MAX-ACCESS  read-only
    STATUS      current
    DESCRIPTION "
Identifies the part number of the module.  This is the
part number assigned to the module at manufacture.
"
    ::= { sonusSystemPowerSupplyStatusEntry 6 }

-- tagpath /system/powerSupplyStatus/manufactureDate
sonusSystemPowerSupplyStatusManufactureDate OBJECT-TYPE
    SYNTAX      SonusNodeSrvrStatMfgDateType
    MAX-ACCESS  read-only
    STATUS      obsolete
    DESCRIPTION "
The date this power supply module was manufactured.
"
    ::= { sonusSystemPowerSupplyStatusEntry 7 }

-- tagpath /system/powerSupplyStatus/inputPower
sonusSystemPowerSupplyStatusInputPower OBJECT-TYPE
    SYNTAX      String (SIZE (0 .. 23))
    MAX-ACCESS  read-only
    STATUS      obsolete
    DESCRIPTION "
Indicates input power in watts.
"
    ::= { sonusSystemPowerSupplyStatusEntry 8 }

-- tagpath /system/powerSupplyStatus/inputVoltage
sonusSystemPowerSupplyStatusInputVoltage OBJECT-TYPE
    SYNTAX      String (SIZE (0 .. 23))
    MAX-ACCESS  read-only
    STATUS      obsolete
    DESCRIPTION "
Indicates input volatge.
"
    ::= { sonusSystemPowerSupplyStatusEntry 9 }

-- tagpath /system/powerSupplyStatus/inputCurrent
sonusSystemPowerSupplyStatusInputCurrent OBJECT-TYPE
    SYNTAX      String (SIZE (0 .. 23))
    MAX-ACCESS  read-only
    STATUS      obsolete
    DESCRIPTION "
Indicates input current.
"
    ::= { sonusSystemPowerSupplyStatusEntry 10 }

-- tagpath /system/powerSupplyStatus/outputPower
sonusSystemPowerSupplyStatusOutputPower OBJECT-TYPE
    SYNTAX      String (SIZE (0 .. 23))
    MAX-ACCESS  read-only
    STATUS      obsolete
    DESCRIPTION "
Indicates output power in watts.
"
    ::= { sonusSystemPowerSupplyStatusEntry 11 }

-- tagpath /system/powerSupplyStatus/outputVoltage
sonusSystemPowerSupplyStatusOutputVoltage OBJECT-TYPE
    SYNTAX      String (SIZE (0 .. 23))
    MAX-ACCESS  read-only
    STATUS      obsolete
    DESCRIPTION "
Indicates output volatge.
"
    ::= { sonusSystemPowerSupplyStatusEntry 12 }

-- tagpath /system/powerSupplyStatus/outputCurrent
sonusSystemPowerSupplyStatusOutputCurrent OBJECT-TYPE
    SYNTAX      String (SIZE (0 .. 23))
    MAX-ACCESS  read-only
    STATUS      obsolete
    DESCRIPTION "
Indicates output current.
"
    ::= { sonusSystemPowerSupplyStatusEntry 13 }

-- tagpath /system/powerSupplyStatus/ambientTemperature
sonusSystemPowerSupplyStatusAmbientTemperature OBJECT-TYPE
    SYNTAX      String (SIZE (0 .. 23))
    MAX-ACCESS  read-only
    STATUS      obsolete
    DESCRIPTION "
Indicates ambient temperature of the power supply unit.
"
    ::= { sonusSystemPowerSupplyStatusEntry 14 }

-- tagpath /system/powerSupplyStatus/fanSpeed
sonusSystemPowerSupplyStatusFanSpeed OBJECT-TYPE
    SYNTAX      String (SIZE (0 .. 23))
    MAX-ACCESS  read-only
    STATUS      obsolete
    DESCRIPTION "
Indicates the fan speed in RPM.
"
    ::= { sonusSystemPowerSupplyStatusEntry 15 }

-- tagpath /system/powerSupplyStatus/powerFault
sonusSystemPowerSupplyStatusPowerFault OBJECT-TYPE
    SYNTAX      TruthValue
    MAX-ACCESS  read-only
    STATUS      current
    DESCRIPTION "
Indicates if there is power fault.
"
    ::= { sonusSystemPowerSupplyStatusEntry 16 }

-- tagpath /system/powerSupplyStatus/voltageFault
sonusSystemPowerSupplyStatusVoltageFault OBJECT-TYPE
    SYNTAX      TruthValue
    MAX-ACCESS  read-only
    STATUS      current
    DESCRIPTION "
Indicates if there is voltage fault.
"
    ::= { sonusSystemPowerSupplyStatusEntry 17 }

-- tagpath /system/powerSupplyStatus/currentFault
sonusSystemPowerSupplyStatusCurrentFault OBJECT-TYPE
    SYNTAX      TruthValue
    MAX-ACCESS  read-only
    STATUS      obsolete
    DESCRIPTION "
Indicates if there is current fault.
"
    ::= { sonusSystemPowerSupplyStatusEntry 18 }

-- tagpath /system/powerSupplyStatus/fanFault
sonusSystemPowerSupplyStatusFanFault OBJECT-TYPE
    SYNTAX      TruthValue
    MAX-ACCESS  read-only
    STATUS      obsolete
    DESCRIPTION "
Indicates if there is fan fault.
"
    ::= { sonusSystemPowerSupplyStatusEntry 19 }

-- tagpath /system/powerSupplyStatus/temperatureFault
sonusSystemPowerSupplyStatusTemperatureFault OBJECT-TYPE
    SYNTAX      TruthValue
    MAX-ACCESS  read-only
    STATUS      obsolete
    DESCRIPTION "
Indicates if there is temperature fault.
"
    ::= { sonusSystemPowerSupplyStatusEntry 20 }

-- tagpath /system/fileTransferStatus
sonusSystemFileTransferStatusTable OBJECT-TYPE
    SYNTAX      SEQUENCE OF SonusSystemFileTransferStatusEntry
    MAX-ACCESS  not-accessible
    STATUS      obsolete
    DESCRIPTION "
File transfer status on the system.
"
    ::= { sonusSystem 9 }

-- tagpath /system/fileTransferStatus
sonusSystemFileTransferStatusEntry OBJECT-TYPE
    SYNTAX      SonusSystemFileTransferStatusEntry
    MAX-ACCESS  not-accessible
    STATUS      obsolete
    DESCRIPTION ""
    INDEX { sonusSystemFileTransferStatusServerName, sonusSystemFileTransferStatusFileName }
        ::= { sonusSystemFileTransferStatusTable 1 }

SonusSystemFileTransferStatusEntry ::=
    SEQUENCE {
        sonusSystemFileTransferStatusServerName String,
        sonusSystemFileTransferStatusFileName String,
        sonusSystemFileTransferStatusSource String,
        sonusSystemFileTransferStatusStartTime String,
        sonusSystemFileTransferStatusCompletion String,
        sonusSystemFileTransferStatusStatus String
    }

-- tagpath /system/fileTransferStatus/serverName
sonusSystemFileTransferStatusServerName OBJECT-TYPE
    SYNTAX      String (SIZE (0 .. 255))
    MAX-ACCESS  not-accessible
    STATUS      obsolete
    DESCRIPTION "
Identifies the server.
"
    ::= { sonusSystemFileTransferStatusEntry 1 }

-- tagpath /system/fileTransferStatus/fileName
sonusSystemFileTransferStatusFileName OBJECT-TYPE
    SYNTAX      String (SIZE (0 .. 255))
    MAX-ACCESS  not-accessible
    STATUS      obsolete
    DESCRIPTION "
Identifies the file.
"
    ::= { sonusSystemFileTransferStatusEntry 2 }

-- tagpath /system/fileTransferStatus/source
sonusSystemFileTransferStatusSource OBJECT-TYPE
    SYNTAX      String (SIZE (0 .. 255))
    MAX-ACCESS  read-only
    STATUS      obsolete
    DESCRIPTION "
Identifies the source from where getting this file.
"
    ::= { sonusSystemFileTransferStatusEntry 3 }

-- tagpath /system/fileTransferStatus/startTime
sonusSystemFileTransferStatusStartTime OBJECT-TYPE
    SYNTAX      String (SIZE (0 .. 255))
    MAX-ACCESS  read-only
    STATUS      obsolete
    DESCRIPTION "
Indicates when the file transfer started.
"
    ::= { sonusSystemFileTransferStatusEntry 4 }

-- tagpath /system/fileTransferStatus/completion
sonusSystemFileTransferStatusCompletion OBJECT-TYPE
    SYNTAX      String (SIZE (0 .. 23))
    MAX-ACCESS  read-only
    STATUS      obsolete
    DESCRIPTION "
Percentage completion so far.
"
    ::= { sonusSystemFileTransferStatusEntry 5 }

-- tagpath /system/fileTransferStatus/status
sonusSystemFileTransferStatusStatus OBJECT-TYPE
    SYNTAX      String (SIZE (0 .. 255))
    MAX-ACCESS  read-only
    STATUS      obsolete
    DESCRIPTION "
Status of the transfer, success/failure reason.
"
    ::= { sonusSystemFileTransferStatusEntry 6 }

-- tagpath /system/syncStatus
sonusSystemSyncStatusTable OBJECT-TYPE
    SYNTAX      SEQUENCE OF SonusSystemSyncStatusEntry
    MAX-ACCESS  not-accessible
    STATUS      current
    DESCRIPTION "
The system server synchronization status table, describes data synchronization state of various items.
"
    ::= { sonusSystem 10 }

-- tagpath /system/syncStatus
sonusSystemSyncStatusEntry OBJECT-TYPE
    SYNTAX      SonusSystemSyncStatusEntry
    MAX-ACCESS  not-accessible
    STATUS      current
    DESCRIPTION ""
    INDEX { sonusSystemSyncStatusSyncModule }
        ::= { sonusSystemSyncStatusTable 1 }

SonusSystemSyncStatusEntry ::=
    SEQUENCE {
        sonusSystemSyncStatusSyncModule String,
        sonusSystemSyncStatusStatus SonusNodeSrvrSyncStatusType
    }

-- tagpath /system/syncStatus/syncModule
sonusSystemSyncStatusSyncModule OBJECT-TYPE
    SYNTAX      String (SIZE (0 .. 255))
    MAX-ACCESS  not-accessible
    STATUS      current
    DESCRIPTION "
Identifies the syncronization item.
"
    ::= { sonusSystemSyncStatusEntry 1 }

-- tagpath /system/syncStatus/status
sonusSystemSyncStatusStatus OBJECT-TYPE
    SYNTAX      SonusNodeSrvrSyncStatusType
    MAX-ACCESS  read-only
    STATUS      current
    DESCRIPTION "
Indicates the inter-CE data synchronization state.
"
    ::= { sonusSystemSyncStatusEntry 2 }

-- tagpath /system/standbySyncStatus
sonusSystemStandbySyncStatusTable OBJECT-TYPE
    SYNTAX      SEQUENCE OF SonusSystemStandbySyncStatusEntry
    MAX-ACCESS  not-accessible
    STATUS      current
    DESCRIPTION "
The standby server synchronization status table.  This table is used for N:1 redundancy where
a standby server support N active servers.  It describes data synchronization state of various items.
"
    ::= { sonusSystem 50 }

-- tagpath /system/standbySyncStatus
sonusSystemStandbySyncStatusEntry OBJECT-TYPE
    SYNTAX      SonusSystemStandbySyncStatusEntry
    MAX-ACCESS  not-accessible
    STATUS      current
    DESCRIPTION ""
    INDEX { sonusSystemStandbySyncStatusActiveServerName, sonusSystemStandbySyncStatusSyncModule }
        ::= { sonusSystemStandbySyncStatusTable 1 }

SonusSystemStandbySyncStatusEntry ::=
    SEQUENCE {
        sonusSystemStandbySyncStatusActiveServerName String,
        sonusSystemStandbySyncStatusSyncModule String,
        sonusSystemStandbySyncStatusStatus SonusNodeSrvrSyncStatusType
    }

-- tagpath /system/standbySyncStatus/activeServerName
sonusSystemStandbySyncStatusActiveServerName OBJECT-TYPE
    SYNTAX      String (SIZE (0 .. 255))
    MAX-ACCESS  not-accessible
    STATUS      current
    DESCRIPTION "
Identifies the active server.
"
    ::= { sonusSystemStandbySyncStatusEntry 1 }

-- tagpath /system/standbySyncStatus/syncModule
sonusSystemStandbySyncStatusSyncModule OBJECT-TYPE
    SYNTAX      String (SIZE (0 .. 255))
    MAX-ACCESS  not-accessible
    STATUS      current
    DESCRIPTION "
Identifies the syncronization item.
"
    ::= { sonusSystemStandbySyncStatusEntry 2 }

-- tagpath /system/standbySyncStatus/status
sonusSystemStandbySyncStatusStatus OBJECT-TYPE
    SYNTAX      SonusNodeSrvrSyncStatusType
    MAX-ACCESS  read-only
    STATUS      current
    DESCRIPTION "
Indicates the inter-CE data synchronization state.
"
    ::= { sonusSystemStandbySyncStatusEntry 3 }

-- tagpath /system/ledStatus
sonusSystemLedStatusTable OBJECT-TYPE
    SYNTAX      SEQUENCE OF SonusSystemLedStatusEntry
    MAX-ACCESS  not-accessible
    STATUS      current
    DESCRIPTION "
Displays status of various LEDs of the server.
"
    ::= { sonusSystem 24 }

-- tagpath /system/ledStatus
sonusSystemLedStatusEntry OBJECT-TYPE
    SYNTAX      SonusSystemLedStatusEntry
    MAX-ACCESS  not-accessible
    STATUS      current
    DESCRIPTION ""
    INDEX { sonusSystemLedStatusServerName, sonusSystemLedStatusLedType }
        ::= { sonusSystemLedStatusTable 1 }

SonusSystemLedStatusEntry ::=
    SEQUENCE {
        sonusSystemLedStatusServerName String,
        sonusSystemLedStatusLedType String,
        sonusSystemLedStatusLedState String,
        sonusSystemLedStatusLedColor String
    }

-- tagpath /system/ledStatus/serverName
sonusSystemLedStatusServerName OBJECT-TYPE
    SYNTAX      String (SIZE (0 .. 255))
    MAX-ACCESS  not-accessible
    STATUS      current
    DESCRIPTION "
Identifies the server.
"
    ::= { sonusSystemLedStatusEntry 1 }

-- tagpath /system/ledStatus/ledType
sonusSystemLedStatusLedType OBJECT-TYPE
    SYNTAX      String (SIZE (0 .. 23))
    MAX-ACCESS  not-accessible
    STATUS      current
    DESCRIPTION "
Indicates the LED type.
"
    ::= { sonusSystemLedStatusEntry 2 }

-- tagpath /system/ledStatus/ledState
sonusSystemLedStatusLedState OBJECT-TYPE
    SYNTAX      String (SIZE (0 .. 23))
    MAX-ACCESS  read-only
    STATUS      current
    DESCRIPTION "
Indicates the LED state.
"
    ::= { sonusSystemLedStatusEntry 3 }

-- tagpath /system/ledStatus/ledColor
sonusSystemLedStatusLedColor OBJECT-TYPE
    SYNTAX      String (SIZE (0 .. 23))
    MAX-ACCESS  read-only
    STATUS      current
    DESCRIPTION "
Indicates the LED color.
"
    ::= { sonusSystemLedStatusEntry 4 }

-- tagpath /system/serverStatus
sonusSystemServerStatusTable OBJECT-TYPE
    SYNTAX      SEQUENCE OF SonusSystemServerStatusEntry
    MAX-ACCESS  not-accessible
    STATUS      current
    DESCRIPTION "
The system server status table describes the status of the
server module.
"
    ::= { sonusSystem 12 }

-- tagpath /system/serverStatus
sonusSystemServerStatusEntry OBJECT-TYPE
    SYNTAX      SonusSystemServerStatusEntry
    MAX-ACCESS  not-accessible
    STATUS      current
    DESCRIPTION ""
    INDEX { sonusSystemServerStatusName }
        ::= { sonusSystemServerStatusTable 1 }

SonusSystemServerStatusEntry ::=
    SEQUENCE {
        sonusSystemServerStatusName String,
        sonusSystemServerStatusHwType SonusNodeSrvrHwType,
        sonusSystemServerStatusSerialNum SonusNodeSrvrStatSerialNumType,
        sonusSystemServerStatusPartNum SonusNodeSrvrStatPartNumType,
        sonusSystemServerStatusManufactureDate SonusNodeSrvrStatMfgDateType,
        sonusSystemServerStatusPlatformVersion SonusNodeSrvrStatSwVersionType,
        sonusSystemServerStatusApplicationVersion SonusNodeSrvrStatSwVersionType,
        sonusSystemServerStatusMgmtRedundancyRole SonusNodeSrvrStatModeType,
        sonusSystemServerStatusUpTime String,
        sonusSystemServerStatusApplicationUpTime String,
        sonusSystemServerStatusLastRestartReason SonusNodeSrvrLastRestartReasonType,
        sonusSystemServerStatusSyncStatus SonusNodeSrvrSyncStatusType,
        sonusSystemServerStatusDaughterBoardPresent TruthValue,
        sonusSystemServerStatusCurrentTime String,
        sonusSystemServerStatusPktPortSpeed SonusNodeSrvrPktPortSpeed,
        sonusSystemServerStatusActualCeName String,
        sonusSystemServerStatusHwSubType SonusNodeSrvrHwType,
        sonusSystemServerStatusFingerprint String
    }

-- tagpath /system/serverStatus/name
sonusSystemServerStatusName OBJECT-TYPE
    SYNTAX      String (SIZE (0 .. 255))
    MAX-ACCESS  not-accessible
    STATUS      current
    DESCRIPTION "
Identifies the server.
"
    ::= { sonusSystemServerStatusEntry 1 }

-- tagpath /system/serverStatus/hwType
sonusSystemServerStatusHwType OBJECT-TYPE
    SYNTAX      SonusNodeSrvrHwType
    MAX-ACCESS  read-only
    STATUS      current
    DESCRIPTION "
Identifies the type of server module the indexed slot has been
configured to accept.  Server modules other than this type are
rejected by the System Manager.
"
    ::= { sonusSystemServerStatusEntry 2 }

-- tagpath /system/serverStatus/serialNum
sonusSystemServerStatusSerialNum OBJECT-TYPE
    SYNTAX      SonusNodeSrvrStatSerialNumType
    MAX-ACCESS  read-only
    STATUS      current
    DESCRIPTION "
Identifies the serial number of the server module.  This is the
serial number assigned to the server module at manufacture.
"
    ::= { sonusSystemServerStatusEntry 3 }

-- tagpath /system/serverStatus/partNum
sonusSystemServerStatusPartNum OBJECT-TYPE
    SYNTAX      SonusNodeSrvrStatPartNumType
    MAX-ACCESS  read-only
    STATUS      current
    DESCRIPTION "
Identifies the part number of the module.  This is the
part number assigned to the module at manufacture.
"
    ::= { sonusSystemServerStatusEntry 4 }

-- tagpath /system/serverStatus/manufactureDate
sonusSystemServerStatusManufactureDate OBJECT-TYPE
    SYNTAX      SonusNodeSrvrStatMfgDateType
    MAX-ACCESS  read-only
    STATUS      obsolete
    DESCRIPTION "
The date this server module assembly was manufactured.
"
    ::= { sonusSystemServerStatusEntry 5 }

-- tagpath /system/serverStatus/platformVersion
sonusSystemServerStatusPlatformVersion OBJECT-TYPE
    SYNTAX      SonusNodeSrvrStatSwVersionType
    MAX-ACCESS  read-only
    STATUS      current
    DESCRIPTION "
Indicates the platform version currently running on server.
"
    ::= { sonusSystemServerStatusEntry 6 }

-- tagpath /system/serverStatus/applicationVersion
sonusSystemServerStatusApplicationVersion OBJECT-TYPE
    SYNTAX      SonusNodeSrvrStatSwVersionType
    MAX-ACCESS  read-only
    STATUS      current
    DESCRIPTION "
Indicates the application version currently running on server.
"
    ::= { sonusSystemServerStatusEntry 7 }

-- tagpath /system/serverStatus/mgmtRedundancyRole
sonusSystemServerStatusMgmtRedundancyRole OBJECT-TYPE
    SYNTAX      SonusNodeSrvrStatModeType
    MAX-ACCESS  read-only
    STATUS      current
    DESCRIPTION "
Indicates the redundancy role of the server (for management entities)
"
    ::= { sonusSystemServerStatusEntry 8 }

-- tagpath /system/serverStatus/upTime
sonusSystemServerStatusUpTime OBJECT-TYPE
    SYNTAX      String (SIZE (0 .. 255))
    MAX-ACCESS  read-only
    STATUS      current
    DESCRIPTION "
Indicates the server module uptime in days/hours/minutes/sec.
"
    ::= { sonusSystemServerStatusEntry 9 }

-- tagpath /system/serverStatus/applicationUpTime
sonusSystemServerStatusApplicationUpTime OBJECT-TYPE
    SYNTAX      String (SIZE (0 .. 255))
    MAX-ACCESS  read-only
    STATUS      current
    DESCRIPTION "
Indicates the application uptime on the server in days/hours/minutes/sec.
"
    ::= { sonusSystemServerStatusEntry 10 }

-- tagpath /system/serverStatus/lastRestartReason
sonusSystemServerStatusLastRestartReason OBJECT-TYPE
    SYNTAX      SonusNodeSrvrLastRestartReasonType
    MAX-ACCESS  read-only
    STATUS      current
    DESCRIPTION "
Indicates the reason for last restart of the server.
"
    ::= { sonusSystemServerStatusEntry 11 }

-- tagpath /system/serverStatus/syncStatus
sonusSystemServerStatusSyncStatus OBJECT-TYPE
    SYNTAX      SonusNodeSrvrSyncStatusType
    MAX-ACCESS  read-only
    STATUS      current
    DESCRIPTION "
Indicates the inter-CE data synchronization state.
"
    ::= { sonusSystemServerStatusEntry 12 }

-- tagpath /system/serverStatus/daughterBoardPresent
sonusSystemServerStatusDaughterBoardPresent OBJECT-TYPE
    SYNTAX      TruthValue
    MAX-ACCESS  read-only
    STATUS      current
    DESCRIPTION "
Indicates if the daughter board exists.
"
    ::= { sonusSystemServerStatusEntry 13 }

-- tagpath /system/serverStatus/currentTime
sonusSystemServerStatusCurrentTime OBJECT-TYPE
    SYNTAX      String (SIZE (0 .. 255))
    MAX-ACCESS  read-only
    STATUS      current
    DESCRIPTION "
Indicates the current system time.
"
    ::= { sonusSystemServerStatusEntry 14 }

-- tagpath /system/serverStatus/pktPortSpeed
sonusSystemServerStatusPktPortSpeed OBJECT-TYPE
    SYNTAX      SonusNodeSrvrPktPortSpeed
    MAX-ACCESS  read-only
    STATUS      current
    DESCRIPTION "
Packet port speed setting.
"
    ::= { sonusSystemServerStatusEntry 15 }

-- tagpath /system/serverStatus/actualCeName
sonusSystemServerStatusActualCeName OBJECT-TYPE
    SYNTAX      String (SIZE (0 .. 255))
    MAX-ACCESS  read-only
    STATUS      current
    DESCRIPTION "
Identifies the given/actual server.
"
    ::= { sonusSystemServerStatusEntry 16 }

-- tagpath /system/serverStatus/hwSubType
sonusSystemServerStatusHwSubType OBJECT-TYPE
    SYNTAX      SonusNodeSrvrHwType
    MAX-ACCESS  read-only
    STATUS      current
    DESCRIPTION "
Identifies the type of server module the indexed slot has been
configured to accept.  Server modules other than this type are
rejected by the System Manager.
"
    ::= { sonusSystemServerStatusEntry 17 }

-- tagpath /system/serverStatus/fingerprint
sonusSystemServerStatusFingerprint OBJECT-TYPE
    SYNTAX      String (SIZE (0 .. 255))
    MAX-ACCESS  read-only
    STATUS      current
    DESCRIPTION "
The licensing fingerprint for the node
"
    ::= { sonusSystemServerStatusEntry 18 }

-- tagpath /system/daughterBoardStatus
sonusSystemDaughterBoardStatusTable OBJECT-TYPE
    SYNTAX      SEQUENCE OF SonusSystemDaughterBoardStatusEntry
    MAX-ACCESS  not-accessible
    STATUS      obsolete
    DESCRIPTION "
Indicates the daughter board status on the server.
"
    ::= { sonusSystem 13 }

-- tagpath /system/daughterBoardStatus
sonusSystemDaughterBoardStatusEntry OBJECT-TYPE
    SYNTAX      SonusSystemDaughterBoardStatusEntry
    MAX-ACCESS  not-accessible
    STATUS      obsolete
    DESCRIPTION ""
    INDEX { sonusSystemDaughterBoardStatusServerName, sonusSystemDaughterBoardStatusSlot }
        ::= { sonusSystemDaughterBoardStatusTable 1 }

SonusSystemDaughterBoardStatusEntry ::=
    SEQUENCE {
        sonusSystemDaughterBoardStatusServerName String,
        sonusSystemDaughterBoardStatusDaughterBoardId String,
        sonusSystemDaughterBoardStatusPresent TruthValue,
        sonusSystemDaughterBoardStatusProductName String,
        sonusSystemDaughterBoardStatusSerialNum SonusNodeSrvrStatSerialNumType,
        sonusSystemDaughterBoardStatusPartNum SonusNodeSrvrStatPartNumType,
        sonusSystemDaughterBoardStatusSlot SonusDspSlotIndex,
        sonusSystemDaughterBoardStatusOperationalStatus DaughterBoardOperationalStatus,
        sonusSystemDaughterBoardStatusLogicalId SonusDspSlotIndex,
        sonusSystemDaughterBoardStatusImageLoadFailureCount Unsigned32,
        sonusSystemDaughterBoardStatusFpgaVersion String
    }

-- tagpath /system/daughterBoardStatus/serverName
sonusSystemDaughterBoardStatusServerName OBJECT-TYPE
    SYNTAX      String (SIZE (0 .. 255))
    MAX-ACCESS  not-accessible
    STATUS      obsolete
    DESCRIPTION "
Identifies the server.
"
    ::= { sonusSystemDaughterBoardStatusEntry 1 }

-- tagpath /system/daughterBoardStatus/daughterBoardId
sonusSystemDaughterBoardStatusDaughterBoardId OBJECT-TYPE
    SYNTAX      String (SIZE (0 .. 23))
    MAX-ACCESS  read-only
    STATUS      obsolete
    DESCRIPTION "
The name of the daughter board.
"
    ::= { sonusSystemDaughterBoardStatusEntry 2 }

-- tagpath /system/daughterBoardStatus/present
sonusSystemDaughterBoardStatusPresent OBJECT-TYPE
    SYNTAX      TruthValue
    MAX-ACCESS  read-only
    STATUS      obsolete
    DESCRIPTION "
Indicates if the module is present or not.
"
    ::= { sonusSystemDaughterBoardStatusEntry 3 }

-- tagpath /system/daughterBoardStatus/productName
sonusSystemDaughterBoardStatusProductName OBJECT-TYPE
    SYNTAX      String (SIZE (0 .. 255))
    MAX-ACCESS  read-only
    STATUS      obsolete
    DESCRIPTION "
Identifies the name (as given by manufacturer) of the module.
"
    ::= { sonusSystemDaughterBoardStatusEntry 4 }

-- tagpath /system/daughterBoardStatus/serialNum
sonusSystemDaughterBoardStatusSerialNum OBJECT-TYPE
    SYNTAX      SonusNodeSrvrStatSerialNumType
    MAX-ACCESS  read-only
    STATUS      obsolete
    DESCRIPTION "
Identifies the serial number of the daughter board module.  This is the
serial number assigned to the server module at manufacture.
"
    ::= { sonusSystemDaughterBoardStatusEntry 5 }

-- tagpath /system/daughterBoardStatus/partNum
sonusSystemDaughterBoardStatusPartNum OBJECT-TYPE
    SYNTAX      SonusNodeSrvrStatPartNumType
    MAX-ACCESS  read-only
    STATUS      obsolete
    DESCRIPTION "
Identifies the part number of the module.  This is the
part number assigned to the module at manufacture.
"
    ::= { sonusSystemDaughterBoardStatusEntry 6 }

-- tagpath /system/daughterBoardStatus/slot
sonusSystemDaughterBoardStatusSlot OBJECT-TYPE
    SYNTAX      SonusDspSlotIndex
    MAX-ACCESS  not-accessible
    STATUS      obsolete
    DESCRIPTION "
Identifies the slot associated with the DSP board.
"
    ::= { sonusSystemDaughterBoardStatusEntry 7 }

-- tagpath /system/daughterBoardStatus/operationalStatus
sonusSystemDaughterBoardStatusOperationalStatus OBJECT-TYPE
    SYNTAX      DaughterBoardOperationalStatus
    MAX-ACCESS  read-only
    STATUS      obsolete
    DESCRIPTION "
Identifies the operational state of the board.
"
    ::= { sonusSystemDaughterBoardStatusEntry 8 }

-- tagpath /system/daughterBoardStatus/logicalId
sonusSystemDaughterBoardStatusLogicalId OBJECT-TYPE
    SYNTAX      SonusDspSlotIndex
    MAX-ACCESS  read-only
    STATUS      obsolete
    DESCRIPTION "
Identifies the logical id of the slot.
"
    ::= { sonusSystemDaughterBoardStatusEntry 9 }

-- tagpath /system/daughterBoardStatus/imageLoadFailureCount
sonusSystemDaughterBoardStatusImageLoadFailureCount OBJECT-TYPE
    SYNTAX      Unsigned32
    MAX-ACCESS  read-only
    STATUS      obsolete
    DESCRIPTION "
Indicates daughter board image load failure count since last successful attempt.
"
    ::= { sonusSystemDaughterBoardStatusEntry 10 }

-- tagpath /system/daughterBoardStatus/fpgaVersion
sonusSystemDaughterBoardStatusFpgaVersion OBJECT-TYPE
    SYNTAX      String (SIZE (0 .. 255))
    MAX-ACCESS  read-only
    STATUS      obsolete
    DESCRIPTION "
FPGA version of slot.
"
    ::= { sonusSystemDaughterBoardStatusEntry 11 }

-- tagpath /system/daughterBoard2Status
sonusSystemDaughterBoard2StatusTable OBJECT-TYPE
    SYNTAX      SEQUENCE OF SonusSystemDaughterBoard2StatusEntry
    MAX-ACCESS  not-accessible
    STATUS      obsolete
    DESCRIPTION "
Indicates the daughter board status on the server.
"
    ::= { sonusSystem 28 }

-- tagpath /system/daughterBoard2Status
sonusSystemDaughterBoard2StatusEntry OBJECT-TYPE
    SYNTAX      SonusSystemDaughterBoard2StatusEntry
    MAX-ACCESS  not-accessible
    STATUS      obsolete
    DESCRIPTION ""
    INDEX { sonusSystemDaughterBoard2StatusServerName, sonusSystemDaughterBoard2StatusSlot }
        ::= { sonusSystemDaughterBoard2StatusTable 1 }

SonusSystemDaughterBoard2StatusEntry ::=
    SEQUENCE {
        sonusSystemDaughterBoard2StatusServerName String,
        sonusSystemDaughterBoard2StatusDaughterBoardId String,
        sonusSystemDaughterBoard2StatusPresent TruthValue,
        sonusSystemDaughterBoard2StatusProductName String,
        sonusSystemDaughterBoard2StatusSerialNum SonusNodeSrvrStatSerialNumType,
        sonusSystemDaughterBoard2StatusPartNum SonusNodeSrvrStatPartNumType,
        sonusSystemDaughterBoard2StatusSlot SonusDspSlotIndex,
        sonusSystemDaughterBoard2StatusOperationalStatus DaughterBoardOperationalStatus,
        sonusSystemDaughterBoard2StatusLogicalId SonusDspSlotIndex,
        sonusSystemDaughterBoard2StatusImageLoadFailureCount Unsigned32,
        sonusSystemDaughterBoard2StatusFpgaVersion String
    }

-- tagpath /system/daughterBoard2Status/serverName
sonusSystemDaughterBoard2StatusServerName OBJECT-TYPE
    SYNTAX      String (SIZE (0 .. 255))
    MAX-ACCESS  not-accessible
    STATUS      obsolete
    DESCRIPTION "
Identifies the server.
"
    ::= { sonusSystemDaughterBoard2StatusEntry 1 }

-- tagpath /system/daughterBoard2Status/daughterBoardId
sonusSystemDaughterBoard2StatusDaughterBoardId OBJECT-TYPE
    SYNTAX      String (SIZE (0 .. 23))
    MAX-ACCESS  read-only
    STATUS      obsolete
    DESCRIPTION "
The name of the daughter board.
"
    ::= { sonusSystemDaughterBoard2StatusEntry 2 }

-- tagpath /system/daughterBoard2Status/present
sonusSystemDaughterBoard2StatusPresent OBJECT-TYPE
    SYNTAX      TruthValue
    MAX-ACCESS  read-only
    STATUS      obsolete
    DESCRIPTION "
Indicates if the module is present or not.
"
    ::= { sonusSystemDaughterBoard2StatusEntry 3 }

-- tagpath /system/daughterBoard2Status/productName
sonusSystemDaughterBoard2StatusProductName OBJECT-TYPE
    SYNTAX      String (SIZE (0 .. 255))
    MAX-ACCESS  read-only
    STATUS      obsolete
    DESCRIPTION "
Identifies the name (as given by manufacturer) of the module.
"
    ::= { sonusSystemDaughterBoard2StatusEntry 4 }

-- tagpath /system/daughterBoard2Status/serialNum
sonusSystemDaughterBoard2StatusSerialNum OBJECT-TYPE
    SYNTAX      SonusNodeSrvrStatSerialNumType
    MAX-ACCESS  read-only
    STATUS      obsolete
    DESCRIPTION "
Identifies the serial number of the daughter board module.  This is the
serial number assigned to the server module at manufacture.
"
    ::= { sonusSystemDaughterBoard2StatusEntry 5 }

-- tagpath /system/daughterBoard2Status/partNum
sonusSystemDaughterBoard2StatusPartNum OBJECT-TYPE
    SYNTAX      SonusNodeSrvrStatPartNumType
    MAX-ACCESS  read-only
    STATUS      obsolete
    DESCRIPTION "
Identifies the part number of the module.  This is the
part number assigned to the module at manufacture.
"
    ::= { sonusSystemDaughterBoard2StatusEntry 6 }

-- tagpath /system/daughterBoard2Status/slot
sonusSystemDaughterBoard2StatusSlot OBJECT-TYPE
    SYNTAX      SonusDspSlotIndex
    MAX-ACCESS  not-accessible
    STATUS      obsolete
    DESCRIPTION "
Identifies the slot associated with the DSP board.
"
    ::= { sonusSystemDaughterBoard2StatusEntry 7 }

-- tagpath /system/daughterBoard2Status/operationalStatus
sonusSystemDaughterBoard2StatusOperationalStatus OBJECT-TYPE
    SYNTAX      DaughterBoardOperationalStatus
    MAX-ACCESS  read-only
    STATUS      obsolete
    DESCRIPTION "
Identifies the operational state of the board.
"
    ::= { sonusSystemDaughterBoard2StatusEntry 8 }

-- tagpath /system/daughterBoard2Status/logicalId
sonusSystemDaughterBoard2StatusLogicalId OBJECT-TYPE
    SYNTAX      SonusDspSlotIndex
    MAX-ACCESS  read-only
    STATUS      obsolete
    DESCRIPTION "
Identifies the logical id of the slot.
"
    ::= { sonusSystemDaughterBoard2StatusEntry 9 }

-- tagpath /system/daughterBoard2Status/imageLoadFailureCount
sonusSystemDaughterBoard2StatusImageLoadFailureCount OBJECT-TYPE
    SYNTAX      Unsigned32
    MAX-ACCESS  read-only
    STATUS      obsolete
    DESCRIPTION "
Indicates daughter board image load failure count since last successful attempt.
"
    ::= { sonusSystemDaughterBoard2StatusEntry 10 }

-- tagpath /system/daughterBoard2Status/fpgaVersion
sonusSystemDaughterBoard2StatusFpgaVersion OBJECT-TYPE
    SYNTAX      String (SIZE (0 .. 255))
    MAX-ACCESS  read-only
    STATUS      obsolete
    DESCRIPTION "
FPGA version of slot.
"
    ::= { sonusSystemDaughterBoard2StatusEntry 11 }

-- tagpath /system/daughterBoard3Status
sonusSystemDaughterBoard3StatusTable OBJECT-TYPE
    SYNTAX      SEQUENCE OF SonusSystemDaughterBoard3StatusEntry
    MAX-ACCESS  not-accessible
    STATUS      current
    DESCRIPTION "
Indicates the daughter board status on the server.
"
    ::= { sonusSystem 29 }

-- tagpath /system/daughterBoard3Status
sonusSystemDaughterBoard3StatusEntry OBJECT-TYPE
    SYNTAX      SonusSystemDaughterBoard3StatusEntry
    MAX-ACCESS  not-accessible
    STATUS      current
    DESCRIPTION ""
    INDEX { sonusSystemDaughterBoard3StatusServerName, sonusSystemDaughterBoard3StatusSlot }
        ::= { sonusSystemDaughterBoard3StatusTable 1 }

SonusSystemDaughterBoard3StatusEntry ::=
    SEQUENCE {
        sonusSystemDaughterBoard3StatusServerName String,
        sonusSystemDaughterBoard3StatusDaughterBoardId String,
        sonusSystemDaughterBoard3StatusPresent TruthValue,
        sonusSystemDaughterBoard3StatusProductName String,
        sonusSystemDaughterBoard3StatusSerialNum SonusNodeSrvrStatSerialNumType,
        sonusSystemDaughterBoard3StatusPartNum SonusNodeSrvrStatPartNumType,
        sonusSystemDaughterBoard3StatusSlot SonusDspSlotIndex,
        sonusSystemDaughterBoard3StatusOperationalStatus DaughterBoardOperationalStatus,
        sonusSystemDaughterBoard3StatusLogicalId SonusDspSlotIndex,
        sonusSystemDaughterBoard3StatusImageLoadFailureCount Unsigned32,
        sonusSystemDaughterBoard3StatusFpgaVersion String
    }

-- tagpath /system/daughterBoard3Status/serverName
sonusSystemDaughterBoard3StatusServerName OBJECT-TYPE
    SYNTAX      String (SIZE (0 .. 255))
    MAX-ACCESS  not-accessible
    STATUS      current
    DESCRIPTION "
Identifies the server.
"
    ::= { sonusSystemDaughterBoard3StatusEntry 1 }

-- tagpath /system/daughterBoard3Status/daughterBoardId
sonusSystemDaughterBoard3StatusDaughterBoardId OBJECT-TYPE
    SYNTAX      String (SIZE (0 .. 23))
    MAX-ACCESS  read-only
    STATUS      current
    DESCRIPTION "
The name of the daughter board.
"
    ::= { sonusSystemDaughterBoard3StatusEntry 2 }

-- tagpath /system/daughterBoard3Status/present
sonusSystemDaughterBoard3StatusPresent OBJECT-TYPE
    SYNTAX      TruthValue
    MAX-ACCESS  read-only
    STATUS      current
    DESCRIPTION "
Indicates if the module is present or not.
"
    ::= { sonusSystemDaughterBoard3StatusEntry 3 }

-- tagpath /system/daughterBoard3Status/productName
sonusSystemDaughterBoard3StatusProductName OBJECT-TYPE
    SYNTAX      String (SIZE (0 .. 255))
    MAX-ACCESS  read-only
    STATUS      current
    DESCRIPTION "
Identifies the name (as given by manufacturer) of the module.
"
    ::= { sonusSystemDaughterBoard3StatusEntry 4 }

-- tagpath /system/daughterBoard3Status/serialNum
sonusSystemDaughterBoard3StatusSerialNum OBJECT-TYPE
    SYNTAX      SonusNodeSrvrStatSerialNumType
    MAX-ACCESS  read-only
    STATUS      current
    DESCRIPTION "
Identifies the serial number of the daughter board module.  This is the
serial number assigned to the server module at manufacture.
"
    ::= { sonusSystemDaughterBoard3StatusEntry 5 }

-- tagpath /system/daughterBoard3Status/partNum
sonusSystemDaughterBoard3StatusPartNum OBJECT-TYPE
    SYNTAX      SonusNodeSrvrStatPartNumType
    MAX-ACCESS  read-only
    STATUS      current
    DESCRIPTION "
Identifies the part number of the module.  This is the
part number assigned to the module at manufacture.
"
    ::= { sonusSystemDaughterBoard3StatusEntry 6 }

-- tagpath /system/daughterBoard3Status/slot
sonusSystemDaughterBoard3StatusSlot OBJECT-TYPE
    SYNTAX      SonusDspSlotIndex
    MAX-ACCESS  not-accessible
    STATUS      current
    DESCRIPTION "
Identifies the slot associated with the DSP board.
"
    ::= { sonusSystemDaughterBoard3StatusEntry 7 }

-- tagpath /system/daughterBoard3Status/operationalStatus
sonusSystemDaughterBoard3StatusOperationalStatus OBJECT-TYPE
    SYNTAX      DaughterBoardOperationalStatus
    MAX-ACCESS  read-only
    STATUS      current
    DESCRIPTION "
Identifies the operational state of the board.
"
    ::= { sonusSystemDaughterBoard3StatusEntry 8 }

-- tagpath /system/daughterBoard3Status/logicalId
sonusSystemDaughterBoard3StatusLogicalId OBJECT-TYPE
    SYNTAX      SonusDspSlotIndex
    MAX-ACCESS  read-only
    STATUS      current
    DESCRIPTION "
Identifies the logical id of the slot.
"
    ::= { sonusSystemDaughterBoard3StatusEntry 9 }

-- tagpath /system/daughterBoard3Status/imageLoadFailureCount
sonusSystemDaughterBoard3StatusImageLoadFailureCount OBJECT-TYPE
    SYNTAX      Unsigned32
    MAX-ACCESS  read-only
    STATUS      current
    DESCRIPTION "
Indicates daughter board image load failure count since last successful attempt.
"
    ::= { sonusSystemDaughterBoard3StatusEntry 10 }

-- tagpath /system/daughterBoard3Status/fpgaVersion
sonusSystemDaughterBoard3StatusFpgaVersion OBJECT-TYPE
    SYNTAX      String (SIZE (0 .. 255))
    MAX-ACCESS  read-only
    STATUS      current
    DESCRIPTION "
FPGA version of slot.
"
    ::= { sonusSystemDaughterBoard3StatusEntry 11 }

-- tagpath /system/serverSoftwareUpgradeStatus
sonusSystemServerSoftwareUpgradeStatusTable OBJECT-TYPE
    SYNTAX      SEQUENCE OF SonusSystemServerSoftwareUpgradeStatusEntry
    MAX-ACCESS  not-accessible
    STATUS      current
    DESCRIPTION "
The system server software upgrade status table describes the status of the
server software upgrade module.
"
    ::= { sonusSystem 14 }

-- tagpath /system/serverSoftwareUpgradeStatus
sonusSystemServerSoftwareUpgradeStatusEntry OBJECT-TYPE
    SYNTAX      SonusSystemServerSoftwareUpgradeStatusEntry
    MAX-ACCESS  not-accessible
    STATUS      current
    DESCRIPTION ""
    INDEX { sonusSystemServerSoftwareUpgradeStatusName }
        ::= { sonusSystemServerSoftwareUpgradeStatusTable 1 }

SonusSystemServerSoftwareUpgradeStatusEntry ::=
    SEQUENCE {
        sonusSystemServerSoftwareUpgradeStatusName String,
        sonusSystemServerSoftwareUpgradeStatusUpgradeStatus SonusNodeServerLiveSoftwareUpgradeStatusType
    }

-- tagpath /system/serverSoftwareUpgradeStatus/name
sonusSystemServerSoftwareUpgradeStatusName OBJECT-TYPE
    SYNTAX      String (SIZE (0 .. 255))
    MAX-ACCESS  not-accessible
    STATUS      current
    DESCRIPTION "
Identifies the server.
"
    ::= { sonusSystemServerSoftwareUpgradeStatusEntry 1 }

-- tagpath /system/serverSoftwareUpgradeStatus/upgradeStatus
sonusSystemServerSoftwareUpgradeStatusUpgradeStatus OBJECT-TYPE
    SYNTAX      SonusNodeServerLiveSoftwareUpgradeStatusType
    MAX-ACCESS  read-only
    STATUS      current
    DESCRIPTION "
Indicates the current status of the server.
"
    ::= { sonusSystemServerSoftwareUpgradeStatusEntry 2 }

-- tagpath /system/softwareUpgradeDetailedStatus
sonusSystemSoftwareUpgradeDetailedStatusTable OBJECT-TYPE
    SYNTAX      SEQUENCE OF SonusSystemSoftwareUpgradeDetailedStatusEntry
    MAX-ACCESS  not-accessible
    STATUS      current
    DESCRIPTION "
The system software upgrade detailed status table describes the detailed status of the
software upgrade module.
"
    ::= { sonusSystem 35 }

-- tagpath /system/softwareUpgradeDetailedStatus
sonusSystemSoftwareUpgradeDetailedStatusEntry OBJECT-TYPE
    SYNTAX      SonusSystemSoftwareUpgradeDetailedStatusEntry
    MAX-ACCESS  not-accessible
    STATUS      current
    DESCRIPTION ""
    INDEX { sonusSystemSoftwareUpgradeDetailedStatusSystemName }
        ::= { sonusSystemSoftwareUpgradeDetailedStatusTable 1 }

SonusSystemSoftwareUpgradeDetailedStatusEntry ::=
    SEQUENCE {
        sonusSystemSoftwareUpgradeDetailedStatusSystemName String,
        sonusSystemSoftwareUpgradeDetailedStatusDetailedStatus SonusDetailedStatusType
    }

-- tagpath /system/softwareUpgradeDetailedStatus/systemName
sonusSystemSoftwareUpgradeDetailedStatusSystemName OBJECT-TYPE
    SYNTAX      String (SIZE (0 .. 255))
    MAX-ACCESS  not-accessible
    STATUS      current
    DESCRIPTION "
Identifies the system.
"
    ::= { sonusSystemSoftwareUpgradeDetailedStatusEntry 1 }

-- tagpath /system/softwareUpgradeDetailedStatus/detailedStatus
sonusSystemSoftwareUpgradeDetailedStatusDetailedStatus OBJECT-TYPE
    SYNTAX      SonusDetailedStatusType
    MAX-ACCESS  read-only
    STATUS      current
    DESCRIPTION "
Prints the detailed upgrade status.
"
    ::= { sonusSystemSoftwareUpgradeDetailedStatusEntry 2 }

-- tagpath /system/licenseRequiredStatus
sonusSystemLicenseRequiredStatusTable OBJECT-TYPE
    SYNTAX      SEQUENCE OF SonusSystemLicenseRequiredStatusEntry
    MAX-ACCESS  not-accessible
    STATUS      current
    DESCRIPTION "
Status information about licenses acquired by this application
"
    ::= { sonusSystem 47 }

-- tagpath /system/licenseRequiredStatus
sonusSystemLicenseRequiredStatusEntry OBJECT-TYPE
    SYNTAX      SonusSystemLicenseRequiredStatusEntry
    MAX-ACCESS  not-accessible
    STATUS      current
    DESCRIPTION ""
    INDEX { sonusSystemLicenseRequiredStatusName, sonusSystemLicenseRequiredStatusFeatureName }
        ::= { sonusSystemLicenseRequiredStatusTable 1 }

SonusSystemLicenseRequiredStatusEntry ::=
    SEQUENCE {
        sonusSystemLicenseRequiredStatusName String,
        sonusSystemLicenseRequiredStatusFeatureName String,
        sonusSystemLicenseRequiredStatusLastAcquiredCount Unsigned32,
        sonusSystemLicenseRequiredStatusLastGoodserverName String,
        sonusSystemLicenseRequiredStatusLastAcquiredDate DateAndTime,
        sonusSystemLicenseRequiredStatusUsingCapacityLicense String,
        sonusSystemLicenseRequiredStatusClemency String,
        sonusSystemLicenseRequiredStatusFailSafeMode String,
        sonusSystemLicenseRequiredStatusServiceAuthorizationMode String
    }

-- tagpath /system/licenseRequiredStatus/name
sonusSystemLicenseRequiredStatusName OBJECT-TYPE
    SYNTAX      String (SIZE (0 .. 255))
    MAX-ACCESS  not-accessible
    STATUS      current
    DESCRIPTION "
Identifies the server.
"
    ::= { sonusSystemLicenseRequiredStatusEntry 1 }

-- tagpath /system/licenseRequiredStatus/featureName
sonusSystemLicenseRequiredStatusFeatureName OBJECT-TYPE
    SYNTAX      String (SIZE (0 .. 23))
    MAX-ACCESS  not-accessible
    STATUS      current
    DESCRIPTION "
The name of the feature
"
    ::= { sonusSystemLicenseRequiredStatusEntry 2 }

-- tagpath /system/licenseRequiredStatus/lastAcquiredCount
sonusSystemLicenseRequiredStatusLastAcquiredCount OBJECT-TYPE
    SYNTAX      Unsigned32
    MAX-ACCESS  read-only
    STATUS      current
    DESCRIPTION "
the number of licenses acquired
"
    ::= { sonusSystemLicenseRequiredStatusEntry 3 }

-- tagpath /system/licenseRequiredStatus/lastGoodserverName
sonusSystemLicenseRequiredStatusLastGoodserverName OBJECT-TYPE
    SYNTAX      String (SIZE (0 .. 255))
    MAX-ACCESS  read-only
    STATUS      current
    DESCRIPTION "
The name used to reference this server
"
    ::= { sonusSystemLicenseRequiredStatusEntry 4 }

-- tagpath /system/licenseRequiredStatus/lastAcquiredDate
sonusSystemLicenseRequiredStatusLastAcquiredDate OBJECT-TYPE
    SYNTAX      DateAndTime
    MAX-ACCESS  read-only
    STATUS      current
    DESCRIPTION "
This date the license was installed
"
    ::= { sonusSystemLicenseRequiredStatusEntry 7 }

-- tagpath /system/licenseRequiredStatus/usingCapacityLicense
sonusSystemLicenseRequiredStatusUsingCapacityLicense OBJECT-TYPE
    SYNTAX      String (SIZE (0 .. 255))
    MAX-ACCESS  read-only
    STATUS      current
    DESCRIPTION "
Was this license obtained using a capacity license
"
    ::= { sonusSystemLicenseRequiredStatusEntry 8 }

-- tagpath /system/licenseRequiredStatus/clemency
sonusSystemLicenseRequiredStatusClemency OBJECT-TYPE
    SYNTAX      String (SIZE (0 .. 255))
    MAX-ACCESS  read-only
    STATUS      current
    DESCRIPTION "
"
    ::= { sonusSystemLicenseRequiredStatusEntry 9 }

-- tagpath /system/licenseRequiredStatus/failSafeMode
sonusSystemLicenseRequiredStatusFailSafeMode OBJECT-TYPE
    SYNTAX      String (SIZE (0 .. 255))
    MAX-ACCESS  read-only
    STATUS      current
    DESCRIPTION "
"
    ::= { sonusSystemLicenseRequiredStatusEntry 10 }

-- tagpath /system/licenseRequiredStatus/serviceAuthorizationMode
sonusSystemLicenseRequiredStatusServiceAuthorizationMode OBJECT-TYPE
    SYNTAX      String (SIZE (0 .. 255))
    MAX-ACCESS  read-only
    STATUS      current
    DESCRIPTION "
"
    ::= { sonusSystemLicenseRequiredStatusEntry 11 }

-- tagpath /system/licenseFeatureStatus
sonusSystemLicenseFeatureStatusTable OBJECT-TYPE
    SYNTAX      SEQUENCE OF SonusSystemLicenseFeatureStatusEntry
    MAX-ACCESS  not-accessible
    STATUS      current
    DESCRIPTION "
Status information about each licensed feature
"
    ::= { sonusSystem 46 }

-- tagpath /system/licenseFeatureStatus
sonusSystemLicenseFeatureStatusEntry OBJECT-TYPE
    SYNTAX      SonusSystemLicenseFeatureStatusEntry
    MAX-ACCESS  not-accessible
    STATUS      current
    DESCRIPTION ""
    INDEX { sonusSystemLicenseFeatureStatusFeatureName }
        ::= { sonusSystemLicenseFeatureStatusTable 1 }

SonusSystemLicenseFeatureStatusEntry ::=
    SEQUENCE {
        sonusSystemLicenseFeatureStatusFeatureName String,
        sonusSystemLicenseFeatureStatusLicenseSought Counter32,
        sonusSystemLicenseFeatureStatusLicenseNotReceived Counter32,
        sonusSystemLicenseFeatureStatusLastUpdateWasLocal String,
        sonusSystemLicenseFeatureStatusLicenseInstalled String,
        sonusSystemLicenseFeatureStatusCurrentLicenseAvailability String,
        sonusSystemLicenseFeatureStatusCurrentLicensesTotal Integer32,
        sonusSystemLicenseFeatureStatusCurrentLicensesInUse Integer32,
        sonusSystemLicenseFeatureStatusLicensingStatus String
    }

-- tagpath /system/licenseFeatureStatus/featureName
sonusSystemLicenseFeatureStatusFeatureName OBJECT-TYPE
    SYNTAX      String (SIZE (0 .. 23))
    MAX-ACCESS  not-accessible
    STATUS      current
    DESCRIPTION "
The name of the feature
"
    ::= { sonusSystemLicenseFeatureStatusEntry 1 }

-- tagpath /system/licenseFeatureStatus/licenseSought
sonusSystemLicenseFeatureStatusLicenseSought OBJECT-TYPE
    SYNTAX      Counter32
    MAX-ACCESS  read-only
    STATUS      current
    DESCRIPTION "
The number of times a license was sought
"
    ::= { sonusSystemLicenseFeatureStatusEntry 2 }

-- tagpath /system/licenseFeatureStatus/licenseNotReceived
sonusSystemLicenseFeatureStatusLicenseNotReceived OBJECT-TYPE
    SYNTAX      Counter32
    MAX-ACCESS  read-only
    STATUS      current
    DESCRIPTION "
The number of times a license was not received
"
    ::= { sonusSystemLicenseFeatureStatusEntry 3 }

-- tagpath /system/licenseFeatureStatus/lastUpdateWasLocal
sonusSystemLicenseFeatureStatusLastUpdateWasLocal OBJECT-TYPE
    SYNTAX      String (SIZE (0 .. 255))
    MAX-ACCESS  read-only
    STATUS      current
    DESCRIPTION "
Was the last update request performed locally
"
    ::= { sonusSystemLicenseFeatureStatusEntry 4 }

-- tagpath /system/licenseFeatureStatus/licenseInstalled
sonusSystemLicenseFeatureStatusLicenseInstalled OBJECT-TYPE
    SYNTAX      String (SIZE (0 .. 255))
    MAX-ACCESS  read-only
    STATUS      current
    DESCRIPTION "
Displays whether the license is installed or not
"
    ::= { sonusSystemLicenseFeatureStatusEntry 5 }

-- tagpath /system/licenseFeatureStatus/currentLicenseAvailability
sonusSystemLicenseFeatureStatusCurrentLicenseAvailability OBJECT-TYPE
    SYNTAX      String (SIZE (0 .. 255))
    MAX-ACCESS  read-only
    STATUS      current
    DESCRIPTION "
Displays current availability of license
"
    ::= { sonusSystemLicenseFeatureStatusEntry 6 }

-- tagpath /system/licenseFeatureStatus/currentLicensesTotal
sonusSystemLicenseFeatureStatusCurrentLicensesTotal OBJECT-TYPE
    SYNTAX      Integer32
    MAX-ACCESS  read-only
    STATUS      current
    DESCRIPTION "
This object indicates usage limit of license
"
    ::= { sonusSystemLicenseFeatureStatusEntry 7 }

-- tagpath /system/licenseFeatureStatus/currentLicensesInUse
sonusSystemLicenseFeatureStatusCurrentLicensesInUse OBJECT-TYPE
    SYNTAX      Integer32
    MAX-ACCESS  read-only
    STATUS      current
    DESCRIPTION "
Indicates the number of licenses currently in use
"
    ::= { sonusSystemLicenseFeatureStatusEntry 8 }

-- tagpath /system/licenseFeatureStatus/licensingStatus
sonusSystemLicenseFeatureStatusLicensingStatus OBJECT-TYPE
    SYNTAX      String (SIZE (0 .. 255))
    MAX-ACCESS  read-only
    STATUS      current
    DESCRIPTION "
Indicates whether Feature or Call addmission is enabled or disabled
"
    ::= { sonusSystemLicenseFeatureStatusEntry 9 }

-- tagpath /system/licenseServerStatus
sonusSystemLicenseServerStatusTable OBJECT-TYPE
    SYNTAX      SEQUENCE OF SonusSystemLicenseServerStatusEntry
    MAX-ACCESS  not-accessible
    STATUS      current
    DESCRIPTION "
Status for license servers
"
    ::= { sonusSystem 37 }

-- tagpath /system/licenseServerStatus
sonusSystemLicenseServerStatusEntry OBJECT-TYPE
    SYNTAX      SonusSystemLicenseServerStatusEntry
    MAX-ACCESS  not-accessible
    STATUS      current
    DESCRIPTION ""
    INDEX { sonusSystemLicenseServerStatusServerName }
        ::= { sonusSystemLicenseServerStatusTable 1 }

SonusSystemLicenseServerStatusEntry ::=
    SEQUENCE {
        sonusSystemLicenseServerStatusServerName String,
        sonusSystemLicenseServerStatusIsCurrentActive String,
        sonusSystemLicenseServerStatusRequestMessagesSent Counter32,
        sonusSystemLicenseServerStatusLicenseGrantMessagesReceived Counter32,
        sonusSystemLicenseServerStatusLicensePartialGrantMessagesReceived Counter32,
        sonusSystemLicenseServerStatusLicenseRejectMessagesReceived Counter32,
        sonusSystemLicenseServerStatusLicenseErrors Counter32
    }

-- tagpath /system/licenseServerStatus/serverName
sonusSystemLicenseServerStatusServerName OBJECT-TYPE
    SYNTAX      String (SIZE (0 .. 23))
    MAX-ACCESS  not-accessible
    STATUS      current
    DESCRIPTION "
The name of the feature
"
    ::= { sonusSystemLicenseServerStatusEntry 1 }

-- tagpath /system/licenseServerStatus/isCurrentActive
sonusSystemLicenseServerStatusIsCurrentActive OBJECT-TYPE
    SYNTAX      String (SIZE (0 .. 23))
    MAX-ACCESS  read-only
    STATUS      current
    DESCRIPTION "
This server was the last server that successfully responded to a licenseRequest
"
    ::= { sonusSystemLicenseServerStatusEntry 2 }

-- tagpath /system/licenseServerStatus/requestMessagesSent
sonusSystemLicenseServerStatusRequestMessagesSent OBJECT-TYPE
    SYNTAX      Counter32
    MAX-ACCESS  read-only
    STATUS      current
    DESCRIPTION "
the number of license requests sent
"
    ::= { sonusSystemLicenseServerStatusEntry 3 }

-- tagpath /system/licenseServerStatus/licenseGrantMessagesReceived
sonusSystemLicenseServerStatusLicenseGrantMessagesReceived OBJECT-TYPE
    SYNTAX      Counter32
    MAX-ACCESS  read-only
    STATUS      current
    DESCRIPTION "
the number of license grant messages receieved
"
    ::= { sonusSystemLicenseServerStatusEntry 4 }

-- tagpath /system/licenseServerStatus/licensePartialGrantMessagesReceived
sonusSystemLicenseServerStatusLicensePartialGrantMessagesReceived OBJECT-TYPE
    SYNTAX      Counter32
    MAX-ACCESS  read-only
    STATUS      current
    DESCRIPTION "
the number of partial license grant messages receieved
"
    ::= { sonusSystemLicenseServerStatusEntry 5 }

-- tagpath /system/licenseServerStatus/licenseRejectMessagesReceived
sonusSystemLicenseServerStatusLicenseRejectMessagesReceived OBJECT-TYPE
    SYNTAX      Counter32
    MAX-ACCESS  read-only
    STATUS      current
    DESCRIPTION "
the number of license reject messages receieved
"
    ::= { sonusSystemLicenseServerStatusEntry 6 }

-- tagpath /system/licenseServerStatus/licenseErrors
sonusSystemLicenseServerStatusLicenseErrors OBJECT-TYPE
    SYNTAX      Counter32
    MAX-ACCESS  read-only
    STATUS      current
    DESCRIPTION "
Errors when attempting to make a request (Includes no-response received and possibly other errors)
"
    ::= { sonusSystemLicenseServerStatusEntry 7 }

-- tagpath /system/licenseLocalBundleInfo
sonusSystemLicenseLocalBundleInfoTable OBJECT-TYPE
    SYNTAX      SEQUENCE OF SonusSystemLicenseLocalBundleInfoEntry
    MAX-ACCESS  not-accessible
    STATUS      obsolete
    DESCRIPTION "
Shows information about all the local licenses stored on the box
"
    ::= { sonusSystem 42 }

-- tagpath /system/licenseLocalBundleInfo
sonusSystemLicenseLocalBundleInfoEntry OBJECT-TYPE
    SYNTAX      SonusSystemLicenseLocalBundleInfoEntry
    MAX-ACCESS  not-accessible
    STATUS      obsolete
    DESCRIPTION ""
    INDEX { sonusSystemLicenseLocalBundleInfoBundleName, sonusSystemLicenseLocalBundleInfoFeatureName }
        ::= { sonusSystemLicenseLocalBundleInfoTable 1 }

SonusSystemLicenseLocalBundleInfoEntry ::=
    SEQUENCE {
        sonusSystemLicenseLocalBundleInfoBundleName String,
        sonusSystemLicenseLocalBundleInfoFeatureName String,
        sonusSystemLicenseLocalBundleInfoLicenseId String,
        sonusSystemLicenseLocalBundleInfoPurchaseOrderId String,
        sonusSystemLicenseLocalBundleInfoLineId String,
        sonusSystemLicenseLocalBundleInfoGenerationDate String,
        sonusSystemLicenseLocalBundleInfoInstallDate DateAndTime,
        sonusSystemLicenseLocalBundleInfoExpirationDate String,
        sonusSystemLicenseLocalBundleInfoUsageLimit Integer32,
        sonusSystemLicenseLocalBundleInfoFingerPrint1 String,
        sonusSystemLicenseLocalBundleInfoFingerPrint2 String,
        sonusSystemLicenseLocalBundleInfoActiveLicenseMode String
    }

-- tagpath /system/licenseLocalBundleInfo/bundleName
sonusSystemLicenseLocalBundleInfoBundleName OBJECT-TYPE
    SYNTAX      String (SIZE (0 .. 23))
    MAX-ACCESS  not-accessible
    STATUS      obsolete
    DESCRIPTION "
The bundle name for the feature
"
    ::= { sonusSystemLicenseLocalBundleInfoEntry 1 }

-- tagpath /system/licenseLocalBundleInfo/featureName
sonusSystemLicenseLocalBundleInfoFeatureName OBJECT-TYPE
    SYNTAX      String (SIZE (0 .. 23))
    MAX-ACCESS  not-accessible
    STATUS      obsolete
    DESCRIPTION "
The feature name
"
    ::= { sonusSystemLicenseLocalBundleInfoEntry 2 }

-- tagpath /system/licenseLocalBundleInfo/licenseId
sonusSystemLicenseLocalBundleInfoLicenseId OBJECT-TYPE
    SYNTAX      String (SIZE (0 .. 23))
    MAX-ACCESS  read-only
    STATUS      obsolete
    DESCRIPTION "
The licenseId
"
    ::= { sonusSystemLicenseLocalBundleInfoEntry 3 }

-- tagpath /system/licenseLocalBundleInfo/purchaseOrderId
sonusSystemLicenseLocalBundleInfoPurchaseOrderId OBJECT-TYPE
    SYNTAX      String (SIZE (0 .. 23))
    MAX-ACCESS  read-only
    STATUS      obsolete
    DESCRIPTION "
The purchase order id
"
    ::= { sonusSystemLicenseLocalBundleInfoEntry 4 }

-- tagpath /system/licenseLocalBundleInfo/lineId
sonusSystemLicenseLocalBundleInfoLineId OBJECT-TYPE
    SYNTAX      String (SIZE (0 .. 23))
    MAX-ACCESS  read-only
    STATUS      obsolete
    DESCRIPTION "
The  line id
"
    ::= { sonusSystemLicenseLocalBundleInfoEntry 5 }

-- tagpath /system/licenseLocalBundleInfo/generationDate
sonusSystemLicenseLocalBundleInfoGenerationDate OBJECT-TYPE
    SYNTAX      String (SIZE (0 .. 255))
    MAX-ACCESS  read-only
    STATUS      obsolete
    DESCRIPTION "
The generation date for this license
"
    ::= { sonusSystemLicenseLocalBundleInfoEntry 6 }

-- tagpath /system/licenseLocalBundleInfo/installDate
sonusSystemLicenseLocalBundleInfoInstallDate OBJECT-TYPE
    SYNTAX      DateAndTime
    MAX-ACCESS  read-only
    STATUS      obsolete
    DESCRIPTION "
This date the license was installed
"
    ::= { sonusSystemLicenseLocalBundleInfoEntry 7 }

-- tagpath /system/licenseLocalBundleInfo/expirationDate
sonusSystemLicenseLocalBundleInfoExpirationDate OBJECT-TYPE
    SYNTAX      String (SIZE (0 .. 255))
    MAX-ACCESS  read-only
    STATUS      obsolete
    DESCRIPTION "
The end date for this license
"
    ::= { sonusSystemLicenseLocalBundleInfoEntry 8 }

-- tagpath /system/licenseLocalBundleInfo/usageLimit
sonusSystemLicenseLocalBundleInfoUsageLimit OBJECT-TYPE
    SYNTAX      Integer32
    MAX-ACCESS  read-only
    STATUS      obsolete
    DESCRIPTION "
The usage limit for this license
"
    ::= { sonusSystemLicenseLocalBundleInfoEntry 9 }

-- tagpath /system/licenseLocalBundleInfo/fingerPrint1
sonusSystemLicenseLocalBundleInfoFingerPrint1 OBJECT-TYPE
    SYNTAX      String (SIZE (0 .. 255))
    MAX-ACCESS  read-only
    STATUS      obsolete
    DESCRIPTION "
The finger print for one of the nodes
"
    ::= { sonusSystemLicenseLocalBundleInfoEntry 10 }

-- tagpath /system/licenseLocalBundleInfo/fingerPrint2
sonusSystemLicenseLocalBundleInfoFingerPrint2 OBJECT-TYPE
    SYNTAX      String (SIZE (0 .. 255))
    MAX-ACCESS  read-only
    STATUS      obsolete
    DESCRIPTION "
If an HA license, The finger print for the other node
"
    ::= { sonusSystemLicenseLocalBundleInfoEntry 11 }

-- tagpath /system/licenseLocalBundleInfo/activeLicenseMode
sonusSystemLicenseLocalBundleInfoActiveLicenseMode OBJECT-TYPE
    SYNTAX      String (SIZE (0 .. 255))
    MAX-ACCESS  read-only
    STATUS      obsolete
    DESCRIPTION "
The active licensing mode
"
    ::= { sonusSystemLicenseLocalBundleInfoEntry 12 }

-- tagpath /system/licenseLegacyBundleInfo
sonusSystemLicenseLegacyBundleInfoTable OBJECT-TYPE
    SYNTAX      SEQUENCE OF SonusSystemLicenseLegacyBundleInfoEntry
    MAX-ACCESS  not-accessible
    STATUS      current
    DESCRIPTION "
Shows information about all the legacy licenses stored on the box
"
    ::= { sonusSystem 43 }

-- tagpath /system/licenseLegacyBundleInfo
sonusSystemLicenseLegacyBundleInfoEntry OBJECT-TYPE
    SYNTAX      SonusSystemLicenseLegacyBundleInfoEntry
    MAX-ACCESS  not-accessible
    STATUS      current
    DESCRIPTION ""
    INDEX { sonusSystemLicenseLegacyBundleInfoBundleName, sonusSystemLicenseLegacyBundleInfoFeatureName }
        ::= { sonusSystemLicenseLegacyBundleInfoTable 1 }

SonusSystemLicenseLegacyBundleInfoEntry ::=
    SEQUENCE {
        sonusSystemLicenseLegacyBundleInfoBundleName String,
        sonusSystemLicenseLegacyBundleInfoFeatureName String,
        sonusSystemLicenseLegacyBundleInfoLicenseId String,
        sonusSystemLicenseLegacyBundleInfoExpirationDate String,
        sonusSystemLicenseLegacyBundleInfoUsageLimit Integer32,
        sonusSystemLicenseLegacyBundleInfoActiveLicenseMode String
    }

-- tagpath /system/licenseLegacyBundleInfo/bundleName
sonusSystemLicenseLegacyBundleInfoBundleName OBJECT-TYPE
    SYNTAX      String (SIZE (0 .. 23))
    MAX-ACCESS  not-accessible
    STATUS      current
    DESCRIPTION "
The bundle name for the feature
"
    ::= { sonusSystemLicenseLegacyBundleInfoEntry 1 }

-- tagpath /system/licenseLegacyBundleInfo/featureName
sonusSystemLicenseLegacyBundleInfoFeatureName OBJECT-TYPE
    SYNTAX      String (SIZE (0 .. 23))
    MAX-ACCESS  not-accessible
    STATUS      current
    DESCRIPTION "
The feature name
"
    ::= { sonusSystemLicenseLegacyBundleInfoEntry 2 }

-- tagpath /system/licenseLegacyBundleInfo/licenseId
sonusSystemLicenseLegacyBundleInfoLicenseId OBJECT-TYPE
    SYNTAX      String (SIZE (0 .. 64))
    MAX-ACCESS  read-only
    STATUS      current
    DESCRIPTION "
The licenseId
"
    ::= { sonusSystemLicenseLegacyBundleInfoEntry 3 }

-- tagpath /system/licenseLegacyBundleInfo/expirationDate
sonusSystemLicenseLegacyBundleInfoExpirationDate OBJECT-TYPE
    SYNTAX      String (SIZE (0 .. 255))
    MAX-ACCESS  read-only
    STATUS      current
    DESCRIPTION "
The expiration date for this license
"
    ::= { sonusSystemLicenseLegacyBundleInfoEntry 4 }

-- tagpath /system/licenseLegacyBundleInfo/usageLimit
sonusSystemLicenseLegacyBundleInfoUsageLimit OBJECT-TYPE
    SYNTAX      Integer32
    MAX-ACCESS  read-only
    STATUS      current
    DESCRIPTION "
The count provisioned in this license
"
    ::= { sonusSystemLicenseLegacyBundleInfoEntry 5 }

-- tagpath /system/licenseLegacyBundleInfo/activeLicenseMode
sonusSystemLicenseLegacyBundleInfoActiveLicenseMode OBJECT-TYPE
    SYNTAX      String (SIZE (0 .. 255))
    MAX-ACCESS  read-only
    STATUS      current
    DESCRIPTION "
The active licensing mode
"
    ::= { sonusSystemLicenseLegacyBundleInfoEntry 13 }

-- tagpath /system/licenseNodeLockedBundleInfo
sonusSystemLicenseNodeLockedBundleInfoTable OBJECT-TYPE
    SYNTAX      SEQUENCE OF SonusSystemLicenseNodeLockedBundleInfoEntry
    MAX-ACCESS  not-accessible
    STATUS      current
    DESCRIPTION "
Shows information about all the nodeLocked licenses stored on the box
"
    ::= { sonusSystem 57 }

-- tagpath /system/licenseNodeLockedBundleInfo
sonusSystemLicenseNodeLockedBundleInfoEntry OBJECT-TYPE
    SYNTAX      SonusSystemLicenseNodeLockedBundleInfoEntry
    MAX-ACCESS  not-accessible
    STATUS      current
    DESCRIPTION ""
    INDEX { sonusSystemLicenseNodeLockedBundleInfoBundleName, sonusSystemLicenseNodeLockedBundleInfoFeatureName }
        ::= { sonusSystemLicenseNodeLockedBundleInfoTable 1 }

SonusSystemLicenseNodeLockedBundleInfoEntry ::=
    SEQUENCE {
        sonusSystemLicenseNodeLockedBundleInfoBundleName String,
        sonusSystemLicenseNodeLockedBundleInfoFeatureName String,
        sonusSystemLicenseNodeLockedBundleInfoLicenseId String,
        sonusSystemLicenseNodeLockedBundleInfoExpirationDate String,
        sonusSystemLicenseNodeLockedBundleInfoUsageLimit Integer32,
        sonusSystemLicenseNodeLockedBundleInfoActiveLicenseMode String
    }

-- tagpath /system/licenseNodeLockedBundleInfo/bundleName
sonusSystemLicenseNodeLockedBundleInfoBundleName OBJECT-TYPE
    SYNTAX      String (SIZE (0 .. 23))
    MAX-ACCESS  not-accessible
    STATUS      current
    DESCRIPTION "
The bundle name for the feature
"
    ::= { sonusSystemLicenseNodeLockedBundleInfoEntry 1 }

-- tagpath /system/licenseNodeLockedBundleInfo/featureName
sonusSystemLicenseNodeLockedBundleInfoFeatureName OBJECT-TYPE
    SYNTAX      String (SIZE (0 .. 23))
    MAX-ACCESS  not-accessible
    STATUS      current
    DESCRIPTION "
The feature name
"
    ::= { sonusSystemLicenseNodeLockedBundleInfoEntry 2 }

-- tagpath /system/licenseNodeLockedBundleInfo/licenseId
sonusSystemLicenseNodeLockedBundleInfoLicenseId OBJECT-TYPE
    SYNTAX      String (SIZE (0 .. 64))
    MAX-ACCESS  read-only
    STATUS      current
    DESCRIPTION "
The licenseId
"
    ::= { sonusSystemLicenseNodeLockedBundleInfoEntry 3 }

-- tagpath /system/licenseNodeLockedBundleInfo/expirationDate
sonusSystemLicenseNodeLockedBundleInfoExpirationDate OBJECT-TYPE
    SYNTAX      String (SIZE (0 .. 255))
    MAX-ACCESS  read-only
    STATUS      current
    DESCRIPTION "
The expiration date for this license
"
    ::= { sonusSystemLicenseNodeLockedBundleInfoEntry 4 }

-- tagpath /system/licenseNodeLockedBundleInfo/usageLimit
sonusSystemLicenseNodeLockedBundleInfoUsageLimit OBJECT-TYPE
    SYNTAX      Integer32
    MAX-ACCESS  read-only
    STATUS      current
    DESCRIPTION "
The count provisioned in this license
"
    ::= { sonusSystemLicenseNodeLockedBundleInfoEntry 5 }

-- tagpath /system/licenseNodeLockedBundleInfo/activeLicenseMode
sonusSystemLicenseNodeLockedBundleInfoActiveLicenseMode OBJECT-TYPE
    SYNTAX      String (SIZE (0 .. 255))
    MAX-ACCESS  read-only
    STATUS      current
    DESCRIPTION "
The active licensing mode
"
    ::= { sonusSystemLicenseNodeLockedBundleInfoEntry 13 }

-- tagpath /system/licenseDomainBundleInfo
sonusSystemLicenseDomainBundleInfoTable OBJECT-TYPE
    SYNTAX      SEQUENCE OF SonusSystemLicenseDomainBundleInfoEntry
    MAX-ACCESS  not-accessible
    STATUS      current
    DESCRIPTION "
Shows information about all the domain licenses stored on the box
"
    ::= { sonusSystem 56 }

-- tagpath /system/licenseDomainBundleInfo
sonusSystemLicenseDomainBundleInfoEntry OBJECT-TYPE
    SYNTAX      SonusSystemLicenseDomainBundleInfoEntry
    MAX-ACCESS  not-accessible
    STATUS      current
    DESCRIPTION ""
    INDEX { sonusSystemLicenseDomainBundleInfoBundleName, sonusSystemLicenseDomainBundleInfoFeatureName, sonusSystemLicenseDomainBundleInfoLineId }
        ::= { sonusSystemLicenseDomainBundleInfoTable 1 }

SonusSystemLicenseDomainBundleInfoEntry ::=
    SEQUENCE {
        sonusSystemLicenseDomainBundleInfoBundleName String,
        sonusSystemLicenseDomainBundleInfoFeatureName String,
        sonusSystemLicenseDomainBundleInfoLicenseId String,
        sonusSystemLicenseDomainBundleInfoPurchaseOrderId String,
        sonusSystemLicenseDomainBundleInfoLineId String,
        sonusSystemLicenseDomainBundleInfoGenerationDate String,
        sonusSystemLicenseDomainBundleInfoInstallDate DateAndTime,
        sonusSystemLicenseDomainBundleInfoExpirationDate String,
        sonusSystemLicenseDomainBundleInfoUsageLimit Integer32,
        sonusSystemLicenseDomainBundleInfoActiveLicenseMode String
    }

-- tagpath /system/licenseDomainBundleInfo/bundleName
sonusSystemLicenseDomainBundleInfoBundleName OBJECT-TYPE
    SYNTAX      String (SIZE (0 .. 23))
    MAX-ACCESS  not-accessible
    STATUS      current
    DESCRIPTION "
The bundle name for the feature
"
    ::= { sonusSystemLicenseDomainBundleInfoEntry 1 }

-- tagpath /system/licenseDomainBundleInfo/featureName
sonusSystemLicenseDomainBundleInfoFeatureName OBJECT-TYPE
    SYNTAX      String (SIZE (0 .. 23))
    MAX-ACCESS  not-accessible
    STATUS      current
    DESCRIPTION "
The feature name
"
    ::= { sonusSystemLicenseDomainBundleInfoEntry 2 }

-- tagpath /system/licenseDomainBundleInfo/licenseId
sonusSystemLicenseDomainBundleInfoLicenseId OBJECT-TYPE
    SYNTAX      String (SIZE (0 .. 64))
    MAX-ACCESS  read-only
    STATUS      obsolete
    DESCRIPTION "
The licenseId
"
    ::= { sonusSystemLicenseDomainBundleInfoEntry 3 }

-- tagpath /system/licenseDomainBundleInfo/purchaseOrderId
sonusSystemLicenseDomainBundleInfoPurchaseOrderId OBJECT-TYPE
    SYNTAX      String (SIZE (0 .. 23))
    MAX-ACCESS  read-only
    STATUS      obsolete
    DESCRIPTION "
The purchase order id
"
    ::= { sonusSystemLicenseDomainBundleInfoEntry 4 }

-- tagpath /system/licenseDomainBundleInfo/lineId
sonusSystemLicenseDomainBundleInfoLineId OBJECT-TYPE
    SYNTAX      String (SIZE (0 .. 64))
    MAX-ACCESS  not-accessible
    STATUS      current
    DESCRIPTION "
The  line id
"
    ::= { sonusSystemLicenseDomainBundleInfoEntry 5 }

-- tagpath /system/licenseDomainBundleInfo/generationDate
sonusSystemLicenseDomainBundleInfoGenerationDate OBJECT-TYPE
    SYNTAX      String (SIZE (0 .. 255))
    MAX-ACCESS  read-only
    STATUS      current
    DESCRIPTION "
The generation date for this license
"
    ::= { sonusSystemLicenseDomainBundleInfoEntry 6 }

-- tagpath /system/licenseDomainBundleInfo/installDate
sonusSystemLicenseDomainBundleInfoInstallDate OBJECT-TYPE
    SYNTAX      DateAndTime
    MAX-ACCESS  read-only
    STATUS      current
    DESCRIPTION "
This date the license was installed
"
    ::= { sonusSystemLicenseDomainBundleInfoEntry 7 }

-- tagpath /system/licenseDomainBundleInfo/expirationDate
sonusSystemLicenseDomainBundleInfoExpirationDate OBJECT-TYPE
    SYNTAX      String (SIZE (0 .. 255))
    MAX-ACCESS  read-only
    STATUS      current
    DESCRIPTION "
The end date for this license
"
    ::= { sonusSystemLicenseDomainBundleInfoEntry 8 }

-- tagpath /system/licenseDomainBundleInfo/usageLimit
sonusSystemLicenseDomainBundleInfoUsageLimit OBJECT-TYPE
    SYNTAX      Integer32
    MAX-ACCESS  read-only
    STATUS      current
    DESCRIPTION "
The usage limit for this license
"
    ::= { sonusSystemLicenseDomainBundleInfoEntry 9 }

-- tagpath /system/licenseDomainBundleInfo/activeLicenseMode
sonusSystemLicenseDomainBundleInfoActiveLicenseMode OBJECT-TYPE
    SYNTAX      String (SIZE (0 .. 255))
    MAX-ACCESS  read-only
    STATUS      current
    DESCRIPTION "
The active licensing mode
"
    ::= { sonusSystemLicenseDomainBundleInfoEntry 11 }

-- tagpath /system/licenseInfo
sonusSystemLicenseInfoTable OBJECT-TYPE
    SYNTAX      SEQUENCE OF SonusSystemLicenseInfoEntry
    MAX-ACCESS  not-accessible
    STATUS      current
    DESCRIPTION "
The license status for registered license features.
"
    ::= { sonusSystem 15 }

-- tagpath /system/licenseInfo
sonusSystemLicenseInfoEntry OBJECT-TYPE
    SYNTAX      SonusSystemLicenseInfoEntry
    MAX-ACCESS  not-accessible
    STATUS      current
    DESCRIPTION ""
    INDEX { sonusSystemLicenseInfoFeatureName, sonusSystemLicenseInfoLicenseId }
        ::= { sonusSystemLicenseInfoTable 1 }

SonusSystemLicenseInfoEntry ::=
    SEQUENCE {
        sonusSystemLicenseInfoFeatureName String,
        sonusSystemLicenseInfoLicenseId String,
        sonusSystemLicenseInfoExpirationDate String,
        sonusSystemLicenseInfoUsageLimit Integer32,
        sonusSystemLicenseInfoSource String,
        sonusSystemLicenseInfoInUse Integer32
    }

-- tagpath /system/licenseInfo/featureName
sonusSystemLicenseInfoFeatureName OBJECT-TYPE
    SYNTAX      String (SIZE (0 .. 255))
    MAX-ACCESS  not-accessible
    STATUS      current
    DESCRIPTION "
This object indicates the feature name
"
    ::= { sonusSystemLicenseInfoEntry 1 }

-- tagpath /system/licenseInfo/licenseId
sonusSystemLicenseInfoLicenseId OBJECT-TYPE
    SYNTAX      String (SIZE (0 .. 64))
    MAX-ACCESS  not-accessible
    STATUS      current
    DESCRIPTION "
This object indicates the license Id.
"
    ::= { sonusSystemLicenseInfoEntry 2 }

-- tagpath /system/licenseInfo/expirationDate
sonusSystemLicenseInfoExpirationDate OBJECT-TYPE
    SYNTAX      String (SIZE (0 .. 255))
    MAX-ACCESS  read-only
    STATUS      current
    DESCRIPTION "
This object indicates the licence expiry date for a feature.
"
    ::= { sonusSystemLicenseInfoEntry 3 }

-- tagpath /system/licenseInfo/usageLimit
sonusSystemLicenseInfoUsageLimit OBJECT-TYPE
    SYNTAX      Integer32
    MAX-ACCESS  read-only
    STATUS      current
    DESCRIPTION "
This object indicates the usageLimit of a feature.
"
    ::= { sonusSystemLicenseInfoEntry 4 }

-- tagpath /system/licenseInfo/source
sonusSystemLicenseInfoSource OBJECT-TYPE
    SYNTAX      String (SIZE (0 .. 255))
    MAX-ACCESS  read-only
    STATUS      current
    DESCRIPTION "
Indicates where the licenses is located: nodeLocked or domain
"
    ::= { sonusSystemLicenseInfoEntry 5 }

-- tagpath /system/licenseInfo/inUse
sonusSystemLicenseInfoInUse OBJECT-TYPE
    SYNTAX      Integer32
    MAX-ACCESS  read-only
    STATUS      current
    DESCRIPTION "
Indicates the number of licenses used by the application
"
    ::= { sonusSystemLicenseInfoEntry 6 }

-- tagpath /system/licenseInfoCurrentStatistics
sonusSystemLicenseInfoCurrentStatisticsTable OBJECT-TYPE
    SYNTAX      SEQUENCE OF SonusSystemLicenseInfoCurrentStatisticsEntry
    MAX-ACCESS  not-accessible
    STATUS      current
    DESCRIPTION "
The license status for registered license features.
"
    ::= { sonusSystem 44 }

-- tagpath /system/licenseInfoCurrentStatistics
sonusSystemLicenseInfoCurrentStatisticsEntry OBJECT-TYPE
    SYNTAX      SonusSystemLicenseInfoCurrentStatisticsEntry
    MAX-ACCESS  not-accessible
    STATUS      current
    DESCRIPTION ""
    INDEX { sonusSystemLicenseInfoCurrentStatisticsFeatureName, sonusSystemLicenseInfoCurrentStatisticsLicenseId }
        ::= { sonusSystemLicenseInfoCurrentStatisticsTable 1 }

SonusSystemLicenseInfoCurrentStatisticsEntry ::=
    SEQUENCE {
        sonusSystemLicenseInfoCurrentStatisticsFeatureName String,
        sonusSystemLicenseInfoCurrentStatisticsLicenseId String,
        sonusSystemLicenseInfoCurrentStatisticsExpirationDate String,
        sonusSystemLicenseInfoCurrentStatisticsUsageLimit Integer32,
        sonusSystemLicenseInfoCurrentStatisticsSource String,
        sonusSystemLicenseInfoCurrentStatisticsInUse Integer32
    }

-- tagpath /system/licenseInfoCurrentStatistics/featureName
sonusSystemLicenseInfoCurrentStatisticsFeatureName OBJECT-TYPE
    SYNTAX      String (SIZE (0 .. 255))
    MAX-ACCESS  not-accessible
    STATUS      current
    DESCRIPTION "
This object indicates the feature name
"
    ::= { sonusSystemLicenseInfoCurrentStatisticsEntry 1 }

-- tagpath /system/licenseInfoCurrentStatistics/licenseId
sonusSystemLicenseInfoCurrentStatisticsLicenseId OBJECT-TYPE
    SYNTAX      String (SIZE (0 .. 64))
    MAX-ACCESS  not-accessible
    STATUS      current
    DESCRIPTION "
This object indicates the license Id.
"
    ::= { sonusSystemLicenseInfoCurrentStatisticsEntry 2 }

-- tagpath /system/licenseInfoCurrentStatistics/expirationDate
sonusSystemLicenseInfoCurrentStatisticsExpirationDate OBJECT-TYPE
    SYNTAX      String (SIZE (0 .. 255))
    MAX-ACCESS  read-only
    STATUS      current
    DESCRIPTION "
This object indicates the licence expiry date for a feature.
"
    ::= { sonusSystemLicenseInfoCurrentStatisticsEntry 3 }

-- tagpath /system/licenseInfoCurrentStatistics/usageLimit
sonusSystemLicenseInfoCurrentStatisticsUsageLimit OBJECT-TYPE
    SYNTAX      Integer32
    MAX-ACCESS  read-only
    STATUS      current
    DESCRIPTION "
This object indicates the usageLimit of a feature.
"
    ::= { sonusSystemLicenseInfoCurrentStatisticsEntry 4 }

-- tagpath /system/licenseInfoCurrentStatistics/source
sonusSystemLicenseInfoCurrentStatisticsSource OBJECT-TYPE
    SYNTAX      String (SIZE (0 .. 255))
    MAX-ACCESS  read-only
    STATUS      current
    DESCRIPTION "
Indicates where the licenses is located: nodeLocked or domain
"
    ::= { sonusSystemLicenseInfoCurrentStatisticsEntry 5 }

-- tagpath /system/licenseInfoCurrentStatistics/inUse
sonusSystemLicenseInfoCurrentStatisticsInUse OBJECT-TYPE
    SYNTAX      Integer32
    MAX-ACCESS  read-only
    STATUS      current
    DESCRIPTION "
Indicates the number of licenses used by the application
"
    ::= { sonusSystemLicenseInfoCurrentStatisticsEntry 6 }

-- tagpath /system/licenseInfoIntervalStatistics
sonusSystemLicenseInfoIntervalStatisticsTable OBJECT-TYPE
    SYNTAX      SEQUENCE OF SonusSystemLicenseInfoIntervalStatisticsEntry
    MAX-ACCESS  not-accessible
    STATUS      current
    DESCRIPTION "
The license status for registered license features.
"
    ::= { sonusSystem 45 }

-- tagpath /system/licenseInfoIntervalStatistics
sonusSystemLicenseInfoIntervalStatisticsEntry OBJECT-TYPE
    SYNTAX      SonusSystemLicenseInfoIntervalStatisticsEntry
    MAX-ACCESS  not-accessible
    STATUS      current
    DESCRIPTION ""
    INDEX { sonusSystemLicenseInfoIntervalStatisticsFeatureName, sonusSystemLicenseInfoIntervalStatisticsLicenseId }
        ::= { sonusSystemLicenseInfoIntervalStatisticsTable 1 }

SonusSystemLicenseInfoIntervalStatisticsEntry ::=
    SEQUENCE {
        sonusSystemLicenseInfoIntervalStatisticsFeatureName String,
        sonusSystemLicenseInfoIntervalStatisticsLicenseId String,
        sonusSystemLicenseInfoIntervalStatisticsExpirationDate String,
        sonusSystemLicenseInfoIntervalStatisticsUsageLimit Integer32,
        sonusSystemLicenseInfoIntervalStatisticsSource String,
        sonusSystemLicenseInfoIntervalStatisticsInUse Integer32
    }

-- tagpath /system/licenseInfoIntervalStatistics/featureName
sonusSystemLicenseInfoIntervalStatisticsFeatureName OBJECT-TYPE
    SYNTAX      String (SIZE (0 .. 255))
    MAX-ACCESS  not-accessible
    STATUS      current
    DESCRIPTION "
This object indicates the feature name
"
    ::= { sonusSystemLicenseInfoIntervalStatisticsEntry 1 }

-- tagpath /system/licenseInfoIntervalStatistics/licenseId
sonusSystemLicenseInfoIntervalStatisticsLicenseId OBJECT-TYPE
    SYNTAX      String (SIZE (0 .. 64))
    MAX-ACCESS  not-accessible
    STATUS      current
    DESCRIPTION "
This object indicates the license Id.
"
    ::= { sonusSystemLicenseInfoIntervalStatisticsEntry 2 }

-- tagpath /system/licenseInfoIntervalStatistics/expirationDate
sonusSystemLicenseInfoIntervalStatisticsExpirationDate OBJECT-TYPE
    SYNTAX      String (SIZE (0 .. 255))
    MAX-ACCESS  read-only
    STATUS      current
    DESCRIPTION "
This object indicates the licence expiry date for a feature.
"
    ::= { sonusSystemLicenseInfoIntervalStatisticsEntry 3 }

-- tagpath /system/licenseInfoIntervalStatistics/usageLimit
sonusSystemLicenseInfoIntervalStatisticsUsageLimit OBJECT-TYPE
    SYNTAX      Integer32
    MAX-ACCESS  read-only
    STATUS      current
    DESCRIPTION "
This object indicates the usageLimit of a feature.
"
    ::= { sonusSystemLicenseInfoIntervalStatisticsEntry 4 }

-- tagpath /system/licenseInfoIntervalStatistics/source
sonusSystemLicenseInfoIntervalStatisticsSource OBJECT-TYPE
    SYNTAX      String (SIZE (0 .. 255))
    MAX-ACCESS  read-only
    STATUS      current
    DESCRIPTION "
Indicates where the licenses is located: nodeLocked or domain
"
    ::= { sonusSystemLicenseInfoIntervalStatisticsEntry 5 }

-- tagpath /system/licenseInfoIntervalStatistics/inUse
sonusSystemLicenseInfoIntervalStatisticsInUse OBJECT-TYPE
    SYNTAX      Integer32
    MAX-ACCESS  read-only
    STATUS      current
    DESCRIPTION "
Indicates the number of licenses used by the application
"
    ::= { sonusSystemLicenseInfoIntervalStatisticsEntry 6 }

-- tagpath /system/baseMacAddress
sonusSystemBaseMacAddressTable OBJECT-TYPE
    SYNTAX      SEQUENCE OF SonusSystemBaseMacAddressEntry
    MAX-ACCESS  not-accessible
    STATUS      current
    DESCRIPTION "
Displays base MAC address of servers
"
    ::= { sonusSystem 16 }

-- tagpath /system/baseMacAddress
sonusSystemBaseMacAddressEntry OBJECT-TYPE
    SYNTAX      SonusSystemBaseMacAddressEntry
    MAX-ACCESS  not-accessible
    STATUS      current
    DESCRIPTION ""
    INDEX { IMPLIED sonusSystemBaseMacAddressServerName }
        ::= { sonusSystemBaseMacAddressTable 1 }

SonusSystemBaseMacAddressEntry ::=
    SEQUENCE {
        sonusSystemBaseMacAddressServerName String,
        sonusSystemBaseMacAddressAssignedBaseAddress HexList,
        sonusSystemBaseMacAddressCurrentBaseAddress HexList,
        sonusSystemBaseMacAddressActiveBaseAddress HexList
    }

-- tagpath /system/baseMacAddress/serverName
sonusSystemBaseMacAddressServerName OBJECT-TYPE
    SYNTAX      String (SIZE (0 .. 255))
    MAX-ACCESS  not-accessible
    STATUS      current
    DESCRIPTION "
Name of server.
"
    ::= { sonusSystemBaseMacAddressEntry 1 }

-- tagpath /system/baseMacAddress/assignedBaseAddress
sonusSystemBaseMacAddressAssignedBaseAddress OBJECT-TYPE
    SYNTAX      HexList (SIZE (6 .. 6))
    MAX-ACCESS  read-only
    STATUS      current
    DESCRIPTION "
MAC address base assigned to this server
"
    ::= { sonusSystemBaseMacAddressEntry 2 }

-- tagpath /system/baseMacAddress/currentBaseAddress
sonusSystemBaseMacAddressCurrentBaseAddress OBJECT-TYPE
    SYNTAX      HexList (SIZE (6 .. 6))
    MAX-ACCESS  read-only
    STATUS      obsolete
    DESCRIPTION "
MAC address base assigned to this server at this time
"
    ::= { sonusSystemBaseMacAddressEntry 3 }

-- tagpath /system/baseMacAddress/activeBaseAddress
sonusSystemBaseMacAddressActiveBaseAddress OBJECT-TYPE
    SYNTAX      HexList (SIZE (6 .. 6))
    MAX-ACCESS  read-only
    STATUS      current
    DESCRIPTION "
MAC address base assigned to the active server
"
    ::= { sonusSystemBaseMacAddressEntry 4 }

-- tagpath /system/cpuUtilCurrentStatistics
sonusSystemCpuUtilCurrentStatisticsTable OBJECT-TYPE
    SYNTAX      SEQUENCE OF SonusSystemCpuUtilCurrentStatisticsEntry
    MAX-ACCESS  not-accessible
    STATUS      current
    DESCRIPTION "
The CPU utilization for the current
interval period.
"
    ::= { sonusSystem 17 }

-- tagpath /system/cpuUtilCurrentStatistics
sonusSystemCpuUtilCurrentStatisticsEntry OBJECT-TYPE
    SYNTAX      SonusSystemCpuUtilCurrentStatisticsEntry
    MAX-ACCESS  not-accessible
    STATUS      current
    DESCRIPTION ""
    INDEX { sonusSystemCpuUtilCurrentStatisticsCeName, sonusSystemCpuUtilCurrentStatisticsCpu }
        ::= { sonusSystemCpuUtilCurrentStatisticsTable 1 }

SonusSystemCpuUtilCurrentStatisticsEntry ::=
    SEQUENCE {
        sonusSystemCpuUtilCurrentStatisticsCeName String,
        sonusSystemCpuUtilCurrentStatisticsCpu Unsigned32,
        sonusSystemCpuUtilCurrentStatisticsAverage Unsigned32,
        sonusSystemCpuUtilCurrentStatisticsHigh Unsigned32,
        sonusSystemCpuUtilCurrentStatisticsLow Unsigned32
    }

-- tagpath /system/cpuUtilCurrentStatistics/ceName
sonusSystemCpuUtilCurrentStatisticsCeName OBJECT-TYPE
    SYNTAX      String (SIZE (0 .. 255))
    MAX-ACCESS  not-accessible
    STATUS      current
    DESCRIPTION "
This object indicates the configured CE name.
"
    ::= { sonusSystemCpuUtilCurrentStatisticsEntry 1 }

-- tagpath /system/cpuUtilCurrentStatistics/cpu
sonusSystemCpuUtilCurrentStatisticsCpu OBJECT-TYPE
    SYNTAX      Unsigned32
    MAX-ACCESS  not-accessible
    STATUS      current
    DESCRIPTION "
The cpu number.
"
    ::= { sonusSystemCpuUtilCurrentStatisticsEntry 2 }

-- tagpath /system/cpuUtilCurrentStatistics/average
sonusSystemCpuUtilCurrentStatisticsAverage OBJECT-TYPE
    SYNTAX      Unsigned32
    MAX-ACCESS  read-only
    STATUS      current
    DESCRIPTION "
The average cpu % utilization for this interval.
"
    ::= { sonusSystemCpuUtilCurrentStatisticsEntry 3 }

-- tagpath /system/cpuUtilCurrentStatistics/high
sonusSystemCpuUtilCurrentStatisticsHigh OBJECT-TYPE
    SYNTAX      Unsigned32
    MAX-ACCESS  read-only
    STATUS      current
    DESCRIPTION "
The high cpu % utilization for this interval.
"
    ::= { sonusSystemCpuUtilCurrentStatisticsEntry 4 }

-- tagpath /system/cpuUtilCurrentStatistics/low
sonusSystemCpuUtilCurrentStatisticsLow OBJECT-TYPE
    SYNTAX      Unsigned32
    MAX-ACCESS  read-only
    STATUS      current
    DESCRIPTION "
The low cpu % utilization for this interval.
"
    ::= { sonusSystemCpuUtilCurrentStatisticsEntry 5 }

-- tagpath /system/cpuUtilIntervalStatistics
sonusSystemCpuUtilIntervalStatisticsTable OBJECT-TYPE
    SYNTAX      SEQUENCE OF SonusSystemCpuUtilIntervalStatisticsEntry
    MAX-ACCESS  not-accessible
    STATUS      current
    DESCRIPTION "
The CPU utilization for the
'n' number of intervals.
"
    ::= { sonusSystem 18 }

-- tagpath /system/cpuUtilIntervalStatistics
sonusSystemCpuUtilIntervalStatisticsEntry OBJECT-TYPE
    SYNTAX      SonusSystemCpuUtilIntervalStatisticsEntry
    MAX-ACCESS  not-accessible
    STATUS      current
    DESCRIPTION ""
    INDEX { sonusSystemCpuUtilIntervalStatisticsNumber, sonusSystemCpuUtilIntervalStatisticsCeName, sonusSystemCpuUtilIntervalStatisticsCpu }
        ::= { sonusSystemCpuUtilIntervalStatisticsTable 1 }

SonusSystemCpuUtilIntervalStatisticsEntry ::=
    SEQUENCE {
        sonusSystemCpuUtilIntervalStatisticsNumber Unsigned32,
        sonusSystemCpuUtilIntervalStatisticsCeName String,
        sonusSystemCpuUtilIntervalStatisticsCpu Unsigned32,
        sonusSystemCpuUtilIntervalStatisticsIntervalValid INTEGER,
        sonusSystemCpuUtilIntervalStatisticsTime Unsigned32,
        sonusSystemCpuUtilIntervalStatisticsAverage Unsigned32,
        sonusSystemCpuUtilIntervalStatisticsHigh Unsigned32,
        sonusSystemCpuUtilIntervalStatisticsLow Unsigned32
    }

-- tagpath /system/cpuUtilIntervalStatistics/number
sonusSystemCpuUtilIntervalStatisticsNumber OBJECT-TYPE
    SYNTAX      Unsigned32
    MAX-ACCESS  not-accessible
    STATUS      current
    DESCRIPTION "
A sequence number which identifies the
interval for which the set of statistics is required.
The interval N identifies the recently completed interval,
Interval N is identifed by the last sequence value and N-( number of intervals)
is the earlest completed interval.
"
    ::= { sonusSystemCpuUtilIntervalStatisticsEntry 1 }

-- tagpath /system/cpuUtilIntervalStatistics/ceName
sonusSystemCpuUtilIntervalStatisticsCeName OBJECT-TYPE
    SYNTAX      String (SIZE (0 .. 255))
    MAX-ACCESS  not-accessible
    STATUS      current
    DESCRIPTION "
This object indicates the configured CE name.
"
    ::= { sonusSystemCpuUtilIntervalStatisticsEntry 2 }

-- tagpath /system/cpuUtilIntervalStatistics/cpu
sonusSystemCpuUtilIntervalStatisticsCpu OBJECT-TYPE
    SYNTAX      Unsigned32
    MAX-ACCESS  not-accessible
    STATUS      current
    DESCRIPTION "
The cpu number.
"
    ::= { sonusSystemCpuUtilIntervalStatisticsEntry 3 }

-- tagpath /system/cpuUtilIntervalStatistics/intervalValid
sonusSystemCpuUtilIntervalStatisticsIntervalValid OBJECT-TYPE
    SYNTAX      INTEGER {true(1),false(2)}
    MAX-ACCESS  read-only
    STATUS      current
    DESCRIPTION "
The member indicating the validity of the interval.
"
    ::= { sonusSystemCpuUtilIntervalStatisticsEntry 4 }

-- tagpath /system/cpuUtilIntervalStatistics/time
sonusSystemCpuUtilIntervalStatisticsTime OBJECT-TYPE
    SYNTAX      Unsigned32
    MAX-ACCESS  read-only
    STATUS      current
    DESCRIPTION "
The system up time when the interval statisitic is collected.
"
    ::= { sonusSystemCpuUtilIntervalStatisticsEntry 5 }

-- tagpath /system/cpuUtilIntervalStatistics/average
sonusSystemCpuUtilIntervalStatisticsAverage OBJECT-TYPE
    SYNTAX      Unsigned32
    MAX-ACCESS  read-only
    STATUS      current
    DESCRIPTION "
The average cpu % utilization for this interval.
"
    ::= { sonusSystemCpuUtilIntervalStatisticsEntry 6 }

-- tagpath /system/cpuUtilIntervalStatistics/high
sonusSystemCpuUtilIntervalStatisticsHigh OBJECT-TYPE
    SYNTAX      Unsigned32
    MAX-ACCESS  read-only
    STATUS      current
    DESCRIPTION "
The high cpu % utilization for this interval.
"
    ::= { sonusSystemCpuUtilIntervalStatisticsEntry 7 }

-- tagpath /system/cpuUtilIntervalStatistics/low
sonusSystemCpuUtilIntervalStatisticsLow OBJECT-TYPE
    SYNTAX      Unsigned32
    MAX-ACCESS  read-only
    STATUS      current
    DESCRIPTION "
The low cpu % utilization for this interval.
"
    ::= { sonusSystemCpuUtilIntervalStatisticsEntry 8 }

-- tagpath /system/memoryUtilCurrentStatistics
sonusSystemMemoryUtilCurrentStatisticsTable OBJECT-TYPE
    SYNTAX      SEQUENCE OF SonusSystemMemoryUtilCurrentStatisticsEntry
    MAX-ACCESS  not-accessible
    STATUS      current
    DESCRIPTION "
The memory utilization for the current
interval period.
"
    ::= { sonusSystem 19 }

-- tagpath /system/memoryUtilCurrentStatistics
sonusSystemMemoryUtilCurrentStatisticsEntry OBJECT-TYPE
    SYNTAX      SonusSystemMemoryUtilCurrentStatisticsEntry
    MAX-ACCESS  not-accessible
    STATUS      current
    DESCRIPTION ""
    INDEX { sonusSystemMemoryUtilCurrentStatisticsCeName }
        ::= { sonusSystemMemoryUtilCurrentStatisticsTable 1 }

SonusSystemMemoryUtilCurrentStatisticsEntry ::=
    SEQUENCE {
        sonusSystemMemoryUtilCurrentStatisticsCeName String,
        sonusSystemMemoryUtilCurrentStatisticsAverage Unsigned32,
        sonusSystemMemoryUtilCurrentStatisticsHigh Unsigned32,
        sonusSystemMemoryUtilCurrentStatisticsLow Unsigned32,
        sonusSystemMemoryUtilCurrentStatisticsAverageSwap Unsigned32,
        sonusSystemMemoryUtilCurrentStatisticsHighSwap Unsigned32,
        sonusSystemMemoryUtilCurrentStatisticsLowSwap Unsigned32
    }

-- tagpath /system/memoryUtilCurrentStatistics/ceName
sonusSystemMemoryUtilCurrentStatisticsCeName OBJECT-TYPE
    SYNTAX      String (SIZE (0 .. 255))
    MAX-ACCESS  not-accessible
    STATUS      current
    DESCRIPTION "
This object indicates the configured CE name.
"
    ::= { sonusSystemMemoryUtilCurrentStatisticsEntry 1 }

-- tagpath /system/memoryUtilCurrentStatistics/average
sonusSystemMemoryUtilCurrentStatisticsAverage OBJECT-TYPE
    SYNTAX      Unsigned32
    MAX-ACCESS  read-only
    STATUS      current
    DESCRIPTION "
The average memory % utilization for this interval.
"
    ::= { sonusSystemMemoryUtilCurrentStatisticsEntry 2 }

-- tagpath /system/memoryUtilCurrentStatistics/high
sonusSystemMemoryUtilCurrentStatisticsHigh OBJECT-TYPE
    SYNTAX      Unsigned32
    MAX-ACCESS  read-only
    STATUS      current
    DESCRIPTION "
The high memory % utilization for this interval.
"
    ::= { sonusSystemMemoryUtilCurrentStatisticsEntry 3 }

-- tagpath /system/memoryUtilCurrentStatistics/low
sonusSystemMemoryUtilCurrentStatisticsLow OBJECT-TYPE
    SYNTAX      Unsigned32
    MAX-ACCESS  read-only
    STATUS      current
    DESCRIPTION "
The low memory % utilization for this interval.
"
    ::= { sonusSystemMemoryUtilCurrentStatisticsEntry 4 }

-- tagpath /system/memoryUtilCurrentStatistics/averageSwap
sonusSystemMemoryUtilCurrentStatisticsAverageSwap OBJECT-TYPE
    SYNTAX      Unsigned32
    MAX-ACCESS  read-only
    STATUS      current
    DESCRIPTION "
The average swap % memory utilization for this interval.
"
    ::= { sonusSystemMemoryUtilCurrentStatisticsEntry 5 }

-- tagpath /system/memoryUtilCurrentStatistics/highSwap
sonusSystemMemoryUtilCurrentStatisticsHighSwap OBJECT-TYPE
    SYNTAX      Unsigned32
    MAX-ACCESS  read-only
    STATUS      current
    DESCRIPTION "
The high swap % memory utilization for this interval.
"
    ::= { sonusSystemMemoryUtilCurrentStatisticsEntry 6 }

-- tagpath /system/memoryUtilCurrentStatistics/lowSwap
sonusSystemMemoryUtilCurrentStatisticsLowSwap OBJECT-TYPE
    SYNTAX      Unsigned32
    MAX-ACCESS  read-only
    STATUS      current
    DESCRIPTION "
The low swap memory % utilization for this interval.
"
    ::= { sonusSystemMemoryUtilCurrentStatisticsEntry 7 }

-- tagpath /system/memoryUtilIntervalStatistics
sonusSystemMemoryUtilIntervalStatisticsTable OBJECT-TYPE
    SYNTAX      SEQUENCE OF SonusSystemMemoryUtilIntervalStatisticsEntry
    MAX-ACCESS  not-accessible
    STATUS      current
    DESCRIPTION "
The memory utilization for the
'n' number of intervals.
"
    ::= { sonusSystem 20 }

-- tagpath /system/memoryUtilIntervalStatistics
sonusSystemMemoryUtilIntervalStatisticsEntry OBJECT-TYPE
    SYNTAX      SonusSystemMemoryUtilIntervalStatisticsEntry
    MAX-ACCESS  not-accessible
    STATUS      current
    DESCRIPTION ""
    INDEX { sonusSystemMemoryUtilIntervalStatisticsNumber, sonusSystemMemoryUtilIntervalStatisticsCeName }
        ::= { sonusSystemMemoryUtilIntervalStatisticsTable 1 }

SonusSystemMemoryUtilIntervalStatisticsEntry ::=
    SEQUENCE {
        sonusSystemMemoryUtilIntervalStatisticsNumber Unsigned32,
        sonusSystemMemoryUtilIntervalStatisticsCeName String,
        sonusSystemMemoryUtilIntervalStatisticsIntervalValid INTEGER,
        sonusSystemMemoryUtilIntervalStatisticsTime Unsigned32,
        sonusSystemMemoryUtilIntervalStatisticsAverage Unsigned32,
        sonusSystemMemoryUtilIntervalStatisticsHigh Unsigned32,
        sonusSystemMemoryUtilIntervalStatisticsLow Unsigned32,
        sonusSystemMemoryUtilIntervalStatisticsAverageSwap Unsigned32,
        sonusSystemMemoryUtilIntervalStatisticsHighSwap Unsigned32,
        sonusSystemMemoryUtilIntervalStatisticsLowSwap Unsigned32
    }

-- tagpath /system/memoryUtilIntervalStatistics/number
sonusSystemMemoryUtilIntervalStatisticsNumber OBJECT-TYPE
    SYNTAX      Unsigned32
    MAX-ACCESS  not-accessible
    STATUS      current
    DESCRIPTION "
A sequence number which identifies the
interval for which the set of statistics is required.
The interval N identifies the recently completed interval,
Interval N is identifed by the last sequence value and N-( number of intervals)
is the earlest completed interval.
"
    ::= { sonusSystemMemoryUtilIntervalStatisticsEntry 1 }

-- tagpath /system/memoryUtilIntervalStatistics/ceName
sonusSystemMemoryUtilIntervalStatisticsCeName OBJECT-TYPE
    SYNTAX      String (SIZE (0 .. 255))
    MAX-ACCESS  not-accessible
    STATUS      current
    DESCRIPTION "
This object indicates the configured CE name.
"
    ::= { sonusSystemMemoryUtilIntervalStatisticsEntry 2 }

-- tagpath /system/memoryUtilIntervalStatistics/intervalValid
sonusSystemMemoryUtilIntervalStatisticsIntervalValid OBJECT-TYPE
    SYNTAX      INTEGER {true(1),false(2)}
    MAX-ACCESS  read-only
    STATUS      current
    DESCRIPTION "
The member indicating the validity of the interval.
"
    ::= { sonusSystemMemoryUtilIntervalStatisticsEntry 3 }

-- tagpath /system/memoryUtilIntervalStatistics/time
sonusSystemMemoryUtilIntervalStatisticsTime OBJECT-TYPE
    SYNTAX      Unsigned32
    MAX-ACCESS  read-only
    STATUS      current
    DESCRIPTION "
The system up time when the interval statisitic is collected.
"
    ::= { sonusSystemMemoryUtilIntervalStatisticsEntry 4 }

-- tagpath /system/memoryUtilIntervalStatistics/average
sonusSystemMemoryUtilIntervalStatisticsAverage OBJECT-TYPE
    SYNTAX      Unsigned32
    MAX-ACCESS  read-only
    STATUS      current
    DESCRIPTION "
The average memory % utilization for this interval.
"
    ::= { sonusSystemMemoryUtilIntervalStatisticsEntry 5 }

-- tagpath /system/memoryUtilIntervalStatistics/high
sonusSystemMemoryUtilIntervalStatisticsHigh OBJECT-TYPE
    SYNTAX      Unsigned32
    MAX-ACCESS  read-only
    STATUS      current
    DESCRIPTION "
The high memory % utilization for this interval.
"
    ::= { sonusSystemMemoryUtilIntervalStatisticsEntry 6 }

-- tagpath /system/memoryUtilIntervalStatistics/low
sonusSystemMemoryUtilIntervalStatisticsLow OBJECT-TYPE
    SYNTAX      Unsigned32
    MAX-ACCESS  read-only
    STATUS      current
    DESCRIPTION "
The low memory % utilization for this interval.
"
    ::= { sonusSystemMemoryUtilIntervalStatisticsEntry 7 }

-- tagpath /system/memoryUtilIntervalStatistics/averageSwap
sonusSystemMemoryUtilIntervalStatisticsAverageSwap OBJECT-TYPE
    SYNTAX      Unsigned32
    MAX-ACCESS  read-only
    STATUS      current
    DESCRIPTION "
The average swap memory % utilization for this interval.
"
    ::= { sonusSystemMemoryUtilIntervalStatisticsEntry 8 }

-- tagpath /system/memoryUtilIntervalStatistics/highSwap
sonusSystemMemoryUtilIntervalStatisticsHighSwap OBJECT-TYPE
    SYNTAX      Unsigned32
    MAX-ACCESS  read-only
    STATUS      current
    DESCRIPTION "
The high swap memory % utilization for this interval.
"
    ::= { sonusSystemMemoryUtilIntervalStatisticsEntry 9 }

-- tagpath /system/memoryUtilIntervalStatistics/lowSwap
sonusSystemMemoryUtilIntervalStatisticsLowSwap OBJECT-TYPE
    SYNTAX      Unsigned32
    MAX-ACCESS  read-only
    STATUS      current
    DESCRIPTION "
The low swap memory % utilization for this interval.
"
    ::= { sonusSystemMemoryUtilIntervalStatisticsEntry 10 }

-- tagpath /system/coredumpList
sonusSystemCoredumpListTable OBJECT-TYPE
    SYNTAX      SEQUENCE OF SonusSystemCoredumpListEntry
    MAX-ACCESS  not-accessible
    STATUS      current
    DESCRIPTION "
List of coredumps on the server(s).
"
    ::= { sonusSystem 21 }

-- tagpath /system/coredumpList
sonusSystemCoredumpListEntry OBJECT-TYPE
    SYNTAX      SonusSystemCoredumpListEntry
    MAX-ACCESS  not-accessible
    STATUS      current
    DESCRIPTION ""
    INDEX { sonusSystemCoredumpListServerName, sonusSystemCoredumpListIndex }
        ::= { sonusSystemCoredumpListTable 1 }

SonusSystemCoredumpListEntry ::=
    SEQUENCE {
        sonusSystemCoredumpListServerName String,
        sonusSystemCoredumpListIndex Unsigned32,
        sonusSystemCoredumpListCoredumpFileName String,
        sonusSystemCoredumpListSize String,
        sonusSystemCoredumpListDateAndTime String,
        sonusSystemCoredumpListNewSinceLastStart TruthValue
    }

-- tagpath /system/coredumpList/serverName
sonusSystemCoredumpListServerName OBJECT-TYPE
    SYNTAX      String (SIZE (0 .. 255))
    MAX-ACCESS  not-accessible
    STATUS      current
    DESCRIPTION "
Identifies the server.
"
    ::= { sonusSystemCoredumpListEntry 1 }

-- tagpath /system/coredumpList/index
sonusSystemCoredumpListIndex OBJECT-TYPE
    SYNTAX      Unsigned32
    MAX-ACCESS  not-accessible
    STATUS      current
    DESCRIPTION "
Index of the coredump file.
"
    ::= { sonusSystemCoredumpListEntry 2 }

-- tagpath /system/coredumpList/coredumpFileName
sonusSystemCoredumpListCoredumpFileName OBJECT-TYPE
    SYNTAX      String (SIZE (0 .. 255))
    MAX-ACCESS  read-only
    STATUS      current
    DESCRIPTION "
The file name of the coredump.
"
    ::= { sonusSystemCoredumpListEntry 3 }

-- tagpath /system/coredumpList/size
sonusSystemCoredumpListSize OBJECT-TYPE
    SYNTAX      String (SIZE (0 .. 23))
    MAX-ACCESS  read-only
    STATUS      current
    DESCRIPTION "
Indicates size of the coredump(KBytes).
"
    ::= { sonusSystemCoredumpListEntry 4 }

-- tagpath /system/coredumpList/dateAndTime
sonusSystemCoredumpListDateAndTime OBJECT-TYPE
    SYNTAX      String (SIZE (0 .. 255))
    MAX-ACCESS  read-only
    STATUS      current
    DESCRIPTION "
Indicates when the coredump occurred.
"
    ::= { sonusSystemCoredumpListEntry 5 }

-- tagpath /system/coredumpList/newSinceLastStart
sonusSystemCoredumpListNewSinceLastStart OBJECT-TYPE
    SYNTAX      TruthValue
    MAX-ACCESS  read-only
    STATUS      current
    DESCRIPTION "
Indicates if the it is new since last restart of the application.
"
    ::= { sonusSystemCoredumpListEntry 6 }

-- tagpath /system/coredumpSummary
sonusSystemCoredumpSummaryTable OBJECT-TYPE
    SYNTAX      SEQUENCE OF SonusSystemCoredumpSummaryEntry
    MAX-ACCESS  not-accessible
    STATUS      current
    DESCRIPTION "
Summary of coredump files on server(s).
"
    ::= { sonusSystem 22 }

-- tagpath /system/coredumpSummary
sonusSystemCoredumpSummaryEntry OBJECT-TYPE
    SYNTAX      SonusSystemCoredumpSummaryEntry
    MAX-ACCESS  not-accessible
    STATUS      current
    DESCRIPTION ""
    INDEX { sonusSystemCoredumpSummaryServerName }
        ::= { sonusSystemCoredumpSummaryTable 1 }

SonusSystemCoredumpSummaryEntry ::=
    SEQUENCE {
        sonusSystemCoredumpSummaryServerName String,
        sonusSystemCoredumpSummaryCoredumpAndTraceCount Unsigned32,
        sonusSystemCoredumpSummaryTotalSize String
    }

-- tagpath /system/coredumpSummary/serverName
sonusSystemCoredumpSummaryServerName OBJECT-TYPE
    SYNTAX      String (SIZE (0 .. 255))
    MAX-ACCESS  not-accessible
    STATUS      current
    DESCRIPTION "
Identifies the server.
"
    ::= { sonusSystemCoredumpSummaryEntry 1 }

-- tagpath /system/coredumpSummary/coredumpAndTraceCount
sonusSystemCoredumpSummaryCoredumpAndTraceCount OBJECT-TYPE
    SYNTAX      Unsigned32
    MAX-ACCESS  read-only
    STATUS      current
    DESCRIPTION "
Number of coredumps and trace files.
"
    ::= { sonusSystemCoredumpSummaryEntry 2 }

-- tagpath /system/coredumpSummary/totalSize
sonusSystemCoredumpSummaryTotalSize OBJECT-TYPE
    SYNTAX      String (SIZE (0 .. 23))
    MAX-ACCESS  read-only
    STATUS      current
    DESCRIPTION "
Indicates the total size of the coredumps(KBytes).
"
    ::= { sonusSystemCoredumpSummaryEntry 3 }

-- tagpath /system/savedConfigList
sonusSystemSavedConfigListTable OBJECT-TYPE
    SYNTAX      SEQUENCE OF SonusSystemSavedConfigListEntry
    MAX-ACCESS  not-accessible
    STATUS      current
    DESCRIPTION "
List of configurations saved on the system.
"
    ::= { sonusSystem 23 }

-- tagpath /system/savedConfigList
sonusSystemSavedConfigListEntry OBJECT-TYPE
    SYNTAX      SonusSystemSavedConfigListEntry
    MAX-ACCESS  not-accessible
    STATUS      current
    DESCRIPTION ""
    INDEX { sonusSystemSavedConfigListIndex }
        ::= { sonusSystemSavedConfigListTable 1 }

SonusSystemSavedConfigListEntry ::=
    SEQUENCE {
        sonusSystemSavedConfigListIndex Unsigned32,
        sonusSystemSavedConfigListFileName String,
        sonusSystemSavedConfigListSize String,
        sonusSystemSavedConfigListVersion String
    }

-- tagpath /system/savedConfigList/index
sonusSystemSavedConfigListIndex OBJECT-TYPE
    SYNTAX      Unsigned32
    MAX-ACCESS  not-accessible
    STATUS      current
    DESCRIPTION "
Index of the saved configuration file.
"
    ::= { sonusSystemSavedConfigListEntry 1 }

-- tagpath /system/savedConfigList/fileName
sonusSystemSavedConfigListFileName OBJECT-TYPE
    SYNTAX      String (SIZE (0 .. 255))
    MAX-ACCESS  read-only
    STATUS      current
    DESCRIPTION "
The file name of the saved configuration.
"
    ::= { sonusSystemSavedConfigListEntry 2 }

-- tagpath /system/savedConfigList/size
sonusSystemSavedConfigListSize OBJECT-TYPE
    SYNTAX      String (SIZE (0 .. 23))
    MAX-ACCESS  read-only
    STATUS      current
    DESCRIPTION "
Indicates size of the saved configuration file(KBytes).
"
    ::= { sonusSystemSavedConfigListEntry 3 }

-- tagpath /system/savedConfigList/version
sonusSystemSavedConfigListVersion OBJECT-TYPE
    SYNTAX      String (SIZE (0 .. 255))
    MAX-ACCESS  read-only
    STATUS      current
    DESCRIPTION "
The software version name of the saved configuration.
"
    ::= { sonusSystemSavedConfigListEntry 4 }

-- tagpath /system/fipsFSMState
sonusSystemFipsFSMStateTable OBJECT-TYPE
    SYNTAX      SEQUENCE OF SonusSystemFipsFSMStateEntry
    MAX-ACCESS  not-accessible
    STATUS      obsolete
    DESCRIPTION "
FIPS finite state machine state. This table is obsolete.
"
    ::= { sonusSystem 31 }

-- tagpath /system/fipsFSMState
sonusSystemFipsFSMStateEntry OBJECT-TYPE
    SYNTAX      SonusSystemFipsFSMStateEntry
    MAX-ACCESS  not-accessible
    STATUS      obsolete
    DESCRIPTION ""
    INDEX { sonusSystemFipsFSMStateIndx }
        ::= { sonusSystemFipsFSMStateTable 1 }

SonusSystemFipsFSMStateEntry ::=
    SEQUENCE {
        sonusSystemFipsFSMStateIndx Unsigned32,
        sonusSystemFipsFSMStateState String,
        sonusSystemFipsFSMStateTimeStamp String,
        sonusSystemFipsFSMStateIssuer String,
        sonusSystemFipsFSMStateMessage String
    }

-- tagpath /system/fipsFSMState/indx
sonusSystemFipsFSMStateIndx OBJECT-TYPE
    SYNTAX      Unsigned32
    MAX-ACCESS  not-accessible
    STATUS      obsolete
    DESCRIPTION "
FIPS FSM state.
"
    ::= { sonusSystemFipsFSMStateEntry 1 }

-- tagpath /system/fipsFSMState/state
sonusSystemFipsFSMStateState OBJECT-TYPE
    SYNTAX      String (SIZE (0 .. 255))
    MAX-ACCESS  read-only
    STATUS      obsolete
    DESCRIPTION "
FIPS FSM state.
"
    ::= { sonusSystemFipsFSMStateEntry 2 }

-- tagpath /system/fipsFSMState/timeStamp
sonusSystemFipsFSMStateTimeStamp OBJECT-TYPE
    SYNTAX      String (SIZE (0 .. 255))
    MAX-ACCESS  read-only
    STATUS      obsolete
    DESCRIPTION "
FIPS FSM time stamp.
"
    ::= { sonusSystemFipsFSMStateEntry 3 }

-- tagpath /system/fipsFSMState/issuer
sonusSystemFipsFSMStateIssuer OBJECT-TYPE
    SYNTAX      String (SIZE (0 .. 255))
    MAX-ACCESS  read-only
    STATUS      obsolete
    DESCRIPTION "
FIPS FSM Issuer.
"
    ::= { sonusSystemFipsFSMStateEntry 4 }

-- tagpath /system/fipsFSMState/message
sonusSystemFipsFSMStateMessage OBJECT-TYPE
    SYNTAX      String (SIZE (0 .. 255))
    MAX-ACCESS  read-only
    STATUS      obsolete
    DESCRIPTION "
FIPS FSM message.
"
    ::= { sonusSystemFipsFSMStateEntry 5 }

-- tagpath /system/fipsFSM2State
sonusSystemFipsFSM2StateTable OBJECT-TYPE
    SYNTAX      SEQUENCE OF SonusSystemFipsFSM2StateEntry
    MAX-ACCESS  not-accessible
    STATUS      current
    DESCRIPTION "
FIPS finite state machine state.
"
    ::= { sonusSystem 33 }

-- tagpath /system/fipsFSM2State
sonusSystemFipsFSM2StateEntry OBJECT-TYPE
    SYNTAX      SonusSystemFipsFSM2StateEntry
    MAX-ACCESS  not-accessible
    STATUS      current
    DESCRIPTION ""
    INDEX { sonusSystemFipsFSM2StateIndx }
        ::= { sonusSystemFipsFSM2StateTable 1 }

SonusSystemFipsFSM2StateEntry ::=
    SEQUENCE {
        sonusSystemFipsFSM2StateIndx Unsigned32,
        sonusSystemFipsFSM2StateState String,
        sonusSystemFipsFSM2StateTimeStamp String,
        sonusSystemFipsFSM2StateIssuer String,
        sonusSystemFipsFSM2StateMessage String
    }

-- tagpath /system/fipsFSM2State/indx
sonusSystemFipsFSM2StateIndx OBJECT-TYPE
    SYNTAX      Unsigned32
    MAX-ACCESS  not-accessible
    STATUS      current
    DESCRIPTION "
FIPS FSM state.
"
    ::= { sonusSystemFipsFSM2StateEntry 1 }

-- tagpath /system/fipsFSM2State/state
sonusSystemFipsFSM2StateState OBJECT-TYPE
    SYNTAX      String (SIZE (0 .. 255))
    MAX-ACCESS  read-only
    STATUS      current
    DESCRIPTION "
FIPS FSM state.
"
    ::= { sonusSystemFipsFSM2StateEntry 2 }

-- tagpath /system/fipsFSM2State/timeStamp
sonusSystemFipsFSM2StateTimeStamp OBJECT-TYPE
    SYNTAX      String (SIZE (0 .. 255))
    MAX-ACCESS  read-only
    STATUS      current
    DESCRIPTION "
FIPS FSM time stamp.
"
    ::= { sonusSystemFipsFSM2StateEntry 3 }

-- tagpath /system/fipsFSM2State/issuer
sonusSystemFipsFSM2StateIssuer OBJECT-TYPE
    SYNTAX      String (SIZE (0 .. 255))
    MAX-ACCESS  read-only
    STATUS      current
    DESCRIPTION "
FIPS FSM Issuer.
"
    ::= { sonusSystemFipsFSM2StateEntry 4 }

-- tagpath /system/fipsFSM2State/message
sonusSystemFipsFSM2StateMessage OBJECT-TYPE
    SYNTAX      String (SIZE (0 .. 255))
    MAX-ACCESS  read-only
    STATUS      current
    DESCRIPTION "
FIPS FSM message.
"
    ::= { sonusSystemFipsFSM2StateEntry 5 }

-- tagpath /system/dodModeStatus
sonusSystemDodModeStatusTable OBJECT-TYPE
    SYNTAX      SEQUENCE OF SonusSystemDodModeStatusEntry
    MAX-ACCESS  not-accessible
    STATUS      current
    DESCRIPTION "
DoD mode status
"
    ::= { sonusSystem 32 }

-- tagpath /system/dodModeStatus
sonusSystemDodModeStatusEntry OBJECT-TYPE
    SYNTAX      SonusSystemDodModeStatusEntry
    MAX-ACCESS  not-accessible
    STATUS      current
    DESCRIPTION ""
    INDEX { sonusSystemDodModeStatusIndx }
        ::= { sonusSystemDodModeStatusTable 1 }

SonusSystemDodModeStatusEntry ::=
    SEQUENCE {
        sonusSystemDodModeStatusIndx Unsigned32,
        sonusSystemDodModeStatusStatus String
    }

-- tagpath /system/dodModeStatus/indx
sonusSystemDodModeStatusIndx OBJECT-TYPE
    SYNTAX      Unsigned32
    MAX-ACCESS  not-accessible
    STATUS      current
    DESCRIPTION ""
    ::= { sonusSystemDodModeStatusEntry 1 }

-- tagpath /system/dodModeStatus/status
sonusSystemDodModeStatusStatus OBJECT-TYPE
    SYNTAX      String (SIZE (0 .. 255))
    MAX-ACCESS  read-only
    STATUS      current
    DESCRIPTION ""
    ::= { sonusSystemDodModeStatusEntry 2 }

-- tagpath /system/macAddressStatus
sonusSystemMacAddressStatusTable OBJECT-TYPE
    SYNTAX      SEQUENCE OF SonusSystemMacAddressStatusEntry
    MAX-ACCESS  not-accessible
    STATUS      obsolete
    DESCRIPTION "
Displays status of MAC address of servers. This table is obsolete.
"
    ::= { sonusSystem 30 }

-- tagpath /system/macAddressStatus
sonusSystemMacAddressStatusEntry OBJECT-TYPE
    SYNTAX      SonusSystemMacAddressStatusEntry
    MAX-ACCESS  not-accessible
    STATUS      obsolete
    DESCRIPTION ""
    INDEX { sonusSystemMacAddressStatusServerName, sonusSystemMacAddressStatusMacAddress }
        ::= { sonusSystemMacAddressStatusTable 1 }

SonusSystemMacAddressStatusEntry ::=
    SEQUENCE {
        sonusSystemMacAddressStatusServerName String,
        sonusSystemMacAddressStatusMacAddress String,
        sonusSystemMacAddressStatusStatus MacAddressStatusType,
        sonusSystemMacAddressStatusUsedBy String,
        sonusSystemMacAddressStatusUsedByPort String
    }

-- tagpath /system/macAddressStatus/serverName
sonusSystemMacAddressStatusServerName OBJECT-TYPE
    SYNTAX      String (SIZE (0 .. 255))
    MAX-ACCESS  not-accessible
    STATUS      obsolete
    DESCRIPTION "
Name of server.
"
    ::= { sonusSystemMacAddressStatusEntry 1 }

-- tagpath /system/macAddressStatus/macAddress
sonusSystemMacAddressStatusMacAddress OBJECT-TYPE
    SYNTAX      String (SIZE (0 .. 255))
    MAX-ACCESS  not-accessible
    STATUS      obsolete
    DESCRIPTION "
Mac address.
"
    ::= { sonusSystemMacAddressStatusEntry 2 }

-- tagpath /system/macAddressStatus/status
sonusSystemMacAddressStatusStatus OBJECT-TYPE
    SYNTAX      MacAddressStatusType
    MAX-ACCESS  read-only
    STATUS      obsolete
    DESCRIPTION "
Status of MAC Address
"
    ::= { sonusSystemMacAddressStatusEntry 3 }

-- tagpath /system/macAddressStatus/usedBy
sonusSystemMacAddressStatusUsedBy OBJECT-TYPE
    SYNTAX      String (SIZE (0 .. 255))
    MAX-ACCESS  read-only
    STATUS      obsolete
    DESCRIPTION "
MAC Address usedBy Server
"
    ::= { sonusSystemMacAddressStatusEntry 4 }

-- tagpath /system/macAddressStatus/usedByPort
sonusSystemMacAddressStatusUsedByPort OBJECT-TYPE
    SYNTAX      String (SIZE (0 .. 255))
    MAX-ACCESS  read-only
    STATUS      obsolete
    DESCRIPTION "
MAC Address usedByPort
"
    ::= { sonusSystemMacAddressStatusEntry 5 }

-- tagpath /system/macAddress2Status
sonusSystemMacAddress2StatusTable OBJECT-TYPE
    SYNTAX      SEQUENCE OF SonusSystemMacAddress2StatusEntry
    MAX-ACCESS  not-accessible
    STATUS      current
    DESCRIPTION "
Displays status of MAC address of servers
"
    ::= { sonusSystem 34 }

-- tagpath /system/macAddress2Status
sonusSystemMacAddress2StatusEntry OBJECT-TYPE
    SYNTAX      SonusSystemMacAddress2StatusEntry
    MAX-ACCESS  not-accessible
    STATUS      current
    DESCRIPTION ""
    INDEX { sonusSystemMacAddress2StatusServerName, sonusSystemMacAddress2StatusMacAddress }
        ::= { sonusSystemMacAddress2StatusTable 1 }

SonusSystemMacAddress2StatusEntry ::=
    SEQUENCE {
        sonusSystemMacAddress2StatusServerName String,
        sonusSystemMacAddress2StatusMacAddress String,
        sonusSystemMacAddress2StatusStatus MacAddressStatusType,
        sonusSystemMacAddress2StatusUsedBy String,
        sonusSystemMacAddress2StatusUsedByPort String
    }

-- tagpath /system/macAddress2Status/serverName
sonusSystemMacAddress2StatusServerName OBJECT-TYPE
    SYNTAX      String (SIZE (0 .. 255))
    MAX-ACCESS  not-accessible
    STATUS      current
    DESCRIPTION "
Name of server.
"
    ::= { sonusSystemMacAddress2StatusEntry 1 }

-- tagpath /system/macAddress2Status/macAddress
sonusSystemMacAddress2StatusMacAddress OBJECT-TYPE
    SYNTAX      String (SIZE (0 .. 255))
    MAX-ACCESS  not-accessible
    STATUS      current
    DESCRIPTION "
Mac address.
"
    ::= { sonusSystemMacAddress2StatusEntry 2 }

-- tagpath /system/macAddress2Status/status
sonusSystemMacAddress2StatusStatus OBJECT-TYPE
    SYNTAX      MacAddressStatusType
    MAX-ACCESS  read-only
    STATUS      current
    DESCRIPTION "
Status of MAC Address
"
    ::= { sonusSystemMacAddress2StatusEntry 3 }

-- tagpath /system/macAddress2Status/usedBy
sonusSystemMacAddress2StatusUsedBy OBJECT-TYPE
    SYNTAX      String (SIZE (0 .. 255))
    MAX-ACCESS  read-only
    STATUS      current
    DESCRIPTION "
MAC Address usedBy Server
"
    ::= { sonusSystemMacAddress2StatusEntry 4 }

-- tagpath /system/macAddress2Status/usedByPort
sonusSystemMacAddress2StatusUsedByPort OBJECT-TYPE
    SYNTAX      String (SIZE (0 .. 255))
    MAX-ACCESS  read-only
    STATUS      current
    DESCRIPTION "
MAC Address usedByPort
"
    ::= { sonusSystemMacAddress2StatusEntry 5 }

-- tagpath /system/gpuStatus
sonusSystemGpuStatusTable OBJECT-TYPE
    SYNTAX      SEQUENCE OF SonusSystemGpuStatusEntry
    MAX-ACCESS  not-accessible
    STATUS      current
    DESCRIPTION "
Displays Information of GPUs present in server
"
    ::= { sonusSystem 53 }

-- tagpath /system/gpuStatus
sonusSystemGpuStatusEntry OBJECT-TYPE
    SYNTAX      SonusSystemGpuStatusEntry
    MAX-ACCESS  not-accessible
    STATUS      current
    DESCRIPTION ""
    INDEX { sonusSystemGpuStatusServerName, sonusSystemGpuStatusGPUNumber }
        ::= { sonusSystemGpuStatusTable 1 }

SonusSystemGpuStatusEntry ::=
    SEQUENCE {
        sonusSystemGpuStatusServerName String,
        sonusSystemGpuStatusGPUNumber Unsigned32,
        sonusSystemGpuStatusMemoryUsage Integer32,
        sonusSystemGpuStatusCurrentTemperature Integer32,
        sonusSystemGpuStatusShutdownTemperature Integer32,
        sonusSystemGpuStatusSlowdownTemperature Integer32,
        sonusSystemGpuStatusMemoryClockSpeed Integer32,
        sonusSystemGpuStatusGraphicsClockSpeed Integer32,
        sonusSystemGpuStatusEccErrors Integer32,
        sonusSystemGpuStatusCurrentEccMode String,
        sonusSystemGpuStatusPendingEccMode String
    }

-- tagpath /system/gpuStatus/serverName
sonusSystemGpuStatusServerName OBJECT-TYPE
    SYNTAX      String (SIZE (0 .. 255))
    MAX-ACCESS  not-accessible
    STATUS      current
    DESCRIPTION "
Name of server.
"
    ::= { sonusSystemGpuStatusEntry 1 }

-- tagpath /system/gpuStatus/GPUNumber
sonusSystemGpuStatusGPUNumber OBJECT-TYPE
    SYNTAX      Unsigned32
    MAX-ACCESS  not-accessible
    STATUS      current
    DESCRIPTION "
Index of GPU.
"
    ::= { sonusSystemGpuStatusEntry 2 }

-- tagpath /system/gpuStatus/memoryUsage
sonusSystemGpuStatusMemoryUsage OBJECT-TYPE
    SYNTAX      Integer32
    MAX-ACCESS  read-only
    STATUS      current
    DESCRIPTION "
Memory usage of GPU(Percent),  -1 is displayed when no data is available
"
    ::= { sonusSystemGpuStatusEntry 3 }

-- tagpath /system/gpuStatus/currentTemperature
sonusSystemGpuStatusCurrentTemperature OBJECT-TYPE
    SYNTAX      Integer32
    MAX-ACCESS  read-only
    STATUS      current
    DESCRIPTION "
Temperature of GPU in degree celsius, -1 is displayed when no data is available
"
    ::= { sonusSystemGpuStatusEntry 4 }

-- tagpath /system/gpuStatus/shutdownTemperature
sonusSystemGpuStatusShutdownTemperature OBJECT-TYPE
    SYNTAX      Integer32
    MAX-ACCESS  read-only
    STATUS      current
    DESCRIPTION "
GPU Shutdown Temperature in degree celsius, -1 is displayed when no data is available
"
    ::= { sonusSystemGpuStatusEntry 5 }

-- tagpath /system/gpuStatus/slowdownTemperature
sonusSystemGpuStatusSlowdownTemperature OBJECT-TYPE
    SYNTAX      Integer32
    MAX-ACCESS  read-only
    STATUS      current
    DESCRIPTION "
GPU Slowdown Temperature in degree celsius, -1 is displayed when no data is available
"
    ::= { sonusSystemGpuStatusEntry 6 }

-- tagpath /system/gpuStatus/memoryClockSpeed
sonusSystemGpuStatusMemoryClockSpeed OBJECT-TYPE
    SYNTAX      Integer32
    MAX-ACCESS  read-only
    STATUS      current
    DESCRIPTION "
Memory clock speed of GPU in degree celsius, -1 is displayed when no data is available
"
    ::= { sonusSystemGpuStatusEntry 7 }

-- tagpath /system/gpuStatus/graphicsClockSpeed
sonusSystemGpuStatusGraphicsClockSpeed OBJECT-TYPE
    SYNTAX      Integer32
    MAX-ACCESS  read-only
    STATUS      current
    DESCRIPTION "
Graphics clock speed of GPU in degree celsius, -1 is displayed when no data is available
"
    ::= { sonusSystemGpuStatusEntry 8 }

-- tagpath /system/gpuStatus/eccErrors
sonusSystemGpuStatusEccErrors OBJECT-TYPE
    SYNTAX      Integer32
    MAX-ACCESS  read-only
    STATUS      current
    DESCRIPTION "
ECC errors, -1 shows no data available
"
    ::= { sonusSystemGpuStatusEntry 9 }

-- tagpath /system/gpuStatus/currentEccMode
sonusSystemGpuStatusCurrentEccMode OBJECT-TYPE
    SYNTAX      String (SIZE (0 .. 255))
    MAX-ACCESS  read-only
    STATUS      current
    DESCRIPTION "
Current ECC mode
"
    ::= { sonusSystemGpuStatusEntry 10 }

-- tagpath /system/gpuStatus/pendingEccMode
sonusSystemGpuStatusPendingEccMode OBJECT-TYPE
    SYNTAX      String (SIZE (0 .. 255))
    MAX-ACCESS  read-only
    STATUS      current
    DESCRIPTION "
Current ECC mode
"
    ::= { sonusSystemGpuStatusEntry 11 }

-- tagpath /system/configStoreFiles
sonusSystemConfigStoreFilesTable OBJECT-TYPE
    SYNTAX      SEQUENCE OF SonusSystemConfigStoreFilesEntry
    MAX-ACCESS  not-accessible
    STATUS      current
    DESCRIPTION "
Displays the configuration files on an external object store service
"
    ::= { sonusSystem 40 }

-- tagpath /system/configStoreFiles
sonusSystemConfigStoreFilesEntry OBJECT-TYPE
    SYNTAX      SonusSystemConfigStoreFilesEntry
    MAX-ACCESS  not-accessible
    STATUS      current
    DESCRIPTION ""
    INDEX { sonusSystemConfigStoreFilesFileName }
        ::= { sonusSystemConfigStoreFilesTable 1 }

SonusSystemConfigStoreFilesEntry ::=
    SEQUENCE {
        sonusSystemConfigStoreFilesFileName String,
        sonusSystemConfigStoreFilesVersion String,
        sonusSystemConfigStoreFilesClusterId Unsigned32
    }

-- tagpath /system/configStoreFiles/fileName
sonusSystemConfigStoreFilesFileName OBJECT-TYPE
    SYNTAX      String (SIZE (0 .. 255))
    MAX-ACCESS  not-accessible
    STATUS      current
    DESCRIPTION "
Name of a configuration file.
"
    ::= { sonusSystemConfigStoreFilesEntry 1 }

-- tagpath /system/configStoreFiles/version
sonusSystemConfigStoreFilesVersion OBJECT-TYPE
    SYNTAX      String (SIZE (0 .. 255))
    MAX-ACCESS  read-only
    STATUS      current
    DESCRIPTION "
The version of the configuration file.
"
    ::= { sonusSystemConfigStoreFilesEntry 2 }

-- tagpath /system/configStoreFiles/clusterId
sonusSystemConfigStoreFilesClusterId OBJECT-TYPE
    SYNTAX      Unsigned32
    MAX-ACCESS  read-only
    STATUS      current
    DESCRIPTION "
The cluster ID of the configuration file.
"
    ::= { sonusSystemConfigStoreFilesEntry 3 }

-- tagpath /system/haConfig
sonusSystemHaConfigTable OBJECT-TYPE
    SYNTAX      SEQUENCE OF SonusSystemHaConfigEntry
    MAX-ACCESS  not-accessible
    STATUS      current
    DESCRIPTION "
Displays the HA port redundancy configuration.
"
    ::= { sonusSystem 36 }

-- tagpath /system/haConfig
sonusSystemHaConfigEntry OBJECT-TYPE
    SYNTAX      SonusSystemHaConfigEntry
    MAX-ACCESS  not-accessible
    STATUS      current
    DESCRIPTION ""
    INDEX { sonusSystemHaConfigServerName }
        ::= { sonusSystemHaConfigTable 1 }

SonusSystemHaConfigEntry ::=
    SEQUENCE {
        sonusSystemHaConfigServerName String,
        sonusSystemHaConfigLeaderElection SonusLeaderElectType,
        sonusSystemHaConfigBondMonitoring SonusBondMonitorType
    }

-- tagpath /system/haConfig/serverName
sonusSystemHaConfigServerName OBJECT-TYPE
    SYNTAX      String (SIZE (0 .. 255))
    MAX-ACCESS  not-accessible
    STATUS      current
    DESCRIPTION "
Name of server.
"
    ::= { sonusSystemHaConfigEntry 1 }

-- tagpath /system/haConfig/leaderElection
sonusSystemHaConfigLeaderElection OBJECT-TYPE
    SYNTAX      SonusLeaderElectType
    MAX-ACCESS  read-only
    STATUS      current
    DESCRIPTION "
Leader Election Algorithm.
"
    ::= { sonusSystemHaConfigEntry 2 }

-- tagpath /system/haConfig/bondMonitoring
sonusSystemHaConfigBondMonitoring OBJECT-TYPE
    SYNTAX      SonusBondMonitorType
    MAX-ACCESS  read-only
    STATUS      current
    DESCRIPTION "
bond device monitoring.
"
    ::= { sonusSystemHaConfigEntry 3 }

-- tagpath /system/rgStatus
sonusSystemRgStatusTable OBJECT-TYPE
    SYNTAX      SEQUENCE OF SonusSystemRgStatusEntry
    MAX-ACCESS  not-accessible
    STATUS      current
    DESCRIPTION "
The system Redundancy Group(RG) status table describes the status of the
instances in RG.
"
    ::= { sonusSystem 51 }

-- tagpath /system/rgStatus
sonusSystemRgStatusEntry OBJECT-TYPE
    SYNTAX      SonusSystemRgStatusEntry
    MAX-ACCESS  not-accessible
    STATUS      current
    DESCRIPTION ""
    INDEX { sonusSystemRgStatusInstanceRgName }
        ::= { sonusSystemRgStatusTable 1 }

SonusSystemRgStatusEntry ::=
    SEQUENCE {
        sonusSystemRgStatusInstanceRgName String,
        sonusSystemRgStatusActualCeName String,
        sonusSystemRgStatusAssignedRole SonusNodeSrvrStatModeType,
        sonusSystemRgStatusCurrentRole String,
        sonusSystemRgStatusNodeId Unsigned32,
        sonusSystemRgStatusServiceId Unsigned32,
        sonusSystemRgStatusSyncStatus SonusNodeSrvrSyncStatusType,
        sonusSystemRgStatusUsingMetavarsOf String,
        sonusSystemRgStatusAppVersion String
    }

-- tagpath /system/rgStatus/instanceRgName
sonusSystemRgStatusInstanceRgName OBJECT-TYPE
    SYNTAX      String (SIZE (0 .. 255))
    MAX-ACCESS  not-accessible
    STATUS      current
    DESCRIPTION "
Identifies the instance.
"
    ::= { sonusSystemRgStatusEntry 1 }

-- tagpath /system/rgStatus/actualCeName
sonusSystemRgStatusActualCeName OBJECT-TYPE
    SYNTAX      String (SIZE (0 .. 255))
    MAX-ACCESS  read-only
    STATUS      current
    DESCRIPTION "
Identifies the given/actual server.
"
    ::= { sonusSystemRgStatusEntry 2 }

-- tagpath /system/rgStatus/assignedRole
sonusSystemRgStatusAssignedRole OBJECT-TYPE
    SYNTAX      SonusNodeSrvrStatModeType
    MAX-ACCESS  read-only
    STATUS      current
    DESCRIPTION "
Indicates the assigned redundancy role of the instance.
"
    ::= { sonusSystemRgStatusEntry 3 }

-- tagpath /system/rgStatus/currentRole
sonusSystemRgStatusCurrentRole OBJECT-TYPE
    SYNTAX      String (SIZE (0 .. 255))
    MAX-ACCESS  read-only
    STATUS      current
    DESCRIPTION "
Indicates the current redundancy role of the instance.
"
    ::= { sonusSystemRgStatusEntry 4 }

-- tagpath /system/rgStatus/nodeId
sonusSystemRgStatusNodeId OBJECT-TYPE
    SYNTAX      Unsigned32
    MAX-ACCESS  read-only
    STATUS      current
    DESCRIPTION "
Node id of the instance.
"
    ::= { sonusSystemRgStatusEntry 5 }

-- tagpath /system/rgStatus/serviceId
sonusSystemRgStatusServiceId OBJECT-TYPE
    SYNTAX      Unsigned32
    MAX-ACCESS  read-only
    STATUS      current
    DESCRIPTION "
Service id of the instance.
"
    ::= { sonusSystemRgStatusEntry 6 }

-- tagpath /system/rgStatus/syncStatus
sonusSystemRgStatusSyncStatus OBJECT-TYPE
    SYNTAX      SonusNodeSrvrSyncStatusType
    MAX-ACCESS  read-only
    STATUS      current
    DESCRIPTION "
Indicates synchronization state of the instance.
"
    ::= { sonusSystemRgStatusEntry 7 }

-- tagpath /system/rgStatus/usingMetavarsOf
sonusSystemRgStatusUsingMetavarsOf OBJECT-TYPE
    SYNTAX      String (SIZE (0 .. 255))
    MAX-ACCESS  read-only
    STATUS      current
    DESCRIPTION "
Indicates the Metavariables this instance is using belongs to which stack/instance.
"
    ::= { sonusSystemRgStatusEntry 8 }

-- tagpath /system/rgStatus/appVersion
sonusSystemRgStatusAppVersion OBJECT-TYPE
    SYNTAX      String (SIZE (0 .. 255))
    MAX-ACCESS  read-only
    STATUS      current
    DESCRIPTION "
Indicates the version of sbc running on this instance
"
    ::= { sonusSystemRgStatusEntry 9 }

END
