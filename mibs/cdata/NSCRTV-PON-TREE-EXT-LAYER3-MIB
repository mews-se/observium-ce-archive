--
-- NSCRTV-PON-TREE-EXT-LAYER3-MIB.my
-- MIB generated by MG-SOFT Visual MIB Builder Version 6.0  Build 88
-- Saturday, January 26, 2019 at 14:15:45
--

	NSCRTV-PON-TREE-EXT-LAYER3-MIB DEFINITIONS ::= BEGIN
 
		IMPORTS
			IpAddress, Unsigned32, OBJECT-TYPE, MODULE-IDENTITY			
				FROM SNMPv2-SMI			
			RowStatus, TruthValue, DateAndTime			
				FROM SNMPv2-TC			
			pon, NscrtvPonExtDeviceIndex			
				FROM VENDOR-COMMON-MIB;
	
	
		-- 1.3.6.1.4.1.34592.1.3.100
		nscrtvPonTreeExt MODULE-IDENTITY 
			LAST-UPDATED "201706051636Z"		-- June 05, 2017 at 16:36 GMT
			ORGANIZATION 
				"Organization."
			CONTACT-INFO 
				"Contact-info."
			DESCRIPTION 
				"Description."
			::= { pon 100 }

		
	
	
--
-- Node definitions
--
	
		-- 1.3.6.1.4.1.34592.1.3.100.7
		layer3ManagementObjects OBJECT IDENTIFIER ::= { nscrtvPonTreeExt 7 }

		
		-- 1.3.6.1.4.1.34592.1.3.100.7.1
		staticManagement OBJECT IDENTIFIER ::= { layer3ManagementObjects 1 }

		
		-- 1.3.6.1.4.1.34592.1.3.100.7.1.1
		ipRouteTable OBJECT-TYPE
			SYNTAX SEQUENCE OF IpRouteEntry
			MAX-ACCESS not-accessible
			STATUS current
			DESCRIPTION
				"Description."
			::= { staticManagement 1 }

		
		-- 1.3.6.1.4.1.34592.1.3.100.7.1.1.1
		ipRouteEntry OBJECT-TYPE
			SYNTAX IpRouteEntry
			MAX-ACCESS not-accessible
			STATUS current
			DESCRIPTION
				"Description."
			INDEX { ipRouteDestinationIpAddrIndex, ipRouteNetMaskIndex, ipRouteProtoIndex, ipRouteNextHopIndex }
			::= { ipRouteTable 1 }

		
		IpRouteEntry ::=
			SEQUENCE { 
				ipRouteDestinationIpAddrIndex
					IpAddress,
				ipRouteNetMaskIndex
					IpAddress,
				ipRouteProtoIndex
					INTEGER,
				ipRouteNextHopIndex
					IpAddress,
				ipRoutePreference
					Unsigned32,
				ipRouteMetric
					Unsigned32,
				ipRouteInterface
					Unsigned32,
				ipRouteRowStatus
					RowStatus,
				ipRouteState
					INTEGER
			 }

		-- 1.3.6.1.4.1.34592.1.3.100.7.1.1.1.1
		ipRouteDestinationIpAddrIndex OBJECT-TYPE
			SYNTAX IpAddress
			MAX-ACCESS not-accessible
			STATUS current
			DESCRIPTION
				"Description."
			::= { ipRouteEntry 1 }

		
		-- 1.3.6.1.4.1.34592.1.3.100.7.1.1.1.2
		ipRouteNetMaskIndex OBJECT-TYPE
			SYNTAX IpAddress
			MAX-ACCESS not-accessible
			STATUS current
			DESCRIPTION
				"Description."
			::= { ipRouteEntry 2 }

		
		-- 1.3.6.1.4.1.34592.1.3.100.7.1.1.1.3
		ipRouteProtoIndex OBJECT-TYPE
			SYNTAX INTEGER
				{
				direct(1),
				static(2),
				rip(3),
				ospf(4),
				pimsm(5),
				bgp(6),
				mbgp(7)
				}
			MAX-ACCESS not-accessible
			STATUS current
			DESCRIPTION
				"Description."
			::= { ipRouteEntry 3 }

		
		-- 1.3.6.1.4.1.34592.1.3.100.7.1.1.1.4
		ipRouteNextHopIndex OBJECT-TYPE
			SYNTAX IpAddress
			MAX-ACCESS not-accessible
			STATUS current
			DESCRIPTION
				"Description."
			::= { ipRouteEntry 4 }

		
		-- 1.3.6.1.4.1.34592.1.3.100.7.1.1.1.5
		ipRoutePreference OBJECT-TYPE
			SYNTAX Unsigned32 (1..255)
			MAX-ACCESS read-create
			STATUS current
			DESCRIPTION
				"Description."
			::= { ipRouteEntry 5 }

		
		-- 1.3.6.1.4.1.34592.1.3.100.7.1.1.1.6
		ipRouteMetric OBJECT-TYPE
			SYNTAX Unsigned32
			MAX-ACCESS read-only
			STATUS current
			DESCRIPTION
				"Description."
			::= { ipRouteEntry 6 }

		
		-- 1.3.6.1.4.1.34592.1.3.100.7.1.1.1.7
		ipRouteInterface OBJECT-TYPE
			SYNTAX Unsigned32
			MAX-ACCESS read-only
			STATUS current
			DESCRIPTION
				"If this value is 0,it indicates that next hop is unreachable,and the others are 
				considered normal."
			::= { ipRouteEntry 7 }

		
		-- 1.3.6.1.4.1.34592.1.3.100.7.1.1.1.8
		ipRouteRowStatus OBJECT-TYPE
			SYNTAX RowStatus
			MAX-ACCESS read-create
			STATUS current
			DESCRIPTION
				"Description."
			::= { ipRouteEntry 8 }

		
		-- 1.3.6.1.4.1.34592.1.3.100.7.1.1.1.9
		ipRouteState OBJECT-TYPE
			SYNTAX INTEGER
			MAX-ACCESS read-only
			STATUS current
			DESCRIPTION
				"Description."
			::= { ipRouteEntry 9 }

		
		-- 1.3.6.1.4.1.34592.1.3.100.7.1.2
		ipRouteCollectTable OBJECT-TYPE
			SYNTAX SEQUENCE OF IpRouteCollectEntry
			MAX-ACCESS not-accessible
			STATUS current
			DESCRIPTION
				"Description."
			::= { staticManagement 2 }

		
		-- 1.3.6.1.4.1.34592.1.3.100.7.1.2.1
		ipRouteCollectEntry OBJECT-TYPE
			SYNTAX IpRouteCollectEntry
			MAX-ACCESS not-accessible
			STATUS current
			DESCRIPTION
				"Description."
			INDEX { ipRouteCollectIndex }
			::= { ipRouteCollectTable 1 }

		
		IpRouteCollectEntry ::=
			SEQUENCE { 
				ipRouteCollectIndex
					Integer32,
				ipRouteCollectinfo
					OCTET STRING
			 }

		-- 1.3.6.1.4.1.34592.1.3.100.7.1.2.1.1
		ipRouteCollectIndex OBJECT-TYPE
			SYNTAX Integer32
			MAX-ACCESS not-accessible
			STATUS current
			DESCRIPTION
				"Description."
			::= { ipRouteCollectEntry 1 }

		
		-- 1.3.6.1.4.1.34592.1.3.100.7.1.2.1.2
		ipRouteCollectinfo OBJECT-TYPE
			SYNTAX OCTET STRING
			MAX-ACCESS read-only
			STATUS current
			DESCRIPTION
				"Description."
			::= { ipRouteCollectEntry 2 }

		
		-- 1.3.6.1.4.1.34592.1.3.100.7.2
		ripManagement OBJECT IDENTIFIER ::= { layer3ManagementObjects 2 }

		
		-- 1.3.6.1.4.1.34592.1.3.100.7.2.1
		ripGlobalMixedTable OBJECT-TYPE
			SYNTAX SEQUENCE OF RipGlobalMixedEntry
			MAX-ACCESS not-accessible
			STATUS current
			DESCRIPTION
				"vty command:router rip"
			::= { ripManagement 1 }

		
		-- 1.3.6.1.4.1.34592.1.3.100.7.2.1.1
		ripGlobalMixedEntry OBJECT-TYPE
			SYNTAX RipGlobalMixedEntry
			MAX-ACCESS not-accessible
			STATUS current
			DESCRIPTION
				"Description."
			INDEX { ripGlobalMixedDeviceIndex }
			::= { ripGlobalMixedTable 1 }

		
		RipGlobalMixedEntry ::=
			SEQUENCE { 
				ripGlobalMixedDeviceIndex
					NscrtvPonExtDeviceIndex,
				ripGlobalMixedEnable
					TruthValue,
				ripGlobalMixedDefaultMetric
					Unsigned32,
				ripGlobalMixedDistance
					Unsigned32,
				ripGlobalMixedTimerUpdate
					Unsigned32,
				ripGlobalMixedTimerTimeout
					Unsigned32,
				ripGlobalMixedTimerGarbage
					Unsigned32,
				ripGlobalMixedTimerReset
					TruthValue,
				ripGlobalMixedVersion
					INTEGER
			 }

		-- 1.3.6.1.4.1.34592.1.3.100.7.2.1.1.1
		ripGlobalMixedDeviceIndex OBJECT-TYPE
			SYNTAX NscrtvPonExtDeviceIndex
			MAX-ACCESS not-accessible
			STATUS current
			DESCRIPTION
				"Description."
			::= { ripGlobalMixedEntry 1 }

		
		-- 1.3.6.1.4.1.34592.1.3.100.7.2.1.1.2
		ripGlobalMixedEnable OBJECT-TYPE
			SYNTAX TruthValue
			MAX-ACCESS read-write
			STATUS current
			DESCRIPTION
				"Description."
			::= { ripGlobalMixedEntry 2 }

		
		-- 1.3.6.1.4.1.34592.1.3.100.7.2.1.1.4
		ripGlobalMixedDefaultMetric OBJECT-TYPE
			SYNTAX Unsigned32 (1..16)
			MAX-ACCESS read-write
			STATUS current
			DESCRIPTION
				"Description."
			::= { ripGlobalMixedEntry 4 }

		
		-- 1.3.6.1.4.1.34592.1.3.100.7.2.1.1.5
		ripGlobalMixedDistance OBJECT-TYPE
			SYNTAX Unsigned32 (1..255)
			MAX-ACCESS read-write
			STATUS current
			DESCRIPTION
				"Description."
			::= { ripGlobalMixedEntry 5 }

		
		-- 1.3.6.1.4.1.34592.1.3.100.7.2.1.1.7
		ripGlobalMixedTimerUpdate OBJECT-TYPE
			SYNTAX Unsigned32 (5..16777215)
			MAX-ACCESS read-write
			STATUS current
			DESCRIPTION
				"Description."
			::= { ripGlobalMixedEntry 7 }

		
		-- 1.3.6.1.4.1.34592.1.3.100.7.2.1.1.8
		ripGlobalMixedTimerTimeout OBJECT-TYPE
			SYNTAX Unsigned32 (5..16777215)
			MAX-ACCESS read-write
			STATUS current
			DESCRIPTION
				"Description."
			::= { ripGlobalMixedEntry 8 }

		
		-- 1.3.6.1.4.1.34592.1.3.100.7.2.1.1.9
		ripGlobalMixedTimerGarbage OBJECT-TYPE
			SYNTAX Unsigned32 (5..16777215)
			MAX-ACCESS read-write
			STATUS current
			DESCRIPTION
				"Description."
			::= { ripGlobalMixedEntry 9 }

		
		-- 1.3.6.1.4.1.34592.1.3.100.7.2.1.1.10
		ripGlobalMixedTimerReset OBJECT-TYPE
			SYNTAX TruthValue
			MAX-ACCESS read-write
			STATUS current
			DESCRIPTION
				"Description."
			::= { ripGlobalMixedEntry 10 }

		
		-- 1.3.6.1.4.1.34592.1.3.100.7.2.1.1.11
		ripGlobalMixedVersion OBJECT-TYPE
			SYNTAX INTEGER
				{
				reset(0),
				version1(1),
				version2(2)
				}
			MAX-ACCESS read-write
			STATUS current
			DESCRIPTION
				"Description."
			::= { ripGlobalMixedEntry 11 }

		
		-- 1.3.6.1.4.1.34592.1.3.100.7.2.4
		ripGlobalNeighborTable OBJECT-TYPE
			SYNTAX SEQUENCE OF RipGlobalNeighborEntry
			MAX-ACCESS not-accessible
			STATUS current
			DESCRIPTION
				"Description."
			::= { ripManagement 4 }

		
		-- 1.3.6.1.4.1.34592.1.3.100.7.2.4.1
		ripGlobalNeighborEntry OBJECT-TYPE
			SYNTAX RipGlobalNeighborEntry
			MAX-ACCESS not-accessible
			STATUS current
			DESCRIPTION
				"Description."
			INDEX { ripGlobalNeighborIpAddrIndex }
			::= { ripGlobalNeighborTable 1 }

		
		RipGlobalNeighborEntry ::=
			SEQUENCE { 
				ripGlobalNeighborIpAddrIndex
					IpAddress,
				ripGlobalNeighborRowStatus
					RowStatus
			 }

		-- 1.3.6.1.4.1.34592.1.3.100.7.2.4.1.1
		ripGlobalNeighborIpAddrIndex OBJECT-TYPE
			SYNTAX IpAddress
			MAX-ACCESS not-accessible
			STATUS current
			DESCRIPTION
				"Description."
			::= { ripGlobalNeighborEntry 1 }

		
		-- 1.3.6.1.4.1.34592.1.3.100.7.2.4.1.6
		ripGlobalNeighborRowStatus OBJECT-TYPE
			SYNTAX RowStatus
			MAX-ACCESS read-create
			STATUS current
			DESCRIPTION
				"Description."
			::= { ripGlobalNeighborEntry 6 }

		
		-- 1.3.6.1.4.1.34592.1.3.100.7.2.6
		ripGlobalNetworkIpTable OBJECT-TYPE
			SYNTAX SEQUENCE OF RipGlobalNetworkIpEntry
			MAX-ACCESS not-accessible
			STATUS current
			DESCRIPTION
				"Description."
			::= { ripManagement 6 }

		
		-- 1.3.6.1.4.1.34592.1.3.100.7.2.6.1
		ripGlobalNetworkIpEntry OBJECT-TYPE
			SYNTAX RipGlobalNetworkIpEntry
			MAX-ACCESS not-accessible
			STATUS current
			DESCRIPTION
				"Description."
			INDEX { ripGlobalNetworkIpAddrIndex, ripGlobalNetworkMaskLenIndex }
			::= { ripGlobalNetworkIpTable 1 }

		
		RipGlobalNetworkIpEntry ::=
			SEQUENCE { 
				ripGlobalNetworkIpAddrIndex
					IpAddress,
				ripGlobalNetworkMaskLenIndex
					Unsigned32,
				ripGlobalNetworkIpRowStatus
					RowStatus
			 }

		-- 1.3.6.1.4.1.34592.1.3.100.7.2.6.1.2
		ripGlobalNetworkIpAddrIndex OBJECT-TYPE
			SYNTAX IpAddress
			MAX-ACCESS not-accessible
			STATUS current
			DESCRIPTION
				"Description."
			::= { ripGlobalNetworkIpEntry 2 }

		
		-- 1.3.6.1.4.1.34592.1.3.100.7.2.6.1.3
		ripGlobalNetworkMaskLenIndex OBJECT-TYPE
			SYNTAX Unsigned32 (0..32)
			MAX-ACCESS not-accessible
			STATUS current
			DESCRIPTION
				"Description."
			::= { ripGlobalNetworkIpEntry 3 }

		
		-- 1.3.6.1.4.1.34592.1.3.100.7.2.6.1.6
		ripGlobalNetworkIpRowStatus OBJECT-TYPE
			SYNTAX RowStatus
			MAX-ACCESS read-create
			STATUS current
			DESCRIPTION
				"Description."
			::= { ripGlobalNetworkIpEntry 6 }

		
		-- 1.3.6.1.4.1.34592.1.3.100.7.2.8
		ripGlobalRedistributeTable OBJECT-TYPE
			SYNTAX SEQUENCE OF RipGlobalRedistributeEntry
			MAX-ACCESS not-accessible
			STATUS current
			DESCRIPTION
				"Description."
			::= { ripManagement 8 }

		
		-- 1.3.6.1.4.1.34592.1.3.100.7.2.8.1
		ripGlobalRedistributeEntry OBJECT-TYPE
			SYNTAX RipGlobalRedistributeEntry
			MAX-ACCESS not-accessible
			STATUS current
			DESCRIPTION
				"Description."
			INDEX { ripGlobalRedistributeProtocolIndex }
			::= { ripGlobalRedistributeTable 1 }

		
		RipGlobalRedistributeEntry ::=
			SEQUENCE { 
				ripGlobalRedistributeProtocolIndex
					INTEGER,
				ripGlobalRedistributeMetric
					Unsigned32,
				ripGlobalRedistributeRowStatus
					RowStatus
			 }

		-- 1.3.6.1.4.1.34592.1.3.100.7.2.8.1.2
		ripGlobalRedistributeProtocolIndex OBJECT-TYPE
			SYNTAX INTEGER
				{
				babel(1),
				bgp(2),
				connected(3),
				isis(4),
				kernel(5),
				ospf(6),
				pim(7),
				static(8),
				default(9)
				}
			MAX-ACCESS not-accessible
			STATUS current
			DESCRIPTION
				"Description."
			::= { ripGlobalRedistributeEntry 2 }

		
		-- 1.3.6.1.4.1.34592.1.3.100.7.2.8.1.3
		ripGlobalRedistributeMetric OBJECT-TYPE
			SYNTAX Unsigned32 (0..16)
			MAX-ACCESS read-create
			STATUS current
			DESCRIPTION
				"Description."
			::= { ripGlobalRedistributeEntry 3 }

		
		-- 1.3.6.1.4.1.34592.1.3.100.7.2.8.1.6
		ripGlobalRedistributeRowStatus OBJECT-TYPE
			SYNTAX RowStatus
			MAX-ACCESS read-create
			STATUS current
			DESCRIPTION
				"Description."
			::= { ripGlobalRedistributeEntry 6 }

		
		-- 1.3.6.1.4.1.34592.1.3.100.7.2.9
		ripGlobalRouteTable OBJECT-TYPE
			SYNTAX SEQUENCE OF RipGlobalRouteEntry
			MAX-ACCESS not-accessible
			STATUS current
			DESCRIPTION
				"Description."
			::= { ripManagement 9 }

		
		-- 1.3.6.1.4.1.34592.1.3.100.7.2.9.1
		ripGlobalRouteEntry OBJECT-TYPE
			SYNTAX RipGlobalRouteEntry
			MAX-ACCESS not-accessible
			STATUS current
			DESCRIPTION
				"Description."
			INDEX { ripGlobalRouteIpAddrIndex, ripGlobalRouteMaskLenIndex }
			::= { ripGlobalRouteTable 1 }

		
		RipGlobalRouteEntry ::=
			SEQUENCE { 
				ripGlobalRouteIpAddrIndex
					IpAddress,
				ripGlobalRouteMaskLenIndex
					Unsigned32,
				ripGlobalRouteRowStatus
					RowStatus
			 }

		-- 1.3.6.1.4.1.34592.1.3.100.7.2.9.1.2
		ripGlobalRouteIpAddrIndex OBJECT-TYPE
			SYNTAX IpAddress
			MAX-ACCESS not-accessible
			STATUS current
			DESCRIPTION
				"Description."
			::= { ripGlobalRouteEntry 2 }

		
		-- 1.3.6.1.4.1.34592.1.3.100.7.2.9.1.3
		ripGlobalRouteMaskLenIndex OBJECT-TYPE
			SYNTAX Unsigned32 (0..32)
			MAX-ACCESS not-accessible
			STATUS current
			DESCRIPTION
				"Description."
			::= { ripGlobalRouteEntry 3 }

		
		-- 1.3.6.1.4.1.34592.1.3.100.7.2.9.1.4
		ripGlobalRouteRowStatus OBJECT-TYPE
			SYNTAX RowStatus
			MAX-ACCESS read-create
			STATUS current
			DESCRIPTION
				"Description."
			::= { ripGlobalRouteEntry 4 }

		
		-- 1.3.6.1.4.1.34592.1.3.100.7.2.10
		ripVlanifTable OBJECT-TYPE
			SYNTAX SEQUENCE OF RipVlanifEntry
			MAX-ACCESS not-accessible
			STATUS current
			DESCRIPTION
				"Description."
			::= { ripManagement 10 }

		
		-- 1.3.6.1.4.1.34592.1.3.100.7.2.10.1
		ripVlanifEntry OBJECT-TYPE
			SYNTAX RipVlanifEntry
			MAX-ACCESS not-accessible
			STATUS current
			DESCRIPTION
				"Description."
			INDEX { ripVlanifVlanIfIndex }
			::= { ripVlanifTable 1 }

		
		RipVlanifEntry ::=
			SEQUENCE { 
				ripVlanifVlanIfIndex
					Unsigned32,
				ripVlanifAuthMode
					INTEGER,
				ripVlanifNoStringOrKeychain
					INTEGER,
				ripVlanifAuthString
					OCTET STRING,
				ripVlanifAuthKeychain
					OCTET STRING,
				ripVlanifRcvVersion
					INTEGER,
				ripVlanifSndVersion
					INTEGER,
				ripVlanifSplit
					TruthValue,
				ripVlanifSplitPoison
					TruthValue,
				ripVlanifPassive
					TruthValue,
				ripVlanifNetwork
					TruthValue
			 }

		-- 1.3.6.1.4.1.34592.1.3.100.7.2.10.1.1
		ripVlanifVlanIfIndex OBJECT-TYPE
			SYNTAX Unsigned32 (1..4094)
			MAX-ACCESS not-accessible
			STATUS current
			DESCRIPTION
				"Description."
			::= { ripVlanifEntry 1 }

		
		-- 1.3.6.1.4.1.34592.1.3.100.7.2.10.1.2
		ripVlanifAuthMode OBJECT-TYPE
			SYNTAX INTEGER
				{
				reset(0),
				text(1),
				md5(2)
				}
			MAX-ACCESS read-write
			STATUS current
			DESCRIPTION
				"Description."
			::= { ripVlanifEntry 2 }

		
		-- 1.3.6.1.4.1.34592.1.3.100.7.2.10.1.3
		ripVlanifNoStringOrKeychain OBJECT-TYPE
			SYNTAX INTEGER
				{
				reset(0),
				string(1),
				keychain(2)
				}
			MAX-ACCESS read-write
			STATUS current
			DESCRIPTION
				"Description."
			::= { ripVlanifEntry 3 }

		
		-- 1.3.6.1.4.1.34592.1.3.100.7.2.10.1.4
		ripVlanifAuthString OBJECT-TYPE
			SYNTAX OCTET STRING (SIZE (1..16))
			MAX-ACCESS read-write
			STATUS current
			DESCRIPTION
				"Description."
			::= { ripVlanifEntry 4 }

		
		-- 1.3.6.1.4.1.34592.1.3.100.7.2.10.1.5
		ripVlanifAuthKeychain OBJECT-TYPE
			SYNTAX OCTET STRING
			MAX-ACCESS read-write
			STATUS current
			DESCRIPTION
				"Description."
			::= { ripVlanifEntry 5 }

		
		-- 1.3.6.1.4.1.34592.1.3.100.7.2.10.1.6
		ripVlanifRcvVersion OBJECT-TYPE
			SYNTAX INTEGER
				{
				reset(0),
				version1(1),
				version2(2),
				version1And2(3)
				}
			MAX-ACCESS read-write
			STATUS current
			DESCRIPTION
				"Description.
				"
			::= { ripVlanifEntry 6 }

		
		-- 1.3.6.1.4.1.34592.1.3.100.7.2.10.1.7
		ripVlanifSndVersion OBJECT-TYPE
			SYNTAX INTEGER
				{
				reset(0),
				version1(1),
				version2(2),
				version1And2(3)
				}
			MAX-ACCESS read-write
			STATUS current
			DESCRIPTION
				"Description."
			::= { ripVlanifEntry 7 }

		
		-- 1.3.6.1.4.1.34592.1.3.100.7.2.10.1.8
		ripVlanifSplit OBJECT-TYPE
			SYNTAX TruthValue
			MAX-ACCESS read-write
			STATUS current
			DESCRIPTION
				"Description."
			::= { ripVlanifEntry 8 }

		
		-- 1.3.6.1.4.1.34592.1.3.100.7.2.10.1.9
		ripVlanifSplitPoison OBJECT-TYPE
			SYNTAX TruthValue
			MAX-ACCESS read-write
			STATUS current
			DESCRIPTION
				"Description."
			::= { ripVlanifEntry 9 }

		
		-- 1.3.6.1.4.1.34592.1.3.100.7.2.10.1.10
		ripVlanifPassive OBJECT-TYPE
			SYNTAX TruthValue
			MAX-ACCESS read-write
			STATUS current
			DESCRIPTION
				"Description."
			::= { ripVlanifEntry 10 }

		
		-- 1.3.6.1.4.1.34592.1.3.100.7.2.10.1.11
		ripVlanifNetwork OBJECT-TYPE
			SYNTAX TruthValue
			MAX-ACCESS read-write
			STATUS current
			DESCRIPTION
				"Description."
			::= { ripVlanifEntry 11 }

		
		-- 1.3.6.1.4.1.34592.1.3.100.7.2.12
		ripKeychainTable OBJECT-TYPE
			SYNTAX SEQUENCE OF RipKeychainEntry
			MAX-ACCESS not-accessible
			STATUS current
			DESCRIPTION
				"Description."
			::= { ripManagement 12 }

		
		-- 1.3.6.1.4.1.34592.1.3.100.7.2.12.1
		ripKeychainEntry OBJECT-TYPE
			SYNTAX RipKeychainEntry
			MAX-ACCESS not-accessible
			STATUS current
			DESCRIPTION
				"Description."
			INDEX { ripKeychainNameIndex, ripKeychainKeyIdIndex }
			::= { ripKeychainTable 1 }

		
		RipKeychainEntry ::=
			SEQUENCE { 
				ripKeychainNameIndex
					OCTET STRING,
				ripKeychainKeyIdIndex
					Unsigned32,
				ripKeychainKeyString
					OCTET STRING,
				ripKeychainKeyNoAccOrSndLifeTime
					INTEGER,
				ripKeychainKeyAccLifeTimeStart
					DateAndTime,
				ripKeychainKeyAccLifeTimeEnd
					DateAndTime,
				ripKeychainKeyAccLifeTimeEndDuration
					Unsigned32,
				ripKeychainKeyAccLifeTimeEndInfinite
					TruthValue,
				ripKeychainKeySndLifeTimeStart
					DateAndTime,
				ripKeychainKeySndLifeTimeEnd
					DateAndTime,
				ripKeychainKeySndLifeTimeEndDuration
					Unsigned32,
				ripKeychainKeySndLifeTimeEndInfinite
					TruthValue,
				ripKeychainRowStatus
					RowStatus
			 }

		-- 1.3.6.1.4.1.34592.1.3.100.7.2.12.1.1
		ripKeychainNameIndex OBJECT-TYPE
			SYNTAX OCTET STRING
			MAX-ACCESS not-accessible
			STATUS current
			DESCRIPTION
				"Description."
			::= { ripKeychainEntry 1 }

		
		-- 1.3.6.1.4.1.34592.1.3.100.7.2.12.1.2
		ripKeychainKeyIdIndex OBJECT-TYPE
			SYNTAX Unsigned32 (0..2147483647)
			MAX-ACCESS not-accessible
			STATUS current
			DESCRIPTION
				"Description."
			::= { ripKeychainEntry 2 }

		
		-- 1.3.6.1.4.1.34592.1.3.100.7.2.12.1.3
		ripKeychainKeyString OBJECT-TYPE
			SYNTAX OCTET STRING
			MAX-ACCESS read-create
			STATUS current
			DESCRIPTION
				"Description."
			::= { ripKeychainEntry 3 }

		
		-- 1.3.6.1.4.1.34592.1.3.100.7.2.12.1.4
		ripKeychainKeyNoAccOrSndLifeTime OBJECT-TYPE
			SYNTAX INTEGER
				{
				reset(0),
				accept(1),
				send(2)
				}
			MAX-ACCESS read-create
			STATUS current
			DESCRIPTION
				"Description."
			::= { ripKeychainEntry 4 }

		
		-- 1.3.6.1.4.1.34592.1.3.100.7.2.12.1.5
		ripKeychainKeyAccLifeTimeStart OBJECT-TYPE
			SYNTAX DateAndTime
			MAX-ACCESS read-create
			STATUS current
			DESCRIPTION
				"Description."
			::= { ripKeychainEntry 5 }

		
		-- 1.3.6.1.4.1.34592.1.3.100.7.2.12.1.6
		ripKeychainKeyAccLifeTimeEnd OBJECT-TYPE
			SYNTAX DateAndTime
			MAX-ACCESS read-create
			STATUS current
			DESCRIPTION
				"Description."
			::= { ripKeychainEntry 6 }

		
		-- 1.3.6.1.4.1.34592.1.3.100.7.2.12.1.7
		ripKeychainKeyAccLifeTimeEndDuration OBJECT-TYPE
			SYNTAX Unsigned32 (1..2147483646)
			MAX-ACCESS read-create
			STATUS current
			DESCRIPTION
				"Description."
			::= { ripKeychainEntry 7 }

		
		-- 1.3.6.1.4.1.34592.1.3.100.7.2.12.1.8
		ripKeychainKeyAccLifeTimeEndInfinite OBJECT-TYPE
			SYNTAX TruthValue
			MAX-ACCESS read-create
			STATUS current
			DESCRIPTION
				"Description."
			::= { ripKeychainEntry 8 }

		
		-- 1.3.6.1.4.1.34592.1.3.100.7.2.12.1.9
		ripKeychainKeySndLifeTimeStart OBJECT-TYPE
			SYNTAX DateAndTime
			MAX-ACCESS read-create
			STATUS current
			DESCRIPTION
				"Description."
			::= { ripKeychainEntry 9 }

		
		-- 1.3.6.1.4.1.34592.1.3.100.7.2.12.1.10
		ripKeychainKeySndLifeTimeEnd OBJECT-TYPE
			SYNTAX DateAndTime
			MAX-ACCESS read-create
			STATUS current
			DESCRIPTION
				"Description."
			::= { ripKeychainEntry 10 }

		
		-- 1.3.6.1.4.1.34592.1.3.100.7.2.12.1.11
		ripKeychainKeySndLifeTimeEndDuration OBJECT-TYPE
			SYNTAX Unsigned32 (1..2147483646)
			MAX-ACCESS read-create
			STATUS current
			DESCRIPTION
				"Description."
			::= { ripKeychainEntry 11 }

		
		-- 1.3.6.1.4.1.34592.1.3.100.7.2.12.1.12
		ripKeychainKeySndLifeTimeEndInfinite OBJECT-TYPE
			SYNTAX TruthValue
			MAX-ACCESS read-create
			STATUS current
			DESCRIPTION
				"Description."
			::= { ripKeychainEntry 12 }

		
		-- 1.3.6.1.4.1.34592.1.3.100.7.2.12.1.13
		ripKeychainRowStatus OBJECT-TYPE
			SYNTAX RowStatus
			MAX-ACCESS read-create
			STATUS current
			DESCRIPTION
				"Description."
			::= { ripKeychainEntry 13 }

		
		-- 1.3.6.1.4.1.34592.1.3.100.7.2.13
		ripStatusRouteNumTable OBJECT-TYPE
			SYNTAX SEQUENCE OF RipStatusRouteNumEntry
			MAX-ACCESS not-accessible
			STATUS current
			DESCRIPTION
				"Description."
			::= { ripManagement 13 }

		
		-- 1.3.6.1.4.1.34592.1.3.100.7.2.13.1
		ripStatusRouteNumEntry OBJECT-TYPE
			SYNTAX RipStatusRouteNumEntry
			MAX-ACCESS not-accessible
			STATUS current
			DESCRIPTION
				"Description."
			INDEX { ripStatusRouteNumDeviceIndex }
			::= { ripStatusRouteNumTable 1 }

		
		RipStatusRouteNumEntry ::=
			SEQUENCE { 
				ripStatusRouteNumDeviceIndex
					NscrtvPonExtDeviceIndex,
				ripStatusRouteHostNumMax
					INTEGER,
				ripStatusRouteHostNumCurrent
					INTEGER,
				ripStatusRouteNetNumMax
					INTEGER,
				ripStatusRouteNetNumCurrent
					INTEGER
			 }

		-- 1.3.6.1.4.1.34592.1.3.100.7.2.13.1.1
		ripStatusRouteNumDeviceIndex OBJECT-TYPE
			SYNTAX NscrtvPonExtDeviceIndex
			MAX-ACCESS not-accessible
			STATUS current
			DESCRIPTION
				"Description."
			::= { ripStatusRouteNumEntry 1 }

		
		-- 1.3.6.1.4.1.34592.1.3.100.7.2.13.1.2
		ripStatusRouteHostNumMax OBJECT-TYPE
			SYNTAX INTEGER
			MAX-ACCESS read-only
			STATUS current
			DESCRIPTION
				"Description."
			::= { ripStatusRouteNumEntry 2 }

		
		-- 1.3.6.1.4.1.34592.1.3.100.7.2.13.1.3
		ripStatusRouteHostNumCurrent OBJECT-TYPE
			SYNTAX INTEGER
			MAX-ACCESS read-only
			STATUS current
			DESCRIPTION
				"Description."
			::= { ripStatusRouteNumEntry 3 }

		
		-- 1.3.6.1.4.1.34592.1.3.100.7.2.13.1.4
		ripStatusRouteNetNumMax OBJECT-TYPE
			SYNTAX INTEGER
			MAX-ACCESS read-only
			STATUS current
			DESCRIPTION
				"Description."
			::= { ripStatusRouteNumEntry 4 }

		
		-- 1.3.6.1.4.1.34592.1.3.100.7.2.13.1.5
		ripStatusRouteNetNumCurrent OBJECT-TYPE
			SYNTAX INTEGER
			MAX-ACCESS read-only
			STATUS current
			DESCRIPTION
				"Description."
			::= { ripStatusRouteNumEntry 5 }

		
		-- 1.3.6.1.4.1.34592.1.3.100.7.2.14
		ripStatusRouteEntryTable OBJECT-TYPE
			SYNTAX SEQUENCE OF RipStatusRouteEntryEntry
			MAX-ACCESS not-accessible
			STATUS current
			DESCRIPTION
				"Description."
			::= { ripManagement 14 }

		
		-- 1.3.6.1.4.1.34592.1.3.100.7.2.14.1
		ripStatusRouteEntryEntry OBJECT-TYPE
			SYNTAX RipStatusRouteEntryEntry
			MAX-ACCESS not-accessible
			STATUS current
			DESCRIPTION
				"Description."
			INDEX { ripStatusRouteEntryIpAddrIndex, ripStatusRouteEntryMaskLenIndex, ripStatusRouteEntryNextHopIndex }
			::= { ripStatusRouteEntryTable 1 }

		
		RipStatusRouteEntryEntry ::=
			SEQUENCE { 
				ripStatusRouteEntryIpAddrIndex
					IpAddress,
				ripStatusRouteEntryMaskLenIndex
					Unsigned32,
				ripStatusRouteEntryNextHopIndex
					IpAddress,
				ripStatusRouteEntryMetric
					Unsigned32,
				ripStatusRouteEntryFlag
					OCTET STRING,
				ripStatusRouteEntryFrom
					OCTET STRING,
				ripStatusRouteEntryTag
					INTEGER,
				ripStatusRouteEntryTime
					OCTET STRING
			 }

		-- 1.3.6.1.4.1.34592.1.3.100.7.2.14.1.4
		ripStatusRouteEntryIpAddrIndex OBJECT-TYPE
			SYNTAX IpAddress
			MAX-ACCESS not-accessible
			STATUS current
			DESCRIPTION
				"Description."
			::= { ripStatusRouteEntryEntry 4 }

		
		-- 1.3.6.1.4.1.34592.1.3.100.7.2.14.1.5
		ripStatusRouteEntryMaskLenIndex OBJECT-TYPE
			SYNTAX Unsigned32 (0..32)
			MAX-ACCESS not-accessible
			STATUS current
			DESCRIPTION
				"Description."
			::= { ripStatusRouteEntryEntry 5 }

		
		-- 1.3.6.1.4.1.34592.1.3.100.7.2.14.1.6
		ripStatusRouteEntryNextHopIndex OBJECT-TYPE
			SYNTAX IpAddress
			MAX-ACCESS not-accessible
			STATUS current
			DESCRIPTION
				"Description."
			::= { ripStatusRouteEntryEntry 6 }

		
		-- 1.3.6.1.4.1.34592.1.3.100.7.2.14.1.7
		ripStatusRouteEntryMetric OBJECT-TYPE
			SYNTAX Unsigned32 (0..16)
			MAX-ACCESS read-only
			STATUS current
			DESCRIPTION
				"Description."
			::= { ripStatusRouteEntryEntry 7 }

		
		-- 1.3.6.1.4.1.34592.1.3.100.7.2.14.1.8
		ripStatusRouteEntryFlag OBJECT-TYPE
			SYNTAX OCTET STRING
			MAX-ACCESS read-only
			STATUS current
			DESCRIPTION
				"Codes: R - RIP, C - connected, S - Static, O - OSPF, B - BGP
				Sub-codes:
				      (n) - normal, (s) - static, (d) - default, (r) - redistribute,
				      (i) - interface"
			::= { ripStatusRouteEntryEntry 8 }

		
		-- 1.3.6.1.4.1.34592.1.3.100.7.2.14.1.9
		ripStatusRouteEntryFrom OBJECT-TYPE
			SYNTAX OCTET STRING
			MAX-ACCESS read-only
			STATUS current
			DESCRIPTION
				"Description."
			::= { ripStatusRouteEntryEntry 9 }

		
		-- 1.3.6.1.4.1.34592.1.3.100.7.2.14.1.10
		ripStatusRouteEntryTag OBJECT-TYPE
			SYNTAX INTEGER
			MAX-ACCESS read-only
			STATUS current
			DESCRIPTION
				"Description."
			::= { ripStatusRouteEntryEntry 10 }

		
		-- 1.3.6.1.4.1.34592.1.3.100.7.2.14.1.11
		ripStatusRouteEntryTime OBJECT-TYPE
			SYNTAX OCTET STRING
			MAX-ACCESS read-only
			STATUS current
			DESCRIPTION
				"Description."
			::= { ripStatusRouteEntryEntry 11 }

		
	
	END

--
-- NSCRTV-PON-TREE-EXT-LAYER3-MIB.my
--
