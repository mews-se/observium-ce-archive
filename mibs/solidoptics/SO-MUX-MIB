SO-MUX-MIB DEFINITIONS ::= BEGIN

--
-- Solid Optics EDFAMUX MIB
--

IMPORTS
        MODULE-IDENTITY, enterprises, OBJECT-TYPE, Integer32 FROM SNMPv2-SMI
        MODULE-COMPLIANCE,OBJECT-GROUP FROM SNMPv2-CONF
;

solidOptics MODULE-IDENTITY
    LAST-UPDATED "202201251144Z"
    ORGANIZATION "Solid Optics"
    CONTACT-INFO
        "Solid Optics EU
        https://www.solid-optics.com/

        EMail: edfamux@solid-optics.eu"
    DESCRIPTION
        "This MIB contains definition of the SNMP objects
        and traps to interface with the EDFAMux."
::= { enterprises 51628 }

edfaMux OBJECT IDENTIFIER ::= { solidOptics 1 }

---
--- EdfaMux definitions
---

dcmDistance OBJECT-TYPE
        SYNTAX Integer32(1..999)
        ACCESS read-only
        STATUS mandatory
        DESCRIPTION
                "The current dispersion in kilometers."
::= {edfaMux 1}

preEdfaSeq OBJECT-TYPE
        SYNTAX PreEdfaSeq
        ACCESS not-accessible
        STATUS mandatory
        DESCRIPTION
                "Descriptive and Status Information for the pre EDFA."
        INDEX  { index }
::= {edfaMux 2}

postEdfaSeq OBJECT-TYPE
        SYNTAX PostEdfaSeq
        ACCESS not-accessible
        STATUS mandatory
        DESCRIPTION
                "Descriptive and Status Information for the post EDFA."
        INDEX  { index }
::= {edfaMux 3}

PreEdfaSeq      ::= SEQUENCE    {
        preIndex                        Integer32,
        prePowerGainValue       OCTET STRING,
        prePowerIn                      OCTET STRING,
        prePowerOut                     OCTET STRING,
        preTemperature          OCTET STRING
}

preIndex OBJECT-TYPE
        SYNTAX Integer32 (0..100)
        MAX-ACCESS not-accessible
        STATUS current
        DESCRIPTION "Column index."
::= { preEdfaSeq 1}

prePowerGainValue OBJECT-TYPE
        SYNTAX  OCTET STRING
        MAX-ACCESS read-only
        STATUS  current
        DESCRIPTION
          "Gain value in dBm."
::= { preEdfaSeq 2 }

prePowerIn OBJECT-TYPE
        SYNTAX  OCTET STRING
        MAX-ACCESS read-only
        STATUS  current
        DESCRIPTION
          "Power in in dBm"
::= { preEdfaSeq 3 }

prePowerOut OBJECT-TYPE
        SYNTAX  OCTET STRING
        MAX-ACCESS read-only
        STATUS  current
        DESCRIPTION
          "Power out in dBm."
::= { preEdfaSeq 4 }


preTemperature OBJECT-TYPE
        SYNTAX  OCTET STRING
        MAX-ACCESS read-only
        STATUS  current
        DESCRIPTION
          "Current temperature in degrees Celsius."
::= { preEdfaSeq 5 }

PostEdfaSeq     ::= SEQUENCE    {
        postIndex                       Integer32,
        postPowerGainValue      OCTET STRING,
        postPowerIn                     OCTET STRING,
        postPowerOut            OCTET STRING,
        postTemperature         OCTET STRING
}

postIndex OBJECT-TYPE
SYNTAX Integer32 (0..100)
MAX-ACCESS not-accessible
STATUS current
DESCRIPTION "Column index."
::= { postEdfaSeq 1}

postPowerGainValue OBJECT-TYPE
        SYNTAX  OCTET STRING
        MAX-ACCESS read-only
        STATUS  current
        DESCRIPTION
          "Gain value in dBm."
::= { postEdfaSeq 2 }

postPowerIn OBJECT-TYPE
        SYNTAX  OCTET STRING
        MAX-ACCESS read-only
        STATUS  current
        DESCRIPTION
          "Power in in dBm"
::= { postEdfaSeq 3 }

postPowerOut OBJECT-TYPE
        SYNTAX  OCTET STRING
        MAX-ACCESS read-only
        STATUS  current
        DESCRIPTION
          "Power out in dBm."
::= { postEdfaSeq 4 }


postTemperature OBJECT-TYPE
        SYNTAX  OCTET STRING
        MAX-ACCESS read-only
        STATUS  current
        DESCRIPTION
          "Current temperature in degrees Celsius."
::= { postEdfaSeq 5 }

END
