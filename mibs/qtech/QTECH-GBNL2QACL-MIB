QTECH-GBNL2QACL-MIB DEFINITIONS ::= BEGIN

    IMPORTS
        MODULE-IDENTITY, OBJECT-TYPE,
        Integer32, Counter64,IpAddress                    FROM SNMPv2-SMI
        
        DisplayString, TruthValue,MacAddress,RowStatus    FROM SNMPv2-TC  
              
        MODULE-COMPLIANCE, OBJECT-GROUP         FROM SNMPv2-CONF
        
        gbnL2                              FROM QTECH-MASTER-MIB
        
        PortList                                FROM Q-BRIDGE-MIB  
        
        mib-2                                   FROM RFC1213-MIB   
        
        VlanId                                  FROM  Q-BRIDGE-MIB
        
        TOSType                                 FROM  OSPF-MIB;
        
        
    gbnL2QACL MODULE-IDENTITY
        LAST-UPDATED    "0309260001Z"  -- sep 26,2003  
        ORGANIZATION    "QTECH LLC"
        CONTACT-INFO    "Basil Budko
                         E-mail: budko@qtech.ru"

        DESCRIPTION     "GBN Enterprise MIB definition."

        REVISION        "0309260001Z"  -- sep 26,2003
        DESCRIPTION     "Initial MIB creation."

        ::= { gbnL2 4 }  
        
AdminStatus ::= TEXTUAL-CONVENTION
    STATUS      current
    DESCRIPTION
       "The AdminStatus of an item: 'valid' indicates that
       it is running,while 'invalid' indicates that it is not."
    SYNTAX      INTEGER { active (1), inactive (2) }   
    
Action ::= TEXTUAL-CONVENTION
    STATUS      current
    DESCRIPTION
       "permit or deny"
    SYNTAX      INTEGER { permit (101), deny (100) }     
    
Dscp ::= TEXTUAL-CONVENTION
    STATUS      current
    DESCRIPTION
       "dscp priority"
    SYNTAX      Integer32 (0..63)   
    
AclType ::= TEXTUAL-CONVENTION
    STATUS      current
    DESCRIPTION
       "standard、extend、link、user"
    SYNTAX      INTEGER { standard(1), extend (2),link(3), user (4) }        
     
PacketFlowType ::= TEXTUAL-CONVENTION
    STATUS      current
    DESCRIPTION
       "broadcast、multicast、unicast"
    SYNTAX      INTEGER { broadcast(1), multicast(2), unicast(3) }  
       
   --
   -- the quene-scheduer QOS 
   --
 
   qosQueueSchedulerGroup  OBJECT IDENTIFIER ::= { gbnL2QACL 1 }
 
   qosWrrQueue1Weight OBJECT-TYPE
       SYNTAX  INTEGER (1..97)   
       ACCESS  read-write
       STATUS  current
       DESCRIPTION
               "Weight of 1th queue(%)."
               --队列1的权重
       ::= { qosQueueSchedulerGroup 1 }   
       
   qosWrrQueue2Weight OBJECT-TYPE
       SYNTAX  INTEGER (1..97)   
       ACCESS  read-write
       STATUS  current
       DESCRIPTION
               "Weight of 2th queue(%)."
               --队列2的权重
       ::= { qosQueueSchedulerGroup 2 }   
       
       
   qosWrrQueue3Weight OBJECT-TYPE
       SYNTAX  INTEGER (1..97)   
       ACCESS  read-write
       STATUS  current
       DESCRIPTION
               "Weight of 3th queue(%)."
               --队列3的权重
       ::= { qosQueueSchedulerGroup 3 }          
       
       
   qosWrrQueue4Weight OBJECT-TYPE
       SYNTAX  INTEGER (1..97)   
       ACCESS  read-write
       STATUS  current
       DESCRIPTION
               "Weight of 4th queue(%)."
               --队列4的权重
       ::= { qosQueueSchedulerGroup 4 }    
          
   qosWrrMaxDelayValue OBJECT-TYPE
       SYNTAX  INTEGER (1..255)   
       ACCESS  read-write
       STATUS  current
       DESCRIPTION
               "队列调度时最高优先级的队列最长等待时间 "
       ::= { qosQueueSchedulerGroup 5 }   
       
   qosQueueSchedulerMode OBJECT-TYPE
       SYNTAX  INTEGER  {
                        strictPriority (1),
                        wrr(2),
                        wrrMaxDelay(3) }
       ACCESS  read-write
       STATUS  current
       DESCRIPTION
               "队列调度模式:绝对优先级、加权轮循调度、最大延时的加权轮循调度  "   
       DEFVAL  { strictPriority }
       ::= { qosQueueSchedulerGroup 6 }

   qosWrrQueue5Weight OBJECT-TYPE
       SYNTAX  INTEGER (1..97)   
       ACCESS  read-write
       STATUS  current
       DESCRIPTION
               "Weight of 5th queue(%)."
               --队列5的权重
       ::= { qosQueueSchedulerGroup 7 }     

   qosWrrQueue6Weight OBJECT-TYPE
       SYNTAX  INTEGER (1..97)   
       ACCESS  read-write
       STATUS  current
       DESCRIPTION
               "Weight of 6th queue(%)."
               --队列6的权重
       ::= { qosQueueSchedulerGroup 8 }  

   qosWrrQueue7Weight OBJECT-TYPE
       SYNTAX  INTEGER (1..97)   
       ACCESS  read-write
       STATUS  current
       DESCRIPTION
               "Weight of 7th queue(%)."
               --队列7的权重
       ::= { qosQueueSchedulerGroup 9 }  

   qosWrrQueue8Weight OBJECT-TYPE
       SYNTAX  INTEGER (1..97)   
       ACCESS  read-write
       STATUS  current
       DESCRIPTION
               "Weight of 8th queue(%)."
               --队列8的权重
       ::= { qosQueueSchedulerGroup 10 }         
              
--  ACL table Variables

--      These parameters apply globally to the swicth's  

 aclNumTable OBJECT-TYPE
        SYNTAX   SEQUENCE OF AclNumEntry
        MAX-ACCESS   not-accessible
        STATUS   current
        DESCRIPTION
           "基于数字的访问控制列表，它一共由五种类型：基于数字的标准访问控制列表、
           基于数字的扩展访问列表、基于数字的二层访问控制列表、基于数字的自定义访
           问控制列表和基于数字的接口访问控制列表。其中标准访问控制列表的取值为1-99，
           扩展访问控制列表的取值为100-199，二层访问控制列表的取值为200-299，自定义
           访问控制列表的取值为300-399."
       ::= { gbnL2QACL 2 }

    aclNumEntry OBJECT-TYPE
        SYNTAX   AclNumEntry
        MAX-ACCESS   not-accessible
        STATUS   current
        DESCRIPTION
           "定义一条基于数字的访问控制列表."
       INDEX { aclNumNumber }
       ::= { aclNumTable 1 }

    AclNumEntry ::=
	    SEQUENCE {
	        aclNumNumber
	            Integer32, 
	        aclNumType
	            AclType, 	            
	        aclNumMatchOrder
	            INTEGER,
	        aclNumTotleSubitems
	            Integer32,
	        aclNumRowStatus
	            RowStatus 
	              }

    aclNumNumber OBJECT-TYPE
        SYNTAX   Integer32
        MAX-ACCESS   read-only
        STATUS   current
        DESCRIPTION
           "基于数字的访问控制列表的标号，它的取值范围为1－399.
           它的取值可以代表此条访问控制列表是属于何种类型。"
        ::= { aclNumEntry 1 }
        
    aclNumType OBJECT-TYPE
        SYNTAX   AclType
        MAX-ACCESS   read-only
        STATUS   current
        DESCRIPTION
           "基于数字的访问控制列表的类型，其中number为1-99为标准ACL，
           100-199为扩展ACL，200-299为二层ACL，300-399为用户自定义ACL."
        ::= { aclNumEntry 2 }        

    aclNumMatchOrder OBJECT-TYPE
        SYNTAX   INTEGER    {
                    config (0),
                    auto (1)
                    }
        MAX-ACCESS   read-write
        STATUS   current
        DESCRIPTION
           "定义一条访问控制列表的配置顺序，auto 所用的“深度优先“  
           原则是指：把指定数据包范围最小的语句排在最前面。这一点可以
           通过比较地址的通配符来实现，通配符越小，则指定的主机的范围
           就越小。比如129.102.1.1 0.0.0.0 指定了一台主机：129.102.1.1
           而129.102.1.1 0.0.255.255 则指定了一个网段： 129.102.1.1 ～
           129.102.255.255，显然前者在访问控制规则中排在前面。具体标准
           为：对于标准访问控制规则的语句，直接比较源地址通配符，通配符
           相同的则按配置顺序；对于基于接口过滤的访问控制规则，配置了'any'
           的规则排在后面，其它按配置顺序；对于扩展访问控制规则，首先比
           较源地址通配符，相同的再比较目的地址通配符，仍相同的则比较端
           口号的范围，范围小的排在前面，如果端口号范围也相同则按配置顺序，
           默认按照用户的配置顺序即config。"  
        DEFVAL { config }        -- config
      ::= { aclNumEntry 3 }

    aclNumTotleSubitems OBJECT-TYPE
        SYNTAX   Integer32
        MAX-ACCESS   read-only
        STATUS   current 
        DESCRIPTION
        "一条访问控制列表可以定义多条子规则，这些子规则按照一定的顺序排列
        成一条访问控制列表，每条ACL最多可以定义128项子规则。"
        ::= { aclNumEntry 4 }
        
    aclNumRowStatus OBJECT-TYPE
        SYNTAX   RowStatus
        MAX-ACCESS   read-write
        STATUS   current 
        DESCRIPTION
        "表示当前ACL的状态，添加或删除。"
        ::= { aclNumEntry 5 }   
        
        
 --ACL子项定义，基于数字的标准访问控制列表子项。
       
  aclNumStdSubitemTable OBJECT-TYPE
        SYNTAX   SEQUENCE OF AclNumStdSubitemEntry
        MAX-ACCESS   not-accessible
        STATUS   current
        DESCRIPTION
           "定义一条标准访问控制列表子项。它是通过目的地址进行过滤的。"
       ::= { gbnL2QACL 3 }

    aclNumStdSubitemEntry OBJECT-TYPE
        SYNTAX   AclNumStdSubitemEntry
        MAX-ACCESS   not-accessible
        STATUS   current
        DESCRIPTION
           "定义一条标准访问控制列表子项."
       INDEX { aclNumStdNum, aclNumStdSubNum }
       ::= { aclNumStdSubitemTable 1 } 
         
    AclNumStdSubitemEntry ::=
	    SEQUENCE {
	        aclNumStdNum
	            Integer32,
	        aclNumStdSubNum
	            Integer32,
	        aclNumStdSubitemAdminStatus
	            AdminStatus,
	        aclNumStdSubitemAction
	            Action,
	        aclNumStdSubitemSrcAddr
	            IpAddress,   
	        aclNumStdSubitemSrcAddrWldmsk
	            IpAddress,
	        aclNumStdFragments
	            TruthValue,
	        aclNumStdTimeRange
	            OCTET STRING,
	        aclNumStdSubitemRowStatus
	            RowStatus        	            
	        }   
	        
    aclNumStdNum OBJECT-TYPE
        SYNTAX   Integer32  (1..99)
        MAX-ACCESS   read-only
        STATUS   current
        DESCRIPTION
           "基于数字的访问控制列表的标号，它的取值范围为1－399，1000-1999.
           它的取值可以代表此条访问控制列表是属于何种类型。"
        ::= { aclNumStdSubitemEntry 1 } 
        
    aclNumStdSubNum OBJECT-TYPE
        SYNTAX   Integer32 (0..127)
        MAX-ACCESS   read-only
        STATUS   current
        DESCRIPTION
           "访问控制列表的子项号，0－127。"
        ::= { aclNumStdSubitemEntry 2 }         

    aclNumStdSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNumStdSubitemEntry 3 } 
       
    aclNumStdSubitemAction OBJECT-TYPE
        SYNTAX   Action
        MAX-ACCESS   read-write
        STATUS   current
        DESCRIPTION
           "定义一条访问列表子项的动作，允许或拒绝。"         
       ::= { aclNumStdSubitemEntry 4 }      
       
    aclNumStdSubitemSrcAddr OBJECT-TYPE
        SYNTAX   IpAddress
        MAX-ACCESS   read-write
        STATUS   current
        DESCRIPTION
           "标准访问控制列表子项的原地址"         
       ::= { aclNumStdSubitemEntry 5 }
       
    aclNumStdSubitemSrcAddrWldmsk OBJECT-TYPE
        SYNTAX   IpAddress
        MAX-ACCESS   read-write
        STATUS   current
        DESCRIPTION
           "标准访问控制列表子项的原地址通配符"         
       ::= { aclNumStdSubitemEntry 6 } 
                  
    aclNumStdFragments OBJECT-TYPE
        SYNTAX   TruthValue
        MAX-ACCESS   read-write
        STATUS   current
        DESCRIPTION
           "标准访问控制列表子项的原地址通配符" 
        DEFVAL { false }        -- invalid                 
       ::= { aclNumStdSubitemEntry 7 }  
  
  
    aclNumStdTimeRange OBJECT-TYPE
        SYNTAX   OCTET STRING (SIZE (0..32))
        MAX-ACCESS   read-write
        STATUS   current 
        DESCRIPTION
        "访问列表子项起作用的时间段"
        ::= { aclNumStdSubitemEntry 8 }
        
    aclNumStdSubitemRowStatus OBJECT-TYPE
        SYNTAX   RowStatus
        MAX-ACCESS   read-write
        STATUS   current 
        DESCRIPTION
        "表示当前ACL子项的状态，添加或删除。"
        ::= { aclNumStdSubitemEntry 9 }  


--ACL子项定义，基于数字的扩展访问控制列表子项。
       
  aclNumExdSubitemTable OBJECT-TYPE
        SYNTAX   SEQUENCE OF AclNumExdSubitemEntry
        MAX-ACCESS   not-accessible
        STATUS   current
        DESCRIPTION
           "定义一条扩展访问控制列表子项。它是通过对标准访问控制列表的补充。"
       ::= { gbnL2QACL 4 }

    aclNumExdSubitemEntry OBJECT-TYPE
        SYNTAX   AclNumExdSubitemEntry
        MAX-ACCESS   not-accessible
        STATUS   current
        DESCRIPTION
           "定义一条标准访问控制列表子项."
       INDEX { aclNumExdNum, aclNumExdSubNum}
       ::= { aclNumExdSubitemTable 1 }

    AclNumExdSubitemEntry ::=
	    SEQUENCE {
	        aclNumExdNum
	            Integer32,
	        aclNumExdSubNum
	            Integer32,
	        aclNumExdSubitemAdminStatus
	            AdminStatus,
	        aclNumExdSubitemAction
	            Action, 
	        aclNumExdSubitemProtocal
	            Integer32, 	            
	        aclNumExdSubitemSrcAddr
	            IpAddress,   
	        aclNumExdSubitemSrcAddrWldmsk
	            IpAddress,               
	        aclNumExdSubitemDstAddr
	            IpAddress,   
	        aclNumExdSubitemDstAddrWldmsk
	            IpAddress,
	        aclNumExdSubitemSrcPort
	            Integer32,   
	        aclNumExdSubitemSrcPortWldmsk
	            Integer32,
	        aclNumExdSubitemDstPort
	            Integer32,
	        aclNumExdSubitemDstPortWldmsk
	            Integer32, 
	        aclNumExdSubitemIcmpType
	            Integer32,
	        aclNumExdSubitemIcmpCode
	            Integer32, 
	        aclNumExdSubitemTcpEstablished
	            TruthValue,
	        aclNumExdSubitemPrecedence
	            Integer32,
	        aclNumExdSubitemTos
	            TOSType,
	        aclNumExdSubitemDscp
	            Dscp,   
	        aclNumExdSubitemFragments
	            TruthValue,
	        aclNumExdSubitemTimeRange
	            OCTET STRING,
	        aclNumExdSubitemRowStatus
	            RowStatus        	            
	        }   
	        
    aclNumExdNum OBJECT-TYPE
        SYNTAX   Integer32  (100..199)
        MAX-ACCESS   read-only
        STATUS   current
        DESCRIPTION
           "基于数字的访问控制列表的标号，它的取值范围为1－399，1000-1999.
           它的取值可以代表此条访问控制列表是属于何种类型。"
        ::= { aclNumExdSubitemEntry 1 } 
        
    aclNumExdSubNum OBJECT-TYPE
        SYNTAX   Integer32 (0..127)
        MAX-ACCESS   read-only
        STATUS   current
        DESCRIPTION
           "访问控制列表的子项号，0－127。"
        ::= { aclNumExdSubitemEntry 2 }         

    aclNumExdSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNumExdSubitemEntry 3 } 
       
    aclNumExdSubitemAction OBJECT-TYPE
        SYNTAX   Action
        MAX-ACCESS   read-write
        STATUS   current
        DESCRIPTION
           "定义一条访问列表子项的动作，允许或拒绝。"         
       ::= { aclNumExdSubitemEntry 4 }
       
    aclNumExdSubitemProtocal OBJECT-TYPE
        SYNTAX   Integer32 (1..255)
        MAX-ACCESS   read-write
        STATUS   current
        DESCRIPTION
           "过滤某种协议类型的报文"
        ::= { aclNumExdSubitemEntry 5 }       
             
       
    aclNumExdSubitemSrcAddr OBJECT-TYPE
        SYNTAX   IpAddress
        MAX-ACCESS   read-write
        STATUS   current
        DESCRIPTION
           "扩展访问控制列表子项的原地址"         
       ::= { aclNumExdSubitemEntry 6 }
       
    aclNumExdSubitemSrcAddrWldmsk OBJECT-TYPE
        SYNTAX   IpAddress
        MAX-ACCESS   read-write
        STATUS   current
        DESCRIPTION
           "扩展访问控制列表子项的原地址通配符"         
       ::= { aclNumExdSubitemEntry 7 } 
       
    aclNumExdSubitemDstAddr OBJECT-TYPE
        SYNTAX   IpAddress
        MAX-ACCESS   read-write
        STATUS   current
        DESCRIPTION
           "扩展访问控制列表子项的目的地址"         
       ::= { aclNumExdSubitemEntry 8 }
       
    aclNumExdSubitemDstAddrWldmsk OBJECT-TYPE
        SYNTAX   IpAddress
        MAX-ACCESS   read-write
        STATUS   current
        DESCRIPTION
           "扩展访问控制列表子项的目的地址通配符"         
       ::= { aclNumExdSubitemEntry 9 }
       
    aclNumExdSubitemSrcPort OBJECT-TYPE
        SYNTAX   Integer32  (0..65535)
        MAX-ACCESS   read-write
        STATUS   current
        DESCRIPTION
           "filter the special TCP/UDP ports"
           --对UDP或TCP报文特定端口号的包进行过滤          
       ::= { aclNumExdSubitemEntry 10 }
       
    aclNumExdSubitemSrcPortWldmsk OBJECT-TYPE
        SYNTAX   Integer32  (0..65535)
        MAX-ACCESS   read-write
        STATUS   current
        DESCRIPTION
           "source ports wildcard"
           --扩展访问控制列表子项的源端口号通配符          
       ::= { aclNumExdSubitemEntry 11 } 
       
    aclNumExdSubitemDstPort OBJECT-TYPE
        SYNTAX   Integer32  (0..65535)
        MAX-ACCESS   read-write
        STATUS   current
        DESCRIPTION
           "filter the special TCP/UDP ports"
           --对UDP或TCP报文特定端口号的包进行过滤         
       ::= { aclNumExdSubitemEntry 12 }
       
    aclNumExdSubitemDstPortWldmsk OBJECT-TYPE
        SYNTAX   Integer32  (0..65535)
        MAX-ACCESS   read-write
        STATUS   current
        DESCRIPTION
           "destination ports wildcard" 
           --扩展访问控制列表子项的源端口号通配符         
       ::= { aclNumExdSubitemEntry 13 }       
       
    aclNumExdSubitemIcmpType OBJECT-TYPE
        SYNTAX   Integer32 (0..255)
        MAX-ACCESS   read-write
        STATUS   current
        DESCRIPTION
           "对ICMP的特定类型的包进行过滤"         
       ::= { aclNumExdSubitemEntry 14 }
       
    aclNumExdSubitemIcmpCode OBJECT-TYPE
        SYNTAX   Integer32 (0..255)
        MAX-ACCESS   read-write
        STATUS   current
        DESCRIPTION
           "对ICMP的特定类型，特定代码的包进行过滤"           
       ::= { aclNumExdSubitemEntry 15 }        

    aclNumExdSubitemTcpEstablished OBJECT-TYPE
        SYNTAX   TruthValue
        MAX-ACCESS   read-write
        STATUS   current
        DESCRIPTION
           "对TCP第一个建链的包进行过滤"  
        DEFVAL { false }        -- invalid           
       ::= { aclNumExdSubitemEntry 16 }
           
    aclNumExdSubitemPrecedence OBJECT-TYPE
        SYNTAX   Integer32 (0..7)
        MAX-ACCESS   read-write
        STATUS   current
        DESCRIPTION
           "对特定IP优先级的包进行过滤"           
       ::= { aclNumExdSubitemEntry 17 }       
       
    aclNumExdSubitemTos OBJECT-TYPE
        SYNTAX   TOSType
        MAX-ACCESS   read-write
        STATUS   current
        DESCRIPTION
           "对数据包中TOS字段等于特定值的包进行过滤"           
       ::= { aclNumExdSubitemEntry 18 }
       
    aclNumExdSubitemDscp OBJECT-TYPE
        SYNTAX   Dscp
        MAX-ACCESS   read-write
        STATUS   current
        DESCRIPTION
           "对数据包中DSCP字段等于特定值的包进行过滤"           
       ::= { aclNumExdSubitemEntry 19 }              
                  
    aclNumExdSubitemFragments OBJECT-TYPE
        SYNTAX   TruthValue
        MAX-ACCESS   read-write
        STATUS   current
        DESCRIPTION
           "扩展访问控制列表子项的目的地址通配符" 
        DEFVAL { false }        -- invalid                 
       ::= { aclNumExdSubitemEntry 20 }  
  
  
    aclNumExdSubitemTimeRange OBJECT-TYPE
        SYNTAX   OCTET STRING (SIZE (0..32))
        MAX-ACCESS   read-write
        STATUS   current 
        DESCRIPTION
        "访问列表子项起作用的时间段"
        ::= { aclNumExdSubitemEntry 21 }
        
    aclNumExdSubitemRowStatus OBJECT-TYPE
        SYNTAX   RowStatus
        MAX-ACCESS   read-write
        STATUS   current 
        DESCRIPTION
        "表示当前ACL子项的状态，添加或删除。"
        ::= { aclNumExdSubitemEntry 22 }
        
        
--ACL子项定义，基于数字的二层访问控制列表子项。
       
  aclNumLnkSubitemTable OBJECT-TYPE
        SYNTAX   SEQUENCE OF AclNumLnkSubitemEntry
        MAX-ACCESS   not-accessible
        STATUS   current
        DESCRIPTION
           "定义一条二层访问控制列表子项。"
       ::= { gbnL2QACL 5 }

    aclNumLnkSubitemEntry OBJECT-TYPE
        SYNTAX   AclNumLnkSubitemEntry
        MAX-ACCESS   not-accessible
        STATUS   current
        DESCRIPTION
           "定义一条二层访问控制列表子项."
       INDEX { aclNumLnkNum, aclNumLnkSubNum}
       ::= { aclNumLnkSubitemTable 1 }

    AclNumLnkSubitemEntry ::=
	    SEQUENCE {
	        aclNumLnkNum
	            Integer32,
	        aclNumLnkSubNum
	            Integer32,
	        aclNumLnkSubitemAdminStatus
	            AdminStatus,
	        aclNumLnkSubitemAction
	            Action,
	        aclNumLnkSubitemProtocal
	            Integer32,
	        aclNumLnkSubitemCos
	            Integer32, 
	        aclNumLnkSubitemSrcVlanID
	            VlanId, 
	        aclNumLnkSubitemSrcMacAddr
	            MacAddress,
	        aclNumLnkSubitemSrcMacWldmsk
	            MacAddress,
	        aclNumLnkSubitemDstMacAddr
	            MacAddress,
	        aclNumLnkSubitemDstMacWldmsk
	            MacAddress,                 	              
	        aclNumLnkSubitemSrcPortNum
	            Integer32,
	        aclNumLnkSubitemDstPortNum
	            Integer32,            
	        aclNumLnkSubitemTimeRange
	            OCTET STRING,
	        aclNumLnkSubitemRowStatus
	            RowStatus        	            
	        }   
	        
    aclNumLnkNum OBJECT-TYPE
        SYNTAX   Integer32 (200..299)
        MAX-ACCESS   read-only
        STATUS   current
        DESCRIPTION
           "基于数字的访问控制列表的标号，它的取值范围为1－399，1000-1999.
           它的取值可以代表此条访问控制列表是属于何种类型。"
        ::= { aclNumLnkSubitemEntry 1 } 
        
    aclNumLnkSubNum OBJECT-TYPE
        SYNTAX   Integer32 (0..127)
        MAX-ACCESS   read-only
        STATUS   current
        DESCRIPTION
           "访问控制列表的子项号，0－127。"
        ::= { aclNumLnkSubitemEntry 2 }         

    aclNumLnkSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNumLnkSubitemEntry 3 } 
       
    aclNumLnkSubitemAction OBJECT-TYPE
        SYNTAX   Action
        MAX-ACCESS   read-write
        STATUS   current
        DESCRIPTION
           "定义一条访问列表子项的动作，允许或拒绝。"         
       ::= { aclNumLnkSubitemEntry 4 }
       
    aclNumLnkSubitemProtocal OBJECT-TYPE
        SYNTAX   Integer32 (1..255)
        MAX-ACCESS   read-write
        STATUS   current
        DESCRIPTION
           "过滤某种协议类型的报文"
        ::= { aclNumLnkSubitemEntry 5 } 
        
    aclNumLnkSubitemCos OBJECT-TYPE
        SYNTAX   Integer32 (0..7)
        MAX-ACCESS   read-write
        STATUS   current
        DESCRIPTION
           "802.1x优先级"
        ::= { aclNumLnkSubitemEntry 6 }            

    aclNumLnkSubitemSrcVlanID OBJECT-TYPE
        SYNTAX   VlanId
        MAX-ACCESS   read-write
        STATUS   current
        DESCRIPTION
           "对VLAN ID为特定值的数据包进行过滤"         
       ::= { aclNumLnkSubitemEntry 7 }	            
	                   
    aclNumLnkSubitemSrcMacAddr OBJECT-TYPE
        SYNTAX   MacAddress
        MAX-ACCESS   read-write
        STATUS   current
        DESCRIPTION
           "它于MAC通配符共同作用得到感兴趣的源MAC地址，并对这些
           MAC地址作处理。"         
       ::= { aclNumLnkSubitemEntry 8 }
       
    aclNumLnkSubitemSrcMacWldmsk OBJECT-TYPE
        SYNTAX   MacAddress
        MAX-ACCESS   read-write
        STATUS   current
        DESCRIPTION
           "它于MAC地址共同作用得到感兴趣的源MAC地址，并对这些
           MAC地址作处理。"        
       ::= { aclNumLnkSubitemEntry 9 }  
       
    aclNumLnkSubitemDstMacAddr OBJECT-TYPE
        SYNTAX   MacAddress
        MAX-ACCESS   read-write
        STATUS   current
        DESCRIPTION
           "它于MAC通配符共同作用得到感兴趣的目的MAC地址，并对这些
           MAC地址作处理。"         
       ::= { aclNumLnkSubitemEntry 10 } 
       
    aclNumLnkSubitemDstMacWldmsk OBJECT-TYPE
        SYNTAX   MacAddress
        MAX-ACCESS   read-write
        STATUS   current
        DESCRIPTION
           "它于MAC地址共同作用得到感兴趣的目的MAC地址，并对这些
           MAC地址作处理。"        
       ::= { aclNumLnkSubitemEntry 11 } 
       
    aclNumLnkSubitemSrcPortNum OBJECT-TYPE
        SYNTAX   Integer32   (1..26)
        MAX-ACCESS   read-write
        STATUS   current
        DESCRIPTION
           "百兆以太网端口号1－24，千兆以太网端口号1－2"                  
       ::= { aclNumLnkSubitemEntry 12 }    
       
    aclNumLnkSubitemDstPortNum OBJECT-TYPE
        SYNTAX   Integer32   (1..29)
        MAX-ACCESS   read-write
        STATUS   current
        DESCRIPTION
           "1－24为百兆以太网端口号1－24，25－26为千兆以太网端口号1－2，27为已知组播，28为CPU端口号，29为DLF"                  
       ::= { aclNumLnkSubitemEntry 13 }    
  
    aclNumLnkSubitemTimeRange OBJECT-TYPE
        SYNTAX   OCTET STRING (SIZE (0..32))
        MAX-ACCESS   read-write
        STATUS   current 
        DESCRIPTION
        "访问列表子项起作用的时间段"
        ::= { aclNumLnkSubitemEntry 14 }
        
    aclNumLnkSubitemRowStatus OBJECT-TYPE
        SYNTAX   RowStatus
        MAX-ACCESS   read-write
        STATUS   current 
        DESCRIPTION
        "表示当前ACL子项的状态，添加或删除。"
        ::= { aclNumLnkSubitemEntry 15 }  

 --ACL子项定义，基于数字的自定义访问控制列表子项。
       
  aclNumUserSubitemTable OBJECT-TYPE
        SYNTAX   SEQUENCE OF AclNumUserSubitemEntry
        MAX-ACCESS   not-accessible
        STATUS   current
        DESCRIPTION
           "定义一条自定义访问控制列表子项。它是通过目的地址进行过滤的。"
       ::= { gbnL2QACL 6 }

    aclNumUserSubitemEntry OBJECT-TYPE
        SYNTAX   AclNumUserSubitemEntry
        MAX-ACCESS   not-accessible
        STATUS   current
        DESCRIPTION
           "定义一条标准访问控制列表子项."
       INDEX { aclNumUserNum, aclNumUserSubNum }
       ::= { aclNumUserSubitemTable 1 } 
         
    AclNumUserSubitemEntry ::=
	    SEQUENCE {
	        aclNumUserNum
	            Integer32,
	        aclNumUserSubNum
	            Integer32,
	        aclNumUserSubitemAdminStatus
	            AdminStatus,
	        aclNumUserSubitemAction
	            Action,    
	        aclNumUserSubitemSrcPortNum
	            Integer32,
	        aclNumUserSubitemDstPortNum
	            Integer32,           	            
	        aclNumUserSubitemRule
	            OCTET STRING,                    
	        aclNumUserSubitemMask
	            OCTET STRING,
	        aclNumUserTimeRange
	            OCTET STRING,
	        aclNumUserSubitemRowStatus
	            RowStatus        	            
	        }   
	        
    aclNumUserNum OBJECT-TYPE
        SYNTAX   Integer32  (300..399)
        MAX-ACCESS   read-only
        STATUS   current
        DESCRIPTION
           "基于数字的访问控制列表的标号，它的取值范围为1－399，1000-1999.
           它的取值可以代表此条访问控制列表是属于何种类型。"
        ::= { aclNumUserSubitemEntry 1 } 
        
    aclNumUserSubNum OBJECT-TYPE
        SYNTAX   Integer32 (0..127)
        MAX-ACCESS   read-only
        STATUS   current
        DESCRIPTION
           "访问控制列表的子项号，0－127。"
        ::= { aclNumUserSubitemEntry 2 }         

    aclNumUserSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNumUserSubitemEntry 3 } 
       
    aclNumUserSubitemAction OBJECT-TYPE
        SYNTAX   Action
        MAX-ACCESS   read-write
        STATUS   current
        DESCRIPTION
           "定义一条访问列表子项的动作，允许或拒绝。"         
       ::= { aclNumUserSubitemEntry 4 }  
       
    aclNumUserSubitemSrcPortNum OBJECT-TYPE
        SYNTAX   Integer32
        MAX-ACCESS   read-write
        STATUS   current
        DESCRIPTION
           "百兆以太网端口号1－24，千兆以太网端口号1－2"                  
       ::= { aclNumUserSubitemEntry 5 }    
       
    aclNumUserSubitemDstPortNum OBJECT-TYPE
        SYNTAX   Integer32   (1..29)
        MAX-ACCESS   read-write
        STATUS   current
        DESCRIPTION
           "1－24为百兆以太网端口号1－24，25－26为千兆以太网端口号1－2，27为已知组播，28为CPU端口号，29为DLF"
       ::= { aclNumUserSubitemEntry 6 }    
                 
    aclNumUserSubitemRule OBJECT-TYPE
        SYNTAX   OCTET STRING (SIZE (0..160))
        MAX-ACCESS   read-write
        STATUS   current
        DESCRIPTION
           "用户自定义访问控制列表子项的匹配字符串"         
       ::= { aclNumUserSubitemEntry 7 }
       
    aclNumUserSubitemMask OBJECT-TYPE
        SYNTAX   OCTET STRING (SIZE (0..160))
        MAX-ACCESS   read-write
        STATUS   current
        DESCRIPTION
           "用户自定义访问控制列表子项的匹配字符串掩码"         
       ::= { aclNumUserSubitemEntry 8 } 
                  
    aclNumUserTimeRange OBJECT-TYPE
        SYNTAX   OCTET STRING (SIZE (0..32))
        MAX-ACCESS   read-write
        STATUS   current 
        DESCRIPTION
        "访问列表子项起作用的时间段"
        ::= { aclNumUserSubitemEntry 9 }
        
    aclNumUserSubitemRowStatus OBJECT-TYPE
        SYNTAX   RowStatus
        MAX-ACCESS   read-write
        STATUS   current 
        DESCRIPTION
        "表示当前ACL子项的状态，添加或删除。"
        ::= { aclNumUserSubitemEntry 10 } 
      
--基于名字的访问控制列表定义       
 aclNamedTable OBJECT-TYPE
        SYNTAX   SEQUENCE OF AclNamedEntry
        MAX-ACCESS   not-accessible
        STATUS   current
        DESCRIPTION
           "基于名字的访问控制列表，它一共由四种类型：基于名字的标准访问控制列表、
           基于数名字的扩展访问列表、基于名字的二层访问控制列表、基于名字的自定义访
           问控制列表."
       ::= { gbnL2QACL 7 }

    aclNamedEntry OBJECT-TYPE
        SYNTAX   AclNamedEntry
        MAX-ACCESS   not-accessible
        STATUS   current
        DESCRIPTION
           "定义一条基于名字的访问控制列表."
       INDEX { aclNamedName }
       ::= { aclNamedTable 1 }

    AclNamedEntry ::=
	    SEQUENCE {
	        aclNamedName
	            OCTET STRING, 
	        aclNamedType
	            AclType,	            
	        aclNamedMatchOrder
	            INTEGER,	        
	        aclNamedTotleSubitems
	            Integer32,
	        aclNamedRowStatus
	            RowStatus
	              }

    aclNamedName OBJECT-TYPE
        SYNTAX   OCTET STRING (SIZE (0..32))
        MAX-ACCESS   read-only
        STATUS   current
        DESCRIPTION
           "基于名字的访问控制列表的名字，各个访问控制列表（包括不同类
           型的访问控制列表）不能重名。"           
        ::= { aclNamedEntry 1 }     
        
    aclNamedType OBJECT-TYPE
        SYNTAX   AclType
        MAX-ACCESS   read-write
        STATUS   current
        DESCRIPTION
           "基于名字的访问控制列表的类型，同基于数字的ACL，但它的类型不由名字决定"           
        ::= { aclNamedEntry 2 }
        

    aclNamedMatchOrder OBJECT-TYPE
        SYNTAX   INTEGER    {
                    config (0),
                    auto (1)
                    }
        MAX-ACCESS   read-write
        STATUS   current
        DESCRIPTION
           "定义一条访问控制列表的配置顺序，auto 所用的“深度优先“  
           原则是指：把指定数据包范围最小的语句排在最前面。这一点可以
           通过比较地址的通配符来实现，通配符越小，则指定的主机的范围
           就越小。比如129.102.1.1 0.0.0.0 指定了一台主机：129.102.1.1
           而129.102.1.1 0.0.255.255 则指定了一个网段： 129.102.1.1 ～
           129.102.255.255，显然前者在访问控制规则中排在前面。具体标准
           为：对于标准访问控制规则的语句，直接比较源地址通配符，通配符
           相同的则按配置顺序；对于基于接口过滤的访问控制规则，配置了'any'
           的规则排在后面，其它按配置顺序；对于扩展访问控制规则，首先比
           较源地址通配符，相同的再比较目的地址通配符，仍相同的则比较端
           口号的范围，范围小的排在前面，如果端口号范围也相同则按配置顺序，
           默认按照用户的配置顺序即config。"  
        DEFVAL { config }        -- config
      ::= { aclNamedEntry 3 }
            
    aclNamedTotleSubitems OBJECT-TYPE
        SYNTAX   Integer32
        MAX-ACCESS   read-only
        STATUS   current 
        DESCRIPTION
        "一条访问控制列表可以定义多条子规则，这些子规则按照一定的顺序排列
        成一条访问控制列表，每条ACL最多可以定义128项子规则。"
        ::= { aclNamedEntry 4 }
        
    aclNamedRowStatus OBJECT-TYPE
        SYNTAX   RowStatus
        MAX-ACCESS   read-write
        STATUS   current 
        DESCRIPTION
        "表示当前ACL的状态，添加或删除。"
        ::= { aclNamedEntry 5 }
        
 --ACL子项定义，基于名字的标准访问控制列表子项。
       
  aclNamedStdSubitemTable OBJECT-TYPE
        SYNTAX   SEQUENCE OF AclNamedStdSubitemEntry
        MAX-ACCESS   not-accessible
        STATUS   current
        DESCRIPTION
           "定义一条标准访问控制列表子项。它是通过目的地址进行过滤的。"
       ::= { gbnL2QACL 8 }

    aclNamedStdSubitemEntry OBJECT-TYPE
        SYNTAX   AclNamedStdSubitemEntry
        MAX-ACCESS   not-accessible
        STATUS   current
        DESCRIPTION
           "定义一条标准访问控制列表子项."
       INDEX { aclNamedStdName, aclNamedStdSubNum }
       ::= { aclNamedStdSubitemTable 1 } 
         
    AclNamedStdSubitemEntry ::=
	    SEQUENCE {
	        aclNamedStdName
	            OCTET STRING,
	        aclNamedStdSubNum
	            Integer32,
	        aclNamedStdSubitemAdminStatus
	            AdminStatus,
	        aclNamedStdSubitemAction
	            Action,
	        aclNamedStdSubitemSrcAddr
	            IpAddress,   
	        aclNamedStdSubitemSrcAddrWldmsk
	            IpAddress,
	        aclNamedStdFragments
	            TruthValue,
	        aclNamedStdTimeRange
	            OCTET STRING,
	        aclNamedStdSubitemRowStatus
	            RowStatus        	            
	        }   
	        
    aclNamedStdName OBJECT-TYPE
        SYNTAX   OCTET STRING (SIZE (0..32))
        MAX-ACCESS   read-only
        STATUS   current
        DESCRIPTION
           "基于名字的访问控制列表的名字，它是一个最多32个字符组成的字符串"
        ::= { aclNamedStdSubitemEntry 1 } 
        
    aclNamedStdSubNum OBJECT-TYPE
        SYNTAX   Integer32 (0..127)
        MAX-ACCESS   read-only
        STATUS   current
        DESCRIPTION
           "访问控制列表的子项号，0－127。"
        ::= { aclNamedStdSubitemEntry 2 }         

    aclNamedStdSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNamedStdSubitemEntry 3 } 
       
    aclNamedStdSubitemAction OBJECT-TYPE
        SYNTAX   Action
        MAX-ACCESS   read-write
        STATUS   current
        DESCRIPTION
           "定义一条访问列表子项的动作，允许或拒绝。"         
       ::= { aclNamedStdSubitemEntry 4 }      
       
    aclNamedStdSubitemSrcAddr OBJECT-TYPE
        SYNTAX   IpAddress
        MAX-ACCESS   read-write
        STATUS   current
        DESCRIPTION
           "标准访问控制列表子项的原地址"         
       ::= { aclNamedStdSubitemEntry 5 }
       
    aclNamedStdSubitemSrcAddrWldmsk OBJECT-TYPE
        SYNTAX   IpAddress
        MAX-ACCESS   read-write
        STATUS   current
        DESCRIPTION
           "标准访问控制列表子项的原地址通配符"         
       ::= { aclNamedStdSubitemEntry 6 } 
                  
    aclNamedStdFragments OBJECT-TYPE
        SYNTAX   TruthValue
        MAX-ACCESS   read-write
        STATUS   current
        DESCRIPTION
           "标准访问控制列表子项的原地址通配符" 
        DEFVAL { false }        -- invalid                 
       ::= { aclNamedStdSubitemEntry 7 }  
  
  
    aclNamedStdTimeRange OBJECT-TYPE
        SYNTAX   OCTET STRING (SIZE (0..256))
        MAX-ACCESS   read-write
        STATUS   current 
        DESCRIPTION
        "访问列表子项起作用的时间段"
        ::= { aclNamedStdSubitemEntry 8 }
        
    aclNamedStdSubitemRowStatus OBJECT-TYPE
        SYNTAX   RowStatus
        MAX-ACCESS   read-write
        STATUS   current 
        DESCRIPTION
        "表示当前ACL子项的状态，添加或删除。"
        ::= { aclNamedStdSubitemEntry 9 }  


--ACL子项定义，基于名字的扩展访问控制列表子项。
       
  aclNamedExdSubitemTable OBJECT-TYPE
        SYNTAX   SEQUENCE OF AclNamedExdSubitemEntry
        MAX-ACCESS   not-accessible
        STATUS   current
        DESCRIPTION
           "定义一条扩展访问控制列表子项。它是通过对标准访问控制列表的补充。"
       ::= { gbnL2QACL 9 }

    aclNamedExdSubitemEntry OBJECT-TYPE
        SYNTAX   AclNamedExdSubitemEntry
        MAX-ACCESS   not-accessible
        STATUS   current
        DESCRIPTION
           "定义一条标准访问控制列表子项."
       INDEX { aclNamedExdName, aclNamedExdSubNum}
       ::= { aclNamedExdSubitemTable 1 }

    AclNamedExdSubitemEntry ::=
	    SEQUENCE {
	        aclNamedExdName
	            OCTET STRING,
	        aclNamedExdSubNum
	            Integer32,
	        aclNamedExdSubitemAdminStatus
	            AdminStatus,
	        aclNamedExdSubitemAction
	            Action, 
	        aclNamedExdSubitemProtocal
	            Integer32, 	            
	        aclNamedExdSubitemSrcAddr
	            IpAddress,   
	        aclNamedExdSubitemSrcAddrWldmsk
	            IpAddress,               
	        aclNamedExdSubitemDstAddr
	            IpAddress,   
	        aclNamedExdSubitemDstAddrWldmsk
	            IpAddress,
	        aclNamedExdSubitemSrcPort
	            Integer32,   
	        aclNamedExdSubitemSrcPortWldmsk
	            Integer32,
	        aclNamedExdSubitemDstPort
	            Integer32,
	        aclNamedExdSubitemDstPortWldmsk
	            Integer32, 
	        aclNamedExdSubitemIcmpType
	            Integer32,
	        aclNamedExdSubitemIcmpCode
	            Integer32, 
	        aclNamedExdSubitemTcpEstablished
	            TruthValue,
	        aclNamedExdSubitemPrecedence
	            Integer32,
	        aclNamedExdSubitemTos
	            TOSType,
	        aclNamedExdSubitemDscp
	            Dscp,   
	        aclNamedExdSubitemFragments
	            TruthValue,
	        aclNamedExdSubitemTimeRange
	            OCTET STRING,
	        aclNamedExdSubitemRowStatus
	            RowStatus        	            
	        }   
	        
    aclNamedExdName OBJECT-TYPE
        SYNTAX   OCTET STRING (SIZE (0..32))
        MAX-ACCESS   read-only
        STATUS   current
        DESCRIPTION
           "基于名字的访问控制列表的名字，它是一个最多32个字符组成的字符串"
        ::= { aclNamedExdSubitemEntry 1 } 
        
    aclNamedExdSubNum OBJECT-TYPE
        SYNTAX   Integer32 (0..127)
        MAX-ACCESS   read-only
        STATUS   current
        DESCRIPTION
           "访问控制列表的子项号，0－127。"
        ::= { aclNamedExdSubitemEntry 2 }         

    aclNamedExdSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNamedExdSubitemEntry 3 } 
       
    aclNamedExdSubitemAction OBJECT-TYPE
        SYNTAX   Action
        MAX-ACCESS   read-write
        STATUS   current
        DESCRIPTION
           "定义一条访问列表子项的动作，允许或拒绝。"         
       ::= { aclNamedExdSubitemEntry 4 }
       
    aclNamedExdSubitemProtocal OBJECT-TYPE
        SYNTAX   Integer32 (1..255)
        MAX-ACCESS   read-write
        STATUS   current
        DESCRIPTION
           "过滤某种协议类型的报文"
        ::= { aclNamedExdSubitemEntry 5 }       
             
       
    aclNamedExdSubitemSrcAddr OBJECT-TYPE
        SYNTAX   IpAddress
        MAX-ACCESS   read-write
        STATUS   current
        DESCRIPTION
           "扩展访问控制列表子项的原地址"         
       ::= { aclNamedExdSubitemEntry 6 }
       
    aclNamedExdSubitemSrcAddrWldmsk OBJECT-TYPE
        SYNTAX   IpAddress
        MAX-ACCESS   read-write
        STATUS   current
        DESCRIPTION
           "扩展访问控制列表子项的原地址通配符"         
       ::= { aclNamedExdSubitemEntry 7 } 
       
    aclNamedExdSubitemDstAddr OBJECT-TYPE
        SYNTAX   IpAddress
        MAX-ACCESS   read-write
        STATUS   current
        DESCRIPTION
           "扩展访问控制列表子项的目的地址"         
       ::= { aclNamedExdSubitemEntry 8 }
       
    aclNamedExdSubitemDstAddrWldmsk OBJECT-TYPE
        SYNTAX   IpAddress
        MAX-ACCESS   read-write
        STATUS   current
        DESCRIPTION
           "扩展访问控制列表子项的目的地址通配符"         
       ::= { aclNamedExdSubitemEntry 9 }
       
    aclNamedExdSubitemSrcPort OBJECT-TYPE
        SYNTAX   Integer32  (0..65535)
        MAX-ACCESS   read-write
        STATUS   current
        DESCRIPTION
           "filter the special TCP/UDP ports"
           --对UDP或TCP报文特定端口号的包进行过滤         
       ::= { aclNamedExdSubitemEntry 10 }
       
    aclNamedExdSubitemSrcPortWldmsk OBJECT-TYPE
        SYNTAX   Integer32  (0..65535)
        MAX-ACCESS   read-write
        STATUS   current
        DESCRIPTION
           "source ports wildcard"
           --扩展访问控制列表子项的源端口号通配符        
       ::= { aclNamedExdSubitemEntry 11 } 
       
    aclNamedExdSubitemDstPort OBJECT-TYPE
        SYNTAX   Integer32  (0..65535)
        MAX-ACCESS   read-write
        STATUS   current
        DESCRIPTION
           "filter the special TCP/UDP ports"
           --对UDP或TCP报文特定端口号的包进行过滤        
       ::= { aclNamedExdSubitemEntry 12 }
       
    aclNamedExdSubitemDstPortWldmsk OBJECT-TYPE
        SYNTAX   Integer32  (0..65535)
        MAX-ACCESS   read-write
        STATUS   current
        DESCRIPTION
           "destination ports wildcard" 
           --扩展访问控制列表子项的源端口号通配符           
       ::= { aclNamedExdSubitemEntry 13 }       
       
    aclNamedExdSubitemIcmpType OBJECT-TYPE
        SYNTAX   Integer32 (0..255)
        MAX-ACCESS   read-write
        STATUS   current
        DESCRIPTION
           "对ICMP的特定类型的包进行过滤"         
       ::= { aclNamedExdSubitemEntry 14 }
       
    aclNamedExdSubitemIcmpCode OBJECT-TYPE
        SYNTAX   Integer32 (0..255)
        MAX-ACCESS   read-write
        STATUS   current
        DESCRIPTION
           "对ICMP的特定类型，特定代码的包进行过滤"           
       ::= { aclNamedExdSubitemEntry 15 }        

    aclNamedExdSubitemTcpEstablished OBJECT-TYPE
        SYNTAX   TruthValue
        MAX-ACCESS   read-write
        STATUS   current
        DESCRIPTION
           "对TCP第一个建链的包进行过滤"  
        DEFVAL { false }        -- invalid           
       ::= { aclNamedExdSubitemEntry 16 }
           
    aclNamedExdSubitemPrecedence OBJECT-TYPE
        SYNTAX   Integer32 (0..7)
        MAX-ACCESS   read-write
        STATUS   current
        DESCRIPTION
           "对特定IP优先级的包进行过滤"           
       ::= { aclNamedExdSubitemEntry 17 }       
       
    aclNamedExdSubitemTos OBJECT-TYPE
        SYNTAX   TOSType
        MAX-ACCESS   read-write
        STATUS   current
        DESCRIPTION
           "对数据包中TOS字段等于特定值的包进行过滤"           
       ::= { aclNamedExdSubitemEntry 18 }
       
    aclNamedExdSubitemDscp OBJECT-TYPE
        SYNTAX   Dscp
        MAX-ACCESS   read-write
        STATUS   current
        DESCRIPTION
           "对数据包中DSCP字段等于特定值的包进行过滤"           
       ::= { aclNamedExdSubitemEntry 19 }              
                  
    aclNamedExdSubitemFragments OBJECT-TYPE
        SYNTAX   TruthValue
        MAX-ACCESS   read-write
        STATUS   current
        DESCRIPTION
           "扩展访问控制列表子项的目的地址通配符" 
        DEFVAL { false }        -- invalid                 
       ::= { aclNamedExdSubitemEntry 20 }  
  
  
    aclNamedExdSubitemTimeRange OBJECT-TYPE
        SYNTAX   OCTET STRING (SIZE (0..256))
        MAX-ACCESS   read-write
        STATUS   current 
        DESCRIPTION
        "访问列表子项起作用的时间段"
        ::= { aclNamedExdSubitemEntry 21 }
        
    aclNamedExdSubitemRowStatus OBJECT-TYPE
        SYNTAX   RowStatus
        MAX-ACCESS   read-write
        STATUS   current 
        DESCRIPTION
        "表示当前ACL子项的状态，添加或删除。"
        ::= { aclNamedExdSubitemEntry 22 }
        
        
--ACL子项定义，基于名字的二层访问控制列表子项。
       
  aclNamedLnkSubitemTable OBJECT-TYPE
        SYNTAX   SEQUENCE OF AclNamedLnkSubitemEntry
        MAX-ACCESS   not-accessible
        STATUS   current
        DESCRIPTION
           "定义一条二层访问控制列表子项。"
       ::= { gbnL2QACL 10 }

    aclNamedLnkSubitemEntry OBJECT-TYPE
        SYNTAX   AclNamedLnkSubitemEntry
        MAX-ACCESS   not-accessible
        STATUS   current
        DESCRIPTION
           "定义一条二层访问控制列表子项."
       INDEX { aclNamedLnkName, aclNamedLnkSubNum}
       ::= { aclNamedLnkSubitemTable 1 }

    AclNamedLnkSubitemEntry ::=
	    SEQUENCE {
	        aclNamedLnkName
	            OCTET STRING,
	        aclNamedLnkSubNum
	            Integer32,
	        aclNamedLnkSubitemAdminStatus
	            AdminStatus,
	        aclNamedLnkSubitemAction
	            Action,
	        aclNamedLnkSubitemProtocal
	            Integer32,
	        aclNamedLnkSubitemCos
	            Integer32,	             
	        aclNamedLnkSubitemSrcVlanID
	            VlanId, 
	        aclNamedLnkSubitemSrcMacAddr
	            MacAddress,
	        aclNamedLnkSubitemSrcMacWldmsk
	            MacAddress,
	        aclNamedLnkSubitemDstMacAddr
	            MacAddress,
	        aclNamedLnkSubitemDstMacWldmsk
	            MacAddress,                 	              
	        aclNamedLnkSubitemSrcPortNum
	            Integer32,
	        aclNamedLnkSubitemDstPortNum
	            Integer32,            
	        aclNamedLnkSubitemTimeRange
	            OCTET STRING,
	        aclNamedLnkSubitemRowStatus
	            RowStatus        	            
	        }   
	        
    aclNamedLnkName OBJECT-TYPE
        SYNTAX   OCTET STRING (SIZE (0..32))
        MAX-ACCESS   read-only
        STATUS   current
        DESCRIPTION
           "基于名字的访问控制列表的名字，它是一个最多32个字符组成的字符串"
        ::= { aclNamedLnkSubitemEntry 1 } 
        
    aclNamedLnkSubNum OBJECT-TYPE
        SYNTAX   Integer32 (0..127)
        MAX-ACCESS   read-only
        STATUS   current
        DESCRIPTION
           "访问控制列表的子项号，0－127。"
        ::= { aclNamedLnkSubitemEntry 2 }         

    aclNamedLnkSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNamedLnkSubitemEntry 3 } 
       
    aclNamedLnkSubitemAction OBJECT-TYPE
        SYNTAX   Action
        MAX-ACCESS   read-write
        STATUS   current
        DESCRIPTION
           "定义一条访问列表子项的动作，允许或拒绝。"         
       ::= { aclNamedLnkSubitemEntry 4 }
       
    aclNamedLnkSubitemProtocal OBJECT-TYPE
        SYNTAX   Integer32 (1..255)
        MAX-ACCESS   read-write
        STATUS   current
        DESCRIPTION
           "过滤某种协议类型的报文"
        ::= { aclNamedLnkSubitemEntry 5 } 
        
    aclNamedLnkSubitemCos OBJECT-TYPE
        SYNTAX   Integer32 (0..7)
        MAX-ACCESS   read-write
        STATUS   current
        DESCRIPTION
           "过滤某种协议类型的报文"
        ::= { aclNamedLnkSubitemEntry 6 }                   

    aclNamedLnkSubitemSrcVlanID OBJECT-TYPE
        SYNTAX   VlanId
        MAX-ACCESS   read-write
        STATUS   current
        DESCRIPTION
           "对VLAN ID为特定值的数据包进行过滤"         
       ::= { aclNamedLnkSubitemEntry 7 }	            
	                   
    aclNamedLnkSubitemSrcMacAddr OBJECT-TYPE
        SYNTAX   MacAddress
        MAX-ACCESS   read-write
        STATUS   current
        DESCRIPTION
           "它于MAC通配符共同作用得到感兴趣的源MAC地址，并对这些
           MAC地址作处理。"         
       ::= { aclNamedLnkSubitemEntry 8 }
       
    aclNamedLnkSubitemSrcMacWldmsk OBJECT-TYPE
        SYNTAX   MacAddress
        MAX-ACCESS   read-write
        STATUS   current
        DESCRIPTION
           "它于MAC地址共同作用得到感兴趣的源MAC地址，并对这些
           MAC地址作处理。"        
       ::= { aclNamedLnkSubitemEntry 9 }  
       
    aclNamedLnkSubitemDstMacAddr OBJECT-TYPE
        SYNTAX   MacAddress
        MAX-ACCESS   read-write
        STATUS   current
        DESCRIPTION
           "它于MAC通配符共同作用得到感兴趣的目的MAC地址，并对这些
           MAC地址作处理。"         
       ::= { aclNamedLnkSubitemEntry 10 } 
       
    aclNamedLnkSubitemDstMacWldmsk OBJECT-TYPE
        SYNTAX   MacAddress
        MAX-ACCESS   read-write
        STATUS   current
        DESCRIPTION
           "它于MAC地址共同作用得到感兴趣的目的MAC地址，并对这些
           MAC地址作处理。"        
       ::= { aclNamedLnkSubitemEntry 11 } 
       
    aclNamedLnkSubitemSrcPortNum OBJECT-TYPE
        SYNTAX   Integer32    (1..26)
        MAX-ACCESS   read-write
        STATUS   current
        DESCRIPTION
           "百兆以太网端口号1－24，千兆以太网端口号1－2"                  
       ::= { aclNamedLnkSubitemEntry 12 }    
       
    aclNamedLnkSubitemDstPortNum OBJECT-TYPE
        SYNTAX   Integer32       (1..29)
        MAX-ACCESS   read-write
        STATUS   current
        DESCRIPTION
           "1－24为百兆以太网端口号1－24，25－26为千兆以太网端口号1－2，27为已知组播，28为CPU端口号，29为DLF"
       ::= { aclNamedLnkSubitemEntry 13 }    
  
    aclNamedLnkSubitemTimeRange OBJECT-TYPE
        SYNTAX   OCTET STRING (SIZE (0..32))
        MAX-ACCESS   read-write
        STATUS   current 
        DESCRIPTION
        "访问列表子项起作用的时间段"
        ::= { aclNamedLnkSubitemEntry 14 }
        
    aclNamedLnkSubitemRowStatus OBJECT-TYPE
        SYNTAX   RowStatus
        MAX-ACCESS   read-write
        STATUS   current 
        DESCRIPTION
        "表示当前ACL子项的状态，添加或删除。"
        ::= { aclNamedLnkSubitemEntry 15 }  

 --ACL子项定义，基于名字的自定义访问控制列表子项。
       
  aclNamedUserSubitemTable OBJECT-TYPE
        SYNTAX   SEQUENCE OF AclNamedUserSubitemEntry
        MAX-ACCESS   not-accessible
        STATUS   current
        DESCRIPTION
           "定义一条自定义访问控制列表子项。它是通过目的地址进行过滤的。"
       ::= { gbnL2QACL 11 }

    aclNamedUserSubitemEntry OBJECT-TYPE
        SYNTAX   AclNamedUserSubitemEntry
        MAX-ACCESS   not-accessible
        STATUS   current
        DESCRIPTION
           "定义一条标准访问控制列表子项."
       INDEX { aclNamedUserName, aclNamedUserSubNum }
       ::= { aclNamedUserSubitemTable 1 } 
                    
    AclNamedUserSubitemEntry ::=
	    SEQUENCE {
	        aclNamedUserName
	            OCTET STRING,
	        aclNamedUserSubNum
	            Integer32,
	        aclNamedUserSubitemAdminStatus
	            AdminStatus,
	        aclNamedUserSubitemAction
	            Action,   
	        aclNamedUserSubitemSrcPortNum
	            Integer32,
	        aclNamedUserSubitemDstPortNum
	            Integer32,  	            
	        aclNamedUserSubitemRule
	            OCTET STRING,                    
	        aclNamedUserSubitemMask
	            OCTET STRING,
	        aclNamedUserTimeRange
	            OCTET STRING,
	        aclNamedUserSubitemRowStatus
	            RowStatus        	            
	        }   
	        
    aclNamedUserName OBJECT-TYPE
        SYNTAX   OCTET STRING (SIZE (0..32))
        MAX-ACCESS   read-only
        STATUS   current
        DESCRIPTION
           "基于名字的访问控制列表的名字，它是一个最多32个字符组成的字符串"
        ::= { aclNamedUserSubitemEntry 1 } 
        
    aclNamedUserSubNum OBJECT-TYPE
        SYNTAX   Integer32 (0..127)
        MAX-ACCESS   read-only
        STATUS   current
        DESCRIPTION
           "访问控制列表的子项号，0－127。"
        ::= { aclNamedUserSubitemEntry 2 }         

    aclNamedUserSubitemAdminStatus OBJECT-TYPE
        SYNTAX   AdminStatus
        MAX-ACCESS   read-only
        STATUS   current
        DESCRIPTION
           "当此项为valid时激活一条访问控制列表，invalid表示只配置了此项
           ACL但并没有下发到硬件开始执行。"  
        DEFVAL { invalid }        -- invalid       
       ::= { aclNamedUserSubitemEntry 3 } 
       
    aclNamedUserSubitemAction OBJECT-TYPE
        SYNTAX   Action
        MAX-ACCESS   read-write
        STATUS   current
        DESCRIPTION
           "定义一条访问列表子项的动作，允许或拒绝。"         
       ::= { aclNamedUserSubitemEntry 4 } 
       
    aclNamedUserSubitemSrcPortNum OBJECT-TYPE
        SYNTAX   Integer32
        MAX-ACCESS   read-write
        STATUS   current
        DESCRIPTION
           "百兆以太网端口号1－24，千兆以太网端口号1－2"                  
       ::= { aclNamedUserSubitemEntry 5 }    
       
    aclNamedUserSubitemDstPortNum OBJECT-TYPE
        SYNTAX   Integer32   (1..29)
        MAX-ACCESS   read-write
        STATUS   current
        DESCRIPTION
           "1－24为百兆以太网端口号1－24，25－26为千兆以太网端口号1－2，27为已知组播，28为CPU端口号，29为DLF"
       ::= { aclNamedUserSubitemEntry 6 }              
       
    aclNamedUserSubitemRule OBJECT-TYPE
        SYNTAX   OCTET STRING (SIZE (0..160))
        MAX-ACCESS   read-write
        STATUS   current
        DESCRIPTION
           "用户自定义访问控制列表子项的匹配字符串"         
       ::= { aclNamedUserSubitemEntry 7 }
       
    aclNamedUserSubitemMask OBJECT-TYPE
        SYNTAX   OCTET STRING (SIZE (0..160))
        MAX-ACCESS   read-write
        STATUS   current
        DESCRIPTION
           "用户自定义访问控制列表子项的匹配字符串掩码"         
       ::= { aclNamedUserSubitemEntry 8 } 
                  
    aclNamedUserTimeRange OBJECT-TYPE
        SYNTAX   OCTET STRING (SIZE (0..256))
        MAX-ACCESS   read-write
        STATUS   current 
        DESCRIPTION
        "访问列表子项起作用的时间段"
        ::= { aclNamedUserSubitemEntry 9 }
        
    aclNamedUserSubitemRowStatus OBJECT-TYPE
        SYNTAX   RowStatus
        MAX-ACCESS   read-write
        STATUS   current 
        DESCRIPTION
        "表示当前ACL子项的状态，添加或删除。"
        ::= { aclNamedUserSubitemEntry 10 } 
 
--时间段定义       
 aclTimeRangeTable OBJECT-TYPE
        SYNTAX   SEQUENCE OF AclTimeRangeEntry
        MAX-ACCESS   not-accessible
        STATUS   current
        DESCRIPTION
           "time range"
       ::= { gbnL2QACL 12 }

    aclTimeRangeEntry OBJECT-TYPE
        SYNTAX   AclTimeRangeEntry
        MAX-ACCESS   not-accessible
        STATUS   current
        DESCRIPTION
           "定义一条时间段."
       INDEX { aclTimeRangeName }
       ::= { aclTimeRangeTable 1 }

    AclTimeRangeEntry ::=
	    SEQUENCE {
	        aclTimeRangeName
	            OCTET STRING,
	        aclTimeRangeTotleAbsolutes
	            Integer32,
	        aclTimeRangeTotlePeriods
	            Integer32,
	        aclTimeRangeActive
	            TruthValue,   
	        aclTimeRangeRowStatus
	            RowStatus
	              }

    aclTimeRangeName OBJECT-TYPE
        SYNTAX   OCTET STRING (SIZE (0..32))
        MAX-ACCESS   read-only
        STATUS   current
        DESCRIPTION
           "时间段的名字"           
        ::= { aclTimeRangeEntry 1 }

    aclTimeRangeTotleAbsolutes OBJECT-TYPE
      SYNTAX   Integer32
        MAX-ACCESS   read-only
        STATUS   current
        DESCRIPTION
           "一个时间段最多可以配置12个绝对时间段，这里为已经配置的绝对时间段的数目"  
        DEFVAL { invalid }        -- invalid       
       ::= { aclTimeRangeEntry 2 }

    aclTimeRangeTotlePeriods OBJECT-TYPE
        SYNTAX   Integer32
        MAX-ACCESS   read-only
        STATUS   current 
        DESCRIPTION
        "一个时间段最多可以配置32个周期时间段，这里为已经配置的周期时间段的数目"
        ::= { aclTimeRangeEntry 3 }

    aclTimeRangeActive OBJECT-TYPE
       SYNTAX   TruthValue
       MAX-ACCESS   read-only
       STATUS   current
       DESCRIPTION
          "时间段的激活状态"                          
      ::= { aclTimeRangeEntry 4 } 
      
    aclTimeRangeRowStatus OBJECT-TYPE
        SYNTAX   RowStatus
        MAX-ACCESS   read-write
        STATUS   current 
        DESCRIPTION
        "表示当前时间段的状态，添加或删除。"
        ::= { aclTimeRangeEntry 5 }
        
 --绝对时间段定义。
       
  aclTimeRangeAbsoluteTable OBJECT-TYPE
        SYNTAX   SEQUENCE OF AclTimeRangeAbsoluteEntry
        MAX-ACCESS   not-accessible
        STATUS   current
        DESCRIPTION
           "定义一个绝对时间段"
       ::= { gbnL2QACL 13 }

    aclTimeRangeAbsoluteEntry OBJECT-TYPE
        SYNTAX   AclTimeRangeAbsoluteEntry
        MAX-ACCESS   not-accessible
        STATUS   current
        DESCRIPTION
           "定义一条绝对时间段."
       INDEX { aclTimeRangeAbsoluteName, aclTimeRangeAbsoluteStartTime,
               aclTimeRangeAbsoluteEndTime }
       ::= { aclTimeRangeAbsoluteTable 1 } 
         
    AclTimeRangeAbsoluteEntry ::=
	    SEQUENCE {
	        aclTimeRangeAbsoluteName
	            OCTET STRING,
	        aclTimeRangeAbsoluteStartTime
	            Unsigned32,
	        aclTimeRangeAbsoluteEndTime
	            Unsigned32,
	        aclTimeRangeAbsoluteRowStatus
	            RowStatus        	            
	        }   
	        
    aclTimeRangeAbsoluteName OBJECT-TYPE
        SYNTAX   OCTET STRING (SIZE (0..32))
        MAX-ACCESS   read-only
        STATUS   current
        DESCRIPTION
           "时间段的名字"
        ::= { aclTimeRangeAbsoluteEntry 1 } 
        
    aclTimeRangeAbsoluteStartTime OBJECT-TYPE
        SYNTAX   Unsigned32
        MAX-ACCESS   read-only
        STATUS   current
        DESCRIPTION
           "绝对时间段起始时间(日历时间)"
        ::= { aclTimeRangeAbsoluteEntry 2 }         

    aclTimeRangeAbsoluteEndTime OBJECT-TYPE
        SYNTAX   Unsigned32
        MAX-ACCESS   read-only
        STATUS   current
        DESCRIPTION
           "绝对时间段终止时间的年份"
        ::= { aclTimeRangeAbsoluteEntry 3 }         
                          
    aclTimeRangeAbsoluteRowStatus OBJECT-TYPE
        SYNTAX   RowStatus
        MAX-ACCESS   read-write
        STATUS   current 
        DESCRIPTION
        "绝对时间段的当前状态"
        ::= { aclTimeRangeAbsoluteEntry 4 }
        
 --周期时间段定义。
       
  aclTimeRangePeriodTable OBJECT-TYPE
        SYNTAX   SEQUENCE OF AclTimeRangePeriodEntry
        MAX-ACCESS   not-accessible
        STATUS   current
        DESCRIPTION
           "定义一个周期时间段"
       ::= { gbnL2QACL 14 }

    aclTimeRangePeriodEntry OBJECT-TYPE
        SYNTAX   AclTimeRangePeriodEntry
        MAX-ACCESS   not-accessible
        STATUS   current
        DESCRIPTION
           "定义一条周期时间段."
       INDEX { aclTimeRangePeriodName, aclTimeRangePeriodStartWeekDay,
               aclTimeRangePeriodStartHour, aclTimeRangePeriodStartMin,
               aclTimeRangePeriodEndWeekDay, aclTimeRangePeriodEndHour,
               aclTimeRangePeriodEndMin }
       ::= { aclTimeRangePeriodTable 1 } 
         
    AclTimeRangePeriodEntry ::=
	    SEQUENCE {
	        aclTimeRangePeriodName
	            OCTET STRING,
	        aclTimeRangePeriodStartWeekDay
	            Unsigned32,
	        aclTimeRangePeriodStartHour
	            Unsigned32,
	        aclTimeRangePeriodStartMin
	            Unsigned32,
	        aclTimeRangePeriodEndWeekDay
	            Unsigned32, 
	        aclTimeRangePeriodEndHour
	            Unsigned32, 
	        aclTimeRangePeriodEndMin
	            Unsigned32, 
	        aclTimeRangePeriodRowStatus
	            RowStatus        	            
	        }   
	        
    aclTimeRangePeriodName OBJECT-TYPE
        SYNTAX   OCTET STRING (SIZE (0..32))
        MAX-ACCESS   read-only
        STATUS   current
        DESCRIPTION
           "时间段的名字"
        ::= { aclTimeRangePeriodEntry 1 } 
        
    aclTimeRangePeriodStartWeekDay OBJECT-TYPE
        SYNTAX   Unsigned32
        MAX-ACCESS   read-only
        STATUS   current
        DESCRIPTION
           "周期时间段起始时间的日期（星期几）"
        ::= { aclTimeRangePeriodEntry 2 }         

    aclTimeRangePeriodStartHour OBJECT-TYPE
        SYNTAX   Unsigned32
        MAX-ACCESS   read-only
        STATUS   current
        DESCRIPTION
           "周期时间段的起始时间（几点）"       
       ::= { aclTimeRangePeriodEntry 3 } 
       
    aclTimeRangePeriodStartMin OBJECT-TYPE
        SYNTAX   Unsigned32
        MAX-ACCESS   read-only
        STATUS   current
        DESCRIPTION
           "周期时间段的起始时间（几分）"          
       ::= { aclTimeRangePeriodEntry 4 }   
       
    aclTimeRangePeriodEndWeekDay OBJECT-TYPE
        SYNTAX   Unsigned32
        MAX-ACCESS   read-only
        STATUS   current
        DESCRIPTION
           "周期时间段终止时间的日期（星期几）"
        ::= { aclTimeRangePeriodEntry 5 }         

    aclTimeRangePeriodEndHour OBJECT-TYPE
        SYNTAX   Unsigned32
        MAX-ACCESS   read-only
        STATUS   current
        DESCRIPTION
           "周期时间段的终止时间（几点）"       
       ::= { aclTimeRangePeriodEntry 6 } 
       
    aclTimeRangePeriodEndMin OBJECT-TYPE
        SYNTAX   Unsigned32
        MAX-ACCESS   read-only
        STATUS   current
        DESCRIPTION
           "周期时间段的终止时间（几分）"          
       ::= { aclTimeRangePeriodEntry 7 }       
                          
    aclTimeRangePeriodRowStatus OBJECT-TYPE
        SYNTAX   RowStatus
        MAX-ACCESS   read-write
        STATUS   current 
        DESCRIPTION
        "周期时间段的当前状态"
        ::= { aclTimeRangePeriodEntry 8 }
                                          
    --
    -- the active ACL group
    --
    
    aclActiveTable OBJECT-TYPE
        SYNTAX  SEQUENCE OF AclActiveEntry
        ACCESS  not-accessible
        STATUS  current
        DESCRIPTION
                "A list of active acl entries. "
        ::= { gbnL2QACL 15 }
  
    aclActiveEntry OBJECT-TYPE
        SYNTAX  AclActiveEntry
        ACCESS  not-accessible
        STATUS  current
        DESCRIPTION
                "A list of active acl entries. "
        INDEX   { aclActiveIndex }
        ::= { aclActiveTable 1 }
  
    AclActiveEntry ::=
        SEQUENCE {
            aclActiveIndex
                INTEGER,
            aclActiveUserGroupName
                OCTET STRING,
            aclActiveUserGroupSubitem
                INTEGER,
            aclActiveIpGroupName
                OCTET STRING,
            aclActiveIpGroupSubitem
                INTEGER,    
            aclActiveLinkGroupName
                OCTET STRING,
            aclActiveLinkGroupSubitem
                INTEGER,    
            aclActiveBlock0Priority
                INTEGER,
            aclActiveBlock1Priority
                INTEGER,  
            aclActiveBlock2Priority
                INTEGER, 
            aclActiveBlock3Priority
                INTEGER,
            aclActiveBlock4Priority
                INTEGER,           
            aclActiveConfigSequence
                INTEGER,      
            aclActiveRunning
                TruthValue,
            aclActiveRowStatus
                RowStatus,
            aclActiveBlock5Priority
                INTEGER,
            aclActiveBlock6Priority
                INTEGER,  
            aclActiveBlock7Priority
                INTEGER, 
            aclActiveBlock8Priority
                INTEGER,
            aclActiveBlock9Priority
                INTEGER,        
            aclActiveBlock10Priority
                INTEGER,
            aclActiveBlock11Priority
                INTEGER        
        }
  
    aclActiveIndex OBJECT-TYPE
        SYNTAX  INTEGER
        ACCESS  read-only
        STATUS  current
        DESCRIPTION
                "A unique value for each active acl.  "
        ::= { aclActiveEntry 1 }
  
    aclActiveUserGroupName OBJECT-TYPE
        SYNTAX  OCTET STRING (SIZE (0..31))
        ACCESS  read-write
        STATUS  current
        DESCRIPTION
                "the name of the active user group acl. "
        ::= { aclActiveEntry 2 }
  
    aclActiveUserGroupSubitem OBJECT-TYPE
        SYNTAX  INTEGER(0..127)
        ACCESS  read-write
        STATUS  current
        DESCRIPTION
                "the number of the active user group acl subitem. "
        ::= { aclActiveEntry 3 }   
  
    aclActiveIpGroupName OBJECT-TYPE
        SYNTAX  OCTET STRING (SIZE (0..31))
        ACCESS  read-write
        STATUS  current
        DESCRIPTION
                "the name of the active ip group acl. "
        ::= { aclActiveEntry 4 }
  
    aclActiveIpGroupSubitem OBJECT-TYPE
        SYNTAX  INTEGER(0..127)
        ACCESS  read-write
        STATUS  current
        DESCRIPTION
                "the number of the active ip group acl subitem. "
        ::= { aclActiveEntry 5 }      
  
    aclActiveLinkGroupName OBJECT-TYPE
        SYNTAX  OCTET STRING (SIZE (0..31))
        ACCESS  read-write
        STATUS  current
        DESCRIPTION
                "the name of the active link group acl. "
        ::= { aclActiveEntry 6 }
  
    aclActiveLinkGroupSubitem OBJECT-TYPE
        SYNTAX  INTEGER(0..127)
        ACCESS  read-write
        STATUS  current
        DESCRIPTION
                "the number of the active link group acl subitem. "
        ::= { aclActiveEntry 7 }                        

    aclActiveBlock0Priority OBJECT-TYPE
        SYNTAX  INTEGER(0..16)
        ACCESS  read-only
        STATUS  current
        DESCRIPTION
                "the block 0 priority of the active ACL. 16 means no filter rules in the Hardware."
        ::= { aclActiveEntry 8 } 

    aclActiveBlock1Priority OBJECT-TYPE
        SYNTAX  INTEGER(0..16)
        ACCESS  read-only
        STATUS  current
        DESCRIPTION
                "the block 1 priority of the active ACL. 16 means no filter rules in the Hardware."
        ::= { aclActiveEntry 9 }
        
    aclActiveBlock2Priority OBJECT-TYPE
        SYNTAX  INTEGER(0..16)
        ACCESS  read-only
        STATUS  current
        DESCRIPTION
                "the block 2 priority of the active ACL. 16 means no filter rules in the Hardware."
        ::= { aclActiveEntry 10 }
        
    aclActiveBlock3Priority OBJECT-TYPE
        SYNTAX  INTEGER(0..16)
        ACCESS  read-only
        STATUS  current
        DESCRIPTION
                "the block 3 priority of the active ACL. 16 means no filter rules in the Hardware."
        ::= { aclActiveEntry 11 }
        
    aclActiveBlock4Priority OBJECT-TYPE
        SYNTAX  INTEGER(0..16)
        ACCESS  read-only
        STATUS  current
        DESCRIPTION
                "the block 4 priority of the active ACL. 16 means no filter rules in the Hardware."
        ::= { aclActiveEntry 12 }

    aclActiveConfigSequence OBJECT-TYPE
        SYNTAX  INTEGER(1..1024)
        ACCESS  read-only
        STATUS  current
        DESCRIPTION
                "the config sequence of the active ACL."
        ::= { aclActiveEntry 13 }
                                    
    aclActiveRunning OBJECT-TYPE
        SYNTAX   TruthValue
        MAX-ACCESS   read-only
        STATUS   current
        DESCRIPTION
           "the running status of the active ACL."                          
       ::= { aclActiveEntry 14 }  
       
    aclActiveRowStatus OBJECT-TYPE
        SYNTAX      RowStatus
        MAX-ACCESS  read-create
        STATUS      current
        DESCRIPTION
            "This object indicates the status of this entry."
        ::= { aclActiveEntry 15 }

    aclActiveBlock5Priority OBJECT-TYPE
        SYNTAX  INTEGER(0..16)
        ACCESS  read-only
        STATUS  current
        DESCRIPTION
                "the block 5 priority of the active ACL. 16 means no filter rules in the Hardware."
                --激活ACL在block 5中的优先级，16表示没有过滤规则在硬件中
        ::= { aclActiveEntry 16 } 

    aclActiveBlock6Priority OBJECT-TYPE
        SYNTAX  INTEGER(0..16)
        ACCESS  read-only
        STATUS  current
        DESCRIPTION
                "the block 6 priority of the active ACL. 16 means no filter rules in the Hardware."
                --激活ACL在block 6中的优先级，16表示没有过滤规则在硬件中
        ::= { aclActiveEntry 17 } 

    aclActiveBlock7Priority OBJECT-TYPE
        SYNTAX  INTEGER(0..16)
        ACCESS  read-only
        STATUS  current
        DESCRIPTION
                "the block 7 priority of the active ACL. 16 means no filter rules in the Hardware."
                --激活ACL在block 7中的优先级，16表示没有过滤规则在硬件中
        ::= { aclActiveEntry 18 }         

    aclActiveBlock8Priority OBJECT-TYPE
        SYNTAX  INTEGER(0..16)
        ACCESS  read-only
        STATUS  current
        DESCRIPTION
                "the block 8 priority of the active ACL. 16 means no filter rules in the Hardware."
                --激活ACL在block 8中的优先级，16表示没有过滤规则在硬件中
        ::= { aclActiveEntry 19 }     

    aclActiveBlock9Priority OBJECT-TYPE
        SYNTAX  INTEGER(0..16)
        ACCESS  read-only
        STATUS  current
        DESCRIPTION
                "the block 9 priority of the active ACL. 16 means no filter rules in the Hardware."
                --激活ACL在block 9中的优先级，16表示没有过滤规则在硬件中
        ::= { aclActiveEntry 20 } 

    aclActiveBlock10Priority OBJECT-TYPE
        SYNTAX  INTEGER(0..16)
        ACCESS  read-only
        STATUS  current
        DESCRIPTION
                "the block 10 priority of the active ACL. 16 means no filter rules in the Hardware."
                --激活ACL在block 10中的优先级，16表示没有过滤规则在硬件中
        ::= { aclActiveEntry 21 } 

    aclActiveBlock11Priority OBJECT-TYPE
        SYNTAX  INTEGER(0..16)
        ACCESS  read-only
        STATUS  current
        DESCRIPTION
                "the block 11 priority of the active ACL. 16 means no filter rules in the Hardware."
                --激活ACL在block 11中的优先级，16表示没有过滤规则在硬件中
        ::= { aclActiveEntry 22 }     
                
    --
    -- the mirror-to QOS group
    --
  
    qosMirrorToTable OBJECT-TYPE
        SYNTAX  SEQUENCE OF QosMirrorToEntry
        ACCESS  not-accessible
        STATUS  current
        DESCRIPTION
                "A list of mirror-to QOS entries. "
        ::= { gbnL2QACL 16 }
  
    qosMirrorToEntry OBJECT-TYPE
        SYNTAX  QosMirrorToEntry
        ACCESS  not-accessible
        STATUS  current
        DESCRIPTION
                "A list of mirror-to QOS entries. "
        INDEX   { qosMirrorToIndex }
        ::= { qosMirrorToTable 1 }
  
    QosMirrorToEntry ::=
        SEQUENCE {
            qosMirrorToIndex
                INTEGER,
            qosMirrorToUserGroupName
                OCTET STRING,
            qosMirrorToUserGroupSubitem
                INTEGER,
            qosMirrorToIpGroupName
                OCTET STRING,
            qosMirrorToIpGroupSubitem
                INTEGER,    
            qosMirrorToLinkGroupName
                OCTET STRING,
            qosMirrorToLinkGroupSubitem
                INTEGER,    
            qosMirrorToInterface
                INTEGER,
            qosMirrorToBlock0Priority
                INTEGER,
            qosMirrorToBlock1Priority
                INTEGER,  
            qosMirrorToBlock2Priority
                INTEGER, 
            qosMirrorToBlock3Priority
                INTEGER,
            qosMirrorToBlock4Priority
                INTEGER,    
            qosMirrorToConfigSequence
                INTEGER,    
            qosMirrorToRunning
                TruthValue,    
            qosMirrorToRowStatus
                RowStatus,
            qosMirrorToBlock5Priority
                INTEGER,
            qosMirrorToBlock6Priority
                INTEGER,  
            qosMirrorToBlock7Priority
                INTEGER, 
            qosMirrorToBlock8Priority
                INTEGER,
            qosMirrorToBlock9Priority
                INTEGER,       
            qosMirrorToBlock10Priority
                INTEGER,
            qosMirrorToBlock11Priority
                INTEGER       
        }
  
    qosMirrorToIndex OBJECT-TYPE
        SYNTAX  INTEGER
        ACCESS  read-only
        STATUS  current
        DESCRIPTION
                "A unique value for each mirror-to QOS.  "
        ::= { qosMirrorToEntry 1 }
  
    qosMirrorToUserGroupName OBJECT-TYPE
        SYNTAX  OCTET STRING (SIZE (0..31))
        ACCESS  read-write
        STATUS  current
        DESCRIPTION
                "the name of the mirror-to QOS user group acl. "
        ::= { qosMirrorToEntry 2 }
  
    qosMirrorToUserGroupSubitem OBJECT-TYPE
        SYNTAX  INTEGER(0..127)
        ACCESS  read-write
        STATUS  current
        DESCRIPTION
                "the number of the mirror-to QOS user group acl subitem. "
        ::= { qosMirrorToEntry 3 }   
  
    qosMirrorToIpGroupName OBJECT-TYPE
        SYNTAX  OCTET STRING (SIZE (0..31))
        ACCESS  read-write
        STATUS  current
        DESCRIPTION
                "the name of the mirror-to QOS ip group acl. "
        ::= { qosMirrorToEntry 4 }
  
    qosMirrorToIpGroupSubitem OBJECT-TYPE
        SYNTAX  INTEGER(0..127)
        ACCESS  read-write
        STATUS  current
        DESCRIPTION
                "the number of the mirror-to QOS ip group acl subitem. "
        ::= { qosMirrorToEntry 5 }      
  
    qosMirrorToLinkGroupName OBJECT-TYPE
        SYNTAX  OCTET STRING (SIZE (0..31))
        ACCESS  read-write
        STATUS  current
        DESCRIPTION
                "the name of the mirror-to QOS link group acl. "
        ::= { qosMirrorToEntry 6 }
  
    qosMirrorToLinkGroupSubitem OBJECT-TYPE
        SYNTAX  INTEGER(0..127)
        ACCESS  read-write
        STATUS  current
        DESCRIPTION
                "the number of the mirror-to QOS link group acl subitem. "
        ::= { qosMirrorToEntry 7 }             
  
    qosMirrorToInterface OBJECT-TYPE
        SYNTAX  INTEGER (1..26)   
        ACCESS  read-write
        STATUS  current
        DESCRIPTION
                "the mirror-to interface of the mirror-to QOS. "
        ::= { qosMirrorToEntry 8 }              

    qosMirrorToBlock0Priority OBJECT-TYPE
        SYNTAX  INTEGER(0..16)
        ACCESS  read-only
        STATUS  current
        DESCRIPTION
                "the block 0 priority of the mirror-to QOS. 16 means no filter rules in the Hardware."
        ::= { qosMirrorToEntry 9 } 

    qosMirrorToBlock1Priority OBJECT-TYPE
        SYNTAX  INTEGER(0..16)
        ACCESS  read-only
        STATUS  current
        DESCRIPTION
                "the block 1 priority of the mirror-to QOS. 16 means no filter rules in the Hardware."
        ::= { qosMirrorToEntry 10 }
        
    qosMirrorToBlock2Priority OBJECT-TYPE
        SYNTAX  INTEGER(0..16)
        ACCESS  read-only
        STATUS  current
        DESCRIPTION
                "the block 2 priority of the mirror-to QOS. 16 means no filter rules in the Hardware."
        ::= { qosMirrorToEntry 11 }
        
    qosMirrorToBlock3Priority OBJECT-TYPE
        SYNTAX  INTEGER(0..16)
        ACCESS  read-only
        STATUS  current
        DESCRIPTION
                "the block 3 priority of the mirror-to QOS. 16 means no filter rules in the Hardware."
        ::= { qosMirrorToEntry 12 }
        
    qosMirrorToBlock4Priority OBJECT-TYPE
        SYNTAX  INTEGER(0..16)
        ACCESS  read-only
        STATUS  current
        DESCRIPTION
                "the block 4 priority of the mirror-to QOS. 16 means no filter rules in the Hardware."
        ::= { qosMirrorToEntry 13 }

    qosMirrorToConfigSequence OBJECT-TYPE
        SYNTAX  INTEGER(1..1024)
        ACCESS  read-only
        STATUS  current
        DESCRIPTION
                "the config sequence of the mirror-to QOS."
        ::= { qosMirrorToEntry 14 }
                
    qosMirrorToRunning OBJECT-TYPE
        SYNTAX   TruthValue
        MAX-ACCESS   read-only
        STATUS   current
        DESCRIPTION
           "the running status of the mirror-to QOS. "                          
       ::= { qosMirrorToEntry 15 } 
       
    qosMirrorToRowStatus OBJECT-TYPE
        SYNTAX      RowStatus
        MAX-ACCESS  read-create
        STATUS      current
        DESCRIPTION
            "This object indicates the status of this entry."
        ::= { qosMirrorToEntry 16 }

    qosMirrorToBlock5Priority OBJECT-TYPE
        SYNTAX  INTEGER(0..16)
        ACCESS  read-only
        STATUS  current
        DESCRIPTION
                "the block 5 priority of the mirror-to QOS. 16 means no filter rules in the Hardware."
                --流镜像在block 5中的优先级，16表示没有过滤规则在硬件中                
        ::= { qosMirrorToEntry 17 }     

    qosMirrorToBlock6Priority OBJECT-TYPE
        SYNTAX  INTEGER(0..16)
        ACCESS  read-only
        STATUS  current
        DESCRIPTION
                "the block 6 priority of the mirror-to QOS. 16 means no filter rules in the Hardware."
                --流镜像在block 6 中的优先级，16表示没有过滤规则在硬件中                
        ::= { qosMirrorToEntry 18 }     

    qosMirrorToBlock7Priority OBJECT-TYPE
        SYNTAX  INTEGER(0..16)
        ACCESS  read-only
        STATUS  current
        DESCRIPTION
                "the block 7 priority of the mirror-to QOS. 16 means no filter rules in the Hardware."
                --流镜像在block 7 中的优先级，16表示没有过滤规则在硬件中                
        ::= { qosMirrorToEntry 19 }         
    
    qosMirrorToBlock8Priority OBJECT-TYPE
        SYNTAX  INTEGER(0..16)
        ACCESS  read-only
        STATUS  current
        DESCRIPTION
                "the block 8 priority of the mirror-to QOS. 16 means no filter rules in the Hardware."
                --流镜像在block 8 中的优先级，16表示没有过滤规则在硬件中                
        ::= { qosMirrorToEntry 20 }         

    qosMirrorToBlock9Priority OBJECT-TYPE
        SYNTAX  INTEGER(0..16)
        ACCESS  read-only
        STATUS  current
        DESCRIPTION
                "the block 9 priority of the mirror-to QOS. 16 means no filter rules in the Hardware."
                --流镜像在block 9 中的优先级，16表示没有过滤规则在硬件中                
        ::= { qosMirrorToEntry 21 }             

    qosMirrorToBlock10Priority OBJECT-TYPE
        SYNTAX  INTEGER(0..16)
        ACCESS  read-only
        STATUS  current
        DESCRIPTION
                "the block 10 priority of the mirror-to QOS. 16 means no filter rules in the Hardware."
                --流镜像在block 10 中的优先级，16表示没有过滤规则在硬件中                
        ::= { qosMirrorToEntry 22 }                 

    qosMirrorToBlock11Priority OBJECT-TYPE
        SYNTAX  INTEGER(0..16)
        ACCESS  read-only
        STATUS  current
        DESCRIPTION
                "the block 11 priority of the mirror-to QOS. 16 means no filter rules in the Hardware."
                --流镜像在block 11 中的优先级，16表示没有过滤规则在硬件中                
        ::= { qosMirrorToEntry 23 }                     
    
   --
   -- the rate-limit QOS 
   --
 
   qosRateLimitTable OBJECT-TYPE
       SYNTAX  SEQUENCE OF QosRateLimitEntry
       ACCESS  not-accessible
       STATUS  current
       DESCRIPTION
               "A list of rate-limit QOS entries. "
       ::= { gbnL2QACL 17 }
 
   qosRateLimitEntry OBJECT-TYPE
       SYNTAX  QosRateLimitEntry
       ACCESS  not-accessible
       STATUS  current
       DESCRIPTION
               "A list of rate-limit QOS entries. "
       INDEX   { qosRateLimitIndex }
       ::= { qosRateLimitTable 1 }
 
   QosRateLimitEntry ::=
       SEQUENCE {
           qosRateLimitIndex
               INTEGER,
           qosRateLimitUserGroupName
               OCTET STRING,
           qosRateLimitUserGroupSubitem
               INTEGER,
           qosRateLimitIpGroupName
               OCTET STRING,
           qosRateLimitIpGroupSubitem
               INTEGER,    
           qosRateLimitLinkGroupName
               OCTET STRING,
           qosRateLimitLinkGroupSubitem
               INTEGER, 
           qosRateLimitIntf
               INTEGER,                  
           qosRateLimitTargetRate
               INTEGER,
           qosRateLimitExceedAction
               INTEGER,    
           qosRateLimitDscpValue
               INTEGER,        
           qosRateLimitBlock0Priority
                INTEGER,
           qosRateLimitBlock1Priority
                INTEGER,  
           qosRateLimitBlock2Priority
                INTEGER, 
           qosRateLimitBlock3Priority
                INTEGER,
           qosRateLimitBlock4Priority
                INTEGER,   
           qosRateLimitConfigSequence
                INTEGER,                         
           qosRateLimitRunning
               TruthValue,       
           qosRateLimitRowStatus
               RowStatus,
           qosRateLimitBlock5Priority
                INTEGER,
           qosRateLimitBlock6Priority
                INTEGER,  
           qosRateLimitBlock7Priority
                INTEGER, 
           qosRateLimitBlock8Priority
                INTEGER,
           qosRateLimitBlock9Priority
                INTEGER,       
           qosRateLimitBlock10Priority
                INTEGER,
           qosRateLimitBlock11Priority
                INTEGER       
       }
 
   qosRateLimitIndex OBJECT-TYPE
       SYNTAX  INTEGER
       ACCESS  read-only
       STATUS  current
       DESCRIPTION
               "A unique value for each rate-limit QOS.  "
       ::= { qosRateLimitEntry 1 }
 
   qosRateLimitUserGroupName OBJECT-TYPE
       SYNTAX  OCTET STRING (SIZE (0..31))
       ACCESS  read-write
       STATUS  current
       DESCRIPTION
               "the name of the rate-limit QOS user group acl. "
       ::= { qosRateLimitEntry 2 }
 
   qosRateLimitUserGroupSubitem OBJECT-TYPE
       SYNTAX  INTEGER(0..127)
       ACCESS  read-write
       STATUS  current
       DESCRIPTION
               "the number of the rate-limit QOS user group acl subitem. "
       ::= { qosRateLimitEntry 3 }   
 
   qosRateLimitIpGroupName OBJECT-TYPE
       SYNTAX  OCTET STRING (SIZE (0..31))
       ACCESS  read-write
       STATUS  current
       DESCRIPTION
               "the name of the rate-limit QOS ip group acl. "
       ::= { qosRateLimitEntry 4 }
 
   qosRateLimitIpGroupSubitem OBJECT-TYPE
       SYNTAX  INTEGER(0..127)
       ACCESS  read-write
       STATUS  current
       DESCRIPTION
               "the number of the rate-limit QOS ip group acl subitem. "
       ::= { qosRateLimitEntry 5 }      
 
   qosRateLimitLinkGroupName OBJECT-TYPE
       SYNTAX  OCTET STRING (SIZE (0..31))
       ACCESS  read-write
       STATUS  current
       DESCRIPTION
               "the name of the rate-limit QOS link group acl. "
       ::= { qosRateLimitEntry 6 }
 
   qosRateLimitLinkGroupSubitem OBJECT-TYPE
       SYNTAX  INTEGER(0..127)
       ACCESS  read-write
       STATUS  current
       DESCRIPTION
               "the number of the rate-limit QOS link group acl subitem. "
       ::= { qosRateLimitEntry 7 }             
    
   qosRateLimitIntf OBJECT-TYPE    
       SYNTAX  INTEGER (1..26)  
       ACCESS  read-write
       STATUS  current
       DESCRIPTION
               "the target rate on this interface. "
       ::= { qosRateLimitEntry 8 }    
    
   qosRateLimitTargetRate OBJECT-TYPE
       SYNTAX  INTEGER (1..100)   
       ACCESS  read-write
       STATUS  current
       DESCRIPTION
               "the target rate of the rate-limit QOS. "
       ::= { qosRateLimitEntry 9 }              
 
   qosRateLimitExceedAction OBJECT-TYPE
       SYNTAX  INTEGER {
                   drop(1),
                   set-dscp-value(2)                          
               }
       ACCESS  read-write
       STATUS  current
       DESCRIPTION
               "the exceed action of the rate-limit QOS. "
       ::= { qosRateLimitEntry 10 } 

   qosRateLimitDscpValue OBJECT-TYPE
       SYNTAX  INTEGER (0..63)   
       ACCESS  read-write
       STATUS  current
       DESCRIPTION
               "the dscp value of the rate-limit QOS. "
       ::= { qosRateLimitEntry 11 } 
  
   qosRateLimitBlock0Priority OBJECT-TYPE
       SYNTAX  INTEGER(0..16)
       ACCESS  read-only
       STATUS  current
       DESCRIPTION
               "the block 0 priority of the rate-limit QOS. 16 means no filter rules in the Hardware."
       ::= { qosRateLimitEntry 12 } 
        
   qosRateLimitBlock1Priority OBJECT-TYPE
       SYNTAX  INTEGER(0..16)
       ACCESS  read-only
       STATUS  current
       DESCRIPTION
               "the block 1 priority of the rate-limit QOS. 16 means no filter rules in the Hardware."
       ::= { qosRateLimitEntry 13 }
        
   qosRateLimitBlock2Priority OBJECT-TYPE
       SYNTAX  INTEGER(0..16)
       ACCESS  read-only
       STATUS  current
       DESCRIPTION
               "the block 2 priority of the rate-limit QOS. 16 means no filter rules in the Hardware."
       ::= { qosRateLimitEntry 14 }
        
   qosRateLimitBlock3Priority OBJECT-TYPE
       SYNTAX  INTEGER(0..16)
       ACCESS  read-only
       STATUS  current
       DESCRIPTION
               "the block 3 priority of the rate-limit QOS. 16 means no filter rules in the Hardware."
       ::= { qosRateLimitEntry 15 }
        
   qosRateLimitBlock4Priority OBJECT-TYPE
       SYNTAX  INTEGER(0..16)
       ACCESS  read-only
       STATUS  current
       DESCRIPTION
               "the block 4 priority of the rate-limit QOS. 16 means no filter rules in the Hardware."
       ::= { qosRateLimitEntry 16 }

   qosRateLimitConfigSequence OBJECT-TYPE
       SYNTAX  INTEGER(1..1024)
       ACCESS  read-only
       STATUS  current
       DESCRIPTION
               "the config sequence of the rate-limit QOS."
       ::= { qosRateLimitEntry 17 }
               
   qosRateLimitRunning OBJECT-TYPE
       SYNTAX   TruthValue
       MAX-ACCESS   read-only
       STATUS   current
       DESCRIPTION
          "the running status of the rate-limit QOS."                          
      ::= { qosRateLimitEntry 18 } 
       
   qosRateLimitRowStatus OBJECT-TYPE
       SYNTAX      RowStatus
       MAX-ACCESS  read-create
       STATUS      current
       DESCRIPTION
           "This object indicates the status of this entry."
       ::= { qosRateLimitEntry 19 }

   qosRateLimitBlock5Priority OBJECT-TYPE
       SYNTAX  INTEGER(0..16)
       ACCESS  read-only
       STATUS  current
       DESCRIPTION
               "the block 5 priority of the rate-limit QOS. 16 means no filter rules in the Hardware."
               --流量监管在block 5 中的优先级，16表示没有过滤规则在硬件中                
       ::= { qosRateLimitEntry 20 }    

   qosRateLimitBlock6Priority OBJECT-TYPE
       SYNTAX  INTEGER(0..16)
       ACCESS  read-only
       STATUS  current
       DESCRIPTION
               "the block 6 priority of the rate-limit QOS. 16 means no filter rules in the Hardware."
               --流量监管在block 6 中的优先级，16表示没有过滤规则在硬件中                
       ::= { qosRateLimitEntry 21 }    

   qosRateLimitBlock7Priority OBJECT-TYPE
       SYNTAX  INTEGER(0..16)
       ACCESS  read-only
       STATUS  current
       DESCRIPTION
               "the block 7 priority of the rate-limit QOS. 16 means no filter rules in the Hardware."
               --流量监管在block 7 中的优先级，16表示没有过滤规则在硬件中                
       ::= { qosRateLimitEntry 22 }     

   qosRateLimitBlock8Priority OBJECT-TYPE
       SYNTAX  INTEGER(0..16)
       ACCESS  read-only
       STATUS  current
       DESCRIPTION
               "the block 8 priority of the rate-limit QOS. 16 means no filter rules in the Hardware."
               --流量监管在block 8 中的优先级，16表示没有过滤规则在硬件中                
       ::= { qosRateLimitEntry 23 }        

   qosRateLimitBlock9Priority OBJECT-TYPE
       SYNTAX  INTEGER(0..16)
       ACCESS  read-only
       STATUS  current
       DESCRIPTION
               "the block 9 priority of the rate-limit QOS. 16 means no filter rules in the Hardware."
               --流量监管在block 9 中的优先级，16表示没有过滤规则在硬件中                
       ::= { qosRateLimitEntry 24 }        

   qosRateLimitBlock10Priority OBJECT-TYPE
       SYNTAX  INTEGER(0..16)
       ACCESS  read-only
       STATUS  current
       DESCRIPTION
               "the block 10 priority of the rate-limit QOS. 16 means no filter rules in the Hardware."
               --流量监管在block 10 中的优先级，16表示没有过滤规则在硬件中                
       ::= { qosRateLimitEntry 25 }  

   qosRateLimitBlock11Priority OBJECT-TYPE
       SYNTAX  INTEGER(0..16)
       ACCESS  read-only
       STATUS  current
       DESCRIPTION
               "the block 11 priority of the rate-limit QOS. 16 means no filter rules in the Hardware."
               --流量监管在block 11 中的优先级，16表示没有过滤规则在硬件中                
       ::= { qosRateLimitEntry 26 }        
       
   --
   -- the traffic-priority QOS 
   --
 
   qosTrafficPriorityTable OBJECT-TYPE
       SYNTAX  SEQUENCE OF QosTrafficPriorityEntry
       ACCESS  not-accessible
       STATUS  current
       DESCRIPTION
               "A list of traffic-priority QOS entries. "
       ::= { gbnL2QACL 18 }
 
   qosTrafficPriorityEntry OBJECT-TYPE
       SYNTAX  QosTrafficPriorityEntry
       ACCESS  not-accessible
       STATUS  current
       DESCRIPTION
               "A list of traffic-priority QOS entries. "
       INDEX   { qosTrafficPriorityIndex }
       ::= { qosTrafficPriorityTable 1 }
 
   QosTrafficPriorityEntry ::=
       SEQUENCE {
           qosTrafficPriorityIndex
               INTEGER,
           qosTrafficPriorityUserGroupName
               OCTET STRING,
           qosTrafficPriorityUserGroupSubitem
               INTEGER,
           qosTrafficPriorityIpGroupName
               OCTET STRING,
           qosTrafficPriorityIpGroupSubitem
               INTEGER,    
           qosTrafficPriorityLinkGroupName
               OCTET STRING,
           qosTrafficPriorityLinkGroupSubitem
               INTEGER,    
           qosTrafficPriorityDscp
               INTEGER,
           qosTrafficPriorityIpPrecedence
               INTEGER,    
           qosTrafficPriorityCos
               INTEGER, 
           qosTrafficPriorityLocalPrecedence
               INTEGER,
           qosTrafficPriorityBlock0Priority
               INTEGER,
           qosTrafficPriorityBlock1Priority
               INTEGER,  
           qosTrafficPriorityBlock2Priority
               INTEGER, 
           qosTrafficPriorityBlock3Priority
               INTEGER,
           qosTrafficPriorityBlock4Priority
               INTEGER,     
           qosTrafficPriorityConfigSequence
               INTEGER,        
           qosTrafficPriorityRunning
               TruthValue,      
           qosTrafficPriorityRowStatus
               RowStatus,
           qosTrafficPriorityBlock5Priority
               INTEGER,
           qosTrafficPriorityBlock6Priority
               INTEGER,  
           qosTrafficPriorityBlock7Priority
               INTEGER, 
           qosTrafficPriorityBlock8Priority
               INTEGER,
           qosTrafficPriorityBlock9Priority
               INTEGER,         
           qosTrafficPriorityBlock10Priority
               INTEGER,
           qosTrafficPriorityBlock11Priority
               INTEGER  
       }
 
   qosTrafficPriorityIndex OBJECT-TYPE
       SYNTAX  INTEGER
       ACCESS  read-only
       STATUS  current
       DESCRIPTION
               "A unique value for each traffic-priority QOS.  "
       ::= { qosTrafficPriorityEntry 1 }
 
   qosTrafficPriorityUserGroupName OBJECT-TYPE
       SYNTAX  OCTET STRING (SIZE (0..31))
       ACCESS  read-write
       STATUS  current
       DESCRIPTION
               "the name of the traffic-priority QOS user group acl. "
       ::= { qosTrafficPriorityEntry 2 }
 
   qosTrafficPriorityUserGroupSubitem OBJECT-TYPE
       SYNTAX  INTEGER(0..127)
       ACCESS  read-write
       STATUS  current
       DESCRIPTION
               "the number of the traffic-priority QOS user group acl subitem. "
       ::= { qosTrafficPriorityEntry 3 }   
 
   qosTrafficPriorityIpGroupName OBJECT-TYPE
       SYNTAX  OCTET STRING (SIZE (0..31))
       ACCESS  read-write
       STATUS  current
       DESCRIPTION
               "the name of the traffic-priority QOS ip group acl. "
       ::= { qosTrafficPriorityEntry 4 }
 
   qosTrafficPriorityIpGroupSubitem OBJECT-TYPE
       SYNTAX  INTEGER(0..127)
       ACCESS  read-write
       STATUS  current
       DESCRIPTION
               "the number of the traffic-priority QOS ip group acl subitem. "
       ::= { qosTrafficPriorityEntry 5 }      
 
   qosTrafficPriorityLinkGroupName OBJECT-TYPE
       SYNTAX  OCTET STRING (SIZE (0..31))
       ACCESS  read-write
       STATUS  current
       DESCRIPTION
               "the name of the traffic-priority QOS link group acl. "
       ::= { qosTrafficPriorityEntry 6 }
 
   qosTrafficPriorityLinkGroupSubitem OBJECT-TYPE
       SYNTAX  INTEGER(0..127)
       ACCESS  read-write
       STATUS  current
       DESCRIPTION
               "the number of the traffic-priority QOS link group acl subitem. "
       ::= { qosTrafficPriorityEntry 7 }             
 
   qosTrafficPriorityDscp OBJECT-TYPE
       SYNTAX  INTEGER (0..63)   
       ACCESS  read-write
       STATUS  current
       DESCRIPTION
               "the DSCP of the traffic-priority QOS. "
       ::= { qosTrafficPriorityEntry 8 }              
 
   qosTrafficPriorityIpPrecedence OBJECT-TYPE
       SYNTAX  INTEGER (0..7)   
       ACCESS  read-write
       STATUS  current
       DESCRIPTION
               "the IP precedence of the traffic-priority QOS. "
       ::= { qosTrafficPriorityEntry 9 }
 
   qosTrafficPriorityCos OBJECT-TYPE
       SYNTAX  INTEGER (0..7)   
       ACCESS  read-write
       STATUS  current
       DESCRIPTION
               "the COS of the traffic-priority QOS. "
       ::= { qosTrafficPriorityEntry 10 }
 
   qosTrafficPriorityLocalPrecedence OBJECT-TYPE
       SYNTAX  INTEGER (0..7)   
       ACCESS  read-write
       STATUS  current
       DESCRIPTION
               "the local precedence of the traffic-priority QOS. "
       ::= { qosTrafficPriorityEntry 11 }

   qosTrafficPriorityBlock0Priority OBJECT-TYPE
       SYNTAX  INTEGER(0..16)
       ACCESS  read-only
       STATUS  current
       DESCRIPTION
               "the block 0 priority of the traffic-priority QOS. 16 means no filter rules in the Hardware."
       ::= { qosTrafficPriorityEntry 12 } 
        
   qosTrafficPriorityBlock1Priority OBJECT-TYPE
       SYNTAX  INTEGER(0..16)
       ACCESS  read-only
       STATUS  current
       DESCRIPTION
               "the block 1 priority of the traffic-priority QOS. 16 means no filter rules in the Hardware."
       ::= { qosTrafficPriorityEntry 13 }
       
   qosTrafficPriorityBlock2Priority OBJECT-TYPE
       SYNTAX  INTEGER(0..16)
       ACCESS  read-only
       STATUS  current
       DESCRIPTION
               "the block 2 priority of the traffic-priority QOS. 16 means no filter rules in the Hardware."
       ::= { qosTrafficPriorityEntry 14 }
        
   qosTrafficPriorityBlock3Priority OBJECT-TYPE
       SYNTAX  INTEGER(0..16)
       ACCESS  read-only
       STATUS  current
       DESCRIPTION
               "the block 3 priority of the traffic-priority QOS. 16 means no filter rules in the Hardware."
       ::= { qosTrafficPriorityEntry 15 }
       
   qosTrafficPriorityBlock4Priority OBJECT-TYPE
       SYNTAX  INTEGER(0..16)
       ACCESS  read-only
       STATUS  current
       DESCRIPTION
               "the block 4 priority of the traffic-priority QOS. 16 means no filter rules in the Hardware."
       ::= { qosTrafficPriorityEntry 16 }

   qosTrafficPriorityConfigSequence OBJECT-TYPE
       SYNTAX  INTEGER(1..1024)
       ACCESS  read-only
       STATUS  current
       DESCRIPTION
               "the config sequence of the traffic-priority QOS."
       ::= { qosTrafficPriorityEntry 17 }
              
   qosTrafficPriorityRunning OBJECT-TYPE
       SYNTAX   TruthValue
       MAX-ACCESS   read-only
       STATUS   current
       DESCRIPTION
           "the running status of the traffic-priority QOS."                          
       ::= { qosTrafficPriorityEntry 18 } 
       
   qosTrafficPriorityRowStatus OBJECT-TYPE
       SYNTAX      RowStatus
       MAX-ACCESS  read-create
       STATUS      current
       DESCRIPTION
           "This object indicates the status of this entry."
       ::= { qosTrafficPriorityEntry 19 }

   qosTrafficPriorityBlock5Priority OBJECT-TYPE
       SYNTAX  INTEGER(0..16)
       ACCESS  read-only
       STATUS  current
       DESCRIPTION
               "the block 5 priority of the traffic-priority QOS. 16 means no filter rules in the Hardware."
               --报文优先级在block 5 中的优先级，16表示没有过滤规则在硬件中                
       ::= { qosTrafficPriorityEntry 20 }      

   qosTrafficPriorityBlock6Priority OBJECT-TYPE
       SYNTAX  INTEGER(0..16)
       ACCESS  read-only
       STATUS  current
       DESCRIPTION
               "the block 6 priority of the traffic-priority QOS. 16 means no filter rules in the Hardware."
               --报文优先级在block 6 中的优先级，16表示没有过滤规则在硬件中                
       ::= { qosTrafficPriorityEntry 21 }       

   qosTrafficPriorityBlock7Priority OBJECT-TYPE
       SYNTAX  INTEGER(0..16)
       ACCESS  read-only
       STATUS  current
       DESCRIPTION
               "the block 7 priority of the traffic-priority QOS. 16 means no filter rules in the Hardware."
               --报文优先级在block 7 中的优先级，16表示没有过滤规则在硬件中                
       ::= { qosTrafficPriorityEntry 22 }       

   qosTrafficPriorityBlock8Priority OBJECT-TYPE
       SYNTAX  INTEGER(0..16)
       ACCESS  read-only
       STATUS  current
       DESCRIPTION
               "the block 8 priority of the traffic-priority QOS. 16 means no filter rules in the Hardware."
               --报文优先级在block 8 中的优先级，16表示没有过滤规则在硬件中                
       ::= { qosTrafficPriorityEntry 23 }       

   qosTrafficPriorityBlock9Priority OBJECT-TYPE
       SYNTAX  INTEGER(0..16)
       ACCESS  read-only
       STATUS  current
       DESCRIPTION
               "the block 9 priority of the traffic-priority QOS. 16 means no filter rules in the Hardware."
               --报文优先级在block 9 中的优先级，16表示没有过滤规则在硬件中                
       ::= { qosTrafficPriorityEntry 24 }       

   qosTrafficPriorityBlock10Priority OBJECT-TYPE
       SYNTAX  INTEGER(0..16)
       ACCESS  read-only
       STATUS  current
       DESCRIPTION
               "the block 10 priority of the traffic-priority QOS. 16 means no filter rules in the Hardware."
               --报文优先级在block 10 中的优先级，16表示没有过滤规则在硬件中                
       ::= { qosTrafficPriorityEntry 25 }    

   qosTrafficPriorityBlock11Priority OBJECT-TYPE
       SYNTAX  INTEGER(0..16)
       ACCESS  read-only
       STATUS  current
       DESCRIPTION
               "the block 11 priority of the traffic-priority QOS. 16 means no filter rules in the Hardware."
               --报文优先级在block 11 中的优先级，16表示没有过滤规则在硬件中                
       ::= { qosTrafficPriorityEntry 26 }       
 
   --
   -- the traffic redirect QOS 
   --
 
   qosTrafficRedirectTable OBJECT-TYPE
       SYNTAX  SEQUENCE OF QosTrafficRedirectEntry
       ACCESS  not-accessible
       STATUS  current
       DESCRIPTION
               "A list of traffic-redirect QOS entries. "
       ::= { gbnL2QACL 19 }
 
   qosTrafficRedirectEntry OBJECT-TYPE
       SYNTAX  QosTrafficRedirectEntry
       ACCESS  not-accessible
       STATUS  current
       DESCRIPTION
               "A list of traffic-redirect QOS entries. "
       INDEX   { qosTrafficRedirectIndex }
       ::= { qosTrafficRedirectTable 1 }
 
   QosTrafficRedirectEntry ::=
       SEQUENCE {
           qosTrafficRedirectIndex
               INTEGER,
           qosTrafficRedirectUserGroupName
               OCTET STRING,
           qosTrafficRedirectUserGroupSubitem
               INTEGER,
           qosTrafficRedirectIpGroupName
               OCTET STRING,
           qosTrafficRedirectIpGroupSubitem
               INTEGER,    
           qosTrafficRedirectLinkGroupName
               OCTET STRING,
           qosTrafficRedirectLinkGroupSubitem
               INTEGER,    
           qosTrafficRedirectInterface
               INTEGER,
           qosTrafficRedirectBlock0Priority
               INTEGER,
           qosTrafficRedirectBlock1Priority
               INTEGER,  
           qosTrafficRedirectBlock2Priority
               INTEGER, 
           qosTrafficRedirectBlock3Priority
               INTEGER,
           qosTrafficRedirectBlock4Priority
               INTEGER,
           qosTrafficRedirectConfigSequence
               INTEGER,    
           qosTrafficRedirectRunning
               TruthValue,     
           qosTrafficRedirectRowStatus
               RowStatus,
           qosTrafficRedirectBlock5Priority
               INTEGER,
           qosTrafficRedirectBlock6Priority
               INTEGER,  
           qosTrafficRedirectBlock7Priority
               INTEGER, 
           qosTrafficRedirectBlock8Priority
               INTEGER,
           qosTrafficRedirectBlock9Priority
               INTEGER,    
           qosTrafficRedirectBlock10Priority
               INTEGER,
           qosTrafficRedirectBlock11Priority
               INTEGER    
       }
 
   qosTrafficRedirectIndex OBJECT-TYPE
       SYNTAX  INTEGER
       ACCESS  read-only
       STATUS  current
       DESCRIPTION
               "A unique value for each traffic-redirect QOS.  "
       ::= { qosTrafficRedirectEntry 1 }
 
   qosTrafficRedirectUserGroupName OBJECT-TYPE
       SYNTAX  OCTET STRING (SIZE (0..31))
       ACCESS  read-write
       STATUS  current
       DESCRIPTION
               "the name of the traffic-redirect QOS user group acl. "
       ::= { qosTrafficRedirectEntry 2 }
 
   qosTrafficRedirectUserGroupSubitem OBJECT-TYPE
       SYNTAX  INTEGER(0..127)
       ACCESS  read-write
       STATUS  current
       DESCRIPTION
               "the number of the traffic-redirect QOS user group acl subitem. "
       ::= { qosTrafficRedirectEntry 3 }   
 
   qosTrafficRedirectIpGroupName OBJECT-TYPE
       SYNTAX  OCTET STRING (SIZE (0..31))
       ACCESS  read-write
       STATUS  current
       DESCRIPTION
               "the name of the traffic-redirect QOS ip group acl. "
       ::= { qosTrafficRedirectEntry 4 }
 
   qosTrafficRedirectIpGroupSubitem OBJECT-TYPE
       SYNTAX  INTEGER(0..127)
       ACCESS  read-write
       STATUS  current
       DESCRIPTION
               "the number of the traffic-redirect QOS ip group acl subitem. "
       ::= { qosTrafficRedirectEntry 5 }      
 
   qosTrafficRedirectLinkGroupName OBJECT-TYPE
       SYNTAX  OCTET STRING (SIZE (0..31))
       ACCESS  read-write
       STATUS  current
       DESCRIPTION
               "the name of the traffic-redirect QOS link group acl. "
       ::= { qosTrafficRedirectEntry 6 }
 
   qosTrafficRedirectLinkGroupSubitem OBJECT-TYPE
       SYNTAX  INTEGER(0..127)
       ACCESS  read-write
       STATUS  current
       DESCRIPTION
               "the number of the traffic-redirect QOS link group acl subitem. "
       ::= { qosTrafficRedirectEntry 7 }             
 
   qosTrafficRedirectInterface OBJECT-TYPE
       SYNTAX  INTEGER (1..28)   
       ACCESS  read-write
       STATUS  current
       DESCRIPTION
               "the redirect interface of the traffic-redirect QOS.1－24 for fast-ethernet port 1－24，25－26 for giga-ethernet port 1－2，28 for CPU port，27 is invaild value. "
       ::= { qosTrafficRedirectEntry 8 }              

   qosTrafficRedirectBlock0Priority OBJECT-TYPE
       SYNTAX  INTEGER(0..16)
       ACCESS  read-only
       STATUS  current
       DESCRIPTION
               "the block 0 priority of the traffic-redirect QOS. 16 means no filter rules in the Hardware."
       ::= { qosTrafficRedirectEntry 9 } 
        
   qosTrafficRedirectBlock1Priority OBJECT-TYPE
       SYNTAX  INTEGER(0..16)
       ACCESS  read-only
       STATUS  current
       DESCRIPTION
               "the block 1 priority of the traffic-redirect QOS. 16 means no filter rules in the Hardware."
       ::= { qosTrafficRedirectEntry 10 }
       
   qosTrafficRedirectBlock2Priority OBJECT-TYPE
       SYNTAX  INTEGER(0..16)
       ACCESS  read-only
       STATUS  current
       DESCRIPTION
               "the block 2 priority of the traffic-redirect QOS. 16 means no filter rules in the Hardware."
       ::= { qosTrafficRedirectEntry 11 }
        
   qosTrafficRedirectBlock3Priority OBJECT-TYPE
       SYNTAX  INTEGER(0..16)
       ACCESS  read-only
       STATUS  current
       DESCRIPTION
               "the block 3 priority of the traffic-redirect QOS. 16 means no filter rules in the Hardware."
       ::= { qosTrafficRedirectEntry 12 }

   qosTrafficRedirectBlock4Priority OBJECT-TYPE
       SYNTAX  INTEGER(0..16)
       ACCESS  read-only
       STATUS  current
       DESCRIPTION
               "the block 4 priority of the traffic-redirect QOS. 16 means no filter rules in the Hardware."
       ::= { qosTrafficRedirectEntry 13 }

   qosTrafficRedirectConfigSequence OBJECT-TYPE
       SYNTAX  INTEGER(1..1024)
       ACCESS  read-only
       STATUS  current
       DESCRIPTION
               "the config sequence of the traffic-redirect QOS."
       ::= { qosTrafficRedirectEntry 14 }
              
   qosTrafficRedirectRunning OBJECT-TYPE
        SYNTAX   TruthValue
        MAX-ACCESS   read-only
        STATUS   current
        DESCRIPTION
           "the running status of the traffic-redirect QOS."                          
       ::= { qosTrafficRedirectEntry 15 } 
       
   qosTrafficRedirectRowStatus OBJECT-TYPE
       SYNTAX      RowStatus
       MAX-ACCESS  read-create
       STATUS      current
       DESCRIPTION
           "This object indicates the status of this entry."
       ::= { qosTrafficRedirectEntry 16 }
 
   qosTrafficRedirectBlock5Priority OBJECT-TYPE
       SYNTAX  INTEGER(0..16)
       ACCESS  read-only
       STATUS  current
       DESCRIPTION
               "the block 5 priority of the traffic-redirect QOS. 16 means no filter rules in the Hardware."
               --报文重定向在block 5 中的优先级，16表示没有过滤规则在硬件中                
       ::= { qosTrafficRedirectEntry 17 } 

   qosTrafficRedirectBlock6Priority OBJECT-TYPE
       SYNTAX  INTEGER(0..16)
       ACCESS  read-only
       STATUS  current
       DESCRIPTION
               "the block 6 priority of the traffic-redirect QOS. 16 means no filter rules in the Hardware."
               --报文重定向在block 6 中的优先级，16表示没有过滤规则在硬件中                
       ::= { qosTrafficRedirectEntry 18 } 

   qosTrafficRedirectBlock7Priority OBJECT-TYPE
       SYNTAX  INTEGER(0..16)
       ACCESS  read-only
       STATUS  current
       DESCRIPTION
               "the block 7 priority of the traffic-redirect QOS. 16 means no filter rules in the Hardware."
               --报文重定向在block 7 中的优先级，16表示没有过滤规则在硬件中                
       ::= { qosTrafficRedirectEntry 19 } 

   qosTrafficRedirectBlock8Priority OBJECT-TYPE
       SYNTAX  INTEGER(0..16)
       ACCESS  read-only
       STATUS  current
       DESCRIPTION
               "the block 8 priority of the traffic-redirect QOS. 16 means no filter rules in the Hardware."
               --报文重定向在block 8 中的优先级，16表示没有过滤规则在硬件中                
       ::= { qosTrafficRedirectEntry 20 } 

   qosTrafficRedirectBlock9Priority OBJECT-TYPE
       SYNTAX  INTEGER(0..16)
       ACCESS  read-only
       STATUS  current
       DESCRIPTION
               "the block 9 priority of the traffic-redirect QOS. 16 means no filter rules in the Hardware."
               --报文重定向在block 9 中的优先级，16表示没有过滤规则在硬件中                
       ::= { qosTrafficRedirectEntry 21 } 

   qosTrafficRedirectBlock10Priority OBJECT-TYPE
       SYNTAX  INTEGER(0..16)
       ACCESS  read-only
       STATUS  current
       DESCRIPTION
               "the block 10 priority of the traffic-redirect QOS. 16 means no filter rules in the Hardware."
               --报文重定向在block 10 中的优先级，16表示没有过滤规则在硬件中                
       ::= { qosTrafficRedirectEntry 22 } 

   qosTrafficRedirectBlock11Priority OBJECT-TYPE
       SYNTAX  INTEGER(0..16)
       ACCESS  read-only
       STATUS  current
       DESCRIPTION
               "the block 11 priority of the traffic-redirect QOS. 16 means no filter rules in the Hardware."
               --报文重定向在block 11 中的优先级，16表示没有过滤规则在硬件中                
       ::= { qosTrafficRedirectEntry 23 } 
                               
   --
   -- the traffic statistics QOS 
   --
 
   qosTrafficStatisticsTable OBJECT-TYPE
       SYNTAX  SEQUENCE OF QosTrafficStatisticsEntry
       ACCESS  not-accessible
       STATUS  current
       DESCRIPTION
               "A list of traffic-statistics QOS entries. "
       ::= { gbnL2QACL 20 }
 
   qosTrafficStatisticsEntry OBJECT-TYPE
       SYNTAX  QosTrafficStatisticsEntry
       ACCESS  not-accessible
       STATUS  current
       DESCRIPTION
               "A list of traffic-statistics QOS entries. "
       INDEX   { qosTrafficStatisticsIndex }
       ::= { qosTrafficStatisticsTable 1 }
 
   QosTrafficStatisticsEntry ::=
       SEQUENCE {
           qosTrafficStatisticsIndex
               INTEGER,
           qosTrafficStatisticsUserGroupName
               OCTET STRING,
           qosTrafficStatisticsUserGroupSubitem
               INTEGER,
           qosTrafficStatisticsIpGroupName
               OCTET STRING,
           qosTrafficStatisticsIpGroupSubitem
               INTEGER,    
           qosTrafficStatisticsLinkGroupName
               OCTET STRING,
           qosTrafficStatisticsLinkGroupSubitem
               INTEGER,  
           qosTrafficStatisticsBlock0Priority
               INTEGER,
           qosTrafficStatisticsBlock1Priority
               INTEGER,  
           qosTrafficStatisticsBlock2Priority
               INTEGER, 
           qosTrafficStatisticsBlock3Priority
               INTEGER,
           qosTrafficStatisticsBlock4Priority
               INTEGER,   
           qosTrafficStatisticsConfigSequence
               INTEGER,     
           qosTrafficStatisticsRunning
               TruthValue,      
           qosTrafficStatisticsRowStatus
               RowStatus,
           qosTrafficStatisticsCounter
               Integer32,
           qosTrafficStatisticsBlock5Priority
               INTEGER,
           qosTrafficStatisticsBlock6Priority
               INTEGER,  
           qosTrafficStatisticsBlock7Priority
               INTEGER, 
           qosTrafficStatisticsBlock8Priority
               INTEGER,
           qosTrafficStatisticsBlock9Priority
               INTEGER,       
           qosTrafficStatisticsBlock10Priority
               INTEGER,
           qosTrafficStatisticsBlock11Priority
               INTEGER      
       }
 
   qosTrafficStatisticsIndex OBJECT-TYPE
       SYNTAX  INTEGER
       ACCESS  read-only
       STATUS  current
       DESCRIPTION
               "A unique value for each traffic-statistics QOS.  "
       ::= { qosTrafficStatisticsEntry 1 }
 
   qosTrafficStatisticsUserGroupName OBJECT-TYPE
       SYNTAX  OCTET STRING (SIZE (0..31))
       ACCESS  read-write
       STATUS  current
       DESCRIPTION
               "the name of the traffic-statistics QOS user group acl. "
       ::= { qosTrafficStatisticsEntry 2 }
 
   qosTrafficStatisticsUserGroupSubitem OBJECT-TYPE
       SYNTAX  INTEGER(0..127)
       ACCESS  read-write
       STATUS  current
       DESCRIPTION
               "the number of the traffic-statistics QOS user group acl subitem. "
       ::= { qosTrafficStatisticsEntry 3 }   
 
   qosTrafficStatisticsIpGroupName OBJECT-TYPE
       SYNTAX  OCTET STRING (SIZE (0..31))
       ACCESS  read-write
       STATUS  current
       DESCRIPTION
               "the name of the traffic-statistics QOS ip group acl. "
       ::= { qosTrafficStatisticsEntry 4 }
 
   qosTrafficStatisticsIpGroupSubitem OBJECT-TYPE
       SYNTAX  INTEGER(0..127)
       ACCESS  read-write
       STATUS  current
       DESCRIPTION
               "the number of the traffic-statistics QOS ip group acl subitem. "
       ::= { qosTrafficStatisticsEntry 5 }      
 
   qosTrafficStatisticsLinkGroupName OBJECT-TYPE
       SYNTAX  OCTET STRING (SIZE (0..31))
       ACCESS  read-write
       STATUS  current
       DESCRIPTION
               "the name of the traffic-statistics QOS link group acl. "
       ::= { qosTrafficStatisticsEntry 6 }
 
   qosTrafficStatisticsLinkGroupSubitem OBJECT-TYPE
       SYNTAX  INTEGER(0..127)
       ACCESS  read-write
       STATUS  current
       DESCRIPTION
               "the number of the traffic-statistics QOS link group acl subitem. "
       ::= { qosTrafficStatisticsEntry 7 }                                  

   qosTrafficStatisticsBlock0Priority OBJECT-TYPE
       SYNTAX  INTEGER(0..16)
       ACCESS  read-only
       STATUS  current
       DESCRIPTION
               "the block 0 priority of the traffic-statistics QOS. 16 means no filter rules in the Hardware."
       ::= { qosTrafficStatisticsEntry 8 } 
        
   qosTrafficStatisticsBlock1Priority OBJECT-TYPE
       SYNTAX  INTEGER(0..16)
       ACCESS  read-only
       STATUS  current
       DESCRIPTION
               "the block 1 priority of the traffic-statistics QOS. 16 means no filter rules in the Hardware."
       ::= { qosTrafficStatisticsEntry 9 }
       
   qosTrafficStatisticsBlock2Priority OBJECT-TYPE
       SYNTAX  INTEGER(0..16)
       ACCESS  read-only
       STATUS  current
       DESCRIPTION
               "the block 2 priority of the traffic-statistics QOS. 16 means no filter rules in the Hardware."
       ::= { qosTrafficStatisticsEntry 10 }
        
   qosTrafficStatisticsBlock3Priority OBJECT-TYPE
       SYNTAX  INTEGER(0..16)
       ACCESS  read-only
       STATUS  current
       DESCRIPTION
               "the block 3 priority of the traffic-statistics QOS. 16 means no filter rules in the Hardware."
       ::= { qosTrafficStatisticsEntry 11 }

   qosTrafficStatisticsBlock4Priority OBJECT-TYPE
       SYNTAX  INTEGER(0..16)
       ACCESS  read-only
       STATUS  current
       DESCRIPTION
               "the block 4 priority of the traffic-statistics QOS. 16 means no filter rules in the Hardware."
       ::= { qosTrafficStatisticsEntry 12 }
       
   qosTrafficStatisticsConfigSequence OBJECT-TYPE
       SYNTAX  INTEGER(1..1024)
       ACCESS  read-only
       STATUS  current
       DESCRIPTION
               "the config sequence of the traffic-statistics QOS."
       ::= { qosTrafficStatisticsEntry 13 }
           
   qosTrafficStatisticsRunning OBJECT-TYPE
        SYNTAX   TruthValue
        MAX-ACCESS   read-only
        STATUS   current
        DESCRIPTION
           "the running status of the traffic-statistics QOS."                          
       ::= { qosTrafficStatisticsEntry 14 } 
       
   qosTrafficStatisticsRowStatus OBJECT-TYPE
       SYNTAX      RowStatus
       MAX-ACCESS  read-create
       STATUS      current
       DESCRIPTION
           "This object indicates the status of this entry."
       ::= { qosTrafficStatisticsEntry 15 }
       
   qosTrafficStatisticsCounter OBJECT-TYPE
       SYNTAX      Integer32
       MAX-ACCESS  read-create
       STATUS      current
       DESCRIPTION
           "This object indicates the value of the counter."
       ::= { qosTrafficStatisticsEntry 16 }      

   qosTrafficStatisticsBlock5Priority OBJECT-TYPE
       SYNTAX  INTEGER(0..16)
       ACCESS  read-only
       STATUS  current
       DESCRIPTION
               "the block 5 priority of the traffic-statistics QOS. 16 means no filter rules in the Hardware."
               --流量统计在block 5 中的优先级，16表示没有过滤规则在硬件中                
       ::= { qosTrafficStatisticsEntry 17 }    

   qosTrafficStatisticsBlock6Priority OBJECT-TYPE
       SYNTAX  INTEGER(0..16)
       ACCESS  read-only
       STATUS  current
       DESCRIPTION
               "the block 6 priority of the traffic-statistics QOS. 16 means no filter rules in the Hardware."
               --流量统计在block 6 中的优先级，16表示没有过滤规则在硬件中                
       ::= { qosTrafficStatisticsEntry 18 }   

   qosTrafficStatisticsBlock7Priority OBJECT-TYPE
       SYNTAX  INTEGER(0..16)
       ACCESS  read-only
       STATUS  current
       DESCRIPTION
               "the block 7 priority of the traffic-statistics QOS. 16 means no filter rules in the Hardware."
               --流量统计在block 7 中的优先级，16表示没有过滤规则在硬件中                
       ::= { qosTrafficStatisticsEntry 19 }   

   qosTrafficStatisticsBlock8Priority OBJECT-TYPE
       SYNTAX  INTEGER(0..16)
       ACCESS  read-only
       STATUS  current
       DESCRIPTION
               "the block 8 priority of the traffic-statistics QOS. 16 means no filter rules in the Hardware."
               --流量统计在block 8 中的优先级，16表示没有过滤规则在硬件中                
       ::= { qosTrafficStatisticsEntry 20 }        

   qosTrafficStatisticsBlock9Priority OBJECT-TYPE
       SYNTAX  INTEGER(0..16)
       ACCESS  read-only
       STATUS  current
       DESCRIPTION
               "the block 9 priority of the traffic-statistics QOS. 16 means no filter rules in the Hardware."
               --流量统计在block 9 中的优先级，16表示没有过滤规则在硬件中                
       ::= { qosTrafficStatisticsEntry 21 }        

   qosTrafficStatisticsBlock10Priority OBJECT-TYPE
       SYNTAX  INTEGER(0..16)
       ACCESS  read-only
       STATUS  current
       DESCRIPTION
               "the block 10 priority of the traffic-statistics QOS. 16 means no filter rules in the Hardware."
               --流量统计在block 10 中的优先级，16表示没有过滤规则在硬件中                
       ::= { qosTrafficStatisticsEntry 22 }      

   qosTrafficStatisticsBlock11Priority OBJECT-TYPE
       SYNTAX  INTEGER(0..16)
       ACCESS  read-only
       STATUS  current
       DESCRIPTION
               "the block 11 priority of the traffic-statistics QOS. 16 means no filter rules in the Hardware."
               --流量统计在block 11 中的优先级，16表示没有过滤规则在硬件中                
       ::= { qosTrafficStatisticsEntry 23 }        
   
   --
   -- the line-rate QOS 
   --
 
   qosLineRateTable OBJECT-TYPE
       SYNTAX  SEQUENCE OF QosLineRateEntry
       ACCESS  not-accessible
       STATUS  current
       DESCRIPTION
               "A list of line-rate QOS entries. "
       ::= { gbnL2QACL 21 }
 
   qosLineRateEntry OBJECT-TYPE
       SYNTAX  QosLineRateEntry
       ACCESS  not-accessible
       STATUS  current
       DESCRIPTION
               "A list of line-rate QOS entries. "
       INDEX   { qosLineRateInterface }
       ::= { qosLineRateTable 1 }
 
   QosLineRateEntry ::=
       SEQUENCE {
           qosLineRateInterface
               INTEGER,                  
           qosLineRateTargetRate
               INTEGER,                  
           qosLineRateRowStatus
               RowStatus                  
       }
 
   qosLineRateInterface OBJECT-TYPE
       SYNTAX  INTEGER (1..26)
       ACCESS  read-only
       STATUS  current
       DESCRIPTION
               "the line rate interface.  "
       ::= { qosLineRateEntry 1 }
       
   qosLineRateTargetRate OBJECT-TYPE
       SYNTAX  INTEGER (1..100)   
       ACCESS  read-write
       STATUS  current
       DESCRIPTION
               "the target rate of the line-rate QOS. "
       ::= { qosLineRateEntry 2 }  
 
   --
   -- the traffic copy to cpu QOS 
   --
 
   qosTrafficCopyToCpuTable OBJECT-TYPE
       SYNTAX  SEQUENCE OF QosTrafficCopyToCpuEntry
       ACCESS  not-accessible
       STATUS  current
       DESCRIPTION
               "A list of traffic-copy-to-cpu QOS entries. "
       ::= { gbnL2QACL 22 }
 
   qosTrafficCopyToCpuEntry OBJECT-TYPE
       SYNTAX  QosTrafficCopyToCpuEntry
       ACCESS  not-accessible
       STATUS  current
       DESCRIPTION
               "A list of traffic-copy-to-cpu QOS entries. "
       INDEX   { qosTrafficCopyToCpuIndex }
       ::= { qosTrafficCopyToCpuTable 1 }
 
   QosTrafficCopyToCpuEntry ::=
       SEQUENCE {
           qosTrafficCopyToCpuIndex
               INTEGER,
           qosTrafficCopyToCpuUserGroupName
               OCTET STRING,
           qosTrafficCopyToCpuUserGroupSubitem
               INTEGER,
           qosTrafficCopyToCpuIpGroupName
               OCTET STRING,
           qosTrafficCopyToCpuIpGroupSubitem
               INTEGER,    
           qosTrafficCopyToCpuLinkGroupName
               OCTET STRING,
           qosTrafficCopyToCpuLinkGroupSubitem
               INTEGER,               
           qosTrafficCopyToCpuBlock0Priority
               INTEGER,
           qosTrafficCopyToCpuBlock1Priority
               INTEGER,  
           qosTrafficCopyToCpuBlock2Priority
               INTEGER, 
           qosTrafficCopyToCpuBlock3Priority
               INTEGER,
           qosTrafficCopyToCpuBlock4Priority
               INTEGER,
           qosTrafficCopyToCpuConfigSequence
               INTEGER,    
           qosTrafficCopyToCpuRunning
               TruthValue,     
           qosTrafficCopyToCpuRowStatus
               RowStatus,
           qosTrafficCopyToCpuBlock5Priority
               INTEGER,
           qosTrafficCopyToCpuBlock6Priority
               INTEGER,  
           qosTrafficCopyToCpuBlock7Priority
               INTEGER, 
           qosTrafficCopyToCpuBlock8Priority
               INTEGER,
           qosTrafficCopyToCpuBlock9Priority
               INTEGER,
           qosTrafficCopyToCpuBlock10Priority
               INTEGER,
           qosTrafficCopyToCpuBlock11Priority
               INTEGER    
       }
 
   qosTrafficCopyToCpuIndex OBJECT-TYPE
       SYNTAX  INTEGER
       ACCESS  read-only
       STATUS  current
       DESCRIPTION
               "A unique value for each traffic-copy-to-cpu QOS.  "
       ::= { qosTrafficCopyToCpuEntry 1 }
 
   qosTrafficCopyToCpuUserGroupName OBJECT-TYPE
       SYNTAX  OCTET STRING (SIZE (0..31))
       ACCESS  read-write
       STATUS  current
       DESCRIPTION
               "the name of the traffic-copy-to-cpu QOS user group acl. "
       ::= { qosTrafficCopyToCpuEntry 2 }
 
   qosTrafficCopyToCpuUserGroupSubitem OBJECT-TYPE
       SYNTAX  INTEGER(0..127)
       ACCESS  read-write
       STATUS  current
       DESCRIPTION
               "the number of the traffic-copy-to-cpu QOS user group acl subitem. "
       ::= { qosTrafficCopyToCpuEntry 3 }   
 
   qosTrafficCopyToCpuIpGroupName OBJECT-TYPE
       SYNTAX  OCTET STRING (SIZE (0..31))
       ACCESS  read-write
       STATUS  current
       DESCRIPTION
               "the name of the traffic-copy-to-cpu QOS ip group acl. "
       ::= { qosTrafficCopyToCpuEntry 4 }
 
   qosTrafficCopyToCpuIpGroupSubitem OBJECT-TYPE
       SYNTAX  INTEGER(0..127)
       ACCESS  read-write
       STATUS  current
       DESCRIPTION
               "the number of the traffic-copy-to-cpu QOS ip group acl subitem. "
       ::= { qosTrafficCopyToCpuEntry 5 }      
 
   qosTrafficCopyToCpuLinkGroupName OBJECT-TYPE
       SYNTAX  OCTET STRING (SIZE (0..31))
       ACCESS  read-write
       STATUS  current
       DESCRIPTION
               "the name of the traffic-copy-to-cpu QOS link group acl. "
       ::= { qosTrafficCopyToCpuEntry 6 }
 
   qosTrafficCopyToCpuLinkGroupSubitem OBJECT-TYPE
       SYNTAX  INTEGER(0..127)
       ACCESS  read-write
       STATUS  current
       DESCRIPTION
               "the number of the traffic-copy-to-cpu QOS link group acl subitem. "
       ::= { qosTrafficCopyToCpuEntry 7 }                           

   qosTrafficCopyToCpuBlock0Priority OBJECT-TYPE
       SYNTAX  INTEGER(0..16)
       ACCESS  read-only
       STATUS  current
       DESCRIPTION
               "the block 0 priority of the traffic-copy-to-cpu QOS. 16 means no filter rules in the Hardware."
       ::= { qosTrafficCopyToCpuEntry 8 } 
        
   qosTrafficCopyToCpuBlock1Priority OBJECT-TYPE
       SYNTAX  INTEGER(0..16)
       ACCESS  read-only
       STATUS  current
       DESCRIPTION
               "the block 1 priority of the traffic-copy-to-cpu QOS. 16 means no filter rules in the Hardware."
       ::= { qosTrafficCopyToCpuEntry 9 }

   qosTrafficCopyToCpuBlock2Priority OBJECT-TYPE
       SYNTAX  INTEGER(0..16)
       ACCESS  read-only
       STATUS  current
       DESCRIPTION
               "the block 2 priority of the traffic-copy-to-cpu QOS. 16 means no filter rules in the Hardware."
       ::= { qosTrafficCopyToCpuEntry 10 }
        
   qosTrafficCopyToCpuBlock3Priority OBJECT-TYPE
       SYNTAX  INTEGER(0..16)
       ACCESS  read-only
       STATUS  current
       DESCRIPTION
               "the block 3 priority of the traffic-copy-to-cpu QOS. 16 means no filter rules in the Hardware."
       ::= { qosTrafficCopyToCpuEntry 11 }

   qosTrafficCopyToCpuBlock4Priority OBJECT-TYPE
       SYNTAX  INTEGER(0..16)
       ACCESS  read-only
       STATUS  current
       DESCRIPTION
               "the block 4 priority of the traffic-copy-to-cpu QOS. 16 means no filter rules in the Hardware."
       ::= { qosTrafficCopyToCpuEntry 12 }

   qosTrafficCopyToCpuConfigSequence OBJECT-TYPE
       SYNTAX  INTEGER(1..1024)
       ACCESS  read-only
       STATUS  current
       DESCRIPTION
               "the config sequence of the traffic-copy-to-cpu QOS."
       ::= { qosTrafficCopyToCpuEntry 13 }
              
   qosTrafficCopyToCpuRunning OBJECT-TYPE
        SYNTAX   TruthValue
        MAX-ACCESS   read-only
        STATUS   current
        DESCRIPTION
           "the running status of the traffic-copy-to-cpu QOS."                          
       ::= { qosTrafficCopyToCpuEntry 14 } 
       
   qosTrafficCopyToCpuRowStatus OBJECT-TYPE
       SYNTAX      RowStatus
       MAX-ACCESS  read-create
       STATUS      current
       DESCRIPTION
           "This object indicates the status of this entry."
       ::= { qosTrafficCopyToCpuEntry 15 }

   qosTrafficCopyToCpuBlock5Priority OBJECT-TYPE
       SYNTAX  INTEGER(0..16)
       ACCESS  read-only
       STATUS  current
       DESCRIPTION
               "the block 5 priority of the traffic-copy-to-cpu QOS. 16 means no filter rules in the Hardware."
               --报文拷贝到CPU在block 5 中的优先级，16表示没有过滤规则在硬件中                
       ::= { qosTrafficCopyToCpuEntry 16 }    

   qosTrafficCopyToCpuBlock6Priority OBJECT-TYPE
       SYNTAX  INTEGER(0..16)
       ACCESS  read-only
       STATUS  current
       DESCRIPTION
               "the block 6 priority of the traffic-copy-to-cpu QOS. 16 means no filter rules in the Hardware."
               --报文拷贝到CPU在block 6 中的优先级，16表示没有过滤规则在硬件中                
       ::= { qosTrafficCopyToCpuEntry 17 } 

   qosTrafficCopyToCpuBlock7Priority OBJECT-TYPE
       SYNTAX  INTEGER(0..16)
       ACCESS  read-only
       STATUS  current
       DESCRIPTION
               "the block 7 priority of the traffic-copy-to-cpu QOS. 16 means no filter rules in the Hardware."
               --报文拷贝到CPU在block 7 中的优先级，16表示没有过滤规则在硬件中                
       ::= { qosTrafficCopyToCpuEntry 18 }   

   qosTrafficCopyToCpuBlock8Priority OBJECT-TYPE
       SYNTAX  INTEGER(0..16)
       ACCESS  read-only
       STATUS  current
       DESCRIPTION
               "the block 8 priority of the traffic-copy-to-cpu QOS. 16 means no filter rules in the Hardware."
               --报文拷贝到CPU在block 8 中的优先级，16表示没有过滤规则在硬件中                
       ::= { qosTrafficCopyToCpuEntry 19 }    

   qosTrafficCopyToCpuBlock9Priority OBJECT-TYPE
       SYNTAX  INTEGER(0..16)
       ACCESS  read-only
       STATUS  current
       DESCRIPTION
               "the block 9 priority of the traffic-copy-to-cpu QOS. 16 means no filter rules in the Hardware."
               --报文拷贝到CPU在block 9 中的优先级，16表示没有过滤规则在硬件中                
       ::= { qosTrafficCopyToCpuEntry 20 }    

   qosTrafficCopyToCpuBlock10Priority OBJECT-TYPE
       SYNTAX  INTEGER(0..16)
       ACCESS  read-only
       STATUS  current
       DESCRIPTION
               "the block 10 priority of the traffic-copy-to-cpu QOS. 16 means no filter rules in the Hardware."
               --报文拷贝到CPU在block 10 中的优先级，16表示没有过滤规则在硬件中                
       ::= { qosTrafficCopyToCpuEntry 21 }  

   qosTrafficCopyToCpuBlock11Priority OBJECT-TYPE
       SYNTAX  INTEGER(0..16)
       ACCESS  read-only
       STATUS  current
       DESCRIPTION
               "the block 11 priority of the traffic-copy-to-cpu QOS. 16 means no filter rules in the Hardware."
               --报文拷贝到CPU在block 11 中的优先级，16表示没有过滤规则在硬件中                
       ::= { qosTrafficCopyToCpuEntry 22 }    
                 
   --
   -- the port-isolation configuration 
   --                                           
   qaclAppPortIsolationGroup  OBJECT IDENTIFIER ::= { gbnL2QACL 23 }
 
   qaclAppPortIsolationDownLinkPorts OBJECT-TYPE
       SYNTAX  PortList         
       ACCESS  read-write
       STATUS  current
       DESCRIPTION
               "qacl application port isolation down link portlist"
               -- QACL应用端口隔离的下行端口列表 --
       ::= { qaclAppPortIsolationGroup 1 }  

   --
   -- the storm control 
   --
 
   stormControlTable OBJECT-TYPE
       SYNTAX  SEQUENCE OF StormControlEntry
       ACCESS  not-accessible
       STATUS  current
       DESCRIPTION
               "A list of storm control entries. "
       ::= { gbnL2QACL 24 }
 
   stormControlEntry OBJECT-TYPE
       SYNTAX  StormControlEntry
       ACCESS  not-accessible
       STATUS  current
       DESCRIPTION
               "A list of storm control entries. "
       INDEX   { stormControlInterface, stormControlType }
       ::= { stormControlTable 1 }
 
   StormControlEntry ::=
       SEQUENCE {
           stormControlInterface
               INTEGER,  
           stormControlType             
               PacketFlowType,                
           stormControlTargetRate
               INTEGER,                  
           stormControlRowStatus
               RowStatus                  
       }
 
   stormControlInterface OBJECT-TYPE
       SYNTAX  INTEGER (1..26)
       ACCESS  read-only
       STATUS  current
       DESCRIPTION
               "the storm control interface. "
               --风暴控制端口
       ::= { stormControlEntry 1 }
       
   stormControlType OBJECT-TYPE
       SYNTAX  PacketFlowType   
       ACCESS  read-only
       STATUS  current
       DESCRIPTION
               "the pack flow type of the storm control. "
               --风暴控制报文流类型
       ::= { stormControlEntry 2 } 
           
   stormControlTargetRate OBJECT-TYPE
       SYNTAX  INTEGER (1..1000)   
       ACCESS  read-write
       STATUS  current
       DESCRIPTION
               "the target rate of the storm control. "
               --风暴控制目标速率
       ::= { stormControlEntry 3 }  

   stormControlRowStatus OBJECT-TYPE
        SYNTAX   RowStatus
        MAX-ACCESS   read-write
        STATUS   current 
        DESCRIPTION
                "row status of the storm control"
                --风暴控制行状态
        ::= { stormControlEntry 4 }    

   --
   -- the traffic rewrite vlan QOS 
   --
 
   qosTrafficRewriteVlanTable OBJECT-TYPE
       SYNTAX  SEQUENCE OF QosTrafficRewriteVlanEntry
       ACCESS  not-accessible
       STATUS  current
       DESCRIPTION
               "A list of traffic-rewrite-vlan QOS entries. "
       ::= { gbnL2QACL 25 }
 
   qosTrafficRewriteVlanEntry OBJECT-TYPE
       SYNTAX  QosTrafficRewriteVlanEntry
       ACCESS  not-accessible
       STATUS  current
       DESCRIPTION
               "A list of traffic-rewrite-vlan QOS entries. "
       INDEX   { qosTrafficRewriteVlanIndex }
       ::= { qosTrafficRewriteVlanTable 1 }
 
   QosTrafficRewriteVlanEntry ::=
       SEQUENCE {
           qosTrafficRewriteVlanIndex
               INTEGER,
           qosTrafficRewriteVlanUserGroupName
               OCTET STRING,
           qosTrafficRewriteVlanUserGroupSubitem
               INTEGER,
           qosTrafficRewriteVlanIpGroupName
               OCTET STRING,
           qosTrafficRewriteVlanIpGroupSubitem
               INTEGER,    
           qosTrafficRewriteVlanLinkGroupName
               OCTET STRING,
           qosTrafficRewriteVlanLinkGroupSubitem
               INTEGER,    
           qosTrafficRewriteVlanInterface
               INTEGER,
           qosTrafficRewriteVlanBlock0Priority
               INTEGER,
           qosTrafficRewriteVlanBlock1Priority
               INTEGER,  
           qosTrafficRewriteVlanBlock2Priority
               INTEGER, 
           qosTrafficRewriteVlanBlock3Priority
               INTEGER,
           qosTrafficRewriteVlanBlock4Priority
               INTEGER,
           qosTrafficRewriteVlanConfigSequence
               INTEGER,    
           qosTrafficRewriteVlanRunning
               TruthValue,     
           qosTrafficRewriteVlanRowStatus
               RowStatus,
           qosTrafficRewriteVlanBlock5Priority
               INTEGER,
           qosTrafficRewriteVlanBlock6Priority
               INTEGER,  
           qosTrafficRewriteVlanBlock7Priority
               INTEGER, 
           qosTrafficRewriteVlanBlock8Priority
               INTEGER,
           qosTrafficRewriteVlanBlock9Priority
               INTEGER,    
           qosTrafficRewriteVlanBlock10Priority
               INTEGER,
           qosTrafficRewriteVlanBlock11Priority
               INTEGER    
       }
 
   qosTrafficRewriteVlanIndex OBJECT-TYPE
       SYNTAX  INTEGER
       ACCESS  read-only
       STATUS  current
       DESCRIPTION
               "A unique value for each traffic-rewrite-vlan QOS.  "
       ::= { qosTrafficRewriteVlanEntry 1 }
 
   qosTrafficRewriteVlanUserGroupName OBJECT-TYPE
       SYNTAX  OCTET STRING (SIZE (0..31))
       ACCESS  read-write
       STATUS  current
       DESCRIPTION
               "the name of the traffic-rewrite-vlan QOS user group acl. "
       ::= { qosTrafficRewriteVlanEntry 2 }
 
   qosTrafficRewriteVlanUserGroupSubitem OBJECT-TYPE
       SYNTAX  INTEGER(0..127)
       ACCESS  read-write
       STATUS  current
       DESCRIPTION
               "the number of the traffic-rewrite-vlan QOS user group acl subitem. "
       ::= { qosTrafficRewriteVlanEntry 3 }   
 
   qosTrafficRewriteVlanIpGroupName OBJECT-TYPE
       SYNTAX  OCTET STRING (SIZE (0..31))
       ACCESS  read-write
       STATUS  current
       DESCRIPTION
               "the name of the traffic-rewrite-vlan QOS ip group acl. "
       ::= { qosTrafficRewriteVlanEntry 4 }
 
   qosTrafficRewriteVlanIpGroupSubitem OBJECT-TYPE
       SYNTAX  INTEGER(0..127)
       ACCESS  read-write
       STATUS  current
       DESCRIPTION
               "the number of the traffic-rewrite-vlan QOS ip group acl subitem. "
       ::= { qosTrafficRewriteVlanEntry 5 }      
 
   qosTrafficRewriteVlanLinkGroupName OBJECT-TYPE
       SYNTAX  OCTET STRING (SIZE (0..31))
       ACCESS  read-write
       STATUS  current
       DESCRIPTION
               "the name of the traffic-rewrite-vlan QOS link group acl. "
       ::= { qosTrafficRewriteVlanEntry 6 }
 
   qosTrafficRewriteVlanLinkGroupSubitem OBJECT-TYPE
       SYNTAX  INTEGER(0..127)
       ACCESS  read-write
       STATUS  current
       DESCRIPTION
               "the number of the traffic-rewrite-vlan QOS link group acl subitem. "
       ::= { qosTrafficRewriteVlanEntry 7 }             
 
   qosTrafficRewriteVlanVid OBJECT-TYPE
       SYNTAX  INTEGER (1..28)   
       ACCESS  read-write
       STATUS  current
       DESCRIPTION
               "the vlan ID of the traffic-rewrite-vlan QOS.1－24 for fast-ethernet port 1－24，25－26 for giga-ethernet port 1－2，28 for CPU port，27 is invaild value. "
       ::= { qosTrafficRewriteVlanEntry 8 }              

   qosTrafficRewriteVlanBlock0Priority OBJECT-TYPE
       SYNTAX  INTEGER(0..16)
       ACCESS  read-only
       STATUS  current
       DESCRIPTION
               "the block 0 priority of the traffic-rewrite-vlan QOS. 16 means no filter rules in the Hardware."
       ::= { qosTrafficRewriteVlanEntry 9 } 
        
   qosTrafficRewriteVlanBlock1Priority OBJECT-TYPE
       SYNTAX  INTEGER(0..16)
       ACCESS  read-only
       STATUS  current
       DESCRIPTION
               "the block 1 priority of the traffic-rewrite-vlan QOS. 16 means no filter rules in the Hardware."
       ::= { qosTrafficRewriteVlanEntry 10 }
       
   qosTrafficRewriteVlanBlock2Priority OBJECT-TYPE
       SYNTAX  INTEGER(0..16)
       ACCESS  read-only
       STATUS  current
       DESCRIPTION
               "the block 2 priority of the traffic-rewrite-vlan QOS. 16 means no filter rules in the Hardware."
       ::= { qosTrafficRewriteVlanEntry 11 }
        
   qosTrafficRewriteVlanBlock3Priority OBJECT-TYPE
       SYNTAX  INTEGER(0..16)
       ACCESS  read-only
       STATUS  current
       DESCRIPTION
               "the block 3 priority of the traffic-rewrite-vlan QOS. 16 means no filter rules in the Hardware."
       ::= { qosTrafficRewriteVlanEntry 12 }

   qosTrafficRewriteVlanBlock4Priority OBJECT-TYPE
       SYNTAX  INTEGER(0..16)
       ACCESS  read-only
       STATUS  current
       DESCRIPTION
               "the block 4 priority of the traffic-rewrite-vlan QOS. 16 means no filter rules in the Hardware."
       ::= { qosTrafficRewriteVlanEntry 13 }

   qosTrafficRewriteVlanConfigSequence OBJECT-TYPE
       SYNTAX  INTEGER(1..1024)
       ACCESS  read-only
       STATUS  current
       DESCRIPTION
               "the config sequence of the traffic-rewrite-vlan QOS."
       ::= { qosTrafficRewriteVlanEntry 14 }
              
   qosTrafficRewriteVlanRunning OBJECT-TYPE
        SYNTAX   TruthValue
        MAX-ACCESS   read-only
        STATUS   current
        DESCRIPTION
           "the running status of the traffic-rewrite-vlan QOS."                          
       ::= { qosTrafficRewriteVlanEntry 15 } 
       
   qosTrafficRewriteVlanRowStatus OBJECT-TYPE
       SYNTAX      RowStatus
       MAX-ACCESS  read-create
       STATUS      current
       DESCRIPTION
           "This object indicates the status of this entry."
       ::= { qosTrafficRewriteVlanEntry 16 }
 
   qosTrafficRewriteVlanBlock5Priority OBJECT-TYPE
       SYNTAX  INTEGER(0..16)
       ACCESS  read-only
       STATUS  current
       DESCRIPTION
               "the block 5 priority of the traffic-rewrite-vlan QOS. 16 means no filter rules in the Hardware."
               --报文重定向在block 5 中的优先级，16表示没有过滤规则在硬件中                
       ::= { qosTrafficRewriteVlanEntry 17 } 

   qosTrafficRewriteVlanBlock6Priority OBJECT-TYPE
       SYNTAX  INTEGER(0..16)
       ACCESS  read-only
       STATUS  current
       DESCRIPTION
               "the block 6 priority of the traffic-rewrite-vlan QOS. 16 means no filter rules in the Hardware."
               --报文重定向在block 6 中的优先级，16表示没有过滤规则在硬件中                
       ::= { qosTrafficRewriteVlanEntry 18 } 

   qosTrafficRewriteVlanBlock7Priority OBJECT-TYPE
       SYNTAX  INTEGER(0..16)
       ACCESS  read-only
       STATUS  current
       DESCRIPTION
               "the block 7 priority of the traffic-rewrite-vlan QOS. 16 means no filter rules in the Hardware."
               --报文重定向在block 7 中的优先级，16表示没有过滤规则在硬件中                
       ::= { qosTrafficRewriteVlanEntry 19 } 

   qosTrafficRewriteVlanBlock8Priority OBJECT-TYPE
       SYNTAX  INTEGER(0..16)
       ACCESS  read-only
       STATUS  current
       DESCRIPTION
               "the block 8 priority of the traffic-rewrite-vlan QOS. 16 means no filter rules in the Hardware."
               --报文重定向在block 8 中的优先级，16表示没有过滤规则在硬件中                
       ::= { qosTrafficRewriteVlanEntry 20 } 

   qosTrafficRewriteVlanBlock9Priority OBJECT-TYPE
       SYNTAX  INTEGER(0..16)
       ACCESS  read-only
       STATUS  current
       DESCRIPTION
               "the block 9 priority of the traffic-rewrite-vlan QOS. 16 means no filter rules in the Hardware."
               --报文重定向在block 9 中的优先级，16表示没有过滤规则在硬件中                
       ::= { qosTrafficRewriteVlanEntry 21 } 

   qosTrafficRewriteVlanBlock10Priority OBJECT-TYPE
       SYNTAX  INTEGER(0..16)
       ACCESS  read-only
       STATUS  current
       DESCRIPTION
               "the block 10 priority of the traffic-rewrite-vlan QOS. 16 means no filter rules in the Hardware."
               --报文重定向在block 10 中的优先级，16表示没有过滤规则在硬件中                
       ::= { qosTrafficRewriteVlanEntry 22 } 

   qosTrafficRewriteVlanBlock11Priority OBJECT-TYPE
       SYNTAX  INTEGER(0..16)
       ACCESS  read-only
       STATUS  current
       DESCRIPTION
               "the block 11 priority of the traffic-rewrite-vlan QOS. 16 means no filter rules in the Hardware."
               --报文重定向在block 11 中的优先级，16表示没有过滤规则在硬件中                
       ::= { qosTrafficRewriteVlanEntry 23 } 
                          
END
