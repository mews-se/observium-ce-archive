-- *******************************************************************
-- QTECH-CT-STANDARD-MIB.mib : QTECH-CT-STANDARD-MIB file
-- February 2010, liangbaitian
--
-- Copyright (c) 2010 by Qtech Networks Co.,Ltd.
-- All rights reserved.
-- *******************************************************************
QTECH-CT-STANDARD-MIB DEFINITIONS ::= BEGIN
    IMPORTS
        MODULE-IDENTITY,
        OBJECT-TYPE,
        Integer32,
        TimeTicks,
        Unsigned32
            FROM SNMPv2-SMI
        TruthValue,
        DisplayString,
        MacAddress,
        RowStatus
            FROM SNMPv2-TC
        MODULE-COMPLIANCE,
        NOTIFICATION-GROUP,
        OBJECT-GROUP
            FROM SNMPv2-CONF
        qtechApgWlanId
            FROM QTECH-AC-MGMT-MIB
        ifIndex
            FROM RFC1213-MIB
        qtechMgmt
            FROM QTECH-SMI;
--*******************************************
--* module definition
--*******************************************            
ctStandardmibmodule MODULE-IDENTITY
    LAST-UPDATED    "201002260000Z"
    ORGANIZATION
        "Qtech Networks Co.,Ltd."
    CONTACT-INFO
        "Tel: 4008-111-000
           E-mail: service@qtech.com.cn "

    DESCRIPTION
       "
       Wlan software private MIB for Qtech SNC according to the China
       Telecom standard. This is device manage MIB.
       "
    REVISION      "201002280000Z"
    DESCRIPTION
       "Initial version of this MIB module."

    ::= { qtechMgmt  71 }

--ctStandardMIBObjectsTable OBJECT IDENTIFIER  ::= { ctStandardmibmodule 1 }
ctStandardMIBObjects OBJECT IDENTIFIER  ::= { ctStandardmibmodule 2 }
ctStandardCompliances OBJECT IDENTIFIER  ::= { ctStandardmibmodule 3 }
ctStandardGroup OBJECT IDENTIFIER  ::= { ctStandardmibmodule 4 }

--**************************************************
--* ctStandardSystemConfigTable begins
--**************************************************

ctStandardSystemConfigTable OBJECT-TYPE
    SYNTAX SEQUENCE OF CTStandardSystemConfigEntry
    MAX-ACCESS not-accessible
    STATUS current
    DESCRIPTION
      " The attribute information table."
    ::={ ctStandardMIBObjects 1 }

ctStandardSystemConfigEntry  OBJECT-TYPE
    SYNTAX CTStandardSystemConfigEntry
    MAX-ACCESS not-accessible
    STATUS current
    DESCRIPTION
      " The attribute information entry."
    INDEX { qtechApgWlanId }
    ::={ ctStandardSystemConfigTable 1 }

CTStandardSystemConfigEntry ::=
    SEQUENCE {
        ctStandardAPConfigurationFileUpdate         TruthValue,
        ctStandardAPVersionFileUpdate               TruthValue,
        ctStandardMomentSTAConnected                TimeTicks
    }

ctStandardAPConfigurationFileUpdate OBJECT-TYPE
    SYNTAX TruthValue
    MAX-ACCESS read-write
    STATUS current
    DESCRIPTION
        " Whether to update the configuration file of AP."
    ::= { ctStandardSystemConfigEntry 1 }

ctStandardAPVersionFileUpdate OBJECT-TYPE
    SYNTAX TruthValue
    MAX-ACCESS read-write
    STATUS current
    DESCRIPTION
        " Whether to update the version file of AP."
    ::= { ctStandardSystemConfigEntry 2 }

ctStandardMomentSTAConnected OBJECT-TYPE
    SYNTAX TimeTicks
    MAX-ACCESS read-only
    STATUS current
    DESCRIPTION
        " The moment the end connected."
    ::= { ctStandardSystemConfigEntry 3 } 

--**************************************************
--* ctStandardSystemConfigTable ends
--**************************************************

--**************************************************
--* apCableInterfaceStatisticsTable begins
--**************************************************
apCableInterfaceStatisticsTable OBJECT-TYPE
    SYNTAX SEQUENCE OF AC8023CableInterfaceStatisticsEntry
    MAX-ACCESS not-accessible
    STATUS current
    DESCRIPTION
      "The table used to apac the configuration information of ap/ac."
    ::={ ctStandardMIBObjects 2 }


apCableInterfaceStatisticsEntry OBJECT-TYPE
    SYNTAX AC8023CableInterfaceStatisticsEntry
    MAX-ACCESS not-accessible
    STATUS current
    DESCRIPTION
      "The entry of the table used to apac the configuration information of ap/ac."
    INDEX { qtechApgWlanId }
    ::={ apCableInterfaceStatisticsTable 1 }


AC8023CableInterfaceStatisticsEntry ::=
    SEQUENCE {
        apIntfaceUnicastPacketsNumReceived          INTEGER,
        apIntfacebroadcastPacketsNumReceived        INTEGER,
        apIntfaceMuticastPacketsNumReceived         INTEGER,
        apIntfacePacketsNumDiscarded                INTEGER,
        apIntfaceUnicastPacketsNumTransmitted       INTEGER,
        apIntfacebroadcastPacketsNumTransmitted     INTEGER,
        apIntfaceMuticastPacketsNumTransmitted      INTEGER
    }

apIntfaceUnicastPacketsNumReceived OBJECT-TYPE
    SYNTAX INTEGER
    MAX-ACCESS read-only
    STATUS current
    DESCRIPTION
        " The count of the unicast packets received by the interface."
    ::= { apCableInterfaceStatisticsEntry 1 }

apIntfacebroadcastPacketsNumReceived OBJECT-TYPE
    SYNTAX INTEGER
    MAX-ACCESS read-only
    STATUS current
    DESCRIPTION
        " The count of the broadcast packets received by the interface."
    ::= { apCableInterfaceStatisticsEntry  2 }

apIntfaceMuticastPacketsNumReceived  OBJECT-TYPE
    SYNTAX INTEGER
    MAX-ACCESS read-only
    STATUS current
    DESCRIPTION
        " The count of the muticast packets received by the interface."
    ::= { apCableInterfaceStatisticsEntry 3 }

apIntfacePacketsNumDiscarded OBJECT-TYPE
    SYNTAX INTEGER
    MAX-ACCESS read-only
    STATUS current
    DESCRIPTION
        " The count of the packets discarded by the interface."
    ::= { apCableInterfaceStatisticsEntry 4 }

apIntfaceUnicastPacketsNumTransmitted OBJECT-TYPE
    SYNTAX INTEGER
    MAX-ACCESS read-only
    STATUS current
    DESCRIPTION
        " The count of the unicast packets transmitted by the interface."
    ::= { apCableInterfaceStatisticsEntry 5 }

apIntfacebroadcastPacketsNumTransmitted OBJECT-TYPE
    SYNTAX INTEGER
    MAX-ACCESS read-only
    STATUS current
    DESCRIPTION
        " The count of the broadcast packets transmitted by the interface."
    ::= { apCableInterfaceStatisticsEntry  6 }

apIntfaceMuticastPacketsNumTransmitted  OBJECT-TYPE
    SYNTAX INTEGER
    MAX-ACCESS read-only
    STATUS current
    DESCRIPTION
        " The count of the muticast packets transmitted by the interface."
    ::= { apCableInterfaceStatisticsEntry 7 }

--**************************************************
--* apCableInterfaceStatisticsTable ends
--**************************************************


--**************************************************
--* ac8023CableInterfaceStatisticsTable begins
--**************************************************
ac8023CableInterfaceStatisticsTable OBJECT-TYPE
    SYNTAX SEQUENCE OF ACCableInterfaceStatisticsEntry
    MAX-ACCESS not-accessible
    STATUS current
    DESCRIPTION
      "The table used to acac the configuration information of ac/ac."
    ::={ ctStandardMIBObjects 3 }


ac8023CableInterfaceStatisticsEntry OBJECT-TYPE
    SYNTAX ACCableInterfaceStatisticsEntry
    MAX-ACCESS not-accessible
    STATUS current
    DESCRIPTION
      "The entry of the table used to acac the configuration information of ac/ac."
    INDEX { qtechApgWlanId }
    ::={ ac8023CableInterfaceStatisticsTable 1 }


ACCableInterfaceStatisticsEntry ::=
    SEQUENCE {
        ac8023IntfaceUnicastPacketsNumReceived          INTEGER,
        ac8023IntfacebroadcastPacketsNumReceived        INTEGER,
        ac8023IntfaceMuticastPacketsNumReceived         INTEGER,
        ac8023IntfacePacketsNumDiscarded                INTEGER,
        ac8023IntfaceUnicastPacketsNumTransmitted       INTEGER,
        ac8023IntfacebroadcastPacketsNumTransmitted     INTEGER,
        ac8023IntfaceMuticastPacketsNumTransmitted      INTEGER
    }

ac8023IntfaceUnicastPacketsNumReceived OBJECT-TYPE
    SYNTAX INTEGER
    MAX-ACCESS read-only
    STATUS current
    DESCRIPTION
        " The count of the unicast packets received by the interface."
    ::= { ac8023CableInterfaceStatisticsEntry 1 }

ac8023IntfacebroadcastPacketsNumReceived OBJECT-TYPE
    SYNTAX INTEGER
    MAX-ACCESS read-only
    STATUS current
    DESCRIPTION
        " The count of the broadcast packets received by the interface."
    ::= { ac8023CableInterfaceStatisticsEntry  2 }

ac8023IntfaceMuticastPacketsNumReceived  OBJECT-TYPE
    SYNTAX INTEGER
    MAX-ACCESS read-only
    STATUS current
    DESCRIPTION
        " The count of the muticast packets received by the interface."
    ::= { ac8023CableInterfaceStatisticsEntry 3 }

ac8023IntfacePacketsNumDiscarded OBJECT-TYPE
    SYNTAX INTEGER
    MAX-ACCESS read-only
    STATUS current
    DESCRIPTION
        " The count of the packets discarded by the interface."
    ::= { ac8023CableInterfaceStatisticsEntry 4 }

ac8023IntfaceUnicastPacketsNumTransmitted OBJECT-TYPE
    SYNTAX INTEGER
    MAX-ACCESS read-only
    STATUS current
    DESCRIPTION
        " The count of the unicast packets transmitted by the interface."
    ::= { ac8023CableInterfaceStatisticsEntry 5 }

ac8023IntfacebroadcastPacketsNumTransmitted OBJECT-TYPE
    SYNTAX INTEGER
    MAX-ACCESS read-only
    STATUS current
    DESCRIPTION
        " The count of the broadcast packets transmitted by the interface."
    ::= { ac8023CableInterfaceStatisticsEntry  6 }

ac8023IntfaceMuticastPacketsNumTransmitted  OBJECT-TYPE
    SYNTAX INTEGER
    MAX-ACCESS read-only
    STATUS current
    DESCRIPTION
        " The count of the muticast packets transmitted by the interface."
    ::= { ac8023CableInterfaceStatisticsEntry 7 }

--**************************************************
--* ac8023CableInterfaceStatisticsTable ends
--**************************************************


--**************************************************
--* ac80211WirelessInterfaceStatisticsTable begins
--**************************************************
ac80211WirelessInterfaceStatisticsTable OBJECT-TYPE
    SYNTAX SEQUENCE OF ACWirelessInterfaceStatisticsEntry
    MAX-ACCESS not-accessible
    STATUS current
    DESCRIPTION
      "The table used to acac the configuration information of ac/ac."
    ::={ ctStandardMIBObjects 4 }

ac80211WirelessInterfaceStatisticsEntry OBJECT-TYPE
    SYNTAX ACWirelessInterfaceStatisticsEntry
    MAX-ACCESS not-accessible
    STATUS current
    DESCRIPTION
      "The entry of the table used to acac the configuration information of ac/ac."
    INDEX { qtechApgWlanId }
    ::={ ac80211WirelessInterfaceStatisticsTable 1 }

ACWirelessInterfaceStatisticsEntry ::=
    SEQUENCE {
        ac80211UplinkPortTraffic                    INTEGER,
        ac80211DownlinkPortTraffic                  INTEGER,
        ac80211UplinkChannelFrameNummissed          INTEGER,
        ac80211UplinkChannelFrameNumRetrans         INTEGER,
        ac80211UplinkChannelTotalFrameNum           INTEGER,
        ac80211DownlinkChannelTotalFrameNum         INTEGER,
        ac80211DownlinkChannelWrongFrameNum         INTEGER,
        ac80211DownlinkChannelFrameNummissed        INTEGER,        
        ac80211DownlinkChannelFrameNumRetrans       INTEGER,
        ac80211DataFrameBytesCountReceived          INTEGER,
        ac80211DataFrameBytesCountTransmitted       INTEGER,        
        ac80211AssociatedFramesCount                INTEGER
    }

ac80211UplinkPortTraffic OBJECT-TYPE
    SYNTAX INTEGER
    MAX-ACCESS read-only
    STATUS current
    DESCRIPTION
        " The traffic of the uplink port."
    ::= { ac80211WirelessInterfaceStatisticsEntry 1 }

ac80211DownlinkPortTraffic OBJECT-TYPE
    SYNTAX INTEGER
    MAX-ACCESS read-only
    STATUS current
    DESCRIPTION
        " The traffic of the downlink port."
    ::= { ac80211WirelessInterfaceStatisticsEntry 2 }

ac80211UplinkChannelFrameNummissed OBJECT-TYPE
    SYNTAX INTEGER
    MAX-ACCESS read-only
    STATUS current
    DESCRIPTION
        " The frame count of the uplink channel missed."
    ::= { ac80211WirelessInterfaceStatisticsEntry 3 }

    
ac80211UplinkChannelFrameNumRetrans OBJECT-TYPE
    SYNTAX INTEGER
    MAX-ACCESS read-only
    STATUS current
    DESCRIPTION
        " The frame count of the uplink channel retransmitted."
    ::= { ac80211WirelessInterfaceStatisticsEntry 4 }

ac80211UplinkChannelTotalFrameNum OBJECT-TYPE
    SYNTAX INTEGER
    MAX-ACCESS read-only
    STATUS current
    DESCRIPTION
        " The total frame count of the uplink channel."
    ::= { ac80211WirelessInterfaceStatisticsEntry 5 }

ac80211DownlinkChannelTotalFrameNum OBJECT-TYPE
    SYNTAX INTEGER
    MAX-ACCESS read-only
    STATUS current
    DESCRIPTION
        " The total frame count of the downlink channel."
    ::= { ac80211WirelessInterfaceStatisticsEntry 6 }

ac80211DownlinkChannelWrongFrameNum OBJECT-TYPE
    SYNTAX INTEGER
    MAX-ACCESS read-only
    STATUS current
    DESCRIPTION
        " The wrong frame count of the downlink channel."
    ::= { ac80211WirelessInterfaceStatisticsEntry 7 }

ac80211DownlinkChannelFrameNummissed OBJECT-TYPE
    SYNTAX INTEGER
    MAX-ACCESS read-only
    STATUS current
    DESCRIPTION
        " The frame count of the downlink channel missed."
    ::= { ac80211WirelessInterfaceStatisticsEntry 8 }
  
ac80211DownlinkChannelFrameNumRetrans OBJECT-TYPE
    SYNTAX INTEGER
    MAX-ACCESS read-only
    STATUS current
    DESCRIPTION
        " The frame count of the downlink channel retransmitted."
    ::= { ac80211WirelessInterfaceStatisticsEntry 9 }

ac80211DataFrameBytesCountReceived OBJECT-TYPE
    SYNTAX INTEGER
    MAX-ACCESS read-only
    STATUS current
    DESCRIPTION
        " The total bytes count of the data frame received."
    ::= { ac80211WirelessInterfaceStatisticsEntry 10 }

ac80211DataFrameBytesCountTransmitted OBJECT-TYPE
    SYNTAX INTEGER
    MAX-ACCESS read-only
    STATUS current
    DESCRIPTION
        " The total bytes count of the data frame transmitted."
    ::= { ac80211WirelessInterfaceStatisticsEntry 11 }
     
ac80211AssociatedFramesCount OBJECT-TYPE
    SYNTAX INTEGER
    MAX-ACCESS read-only
    STATUS current
    DESCRIPTION
        " The count of the frames associated."
    ::= { ac80211WirelessInterfaceStatisticsEntry 12 }
    
--**************************************************
--* ac80211WirelessInterfaceStatisticsTable ends
--**************************************************

-- ******************************************************************** 
-- * Compliance Statements - RSN 
-- ******************************************************************** 
ctStandardCompliance MODULE-COMPLIANCE 
    STATUS current 
    DESCRIPTION 
          "The compliance statement for CT-MIB." 
    MODULE -- this module 
    MANDATORY-GROUPS
        { 
            ctStandardBase
        } 
    -- OPTIONAL-GROUPS {dot11RSNPMKcachingGroup } 
::= { ctStandardCompliances 2 } 


-- ******************************************************************** 
-- * Groups - units of conformance - RSN 
-- *****************************************************************

ctStandardBase OBJECT-GROUP 
    OBJECTS {
        ctStandardAPConfigurationFileUpdate,
        ctStandardAPVersionFileUpdate,
        ctStandardMomentSTAConnected,
        apIntfaceUnicastPacketsNumReceived,
        apIntfacebroadcastPacketsNumReceived,
        apIntfaceMuticastPacketsNumReceived,
        apIntfacePacketsNumDiscarded,
        apIntfaceUnicastPacketsNumTransmitted,
        apIntfacebroadcastPacketsNumTransmitted,
        apIntfaceMuticastPacketsNumTransmitted,
        ac8023IntfaceUnicastPacketsNumReceived,
        ac8023IntfacebroadcastPacketsNumReceived,
        ac8023IntfaceMuticastPacketsNumReceived,
        ac8023IntfacePacketsNumDiscarded,
        ac8023IntfaceUnicastPacketsNumTransmitted,
        ac8023IntfacebroadcastPacketsNumTransmitted,
        ac8023IntfaceMuticastPacketsNumTransmitted,
        ac80211UplinkPortTraffic,
        ac80211DownlinkPortTraffic,
        ac80211UplinkChannelFrameNummissed,
        ac80211UplinkChannelFrameNumRetrans,
        ac80211UplinkChannelTotalFrameNum,
        ac80211DownlinkChannelTotalFrameNum,
        ac80211DownlinkChannelWrongFrameNum,
        ac80211DownlinkChannelFrameNummissed,     
        ac80211DownlinkChannelFrameNumRetrans,
        ac80211DataFrameBytesCountReceived,
        ac80211DataFrameBytesCountTransmitted,        
        ac80211AssociatedFramesCount
    }    
    STATUS current 
    DESCRIPTION 
        "The object class provides the necessary support for 
        managing functionality in the STA." 
    ::= { ctStandardGroup 1 }
    
END
