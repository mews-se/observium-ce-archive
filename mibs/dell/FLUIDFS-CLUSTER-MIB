-- Renamed by Observium Developers
FLUIDFS-CLUSTER-MIB DEFINITIONS ::= BEGIN

IMPORTS
        OBJECT-TYPE, NOTIFICATION-TYPE, MODULE-IDENTITY, TimeTicks, Counter64, enterprises
                        FROM SNMPv2-SMI
        TEXTUAL-CONVENTION, DisplayString
                        FROM SNMPv2-TC
        InetAddress, InetAddressType
                        FROM INET-ADDRESS-MIB;

fluidFSMIBIdentity MODULE-IDENTITY
        LAST-UPDATED "201302181350Z"
        ORGANIZATION "Dell"
        CONTACT-INFO ""
        DESCRIPTION "FluidFS MIB"
        REVISION "201302181350Z"
        DESCRIPTION "FluidFS Snmp traps interface."
::= { fluidFS 100 }


dell               OBJECT IDENTIFIER ::= { enterprises          674 }
enterpriseSoftware OBJECT IDENTIFIER ::= { dell               11000 }
storageMgmt        OBJECT IDENTIFIER ::= { enterpriseSoftware  2000 }
fluidFS 	   OBJECT IDENTIFIER ::= { storageMgmt          200 }

fluidFSCluster	OBJECT IDENTIFIER ::= { fluidFS 2 }

fluidFSEvents   OBJECT IDENTIFIER ::= { fluidFS 20 }
fluidFSEventsParams OBJECT IDENTIFIER ::= { fluidFS 21 }
fluidFSEventsGeneralParams OBJECT IDENTIFIER ::= { fluidFS 22 }
fluidFSGeneralEvents   OBJECT IDENTIFIER ::= { fluidFS 23 }

	fluidFSCluName OBJECT-TYPE
		SYNTAX	DisplayString
		MAX-ACCESS	read-write
		STATUS	current
		DESCRIPTION
			"The name of the cluster."
		::= { fluidFSCluster 1 }

	fluidFSCluNodeName OBJECT-TYPE
		SYNTAX  DisplayString
		MAX-ACCESS  read-only
		STATUS  current
		DESCRIPTION
			"The name of the node."
		::= { fluidFSCluster 4 1 2 }

	fluidFSCluResourceName OBJECT-TYPE
		SYNTAX  DisplayString
		MAX-ACCESS  read-only
		STATUS  current
		DESCRIPTION
			"The name of the resource. It must be unique within the cluster."
		::= { fluidFSCluster 5 1 2 }

	fluidFSCluResourceOwnerNode OBJECT-TYPE
		SYNTAX  DisplayString
		MAX-ACCESS  read-only
		STATUS  current
		DESCRIPTION
			"The node in the cluster where the group of the resource is
			currently online."
		::= { fluidFSCluster 5 1 4 }




--
-- General Event Description
--

	fluidFSGenEventDesc OBJECT-TYPE
		SYNTAX  DisplayString
		MAX-ACCESS  read-only
		STATUS  current
		DESCRIPTION
			"A string describing the general event."
		::= { fluidFS 10 }


	fluidFSFileName OBJECT-TYPE
                SYNTAX  DisplayString
                MAX-ACCESS  read-only
                STATUS  current
                DESCRIPTION
                        "The file name."
                ::= { fluidFS 11 }
 

--
--  Cluster Trap Definition
--
--  The fluidFS enterprise			   (1.3.6.1.4.1.8010)
--

        sysName OBJECT-TYPE
                SYNTAX  DisplayString
                MAX-ACCESS  read-only
                STATUS  current
                DESCRIPTION
                "General system name"
        ::= { fluidFSEventsGeneralParams 1 }

	fluidFSCluOK NOTIFICATION-TYPE
		OBJECTS  { sysName, fluidFSCluName }
		STATUS current
		DESCRIPTION
			"This trap will be sent any time the condition of the cluster
			 becomes ok."

		--#TYPE		"Cluster OK"
		--#SUMMARY	"Cluster %s is ok."
		--#ARGUMENTS	{1}
		--#SEVERITY	NORMAL
		--#TIMEINDEX	99
		--#STATE	OK
	::= { fluidFSGeneralEvents 1 }

	fluidFSCluDegraded NOTIFICATION-TYPE
		OBJECTS  { sysName, fluidFSCluName }
		STATUS current
		DESCRIPTION
			"This trap will be sent any time the condition of the cluster
			 becomes degraded."

		--#TYPE		"Cluster Degraded"
		--#SUMMARY	"Cluster %s has become degraded."
		--#ARGUMENTS	{1}
		--#SEVERITY	MAJOR
		--#TIMEINDEX	99
		--#STATE	DEGRADED
	::= { fluidFSGeneralEvents 2 }

	fluidFSCluFailed NOTIFICATION-TYPE
		OBJECTS  { sysName, fluidFSCluName }
                STATUS current
		DESCRIPTION
			"This trap will be sent any time the condition of the cluster
			 becomes failed."

		--#TYPE		"Cluster Failed"
		--#SUMMARY	"Cluster %s has failed."
		--#ARGUMENTS	{1}
		--#SEVERITY	MAJOR
		--#TIMEINDEX	99
		--#STATE	FAILED
	::= { fluidFSGeneralEvents 3 }

	fluidFSCluNodeOK NOTIFICATION-TYPE
		OBJECTS  { sysName, fluidFSCluNodeName }
                STATUS current
		DESCRIPTION
			"This trap will be sent any time the condition of a node in
			 the cluster becomes ok."

		--#TYPE		"Cluster Node OK"
		--#SUMMARY	"Cluster %s node %s is ok."
		--#ARGUMENTS	{0,1}
		--#SEVERITY	NORMAL
		--#TIMEINDEX	99
		--#STATE	OK
	::= { fluidFSGeneralEvents 4 }
		
	fluidFSCluNodeDegraded NOTIFICATION-TYPE
		OBJECTS  { sysName, fluidFSCluNodeName }
                STATUS current
		DESCRIPTION
			"This trap will be sent any time the condition of a node in
			 the cluster becomes degraded.

			 User Action: Make a note of the cluster node name then
			 check the node for the cause of the degraded condition."

		--#TYPE	  "Cluster Node Degraded"
		--#SUMMARY   "Cluster %s node %s has become degraded."
		--#ARGUMENTS {0,1}
		--#SEVERITY  MAJOR
		--#TIMEINDEX 99
		--#STATE	 DEGRADED
	::= { fluidFSGeneralEvents 5 }

	fluidFSCluNodeFailed NOTIFICATION-TYPE
		OBJECTS  { sysName, fluidFSCluNodeName }
                STATUS current
		DESCRIPTION
			"This trap will be sent any time the condition of a node in
			 the cluster becomes failed.

			 User Action: Make a note of the cluster node name
			 then check the node for the cause of the failure."

		--#TYPE		"Cluster Node Failed"
		--#SUMMARY	"Cluster %s node %s has failed."
		--#ARGUMENTS	{0,1}
		--#SEVERITY	MAJOR
		--#TIMEINDEX	99
		--#STATE	FAILED
	::= { fluidFSGeneralEvents 6 }

	fluidFSCluResourceOK NOTIFICATION-TYPE
		OBJECTS  { sysName, fluidFSCluResourceName, fluidFSCluResourceOwnerNode }
                STATUS current
		DESCRIPTION
			"This trap will be sent any time the condition of a cluster
			 resource becomes ok."

		--#TYPE		"Cluster Resource OK"
		--#SUMMARY	"Cluster %s resource %s on node %s is ok."
		--#ARGUMENTS	{0,1,2}
		--#SEVERITY	NORMAL
		--#TIMEINDEX	99
		--#STATE	OK
	::= { fluidFSGeneralEvents 7 }
	
	fluidFSCluResourceDegraded NOTIFICATION-TYPE
		OBJECTS  { sysName, fluidFSCluResourceName, fluidFSCluResourceOwnerNode }
                STATUS current
		DESCRIPTION
			"This trap will be sent any time the condition of a cluster
			 resource becomes degraded.

			 User Action: Make a note of the cluster resource name then
			 check the resource for the cause of the degraded condition."

		--#TYPE		"Cluster Resource Degraded"
		--#SUMMARY	"Cluster %s resource %s on node %s has become degraded."
		--#ARGUMENTS	{0,1,2}
		--#SEVERITY	MAJOR
		--#TIMEINDEX	99
		--#STATE	DEGRADED
	::= { fluidFSGeneralEvents 8 }

	fluidFSCluResourceFailed NOTIFICATION-TYPE
		OBJECTS  { sysName, fluidFSCluResourceName, fluidFSCluResourceOwnerNode }
                STATUS current
		DESCRIPTION
			"This trap will be sent any time the condition of a cluster
			 resource becomes failed.

			 User Action: Make a note of the cluster resource name
			 then check the resource for the cause of the failure."

		--#TYPE		"Cluster Resource Failed"
		--#SUMMARY	"Cluster %s resource %s on node %s has failed."
		--#ARGUMENTS	{0,1,2}
		--#SEVERITY	MAJOR
		--#TIMEINDEX	99
		--#STATE	FAILED
	::= { fluidFSGeneralEvents 9 }

	fluidFSGenNormalEvent NOTIFICATION-TYPE
		OBJECTS  { sysName, fluidFSGenEventDesc, fluidFSCluNodeName }
                STATUS current
		DESCRIPTION
			"This trap will be sent for normal events."

		--#TYPE		"Normal Event"
		--#SUMMARY	"%s has occurred on %s"
		--#ARGUMENTS	{1,2}
		--#SEVERITY	NORMAL
		--#TIMEINDEX	99
		--#STATE	OK
	::= { fluidFSGeneralEvents 14 }

	fluidFSGenMinorEvent NOTIFICATION-TYPE
		OBJECTS  { sysName, fluidFSGenEventDesc, fluidFSCluNodeName }
                STATUS current
		DESCRIPTION
			"This trap will be sent for minor events."

		--#TYPE		"Minor Event"
		--#SUMMARY	"%s has occurred on %s"
		--#ARGUMENTS	{1,2}
		--#SEVERITY	CRITICAL
		--#TIMEINDEX	99
		--#STATE	DEGRADED
	::= { fluidFSGeneralEvents 15 }

	fluidFSGenMajorEvent NOTIFICATION-TYPE
		OBJECTS  { sysName, fluidFSGenEventDesc, fluidFSCluNodeName }
                STATUS current
		DESCRIPTION
			"This trap will be sent for major events."

		--#TYPE		"Major Event"
		--#SUMMARY	"%s has occurred on %s"
		--#ARGUMENTS	{1,2}
		--#SEVERITY	Major
		--#TIMEINDEX	99
		--#STATE	DEGRADED
	::= { fluidFSGeneralEvents 16 }

	fluidFSGenCriticalEvent NOTIFICATION-TYPE
		OBJECTS  { sysName, fluidFSGenEventDesc, fluidFSCluNodeName }
                STATUS current
		DESCRIPTION
			"This trap will be sent for critical events."

		--#TYPE		"Critical Event"
		--#SUMMARY	"%s has occurred on %s"
		--#ARGUMENTS	{1,2}
		--#SEVERITY	CRITICAL
		--#TIMEINDEX	99
		--#STATE	FAILED
	::= { fluidFSGeneralEvents 17 }


	fluidFSAntiVirusEvent NOTIFICATION-TYPE
                OBJECTS  { sysName, fluidFSFileName }
                STATUS current
                DESCRIPTION
                        "The antivirus software on or connected to system
                         detected a virus."
                                                                                                                          
                --#TYPE         "Virus detected"
                --#SUMMARY      "Antivirus Software on %s found a virus in file %s"
                --#ARGUMENTS    {0,1}
                --#SEVERITY     MAJOR
                --#TIMEINDEX    99
                --#STATE        DEGRADED
        ::= { fluidFSGeneralEvents 18 }
 
    fluidFSEventsParamsAdmin OBJECT IDENTIFIER ::= { fluidFSEventsParams 1 } 
    
    
    fluidFSEventsAdmin OBJECT IDENTIFIER ::= { fluidFSEvents 1 } 
    
    
    fluidFSEventsParamsAdminUsername OBJECT-TYPE
       SYNTAX  DisplayString
       MAX-ACCESS  read-only
       STATUS  current
       DESCRIPTION
           "User name which performed the operation"
       ::= { fluidFSEventsParamsAdmin 1 }
    
    
    fluidFSEventsParamsAdminAdministrator OBJECT-TYPE
       SYNTAX  DisplayString
       MAX-ACCESS  read-only
       STATUS  current
       DESCRIPTION
           "System administrator"
       ::= { fluidFSEventsParamsAdmin 2 }
    
    
    fluidFSEventsParamsAdminLocaluser OBJECT-TYPE
       SYNTAX  DisplayString
       MAX-ACCESS  read-only
       STATUS  current
       DESCRIPTION
           "Local user name"
       ::= { fluidFSEventsParamsAdmin 3 }
    
    
    fluidFSEventsParamsAdminLocalgroup OBJECT-TYPE
       SYNTAX  DisplayString
       MAX-ACCESS  read-only
       STATUS  current
       DESCRIPTION
           "Local group name"
       ::= { fluidFSEventsParamsAdmin 4 }
    
    
    fluidFSEventsParamsAdminTenantId OBJECT-TYPE
       SYNTAX  DisplayString
       MAX-ACCESS  read-only
       STATUS  current
       DESCRIPTION
           ""
       ::= { fluidFSEventsParamsAdmin 5 }
    
    
    fluidFSEventsParamsAdminVirtualVolume OBJECT-TYPE
       SYNTAX  DisplayString
       MAX-ACCESS  read-only
       STATUS  current
       DESCRIPTION
           "NAS volume"
       ::= { fluidFSEventsParamsAdmin 6 }
    
    
    fluidFSEventsParamsAdminHost OBJECT-TYPE
       SYNTAX  DisplayString
       MAX-ACCESS  read-only
       STATUS  current
       DESCRIPTION
           "Antivirus host"
       ::= { fluidFSEventsParamsAdmin 7 }
    
    
    fluidFSEventsParamsAdminPort OBJECT-TYPE
       SYNTAX  INTEGER
       MAX-ACCESS  read-only
       STATUS  current
       DESCRIPTION
           "Antivirus port"
       ::= { fluidFSEventsParamsAdmin 8 }
    
    
    fluidFSEventsParamsAdminShareName OBJECT-TYPE
       SYNTAX  DisplayString
       MAX-ACCESS  read-only
       STATUS  current
       DESCRIPTION
           "SMB share name"
       ::= { fluidFSEventsParamsAdmin 9 }
    
    
    fluidFSEventsParamsAdminNodeId OBJECT-TYPE
       SYNTAX  INTEGER
       MAX-ACCESS  read-only
       STATUS  current
       DESCRIPTION
           "Node id"
       ::= { fluidFSEventsParamsAdmin 10 }
    
    
    fluidFSEventsParamsAdminPid OBJECT-TYPE
       SYNTAX  INTEGER
       MAX-ACCESS  read-only
       STATUS  current
       DESCRIPTION
           "Process id"
       ::= { fluidFSEventsParamsAdmin 11 }
    
    
    fluidFSEventsParamsAdminVirtualInterface OBJECT-TYPE
       SYNTAX  DisplayString
       MAX-ACCESS  read-only
       STATUS  current
       DESCRIPTION
           "Virtual interface"
       ::= { fluidFSEventsParamsAdmin 12 }
    
    
    fluidFSEventsParamsAdminClusterName OBJECT-TYPE
       SYNTAX  DisplayString
       MAX-ACCESS  read-only
       STATUS  current
       DESCRIPTION
           "Cluster name"
       ::= { fluidFSEventsParamsAdmin 13 }
    
    
    fluidFSEventsParamsAdminSnapshotName OBJECT-TYPE
       SYNTAX  DisplayString
       MAX-ACCESS  read-only
       STATUS  current
       DESCRIPTION
           "Snapshot name"
       ::= { fluidFSEventsParamsAdmin 14 }
    
    
    fluidFSEventsParamsAdminNewSnapshotName OBJECT-TYPE
       SYNTAX  DisplayString
       MAX-ACCESS  read-only
       STATUS  current
       DESCRIPTION
           "New snapshot name"
       ::= { fluidFSEventsParamsAdmin 15 }
    
    
    fluidFSEventsParamsAdminStaticRoutes OBJECT-TYPE
       SYNTAX  DisplayString
       MAX-ACCESS  read-only
       STATUS  current
       DESCRIPTION
           "Static routes list"
       ::= { fluidFSEventsParamsAdmin 16 }
    
    
    fluidFSEventsParamsAdminNFSExportPath OBJECT-TYPE
       SYNTAX  DisplayString
       MAX-ACCESS  read-only
       STATUS  current
       DESCRIPTION
           "Path of NFS export"
       ::= { fluidFSEventsParamsAdmin 17 }
    
    
    fluidFSEventsParamsAdminQuotaUserName OBJECT-TYPE
       SYNTAX  DisplayString
       MAX-ACCESS  read-only
       STATUS  current
       DESCRIPTION
           "User name on which the quota is defined"
       ::= { fluidFSEventsParamsAdmin 18 }
    
    
    fluidFSEventsParamsAdminQuotaGroupName OBJECT-TYPE
       SYNTAX  DisplayString
       MAX-ACCESS  read-only
       STATUS  current
       DESCRIPTION
           "Group name on which the quota is defined"
       ::= { fluidFSEventsParamsAdmin 19 }
    
    
    fluidFSEventsParamsAdminFileLevelReplicationSchedule OBJECT-TYPE
       SYNTAX  DisplayString
       MAX-ACCESS  read-only
       STATUS  current
       DESCRIPTION
           "Scheduling configuration of file level replication"
       ::= { fluidFSEventsParamsAdmin 20 }
    
    
    fluidFSEventsParamsAdminReplicationSource OBJECT-TYPE
       SYNTAX  DisplayString
       MAX-ACCESS  read-only
       STATUS  current
       DESCRIPTION
           "Source volume of block level replication (volume@cluster)"
       ::= { fluidFSEventsParamsAdmin 21 }
    
    
    fluidFSEventsParamsAdminReplicationDestination OBJECT-TYPE
       SYNTAX  DisplayString
       MAX-ACCESS  read-only
       STATUS  current
       DESCRIPTION
           "Destination volume of block level replication (volume@cluster)"
       ::= { fluidFSEventsParamsAdmin 22 }
    
    
    fluidFSEventsParamsAdminReplicationSourceVolume OBJECT-TYPE
       SYNTAX  DisplayString
       MAX-ACCESS  read-only
       STATUS  current
       DESCRIPTION
           "Source volume of block level replication"
       ::= { fluidFSEventsParamsAdmin 23 }
    
    
    fluidFSEventsParamsAdminReplicationDestinationVolume OBJECT-TYPE
       SYNTAX  DisplayString
       MAX-ACCESS  read-only
       STATUS  current
       DESCRIPTION
           "Destination volume of block level replication"
       ::= { fluidFSEventsParamsAdmin 24 }
    
    
    fluidFSEventsParamsAdminReplicationDestinationCluster OBJECT-TYPE
       SYNTAX  DisplayString
       MAX-ACCESS  read-only
       STATUS  current
       DESCRIPTION
           "Destination cluster of block level replication"
       ::= { fluidFSEventsParamsAdmin 25 }
    
    
    fluidFSEventsParamsAdminFileLevelReplicationTask OBJECT-TYPE
       SYNTAX  DisplayString
       MAX-ACCESS  read-only
       STATUS  current
       DESCRIPTION
           "Task name of file level replication"
       ::= { fluidFSEventsParamsAdmin 26 }
    
    
    fluidFSEventsParamsAdminTrustedCluster OBJECT-TYPE
       SYNTAX  DisplayString
       MAX-ACCESS  read-only
       STATUS  current
       DESCRIPTION
           "Trusted cluster name"
       ::= { fluidFSEventsParamsAdmin 27 }
    
    
    fluidFSEventsParamsAdminPackageName OBJECT-TYPE
       SYNTAX  DisplayString
       MAX-ACCESS  read-only
       STATUS  current
       DESCRIPTION
           "Package name"
       ::= { fluidFSEventsParamsAdmin 28 }
    
    
    fluidFSEventsParamsAdminCIFSShareNames OBJECT-TYPE
       SYNTAX  DisplayString
       MAX-ACCESS  read-only
       STATUS  current
       DESCRIPTION
           "CIFSShareNames"
       ::= { fluidFSEventsParamsAdmin 29 }
    
    
    fluidFSEventsParamsAdminSubnetName OBJECT-TYPE
       SYNTAX  DisplayString
       MAX-ACCESS  read-only
       STATUS  current
       DESCRIPTION
           "Subnet name"
       ::= { fluidFSEventsParamsAdmin 30 }
    
    
    fluidFSEventsParamsAdminSrcUsername OBJECT-TYPE
       SYNTAX  DisplayString
       MAX-ACCESS  read-only
       STATUS  current
       DESCRIPTION
           "Source user for user mapping"
       ::= { fluidFSEventsParamsAdmin 31 }
    
    
    fluidFSEventsParamsAdminDstUsername OBJECT-TYPE
       SYNTAX  DisplayString
       MAX-ACCESS  read-only
       STATUS  current
       DESCRIPTION
           "Destination user for user mapping"
       ::= { fluidFSEventsParamsAdmin 32 }
    
    
    fluidFSEventsParamsAdminGuestAccountUsername OBJECT-TYPE
       SYNTAX  DisplayString
       MAX-ACCESS  read-only
       STATUS  current
       DESCRIPTION
           "Protocols guest account"
       ::= { fluidFSEventsParamsAdmin 33 }
    
    
    fluidFSEventsParamsAdminUsersRepositoryType OBJECT-TYPE
       SYNTAX  DisplayString
       MAX-ACCESS  read-only
       STATUS  current
       DESCRIPTION
           "Users repository type (Windows/Unix...)"
       ::= { fluidFSEventsParamsAdmin 34 }
    
    
    fluidFSEventsParamsAdminComponent OBJECT-TYPE
       SYNTAX  DisplayString
       MAX-ACCESS  read-only
       STATUS  current
       DESCRIPTION
           "The API component"
       ::= { fluidFSEventsParamsAdmin 35 }
    
    
    fluidFSEventsParamsAdminArgsList OBJECT-TYPE
       SYNTAX  DisplayString
       MAX-ACCESS  read-only
       STATUS  current
       DESCRIPTION
           "The input arguments"
       ::= { fluidFSEventsParamsAdmin 36 }
    
    
    fluidFSEventsParamsAdminNodeIdEven OBJECT-TYPE
       SYNTAX  DisplayString
       MAX-ACCESS  read-only
       STATUS  current
       DESCRIPTION
           "Even Controller id"
       ::= { fluidFSEventsParamsAdmin 37 }
    
    
    fluidFSEventsParamsAdminNodeIdOdd OBJECT-TYPE
       SYNTAX  DisplayString
       MAX-ACCESS  read-only
       STATUS  current
       DESCRIPTION
           "Odd Controller id"
       ::= { fluidFSEventsParamsAdmin 38 }
    
    
    fluidFSEventsParamsAdminNewSize OBJECT-TYPE
       SYNTAX  DisplayString
       MAX-ACCESS  read-only
       STATUS  current
       DESCRIPTION
           "Size being added to the FS (GB)"
       ::= { fluidFSEventsParamsAdmin 39 }
    
    
    fluidFSEventsParamsAdminLunsList OBJECT-TYPE
       SYNTAX  DisplayString
       MAX-ACCESS  read-only
       STATUS  current
       DESCRIPTION
           "List of LUN id's"
       ::= { fluidFSEventsParamsAdmin 40 }
    
    
    fluidFSEventsParamsAdminSpVersion OBJECT-TYPE
       SYNTAX  DisplayString
       MAX-ACCESS  read-only
       STATUS  current
       DESCRIPTION
           "SP Version"
       ::= { fluidFSEventsParamsAdmin 41 }
    
    
    fluidFSEventsParamsAdminUnsignedNodeId OBJECT-TYPE
       SYNTAX  DisplayString
       MAX-ACCESS  read-only
       STATUS  current
       DESCRIPTION
           "Node id"
       ::= { fluidFSEventsParamsAdmin 42 }
    
    
    fluidFSEventsParamsAdminOldSize OBJECT-TYPE
       SYNTAX  DisplayString
       MAX-ACCESS  read-only
       STATUS  current
       DESCRIPTION
           "Current size of the FS (GB)"
       ::= { fluidFSEventsParamsAdmin 43 }
    
    
    fluidFSEventsParamsAdminSpError OBJECT-TYPE
       SYNTAX  DisplayString
       MAX-ACCESS  read-only
       STATUS  current
       DESCRIPTION
           "SP Error reason"
       ::= { fluidFSEventsParamsAdmin 44 }
    
    
    fluidFSEventsParamsAdminGeneralEventText OBJECT-TYPE
       SYNTAX  DisplayString
       MAX-ACCESS  read-only
       STATUS  current
       DESCRIPTION
           "A general free text parameter, that can be sent to EQL which does not support it yet"
       ::= { fluidFSEventsParamsAdmin 45 }
    
    
    fluidFSEventsParamsAdminNewAtimeValue OBJECT-TYPE
       SYNTAX  DisplayString
       MAX-ACCESS  read-only
       STATUS  current
       DESCRIPTION
           "New value of atime granularity"
       ::= { fluidFSEventsParamsAdmin 46 }
    
    
    fluidFSEventsParamsAdminDiagnosticName OBJECT-TYPE
       SYNTAX  DisplayString
       MAX-ACCESS  read-only
       STATUS  current
       DESCRIPTION
           "The diagnostic name"
       ::= { fluidFSEventsParamsAdmin 47 }
    
    
    fluidFSEventsParamsAdminWWNPort1 OBJECT-TYPE
       SYNTAX  DisplayString
       MAX-ACCESS  read-only
       STATUS  current
       DESCRIPTION
           "WWN Port1"
       ::= { fluidFSEventsParamsAdmin 48 }
    
    
    fluidFSEventsParamsAdminWWNPort2 OBJECT-TYPE
       SYNTAX  DisplayString
       MAX-ACCESS  read-only
       STATUS  current
       DESCRIPTION
           "WWN Port2"
       ::= { fluidFSEventsParamsAdmin 49 }
    
    
    fluidFSEventsParamsAdminNumLuns OBJECT-TYPE
       SYNTAX  DisplayString
       MAX-ACCESS  read-only
       STATUS  current
       DESCRIPTION
           "Number of LUNs added to the FS"
       ::= { fluidFSEventsParamsAdmin 50 }
    
    
    fluidFSEventsParamsAdminUi OBJECT-TYPE
       SYNTAX  DisplayString
       MAX-ACCESS  read-only
       STATUS  current
       DESCRIPTION
           "The interface name"
       ::= { fluidFSEventsParamsAdmin 51 }
    
    
    fluidFSEventsParamsAdminErrCode OBJECT-TYPE
       SYNTAX  INTEGER
       MAX-ACCESS  read-only
       STATUS  current
       DESCRIPTION
           "Internal code of error"
       ::= { fluidFSEventsParamsAdmin 52 }
    
    
    fluidFSEventsParamsAdminControllerId OBJECT-TYPE
       SYNTAX  DisplayString
       MAX-ACCESS  read-only
       STATUS  current
       DESCRIPTION
           "Controller ID"
       ::= { fluidFSEventsParamsAdmin 53 }
    
    
    fluidFSEventsParamsAdminApplianceId OBJECT-TYPE
       SYNTAX  DisplayString
       MAX-ACCESS  read-only
       STATUS  current
       DESCRIPTION
           "NAS appliance ID"
       ::= { fluidFSEventsParamsAdmin 54 }
    
    
    fluidFSEventsParamsAdminApplianceServiceTag OBJECT-TYPE
       SYNTAX  DisplayString
       MAX-ACCESS  read-only
       STATUS  current
       DESCRIPTION
           "NAS appliance service tag"
       ::= { fluidFSEventsParamsAdmin 55 }
    
    
    fluidFSEventsParamsAdminEscalationPeriodInMinutes OBJECT-TYPE
       SYNTAX  DisplayString
       MAX-ACCESS  read-only
       STATUS  current
       DESCRIPTION
           "Escalation Expiration Period (Minutes)"
       ::= { fluidFSEventsParamsAdmin 56 }
    
    
    fluidFSEventsParamsAdminObjectName OBJECT-TYPE
       SYNTAX  DisplayString
       MAX-ACCESS  read-only
       STATUS  current
       DESCRIPTION
           "Name of the configuration object"
       ::= { fluidFSEventsParamsAdmin 57 }
    
    
    fluidFSEventsParamsAdminRecommendedMaxCount OBJECT-TYPE
       SYNTAX  INTEGER
       MAX-ACCESS  read-only
       STATUS  current
       DESCRIPTION
           "recommended maximum amount of the configuration object"
       ::= { fluidFSEventsParamsAdmin 58 }
    
    
    fluidFSEventsParamsAdminFSID OBJECT-TYPE
       SYNTAX  INTEGER
       MAX-ACCESS  read-only
       STATUS  current
       DESCRIPTION
           ""
       ::= { fluidFSEventsParamsAdmin 59 }
    
    
    fluidFSEventsParamsAdminTenantName OBJECT-TYPE
       SYNTAX  DisplayString
       MAX-ACCESS  read-only
       STATUS  current
       DESCRIPTION
           ""
       ::= { fluidFSEventsParamsAdmin 60 }
    
    
    fluidFSEventsParamsAdminVolumeName OBJECT-TYPE
       SYNTAX  DisplayString
       MAX-ACCESS  read-only
       STATUS  current
       DESCRIPTION
           ""
       ::= { fluidFSEventsParamsAdmin 61 }
    
    
    fluidFSEventAdminGeneralFutureTenantScopeEventInfo NOTIFICATION-TYPE
       OBJECTS { sysName, fluidFSEventsParamsAdminTenantId, fluidFSEventsParamsAdminGeneralEventText }
       STATUS current
       DESCRIPTION
           "Tenant scope event. Tenant {{TenantName}} (ID={{TenantId}}): {{generalEventText}}."
           --#TYPE         "Normal Event"
           --#SUMMARY      Tenant scope event. Tenant %s (ID=%s): %s.
           --#ARGUMENTS    {1,2}
           --#SEVERITY     INFORMATIONAL
           --#TIMEINDEX    99
           --#STATE        OK
       ::= { fluidFSEventsAdmin 1 } 
    
    
    fluidFSEventAdminGeneralFutureVolumeScopeEventInfo NOTIFICATION-TYPE
       OBJECTS { sysName, fluidFSEventsParamsAdminFSID, fluidFSEventsParamsAdminGeneralEventText }
       STATUS current
       DESCRIPTION
           "NAS Volume scope event. NAS Volume {{VolumeName}} (ID={{FSID}}): {{generalEventText}}."
           --#TYPE         "Normal Event"
           --#SUMMARY      NAS Volume scope event. NAS Volume %s (ID=%d): %s.
           --#ARGUMENTS    {1,2}
           --#SEVERITY     INFORMATIONAL
           --#TIMEINDEX    99
           --#STATE        OK
       ::= { fluidFSEventsAdmin 11 } 
    
    
    fluidFSEventAdminPauseReplication NOTIFICATION-TYPE
       OBJECTS { sysName, fluidFSEventsParamsAdminUsername, fluidFSEventsParamsAdminReplicationSource, fluidFSEventsParamsAdminReplicationDestination }
       STATUS current
       DESCRIPTION
           "The user {{username}} paused the replication from {{replicationSource}} to {{replicationDestination}}."
           --#TYPE         "Normal Event"
           --#SUMMARY      The user %s paused the replication from %s to %s.
           --#ARGUMENTS    {1,2,3}
           --#SEVERITY     INFORMATIONAL
           --#TIMEINDEX    99
           --#STATE        OK
       ::= { fluidFSEventsAdmin 102 } 
    
    
    fluidFSEventAdminResumeReplication NOTIFICATION-TYPE
       OBJECTS { sysName, fluidFSEventsParamsAdminUsername, fluidFSEventsParamsAdminReplicationSource, fluidFSEventsParamsAdminReplicationDestination }
       STATUS current
       DESCRIPTION
           "The user {{username}} resumed the replication from {{replicationSource}} to {{replicationDestination}}."
           --#TYPE         "Normal Event"
           --#SUMMARY      The user %s resumed the replication from %s to %s.
           --#ARGUMENTS    {1,2,3}
           --#SEVERITY     INFORMATIONAL
           --#TIMEINDEX    99
           --#STATE        OK
       ::= { fluidFSEventsAdmin 103 } 
    
    
    fluidFSEventAdminStartedImmediateReplication NOTIFICATION-TYPE
       OBJECTS { sysName, fluidFSEventsParamsAdminUsername, fluidFSEventsParamsAdminReplicationSource, fluidFSEventsParamsAdminReplicationDestination }
       STATUS current
       DESCRIPTION
           "The user {{username}} started immediate replication from {{replicationSource}} to {{replicationDestination}}."
           --#TYPE         "Normal Event"
           --#SUMMARY      The user %s started immediate replication from %s to %s.
           --#ARGUMENTS    {1,2,3}
           --#SEVERITY     INFORMATIONAL
           --#TIMEINDEX    99
           --#STATE        OK
       ::= { fluidFSEventsAdmin 104 } 
    
    
    fluidFSEventAdminDetachReplication NOTIFICATION-TYPE
       OBJECTS { sysName, fluidFSEventsParamsAdminUsername, fluidFSEventsParamsAdminReplicationSource, fluidFSEventsParamsAdminReplicationDestination }
       STATUS current
       DESCRIPTION
           "The user {{username}} detached the destination NAS volume {{replicationDestination}} from source NAS volume {{replicationSource}}."
           --#TYPE         "Normal Event"
           --#SUMMARY      The user %s detached the destination NAS volume %s from source NAS volume %s.
           --#ARGUMENTS    {1,2,3}
           --#SEVERITY     INFORMATIONAL
           --#TIMEINDEX    99
           --#STATE        OK
       ::= { fluidFSEventsAdmin 105 } 
    
    
    fluidFSEventAdminAttachReplication NOTIFICATION-TYPE
       OBJECTS { sysName, fluidFSEventsParamsAdminUsername, fluidFSEventsParamsAdminReplicationSourceVolume, fluidFSEventsParamsAdminReplicationDestinationVolume, fluidFSEventsParamsAdminReplicationDestinationCluster }
       STATUS current
       DESCRIPTION
           "The user {{username}} attached the destination NAS volume {{replicationDestinationVolume}}@{{replicationDestinationCluster}} to NAS volume {{replicationSourceVolume}}."
           --#TYPE         "Normal Event"
           --#SUMMARY      The user %s attached the destination NAS volume %s@%s to NAS volume %s.
           --#ARGUMENTS    {1,2,3,4}
           --#SEVERITY     INFORMATIONAL
           --#TIMEINDEX    99
           --#STATE        OK
       ::= { fluidFSEventsAdmin 106 } 
    
    
    fluidFSEventAdminAddTrustedCluster NOTIFICATION-TYPE
       OBJECTS { sysName, fluidFSEventsParamsAdminUsername, fluidFSEventsParamsAdminTrustedCluster }
       STATUS current
       DESCRIPTION
           "The user {{username}} added a new replication partner named {{trustedCluster}}."
           --#TYPE         "Normal Event"
           --#SUMMARY      The user %s added a new replication partner named %s.
           --#ARGUMENTS    {1,2}
           --#SEVERITY     INFORMATIONAL
           --#TIMEINDEX    99
           --#STATE        OK
       ::= { fluidFSEventsAdmin 110 } 
    
    
    fluidFSEventAdminUpdateTrustedClusterConf NOTIFICATION-TYPE
       OBJECTS { sysName, fluidFSEventsParamsAdminUsername, fluidFSEventsParamsAdminTrustedCluster }
       STATUS current
       DESCRIPTION
           "The user {{username}} updated the replication partner configuration for {{trustedCluster}}."
           --#TYPE         "Normal Event"
           --#SUMMARY      The user %s updated the replication partner configuration for %s.
           --#ARGUMENTS    {1,2}
           --#SEVERITY     INFORMATIONAL
           --#TIMEINDEX    99
           --#STATE        OK
       ::= { fluidFSEventsAdmin 111 } 
    
    
    fluidFSEventAdminRemoveTrustedCluster NOTIFICATION-TYPE
       OBJECTS { sysName, fluidFSEventsParamsAdminUsername, fluidFSEventsParamsAdminTrustedCluster }
       STATUS current
       DESCRIPTION
           "The user {{username}} removed the cluster {{trustedCluster}} from the list of replication partners."
           --#TYPE         "Normal Event"
           --#SUMMARY      The user %s removed the cluster %s from the list of replication partners.
           --#ARGUMENTS    {1,2}
           --#SEVERITY     INFORMATIONAL
           --#TIMEINDEX    99
           --#STATE        OK
       ::= { fluidFSEventsAdmin 112 } 
    
    
    fluidFSEventAdminSpInstalled NOTIFICATION-TYPE
       OBJECTS { sysName, fluidFSEventsParamsAdminPackageName }
       STATUS current
       DESCRIPTION
           "{{packageName}} bundle installation completed successfully."
           --#TYPE         "Normal Event"
           --#SUMMARY      %s bundle installation completed successfully.
           --#ARGUMENTS    {1}
           --#SEVERITY     MAJOR
           --#TIMEINDEX    99
           --#STATE        OK
       ::= { fluidFSEventsAdmin 122 } 
    
    
    fluidFSEventAdminServicePackStarted NOTIFICATION-TYPE
       OBJECTS { sysName, fluidFSEventsParamsAdminSpVersion }
       STATUS current
       DESCRIPTION
           "Firmware DellFluidFS-{{spVersion}} installation started   Description:  Firmware DellFluidFS-{{spVersion}} installation started   Action Items:  You should follow the installation process in the CLI / WUI and the event log to verify it successfully completes"
           --#TYPE         "Normal Event"
           --#SUMMARY      Firmware DellFluidFS-%s installation started   Description:  Firmware DellFluidFS-%s installation started   Action Items:  You should follow the installation process in the CLI / WUI and the event log to verify it successfully completes
           --#ARGUMENTS    {1}
           --#SEVERITY     INFORMATIONAL
           --#TIMEINDEX    99
           --#STATE        OK
       ::= { fluidFSEventsAdmin 154 } 
    
    
    fluidFSEventAdminServicePackFailed NOTIFICATION-TYPE
       OBJECTS { sysName, fluidFSEventsParamsAdminSpVersion, fluidFSEventsParamsAdminSpError }
       STATUS current
       DESCRIPTION
           "Firmware DellFluidFS-{{spVersion}} failed to install.   Description:  Firmware DellFluidFS-{{spVersion}} failed to install, reason: {{spError}}.   Action Items:  System may be in inconsistent state, please check system validation in CLI / WUI.[[nl]]If system is in unstable state (i.e. some controllers are reported down) then escalate to resolve the situation."
           --#TYPE         "Normal Event"
           --#SUMMARY      Firmware DellFluidFS-%s failed to install.   Description:  Firmware DellFluidFS-%s failed to install, reason: %s.   Action Items:  System may be in inconsistent state, please check system validation in CLI / WUI.[[nl]]If system is in unstable state (i.e. some controllers are reported down) then escalate to resolve the situation.
           --#ARGUMENTS    {1,2}
           --#SEVERITY     MAJOR
           --#TIMEINDEX    99
           --#STATE        OK
       ::= { fluidFSEventsAdmin 155 } 
    
    
    fluidFSEventAdminServicePackFinished NOTIFICATION-TYPE
       OBJECTS { sysName, fluidFSEventsParamsAdminSpVersion }
       STATUS current
       DESCRIPTION
           "Successfully upgraded to firmware DellFluidFS-{{spVersion}}."
           --#TYPE         "Normal Event"
           --#SUMMARY      Successfully upgraded to firmware DellFluidFS-%s.
           --#ARGUMENTS    {1}
           --#SEVERITY     INFORMATIONAL
           --#TIMEINDEX    99
           --#STATE        OK
       ::= { fluidFSEventsAdmin 156 } 
    
    
    fluidFSEventAdminGeneralFutureEventInfo NOTIFICATION-TYPE
       OBJECTS { sysName, fluidFSEventsParamsAdminGeneralEventText }
       STATUS current
       DESCRIPTION
           "{{generalEventText}}"
           --#TYPE         "Normal Event"
           --#SUMMARY      %s
           --#ARGUMENTS    {1}
           --#SEVERITY     INFORMATIONAL
           --#TIMEINDEX    99
           --#STATE        OK
       ::= { fluidFSEventsAdmin 162 } 
    
    
    fluidFSEventAdminGeneralFutureEventMajor NOTIFICATION-TYPE
       OBJECTS { sysName, fluidFSEventsParamsAdminGeneralEventText }
       STATUS current
       DESCRIPTION
           "{{generalEventText}}"
           --#TYPE         "Normal Event"
           --#SUMMARY      %s
           --#ARGUMENTS    {1}
           --#SEVERITY     MAJOR
           --#TIMEINDEX    99
           --#STATE        OK
       ::= { fluidFSEventsAdmin 163 } 
    
    
    fluidFSEventAdminGeneralFutureEventCrit NOTIFICATION-TYPE
       OBJECTS { sysName, fluidFSEventsParamsAdminGeneralEventText }
       STATUS current
       DESCRIPTION
           "{{generalEventText}}"
           --#TYPE         "Normal Event"
           --#SUMMARY      %s
           --#ARGUMENTS    {1}
           --#SEVERITY     INFORMATIONAL
           --#TIMEINDEX    99
           --#STATE        OK
       ::= { fluidFSEventsAdmin 164 } 
    
    
    fluidFSEventAdminGeneralFutureEventWarning NOTIFICATION-TYPE
       OBJECTS { sysName, fluidFSEventsParamsAdminGeneralEventText }
       STATUS current
       DESCRIPTION
           "{{generalEventText}}"
           --#TYPE         "Normal Event"
           --#SUMMARY      %s
           --#ARGUMENTS    {1}
           --#SEVERITY     INFORMATIONAL
           --#TIMEINDEX    99
           --#STATE        OK
       ::= { fluidFSEventsAdmin 165 } 
    
    
    fluidFSEventAdminCancelReplication NOTIFICATION-TYPE
       OBJECTS { sysName, fluidFSEventsParamsAdminUsername, fluidFSEventsParamsAdminReplicationSource, fluidFSEventsParamsAdminReplicationDestination }
       STATUS current
       DESCRIPTION
           "{{username}} cancelled the replication from {{replicationSource}} to {{replicationDestination}}."
           --#TYPE         "Normal Event"
           --#SUMMARY      %s cancelled the replication from %s to %s.
           --#ARGUMENTS    {1,2,3}
           --#SEVERITY     INFORMATIONAL
           --#TIMEINDEX    99
           --#STATE        OK
       ::= { fluidFSEventsAdmin 167 } 
    
    
    fluidFSEventAdminDisableReplication NOTIFICATION-TYPE
       OBJECTS { sysName, fluidFSEventsParamsAdminUsername, fluidFSEventsParamsAdminReplicationSource, fluidFSEventsParamsAdminReplicationDestination }
       STATUS current
       DESCRIPTION
           "Replication-policy of NAS volumes {{replicationSource}} and {{replicationDestination}} was disabled.   Description:  The user {{username}} disabled the replication-policy of the destination NAS volume {{replicationDestination}} and the source NAS volume {{replicationSource}}."
           --#TYPE         "Normal Event"
           --#SUMMARY      Replication-policy of NAS volumes %s and %s was disabled.   Description:  The user %s disabled the replication-policy of the destination NAS volume %s and the source NAS volume %s.
           --#ARGUMENTS    {1,2,3}
           --#SEVERITY     INFORMATIONAL
           --#TIMEINDEX    99
           --#STATE        OK
       ::= { fluidFSEventsAdmin 170 } 
    
    
    fluidFSEventAdminEnableReplication NOTIFICATION-TYPE
       OBJECTS { sysName, fluidFSEventsParamsAdminUsername, fluidFSEventsParamsAdminReplicationSourceVolume, fluidFSEventsParamsAdminReplicationDestinationVolume, fluidFSEventsParamsAdminReplicationDestinationCluster }
       STATUS current
       DESCRIPTION
           "Replication-policy of NAS volumes {{replicationSourceVolume}} and {{replicationDestinationVolume}} was enabled.   Description:  The user {{username}} enabled replication: re-attached NAS volume {{replicationDestinationVolume}} on cluster {{replicationDestinationCluster}} to local NAS volume {{replicationSourceVolume}}."
           --#TYPE         "Normal Event"
           --#SUMMARY      Replication-policy of NAS volumes %s and %s was enabled.   Description:  The user %s enabled replication: re-attached NAS volume %s on cluster %s to local NAS volume %s.
           --#ARGUMENTS    {1,2,3,4}
           --#SEVERITY     INFORMATIONAL
           --#TIMEINDEX    99
           --#STATE        OK
       ::= { fluidFSEventsAdmin 171 } 
    
    
    fluidFSEventAdminAdminLoggedInToInterface NOTIFICATION-TYPE
       OBJECTS { sysName, fluidFSEventsParamsAdminUsername, fluidFSEventsParamsAdminUi }
       STATUS current
       DESCRIPTION
           "The user {{username}} logged in to {{ui}}."
           --#TYPE         "Normal Event"
           --#SUMMARY      The user %s logged in to %s.
           --#ARGUMENTS    {1,2}
           --#SEVERITY     INFORMATIONAL
           --#TIMEINDEX    99
           --#STATE        OK
       ::= { fluidFSEventsAdmin 180 } 
    
    
    fluidFSEventAdminFormatFileSystemMkfsFailed NOTIFICATION-TYPE
       OBJECTS { sysName, fluidFSEventsParamsAdminErrCode }
       STATUS current
       DESCRIPTION
           "Format failed during execution of File System Structures Initialization phase.   Internal Information:  mkfs.sh failed with error code {{ErrCode}}"
           --#TYPE         "Normal Event"
           --#SUMMARY      Format failed during execution of File System Structures Initialization phase.   Internal Information:  mkfs.sh failed with error code %d
           --#ARGUMENTS    {1}
           --#SEVERITY     INFORMATIONAL
           --#TIMEINDEX    99
           --#STATE        OK
       ::= { fluidFSEventsAdmin 181 } 
    
    
    fluidFSEventAdminIncrementalFormatFileSystemMkfsFailed NOTIFICATION-TYPE
       OBJECTS { sysName, fluidFSEventsParamsAdminErrCode }
       STATUS current
       DESCRIPTION
           "Incremental Format failed during execution of File System Structures Initialization phase.   Internal Information:  mkfs.sh failed with error code {{ErrCode}}"
           --#TYPE         "Normal Event"
           --#SUMMARY      Incremental Format failed during execution of File System Structures Initialization phase.   Internal Information:  mkfs.sh failed with error code %d
           --#ARGUMENTS    {1}
           --#SEVERITY     INFORMATIONAL
           --#TIMEINDEX    99
           --#STATE        OK
       ::= { fluidFSEventsAdmin 182 } 
    
    
    fluidFSEventAdminControllerAutoAttachStart NOTIFICATION-TYPE
       OBJECTS { sysName, fluidFSEventsParamsAdminControllerId, fluidFSEventsParamsAdminApplianceId }
       STATUS current
       DESCRIPTION
           "Auto attach of NAS controller {{controllerId}} in appliance {{applianceId}} has started.   Action Items:  You should follow the attachment process in the CLI / WUI to verify it successfully completes."
           --#TYPE         "Normal Event"
           --#SUMMARY      Auto attach of NAS controller %s in appliance %s has started.   Action Items:  You should follow the attachment process in the CLI / WUI to verify it successfully completes.
           --#ARGUMENTS    {1,2}
           --#SEVERITY     INFORMATIONAL
           --#TIMEINDEX    99
           --#STATE        OK
       ::= { fluidFSEventsAdmin 185 } 
    
    
    fluidFSEventAdminControllerAutoDetachStart NOTIFICATION-TYPE
       OBJECTS { sysName, fluidFSEventsParamsAdminControllerId, fluidFSEventsParamsAdminApplianceId }
       STATUS current
       DESCRIPTION
           "Auto detach of NAS controller {{controllerId}} in appliance {{applianceId}} has started.   Action Items:  You should follow the detachment process in the CLI / WUI to verify it successfully completes."
           --#TYPE         "Normal Event"
           --#SUMMARY      Auto detach of NAS controller %s in appliance %s has started.   Action Items:  You should follow the detachment process in the CLI / WUI to verify it successfully completes.
           --#ARGUMENTS    {1,2}
           --#SEVERITY     INFORMATIONAL
           --#TIMEINDEX    99
           --#STATE        OK
       ::= { fluidFSEventsAdmin 186 } 
    
    
    fluidFSEventAdminApplianceCreateStart NOTIFICATION-TYPE
       OBJECTS { sysName, fluidFSEventsParamsAdminApplianceId, fluidFSEventsParamsAdminApplianceServiceTag }
       STATUS current
       DESCRIPTION
           "Create of NAS Appliance {{applianceId}} ({{applianceServiceTag}}) has started.   Action Items:  You should follow the appliance create process in the CLI / WUI to verify it successfully completes."
           --#TYPE         "Normal Event"
           --#SUMMARY      Create of NAS Appliance %s (%s) has started.   Action Items:  You should follow the appliance create process in the CLI / WUI to verify it successfully completes.
           --#ARGUMENTS    {1,2}
           --#SEVERITY     INFORMATIONAL
           --#TIMEINDEX    99
           --#STATE        OK
       ::= { fluidFSEventsAdmin 187 } 
    
    
    fluidFSEventAdminEnableEscalationAccess NOTIFICATION-TYPE
       OBJECTS { sysName, fluidFSEventsParamsAdminEscalationPeriodInMinutes }
       STATUS current
       DESCRIPTION
           "Escalation access was enabled for {{escalationPeriodInMinutes}} minutes."
           --#TYPE         "Normal Event"
           --#SUMMARY      Escalation access was enabled for %s minutes.
           --#ARGUMENTS    {1}
           --#SEVERITY     INFORMATIONAL
           --#TIMEINDEX    99
           --#STATE        OK
       ::= { fluidFSEventsAdmin 188 } 
    
    
    fluidFSEventAdminConfigurationObjectSoftLimitExceeded NOTIFICATION-TYPE
       OBJECTS { sysName, fluidFSEventsParamsAdminUsername, fluidFSEventsParamsAdminObjectName, fluidFSEventsParamsAdminRecommendedMaxCount }
       STATUS current
       DESCRIPTION
           "User {{username}} created {{objectName}} exceeding the maximum recommended count {{recommendedMaxCount}}."
           --#TYPE         "Normal Event"
           --#SUMMARY      User %s created %s exceeding the maximum recommended count %d.
           --#ARGUMENTS    {1,2,3}
           --#SEVERITY     INFORMATIONAL
           --#TIMEINDEX    99
           --#STATE        OK
       ::= { fluidFSEventsAdmin 189 } 
    
    
    fluidFSEventAdminControllerAttachStart NOTIFICATION-TYPE
       OBJECTS { sysName, fluidFSEventsParamsAdminControllerId, fluidFSEventsParamsAdminUsername }
       STATUS current
       DESCRIPTION
           "Attach of NAS controller {{controllerId}} has started by {{username}}."
           --#TYPE         "Normal Event"
           --#SUMMARY      Attach of NAS controller %s has started by %s.
           --#ARGUMENTS    {1,2}
           --#SEVERITY     INFORMATIONAL
           --#TIMEINDEX    99
           --#STATE        OK
       ::= { fluidFSEventsAdmin 190 } 
    
    
    fluidFSEventAdminControllerAttachEnd NOTIFICATION-TYPE
       OBJECTS { sysName, fluidFSEventsParamsAdminControllerId }
       STATUS current
       DESCRIPTION
           "Attach of NAS controller {{controllerId}} has completed successfully."
           --#TYPE         "Normal Event"
           --#SUMMARY      Attach of NAS controller %s has completed successfully.
           --#ARGUMENTS    {1}
           --#SEVERITY     INFORMATIONAL
           --#TIMEINDEX    99
           --#STATE        OK
       ::= { fluidFSEventsAdmin 191 } 
    
    
    fluidFSEventAdminControllerDetachStart NOTIFICATION-TYPE
       OBJECTS { sysName, fluidFSEventsParamsAdminControllerId, fluidFSEventsParamsAdminUsername }
       STATUS current
       DESCRIPTION
           "Detach of NAS controller {{controllerId}} was started by {{username}}."
           --#TYPE         "Normal Event"
           --#SUMMARY      Detach of NAS controller %s was started by %s.
           --#ARGUMENTS    {1,2}
           --#SEVERITY     INFORMATIONAL
           --#TIMEINDEX    99
           --#STATE        OK
       ::= { fluidFSEventsAdmin 192 } 
    
    
    fluidFSEventAdminControllerDetachEnd NOTIFICATION-TYPE
       OBJECTS { sysName, fluidFSEventsParamsAdminControllerId }
       STATUS current
       DESCRIPTION
           "Detach of NAS controller {{controllerId}} has completed successfully."
           --#TYPE         "Normal Event"
           --#SUMMARY      Detach of NAS controller %s has completed successfully.
           --#ARGUMENTS    {1}
           --#SEVERITY     INFORMATIONAL
           --#TIMEINDEX    99
           --#STATE        OK
       ::= { fluidFSEventsAdmin 193 } 
    
    
    fluidFSEventAdminApplianceJoinStart NOTIFICATION-TYPE
       OBJECTS { sysName, fluidFSEventsParamsAdminApplianceId, fluidFSEventsParamsAdminUsername }
       STATUS current
       DESCRIPTION
           "Join of NAS Appliance {{applianceId}} was started by {{username}}.   Action Items:  You should follow the appliance join process in the CLI / WUI to verify it successfully completes."
           --#TYPE         "Normal Event"
           --#SUMMARY      Join of NAS Appliance %s was started by %s.   Action Items:  You should follow the appliance join process in the CLI / WUI to verify it successfully completes.
           --#ARGUMENTS    {1,2}
           --#SEVERITY     INFORMATIONAL
           --#TIMEINDEX    99
           --#STATE        OK
       ::= { fluidFSEventsAdmin 194 } 
    
    
    fluidFSEventAdminApplianceJoinEnd NOTIFICATION-TYPE
       OBJECTS { sysName, fluidFSEventsParamsAdminApplianceId }
       STATUS current
       DESCRIPTION
           "Join of NAS Appliance {{applianceId}} has completed successfully."
           --#TYPE         "Normal Event"
           --#SUMMARY      Join of NAS Appliance %s has completed successfully.
           --#ARGUMENTS    {1}
           --#SEVERITY     INFORMATIONAL
           --#TIMEINDEX    99
           --#STATE        OK
       ::= { fluidFSEventsAdmin 195 } 
    
    
    fluidFSEventsParamsHardware OBJECT IDENTIFIER ::= { fluidFSEventsParams 2 } 
    
    
    fluidFSEventsHardware OBJECT IDENTIFIER ::= { fluidFSEvents 2 } 
    
    
    fluidFSEventsParamsHardwareNodeName OBJECT-TYPE
       SYNTAX  DisplayString
       MAX-ACCESS  read-only
       STATUS  current
       DESCRIPTION
           "Controller name"
       ::= { fluidFSEventsParamsHardware 1 }
    
    
    fluidFSEventsParamsHardwareNetworkId OBJECT-TYPE
       SYNTAX  DisplayString
       MAX-ACCESS  read-only
       STATUS  current
       DESCRIPTION
           ""
       ::= { fluidFSEventsParamsHardware 2 }
    
    
    fluidFSEventsParamsHardwarePrefix OBJECT-TYPE
       SYNTAX  INTEGER
       MAX-ACCESS  read-only
       STATUS  current
       DESCRIPTION
           ""
       ::= { fluidFSEventsParamsHardware 3 }
    
    
    fluidFSEventsParamsHardwareCpuName OBJECT-TYPE
       SYNTAX  DisplayString
       MAX-ACCESS  read-only
       STATUS  current
       DESCRIPTION
           "CPU name in the controller"
       ::= { fluidFSEventsParamsHardware 4 }
    
    
    fluidFSEventsParamsHardwareCpuTemperature OBJECT-TYPE
       SYNTAX  DisplayString
       MAX-ACCESS  read-only
       STATUS  current
       DESCRIPTION
           "CPU temprature"
       ::= { fluidFSEventsParamsHardware 5 }
    
    
    fluidFSEventsParamsHardwareVlanTag OBJECT-TYPE
       SYNTAX  INTEGER
       MAX-ACCESS  read-only
       STATUS  current
       DESCRIPTION
           ""
       ::= { fluidFSEventsParamsHardware 6 }
    
    
    fluidFSEventsParamsHardwareDestinationNetwork OBJECT-TYPE
       SYNTAX  DisplayString
       MAX-ACCESS  read-only
       STATUS  current
       DESCRIPTION
           ""
       ::= { fluidFSEventsParamsHardware 7 }
    
    
    fluidFSEventsParamsHardwareCpuSpeed OBJECT-TYPE
       SYNTAX  INTEGER
       MAX-ACCESS  read-only
       STATUS  current
       DESCRIPTION
           "CPU speed"
       ::= { fluidFSEventsParamsHardware 8 }
    
    
    fluidFSEventsParamsHardwareAverageSpeed OBJECT-TYPE
       SYNTAX  INTEGER
       MAX-ACCESS  read-only
       STATUS  current
       DESCRIPTION
           "Average CPU speed"
       ::= { fluidFSEventsParamsHardware 9 }
    
    
    fluidFSEventsParamsHardwareNodeId OBJECT-TYPE
       SYNTAX  INTEGER
       MAX-ACCESS  read-only
       STATUS  current
       DESCRIPTION
           "Controller id"
       ::= { fluidFSEventsParamsHardware 10 }
    
    
    fluidFSEventsParamsHardwareNetworkName OBJECT-TYPE
       SYNTAX  DisplayString
       MAX-ACCESS  read-only
       STATUS  current
       DESCRIPTION
           "Network name"
       ::= { fluidFSEventsParamsHardware 11 }
    
    
    fluidFSEventsParamsHardwarePacketLoss OBJECT-TYPE
       SYNTAX  INTEGER
       MAX-ACCESS  read-only
       STATUS  current
       DESCRIPTION
           "Packet loss percentage"
       ::= { fluidFSEventsParamsHardware 12 }
    
    
    fluidFSEventsParamsHardwareEthName OBJECT-TYPE
       SYNTAX  DisplayString
       MAX-ACCESS  read-only
       STATUS  current
       DESCRIPTION
           "Eth name"
       ::= { fluidFSEventsParamsHardware 13 }
    
    
    fluidFSEventsParamsHardwareLunId OBJECT-TYPE
       SYNTAX  DisplayString
       MAX-ACCESS  read-only
       STATUS  current
       DESCRIPTION
           "LUN SCSI ID"
       ::= { fluidFSEventsParamsHardware 14 }
    
    
    fluidFSEventsParamsHardwareFromNode OBJECT-TYPE
       SYNTAX  INTEGER
       MAX-ACCESS  read-only
       STATUS  current
       DESCRIPTION
           ""
       ::= { fluidFSEventsParamsHardware 15 }
    
    
    fluidFSEventsParamsHardwareToNode OBJECT-TYPE
       SYNTAX  INTEGER
       MAX-ACCESS  read-only
       STATUS  current
       DESCRIPTION
           ""
       ::= { fluidFSEventsParamsHardware 16 }
    
    
    fluidFSEventsParamsHardwareFromEth OBJECT-TYPE
       SYNTAX  DisplayString
       MAX-ACCESS  read-only
       STATUS  current
       DESCRIPTION
           ""
       ::= { fluidFSEventsParamsHardware 17 }
    
    
    fluidFSEventsParamsHardwareToEth OBJECT-TYPE
       SYNTAX  DisplayString
       MAX-ACCESS  read-only
       STATUS  current
       DESCRIPTION
           ""
       ::= { fluidFSEventsParamsHardware 18 }
    
    
    fluidFSEventsParamsHardwareTapeName OBJECT-TYPE
       SYNTAX  DisplayString
       MAX-ACCESS  read-only
       STATUS  current
       DESCRIPTION
           "Tape device name"
       ::= { fluidFSEventsParamsHardware 19 }
    
    
    fluidFSEventsParamsHardwareBatteryPercentage OBJECT-TYPE
       SYNTAX  INTEGER
       MAX-ACCESS  read-only
       STATUS  current
       DESCRIPTION
           "BPS battery percentage"
       ::= { fluidFSEventsParamsHardware 20 }
    
    
    fluidFSEventsParamsHardwareBatteryRemainTime OBJECT-TYPE
       SYNTAX  INTEGER
       MAX-ACCESS  read-only
       STATUS  current
       DESCRIPTION
           "BPS battery remaining time"
       ::= { fluidFSEventsParamsHardware 21 }
    
    
    fluidFSEventsParamsHardwareSubnetName OBJECT-TYPE
       SYNTAX  DisplayString
       MAX-ACCESS  read-only
       STATUS  current
       DESCRIPTION
           "Subnet name"
       ::= { fluidFSEventsParamsHardware 22 }
    
    
    fluidFSEventsParamsHardwareHostName OBJECT-TYPE
       SYNTAX  DisplayString
       MAX-ACCESS  read-only
       STATUS  current
       DESCRIPTION
           "Host name"
       ::= { fluidFSEventsParamsHardware 23 }
    
    
    fluidFSEventsParamsHardwareBatteryLastReplace OBJECT-TYPE
       SYNTAX  INTEGER
       MAX-ACCESS  read-only
       STATUS  current
       DESCRIPTION
           "Battery Last Replace"
       ::= { fluidFSEventsParamsHardware 24 }
    
    
    fluidFSEventsParamsHardwareDeviceTypeName OBJECT-TYPE
       SYNTAX  DisplayString
       MAX-ACCESS  read-only
       STATUS  current
       DESCRIPTION
           "Device Type Name"
       ::= { fluidFSEventsParamsHardware 25 }
    
    
    fluidFSEventsParamsHardwareDeviceName OBJECT-TYPE
       SYNTAX  DisplayString
       MAX-ACCESS  read-only
       STATUS  current
       DESCRIPTION
           "Device Name"
       ::= { fluidFSEventsParamsHardware 26 }
    
    
    fluidFSEventsParamsHardwareTemperature OBJECT-TYPE
       SYNTAX  INTEGER
       MAX-ACCESS  read-only
       STATUS  current
       DESCRIPTION
           "Temperature"
       ::= { fluidFSEventsParamsHardware 27 }
    
    
    fluidFSEventsParamsHardwareMeltingDistance OBJECT-TYPE
       SYNTAX  INTEGER
       MAX-ACCESS  read-only
       STATUS  current
       DESCRIPTION
           "Melting Distance"
       ::= { fluidFSEventsParamsHardware 28 }
    
    
    fluidFSEventsParamsHardwareDeviceState OBJECT-TYPE
       SYNTAX  DisplayString
       MAX-ACCESS  read-only
       STATUS  current
       DESCRIPTION
           "Device State"
       ::= { fluidFSEventsParamsHardware 29 }
    
    
    fluidFSEventsParamsHardwareFirstNodeId OBJECT-TYPE
       SYNTAX  INTEGER
       MAX-ACCESS  read-only
       STATUS  current
       DESCRIPTION
           "First Controller ID"
       ::= { fluidFSEventsParamsHardware 30 }
    
    
    fluidFSEventsParamsHardwareSecondNodeId OBJECT-TYPE
       SYNTAX  INTEGER
       MAX-ACCESS  read-only
       STATUS  current
       DESCRIPTION
           "Second Controller ID"
       ::= { fluidFSEventsParamsHardware 31 }
    
    
    fluidFSEventsParamsHardwareBondName OBJECT-TYPE
       SYNTAX  DisplayString
       MAX-ACCESS  read-only
       STATUS  current
       DESCRIPTION
           "Bond Name"
       ::= { fluidFSEventsParamsHardware 32 }
    
    
    fluidFSEventsParamsHardwareBandwidth OBJECT-TYPE
       SYNTAX  INTEGER
       MAX-ACCESS  read-only
       STATUS  current
       DESCRIPTION
           "Bandwidth"
       ::= { fluidFSEventsParamsHardware 33 }
    
    
    fluidFSEventsParamsHardwareDiskName OBJECT-TYPE
       SYNTAX  DisplayString
       MAX-ACCESS  read-only
       STATUS  current
       DESCRIPTION
           "Local disk name"
       ::= { fluidFSEventsParamsHardware 34 }
    
    
    fluidFSEventsParamsHardwareMemoryFirstNode OBJECT-TYPE
       SYNTAX  DisplayString
       MAX-ACCESS  read-only
       STATUS  current
       DESCRIPTION
           "Memory on first controller"
       ::= { fluidFSEventsParamsHardware 35 }
    
    
    fluidFSEventsParamsHardwareMemorySecondNode OBJECT-TYPE
       SYNTAX  DisplayString
       MAX-ACCESS  read-only
       STATUS  current
       DESCRIPTION
           "Memory on second controller"
       ::= { fluidFSEventsParamsHardware 36 }
    
    
    fluidFSEventsParamsHardwareActualMtu OBJECT-TYPE
       SYNTAX  INTEGER
       MAX-ACCESS  read-only
       STATUS  current
       DESCRIPTION
           "Actual MTU"
       ::= { fluidFSEventsParamsHardware 37 }
    
    
    fluidFSEventsParamsHardwareOptimalMtu OBJECT-TYPE
       SYNTAX  INTEGER
       MAX-ACCESS  read-only
       STATUS  current
       DESCRIPTION
           "Optimal Mtu"
       ::= { fluidFSEventsParamsHardware 38 }
    
    
    fluidFSEventsParamsHardwareBpsLogInfo OBJECT-TYPE
       SYNTAX  DisplayString
       MAX-ACCESS  read-only
       STATUS  current
       DESCRIPTION
           "Bps Log Info"
       ::= { fluidFSEventsParamsHardware 39 }
    
    
    fluidFSEventsParamsHardwareBpsAlarm OBJECT-TYPE
       SYNTAX  DisplayString
       MAX-ACCESS  read-only
       STATUS  current
       DESCRIPTION
           "BPS Alarm message"
       ::= { fluidFSEventsParamsHardware 40 }
    
    
    fluidFSEventsParamsHardwarePowerSuppliesRedundancyStatus OBJECT-TYPE
       SYNTAX  DisplayString
       MAX-ACCESS  read-only
       STATUS  current
       DESCRIPTION
           "power supplies redundancy status"
       ::= { fluidFSEventsParamsHardware 41 }
    
    
    fluidFSEventsParamsHardwarePowerSuppliesElementStatus OBJECT-TYPE
       SYNTAX  DisplayString
       MAX-ACCESS  read-only
       STATUS  current
       DESCRIPTION
           "power supplies element status"
       ::= { fluidFSEventsParamsHardware 42 }
    
    
    fluidFSEventsParamsHardwarePowerSuppliesElementLocation OBJECT-TYPE
       SYNTAX  DisplayString
       MAX-ACCESS  read-only
       STATUS  current
       DESCRIPTION
           "power supplies element location"
       ::= { fluidFSEventsParamsHardware 43 }
    
    
    fluidFSEventsParamsHardwarePowerSuppliesElementsCount OBJECT-TYPE
       SYNTAX  INTEGER
       MAX-ACCESS  read-only
       STATUS  current
       DESCRIPTION
           "The number of power supplies elements"
       ::= { fluidFSEventsParamsHardware 44 }
    
    
    fluidFSEventsParamsHardwareChassisID OBJECT-TYPE
       SYNTAX  DisplayString
       MAX-ACCESS  read-only
       STATUS  current
       DESCRIPTION
           "Appliance chassis ID"
       ::= { fluidFSEventsParamsHardware 45 }
    
    
    fluidFSEventsParamsHardwareTemperatureSensorName OBJECT-TYPE
       SYNTAX  DisplayString
       MAX-ACCESS  read-only
       STATUS  current
       DESCRIPTION
           "Temperature sensor name"
       ::= { fluidFSEventsParamsHardware 46 }
    
    
    fluidFSEventsParamsHardwareTemperatureSensorStatus OBJECT-TYPE
       SYNTAX  DisplayString
       MAX-ACCESS  read-only
       STATUS  current
       DESCRIPTION
           "Temperature sensor status"
       ::= { fluidFSEventsParamsHardware 47 }
    
    
    fluidFSEventsParamsHardwareTemperatureSensorValue OBJECT-TYPE
       SYNTAX  INTEGER
       MAX-ACCESS  read-only
       STATUS  current
       DESCRIPTION
           "Temperature sensor value"
       ::= { fluidFSEventsParamsHardware 48 }
    
    
    fluidFSEventsParamsHardwareTemperatureSensorErrorThreshold OBJECT-TYPE
       SYNTAX  INTEGER
       MAX-ACCESS  read-only
       STATUS  current
       DESCRIPTION
           "Temperature sensor error threshold"
       ::= { fluidFSEventsParamsHardware 49 }
    
    
    fluidFSEventsParamsHardwareTemperatureSensorWarningThreshold OBJECT-TYPE
       SYNTAX  INTEGER
       MAX-ACCESS  read-only
       STATUS  current
       DESCRIPTION
           "Temperature sensor warning threshold"
       ::= { fluidFSEventsParamsHardware 50 }
    
    
    fluidFSEventsParamsHardwarePowerSupplyName OBJECT-TYPE
       SYNTAX  DisplayString
       MAX-ACCESS  read-only
       STATUS  current
       DESCRIPTION
           "Power supply name"
       ::= { fluidFSEventsParamsHardware 51 }
    
    
    fluidFSEventsParamsHardwarePowerSupplyStatus OBJECT-TYPE
       SYNTAX  DisplayString
       MAX-ACCESS  read-only
       STATUS  current
       DESCRIPTION
           "Power supply status"
       ::= { fluidFSEventsParamsHardware 52 }
    
    
    fluidFSEventsParamsHardwareBpsName OBJECT-TYPE
       SYNTAX  DisplayString
       MAX-ACCESS  read-only
       STATUS  current
       DESCRIPTION
           "BPS name"
       ::= { fluidFSEventsParamsHardware 53 }
    
    
    fluidFSEventsParamsHardwareBpsStatus OBJECT-TYPE
       SYNTAX  DisplayString
       MAX-ACCESS  read-only
       STATUS  current
       DESCRIPTION
           "BPS status"
       ::= { fluidFSEventsParamsHardware 54 }
    
    
    fluidFSEventsParamsHardwareBpsBatteryRuntime OBJECT-TYPE
       SYNTAX  INTEGER
       MAX-ACCESS  read-only
       STATUS  current
       DESCRIPTION
           "BPS battery runtime"
       ::= { fluidFSEventsParamsHardware 55 }
    
    
    fluidFSEventsParamsHardwareBpsBatteryCharge OBJECT-TYPE
       SYNTAX  INTEGER
       MAX-ACCESS  read-only
       STATUS  current
       DESCRIPTION
           "BPS battery charge"
       ::= { fluidFSEventsParamsHardware 56 }
    
    
    fluidFSEventsParamsHardwareComponentIndex OBJECT-TYPE
       SYNTAX  INTEGER
       MAX-ACCESS  read-only
       STATUS  current
       DESCRIPTION
           "Component index in group of components"
       ::= { fluidFSEventsParamsHardware 57 }
    
    
    fluidFSEventsParamsHardwareChassisId OBJECT-TYPE
       SYNTAX  DisplayString
       MAX-ACCESS  read-only
       STATUS  current
       DESCRIPTION
           "deprecated - a duplication of above parameter chassisID"
       ::= { fluidFSEventsParamsHardware 58 }
    
    
    fluidFSEventsParamsHardwareApplianceServiceTag OBJECT-TYPE
       SYNTAX  DisplayString
       MAX-ACCESS  read-only
       STATUS  current
       DESCRIPTION
           "Appliance service tag"
       ::= { fluidFSEventsParamsHardware 59 }
    
    
    fluidFSEventsParamsHardwareApplianceId OBJECT-TYPE
       SYNTAX  INTEGER
       MAX-ACCESS  read-only
       STATUS  current
       DESCRIPTION
           "Appliance index"
       ::= { fluidFSEventsParamsHardware 60 }
    
    
    fluidFSEventsParamsHardwareFcHbaName OBJECT-TYPE
       SYNTAX  DisplayString
       MAX-ACCESS  read-only
       STATUS  current
       DESCRIPTION
           "Fibre channel HBA port name"
       ::= { fluidFSEventsParamsHardware 61 }
    
    
    fluidFSEventsParamsHardwareComponentName OBJECT-TYPE
       SYNTAX  DisplayString
       MAX-ACCESS  read-only
       STATUS  current
       DESCRIPTION
           "Component name in group of components"
       ::= { fluidFSEventsParamsHardware 62 }
    
    
    fluidFSEventsParamsHardwareContextBasedServiceTag OBJECT-TYPE
       SYNTAX  DisplayString
       MAX-ACCESS  read-only
       STATUS  current
       DESCRIPTION
           "Contrller or appliance service tag"
       ::= { fluidFSEventsParamsHardware 63 }
    
    
    fluidFSEventsParamsHardwareTargetEthName OBJECT-TYPE
       SYNTAX  DisplayString
       MAX-ACCESS  read-only
       STATUS  current
       DESCRIPTION
           "Target eth name in mesh connectivity monitoring"
       ::= { fluidFSEventsParamsHardware 64 }
    
    
    fluidFSEventsParamsHardwareIp OBJECT-TYPE
       SYNTAX  DisplayString
       MAX-ACCESS  read-only
       STATUS  current
       DESCRIPTION
           "Monitored external server ip"
       ::= { fluidFSEventsParamsHardware 65 }
    
    
    fluidFSEventsParamsHardwareExtSrvType OBJECT-TYPE
       SYNTAX  DisplayString
       MAX-ACCESS  read-only
       STATUS  current
       DESCRIPTION
           "Monitored external server ip"
       ::= { fluidFSEventsParamsHardware 66 }
    
    
    fluidFSEventsParamsHardwareDiskModel OBJECT-TYPE
       SYNTAX  DisplayString
       MAX-ACCESS  read-only
       STATUS  current
       DESCRIPTION
           "Local disk model name"
       ::= { fluidFSEventsParamsHardware 67 }
    
    
    fluidFSEventsParamsHardwareDiskSerial OBJECT-TYPE
       SYNTAX  DisplayString
       MAX-ACCESS  read-only
       STATUS  current
       DESCRIPTION
           "Local disk serial number"
       ::= { fluidFSEventsParamsHardware 68 }
    
    
    fluidFSEventsParamsHardwareDiskOverallReads OBJECT-TYPE
       SYNTAX  DisplayString
       MAX-ACCESS  read-only
       STATUS  current
       DESCRIPTION
           "Disk overall reads in MB"
       ::= { fluidFSEventsParamsHardware 69 }
    
    
    fluidFSEventsParamsHardwareDiskOverallWrites OBJECT-TYPE
       SYNTAX  DisplayString
       MAX-ACCESS  read-only
       STATUS  current
       DESCRIPTION
           "Disk overall writes in MB"
       ::= { fluidFSEventsParamsHardware 70 }
    
    
    fluidFSEventsParamsHardwareBadSectorsCount OBJECT-TYPE
       SYNTAX  DisplayString
       MAX-ACCESS  read-only
       STATUS  current
       DESCRIPTION
           "HDD bad sectors count"
       ::= { fluidFSEventsParamsHardware 71 }
    
    
    fluidFSEventsParamsHardwareFailedWritesCount OBJECT-TYPE
       SYNTAX  DisplayString
       MAX-ACCESS  read-only
       STATUS  current
       DESCRIPTION
           "SSD failed writes count"
       ::= { fluidFSEventsParamsHardware 72 }
    
    
    fluidFSEventsParamsHardwareSupportedModels OBJECT-TYPE
       SYNTAX  DisplayString
       MAX-ACCESS  read-only
       STATUS  current
       DESCRIPTION
           ""
       ::= { fluidFSEventsParamsHardware 73 }
    
    
    fluidFSEventsParamsHardwareId OBJECT-TYPE
       SYNTAX  DisplayString
       MAX-ACCESS  read-only
       STATUS  current
       DESCRIPTION
           ""
       ::= { fluidFSEventsParamsHardware 74 }
    
    
    fluidFSEventsParamsHardwarePciSlot OBJECT-TYPE
       SYNTAX  INTEGER
       MAX-ACCESS  read-only
       STATUS  current
       DESCRIPTION
           "Slot number"
       ::= { fluidFSEventsParamsHardware 75 }
    
    
    fluidFSEventsParamsHardwarePciCard OBJECT-TYPE
       SYNTAX  DisplayString
       MAX-ACCESS  read-only
       STATUS  current
       DESCRIPTION
           "Full description of a PCI card"
       ::= { fluidFSEventsParamsHardware 76 }
    
    
    fluidFSEventHardwareNoPacketLossInSubnetHost NOTIFICATION-TYPE
       OBJECTS { sysName, fluidFSEventsParamsHardwareNodeId, fluidFSEventsParamsHardwareSubnetName, fluidFSEventsParamsHardwareHostName }
       STATUS current
       DESCRIPTION
           "NAS Controller {{nodeId}} has no packet loss to host {{hostName}} on {{subnetName}} subnet."
           --#TYPE         "Normal Event"
           --#SUMMARY      NAS Controller %d has no packet loss to host %s on %s subnet.
           --#ARGUMENTS    {1,2,3}
           --#SEVERITY     INFORMATIONAL
           --#TIMEINDEX    99
           --#STATE        OK
       ::= { fluidFSEventsHardware 1 } 
    
    
    fluidFSEventHardwarePacketLossInSubnet NOTIFICATION-TYPE
       OBJECTS { sysName, fluidFSEventsParamsHardwareNodeId, fluidFSEventsParamsHardwareSubnetName, fluidFSEventsParamsHardwareHostName, fluidFSEventsParamsHardwarePacketLoss, fluidFSEventsParamsHardwareNetworkId, fluidFSEventsParamsHardwarePrefix, fluidFSEventsParamsHardwareVlanTag }
       STATUS current
       DESCRIPTION
           "NAS Controller {{nodeId}} had packet loss to {{subnetName}}.   Description:  NAS Controller {{nodeId}} had {{packetLoss}}% packet loss to IP address {{subnetName}} on host {{hostName}}. Subnet identifier {{network_id}}, prefix {{prefix}}, vlan tag id {{vlanTag}}."
           --#TYPE         "Normal Event"
           --#SUMMARY      NAS Controller %d had packet loss to %s.   Description:  NAS Controller %d had %d% packet loss to IP address %s on host %s. Subnet identifier %s, prefix %d, vlan tag id %d.
           --#ARGUMENTS    {1,2,3,4,5,6,7}
           --#SEVERITY     MAJOR
           --#TIMEINDEX    99
           --#STATE        OK
       ::= { fluidFSEventsHardware 4 } 
    
    
    fluidFSEventHardwareNoPacketLossInSubnet NOTIFICATION-TYPE
       OBJECTS { sysName, fluidFSEventsParamsHardwareNodeId, fluidFSEventsParamsHardwareSubnetName, fluidFSEventsParamsHardwareHostName, fluidFSEventsParamsHardwareNetworkId, fluidFSEventsParamsHardwarePrefix, fluidFSEventsParamsHardwareVlanTag }
       STATUS current
       DESCRIPTION
           "NAS Controller {{nodeId}} has no packet loss on {{subnetName}}.   Description:  NAS Controller {{nodeId}} has no packet loss to IP address {{subnetName}} on host {{hostName}}. Subnet identifier {{network_id}}, prefix {{prefix}}, vlan tag id {{vlanTag}}."
           --#TYPE         "Normal Event"
           --#SUMMARY      NAS Controller %d has no packet loss on %s.   Description:  NAS Controller %d has no packet loss to IP address %s on host %s. Subnet identifier %s, prefix %d, vlan tag id %d.
           --#ARGUMENTS    {1,2,3,4,5,6}
           --#SEVERITY     INFORMATIONAL
           --#TIMEINDEX    99
           --#STATE        OK
       ::= { fluidFSEventsHardware 6 } 
    
    
    fluidFSEventHardwareNoPacketLossJumboInSubnetHost NOTIFICATION-TYPE
       OBJECTS { sysName, fluidFSEventsParamsHardwareNodeId, fluidFSEventsParamsHardwareSubnetName, fluidFSEventsParamsHardwareHostName }
       STATUS current
       DESCRIPTION
           "NAS Controller {{nodeId}} has no packet loss (using jumbo frames) to host {{hostName}} on {{subnetName}} subnet."
           --#TYPE         "Normal Event"
           --#SUMMARY      NAS Controller %d has no packet loss (using jumbo frames) to host %s on %s subnet.
           --#ARGUMENTS    {1,2,3}
           --#SEVERITY     INFORMATIONAL
           --#TIMEINDEX    99
           --#STATE        OK
       ::= { fluidFSEventsHardware 7 } 
    
    
    fluidFSEventHardwarePacketLossJumboInSubnet NOTIFICATION-TYPE
       OBJECTS { sysName, fluidFSEventsParamsHardwareNodeId, fluidFSEventsParamsHardwareSubnetName, fluidFSEventsParamsHardwareHostName, fluidFSEventsParamsHardwarePacketLoss, fluidFSEventsParamsHardwareNetworkId, fluidFSEventsParamsHardwarePrefix, fluidFSEventsParamsHardwareVlanTag }
       STATUS current
       DESCRIPTION
           "NAS Controller {{nodeId}} had jumbo packet loss.   Description:  NAS Controller {{nodeId}} had {{packetLoss}}% packet loss to IP address {{subnetName}} on host {{hostName}} (using jumbo frames). Subnet identifier {{network_id}}, prefix {{prefix}}, vlan tag id {{vlanTag}}."
           --#TYPE         "Normal Event"
           --#SUMMARY      NAS Controller %d had jumbo packet loss.   Description:  NAS Controller %d had %d% packet loss to IP address %s on host %s (using jumbo frames). Subnet identifier %s, prefix %d, vlan tag id %d.
           --#ARGUMENTS    {1,2,3,4,5,6,7}
           --#SEVERITY     MAJOR
           --#TIMEINDEX    99
           --#STATE        OK
       ::= { fluidFSEventsHardware 8 } 
    
    
    fluidFSEventHardwareNoPacketLossJumboInSubnet NOTIFICATION-TYPE
       OBJECTS { sysName, fluidFSEventsParamsHardwareNodeId, fluidFSEventsParamsHardwareSubnetName, fluidFSEventsParamsHardwareHostName, fluidFSEventsParamsHardwareNetworkId, fluidFSEventsParamsHardwarePrefix, fluidFSEventsParamsHardwareVlanTag }
       STATUS current
       DESCRIPTION
           "NAS Controller {{nodeId}} has no jumbo packet loss.   Description:  NAS Controller {{nodeId}} has no packet loss to IP address {{subnetName}} on host {{hostName}} (using jumbo frames). Subnet identifier {{network_id}}, prefix {{prefix}}, vlan tag id {{vlanTag}}."
           --#TYPE         "Normal Event"
           --#SUMMARY      NAS Controller %d has no jumbo packet loss.   Description:  NAS Controller %d has no packet loss to IP address %s on host %s (using jumbo frames). Subnet identifier %s, prefix %d, vlan tag id %d.
           --#ARGUMENTS    {1,2,3,4,5,6}
           --#SEVERITY     INFORMATIONAL
           --#TIMEINDEX    99
           --#STATE        OK
       ::= { fluidFSEventsHardware 12 } 
    
    
    fluidFSEventHardwareCantReachSubnet NOTIFICATION-TYPE
       OBJECTS { sysName, fluidFSEventsParamsHardwareNodeId, fluidFSEventsParamsHardwareSubnetName, fluidFSEventsParamsHardwareHostName, fluidFSEventsParamsHardwareNetworkId, fluidFSEventsParamsHardwarePrefix, fluidFSEventsParamsHardwareVlanTag }
       STATUS current
       DESCRIPTION
           "NAS Controller {{nodeId}} cannot reach IP {{subnetName}}   Description:  NAS Controller {{nodeId}} cannot reach IP address {{subnetName}} on host {{hostName}}. Subnet identifier {{network_id}}, prefix {{prefix}}, vlan tag id {{vlanTag}}."
           --#TYPE         "Normal Event"
           --#SUMMARY      NAS Controller %d cannot reach IP %s   Description:  NAS Controller %d cannot reach IP address %s on host %s. Subnet identifier %s, prefix %d, vlan tag id %d.
           --#ARGUMENTS    {1,2,3,4,5,6}
           --#SEVERITY     MAJOR
           --#TIMEINDEX    99
           --#STATE        OK
       ::= { fluidFSEventsHardware 13 } 
    
    
    fluidFSEventHardwareCantReachJumboSubnet NOTIFICATION-TYPE
       OBJECTS { sysName, fluidFSEventsParamsHardwareNodeId, fluidFSEventsParamsHardwareSubnetName, fluidFSEventsParamsHardwareHostName, fluidFSEventsParamsHardwareNetworkId, fluidFSEventsParamsHardwarePrefix, fluidFSEventsParamsHardwareVlanTag }
       STATUS current
       DESCRIPTION
           "NAS Controller {{nodeId}} cannot reach IP using (jumbo frames)   Description:  NAS Controller {{nodeId}} cannot reach IP address {{subnetName}} on host {{hostName}} (using jumbo frames). Subnet identifier {{network_id}}, prefix {{prefix}}, vlan tag id {{vlanTag}}."
           --#TYPE         "Normal Event"
           --#SUMMARY      NAS Controller %d cannot reach IP using (jumbo frames)   Description:  NAS Controller %d cannot reach IP address %s on host %s (using jumbo frames). Subnet identifier %s, prefix %d, vlan tag id %d.
           --#ARGUMENTS    {1,2,3,4,5,6}
           --#SEVERITY     MAJOR
           --#TIMEINDEX    99
           --#STATE        OK
       ::= { fluidFSEventsHardware 18 } 
    
    
    fluidFSEventHardwareEthHasErrors NOTIFICATION-TYPE
       OBJECTS { sysName, fluidFSEventsParamsHardwareNodeId, fluidFSEventsParamsHardwareBondName, fluidFSEventsParamsHardwareEthName }
       STATUS current
       DESCRIPTION
           "{{ethName}} (part of {{bondName}}) on NAS Controller {{nodeId}} has errors."
           --#TYPE         "Normal Event"
           --#SUMMARY      %s (part of %s) on NAS Controller %d has errors.
           --#ARGUMENTS    {1,2,3}
           --#SEVERITY     INFORMATIONAL
           --#TIMEINDEX    99
           --#STATE        OK
       ::= { fluidFSEventsHardware 35 } 
    
    
    fluidFSEventHardwareEthHasDrops NOTIFICATION-TYPE
       OBJECTS { sysName, fluidFSEventsParamsHardwareNodeId, fluidFSEventsParamsHardwareBondName, fluidFSEventsParamsHardwareEthName }
       STATUS current
       DESCRIPTION
           "{{ethName}} (part of {{bondName}}) on NAS Controller {{nodeId}} has drops."
           --#TYPE         "Normal Event"
           --#SUMMARY      %s (part of %s) on NAS Controller %d has drops.
           --#ARGUMENTS    {1,2,3}
           --#SEVERITY     INFORMATIONAL
           --#TIMEINDEX    99
           --#STATE        OK
       ::= { fluidFSEventsHardware 36 } 
    
    
    fluidFSEventHardwareCantReachDefaultGateway NOTIFICATION-TYPE
       OBJECTS { sysName, fluidFSEventsParamsHardwareNodeId, fluidFSEventsParamsHardwareIp }
       STATUS current
       DESCRIPTION
           "NAS Controller{{nodeId}} cannot reach default gateway {{ip}}."
           --#TYPE         "Normal Event"
           --#SUMMARY      NAS Controller%d cannot reach default gateway %s.
           --#ARGUMENTS    {1,2}
           --#SEVERITY     MAJOR
           --#TIMEINDEX    99
           --#STATE        OK
       ::= { fluidFSEventsHardware 38 } 
    
    
    fluidFSEventHardwareCanReachDefaultGateway NOTIFICATION-TYPE
       OBJECTS { sysName, fluidFSEventsParamsHardwareNodeId, fluidFSEventsParamsHardwareIp }
       STATUS current
       DESCRIPTION
           "NAS Controller{{nodeId}} can reach default gateway {{ip}}."
           --#TYPE         "Normal Event"
           --#SUMMARY      NAS Controller%d can reach default gateway %s.
           --#ARGUMENTS    {1,2}
           --#SEVERITY     INFORMATIONAL
           --#TIMEINDEX    99
           --#STATE        OK
       ::= { fluidFSEventsHardware 39 } 
    
    
    fluidFSEventHardwarePacketLossInSubnetHost NOTIFICATION-TYPE
       OBJECTS { sysName, fluidFSEventsParamsHardwareNodeId, fluidFSEventsParamsHardwareSubnetName, fluidFSEventsParamsHardwareHostName, fluidFSEventsParamsHardwarePacketLoss }
       STATUS current
       DESCRIPTION
           "NAS Controller {{nodeId}} had {{packetLoss}}% packet loss to host {{hostName}} on {{subnetName}} subnet."
           --#TYPE         "Normal Event"
           --#SUMMARY      NAS Controller %d had %d% packet loss to host %s on %s subnet.
           --#ARGUMENTS    {1,2,3,4}
           --#SEVERITY     MAJOR
           --#TIMEINDEX    99
           --#STATE        OK
       ::= { fluidFSEventsHardware 56 } 
    
    
    fluidFSEventHardwareNoLinkInEthOnController NOTIFICATION-TYPE
       OBJECTS { sysName, fluidFSEventsParamsHardwareNodeId, fluidFSEventsParamsHardwareEthName }
       STATUS current
       DESCRIPTION
           "Eth{{ethName}} which belongs to NAS Controller {{nodeId}} is down."
           --#TYPE         "Normal Event"
           --#SUMMARY      Eth%s which belongs to NAS Controller %d is down.
           --#ARGUMENTS    {1,2}
           --#SEVERITY     MAJOR
           --#TIMEINDEX    99
           --#STATE        OK
       ::= { fluidFSEventsHardware 57 } 
    
    
    fluidFSEventHardwareEthLinkRestoredOnController NOTIFICATION-TYPE
       OBJECTS { sysName, fluidFSEventsParamsHardwareNodeId, fluidFSEventsParamsHardwareEthName }
       STATUS current
       DESCRIPTION
           "Eth{{ethName}} which belongs to NAS Controller {{nodeId}} is restored."
           --#TYPE         "Normal Event"
           --#SUMMARY      Eth%s which belongs to NAS Controller %d is restored.
           --#ARGUMENTS    {1,2}
           --#SEVERITY     INFORMATIONAL
           --#TIMEINDEX    99
           --#STATE        OK
       ::= { fluidFSEventsHardware 58 } 
    
    
    fluidFSEventHardwarePacketLossJumboInSubnetHost NOTIFICATION-TYPE
       OBJECTS { sysName, fluidFSEventsParamsHardwareNodeId, fluidFSEventsParamsHardwareSubnetName, fluidFSEventsParamsHardwareHostName, fluidFSEventsParamsHardwarePacketLoss }
       STATUS current
       DESCRIPTION
           "NAS Controller {{nodeId}} had {{packetLoss}}% packet loss (using jumbo frames) to host {{hostName}} on {{subnetName}} subnet."
           --#TYPE         "Normal Event"
           --#SUMMARY      NAS Controller %d had %d% packet loss (using jumbo frames) to host %s on %s subnet.
           --#ARGUMENTS    {1,2,3,4}
           --#SEVERITY     MAJOR
           --#TIMEINDEX    99
           --#STATE        OK
       ::= { fluidFSEventsHardware 59 } 
    
    
    fluidFSEventHardwareCantReachSubnetHost NOTIFICATION-TYPE
       OBJECTS { sysName, fluidFSEventsParamsHardwareNodeId, fluidFSEventsParamsHardwareSubnetName, fluidFSEventsParamsHardwareHostName }
       STATUS current
       DESCRIPTION
           "NAS Controller {{nodeId}} cannot reach host {{hostName}} on {{subnetName}} subnet."
           --#TYPE         "Normal Event"
           --#SUMMARY      NAS Controller %d cannot reach host %s on %s subnet.
           --#ARGUMENTS    {1,2,3}
           --#SEVERITY     MAJOR
           --#TIMEINDEX    99
           --#STATE        OK
       ::= { fluidFSEventsHardware 60 } 
    
    
    fluidFSEventHardwareCantReachJumboSubnetHost NOTIFICATION-TYPE
       OBJECTS { sysName, fluidFSEventsParamsHardwareNodeId, fluidFSEventsParamsHardwareSubnetName, fluidFSEventsParamsHardwareHostName }
       STATUS current
       DESCRIPTION
           "NAS Controller {{nodeId}} cannot reach (using jumbo frames) host {{hostName}} on {{subnetName}} subnet."
           --#TYPE         "Normal Event"
           --#SUMMARY      NAS Controller %d cannot reach (using jumbo frames) host %s on %s subnet.
           --#ARGUMENTS    {1,2,3}
           --#SEVERITY     MAJOR
           --#TIMEINDEX    99
           --#STATE        OK
       ::= { fluidFSEventsHardware 61 } 
    
    
    fluidFSEventHardwareBpsAccessibilityNormal NOTIFICATION-TYPE
       OBJECTS { sysName, fluidFSEventsParamsHardwareContextBasedServiceTag, fluidFSEventsParamsHardwareNodeId }
       STATUS current
       DESCRIPTION
           "NAS Controller{{nodeId}} BPS reachability is back to normal (service tag: {{contextBasedServiceTag}})."
           --#TYPE         "Normal Event"
           --#SUMMARY      NAS Controller%d BPS reachability is back to normal (service tag: %s).
           --#ARGUMENTS    {1,2}
           --#SEVERITY     INFORMATIONAL
           --#TIMEINDEX    99
           --#STATE        OK
       ::= { fluidFSEventsHardware 109 } 
    
    
    fluidFSEventHardwareBpsNormal NOTIFICATION-TYPE
       OBJECTS { sysName, fluidFSEventsParamsHardwareContextBasedServiceTag, fluidFSEventsParamsHardwareNodeId, fluidFSEventsParamsHardwareBpsBatteryCharge }
       STATUS current
       DESCRIPTION
           "BPS on NAS Controller{{nodeId}} is back to normal operation. Charge is {{bpsBatteryCharge}}% (service tag: {{contextBasedServiceTag}})."
           --#TYPE         "Normal Event"
           --#SUMMARY      BPS on NAS Controller%d is back to normal operation. Charge is %d% (service tag: %s).
           --#ARGUMENTS    {1,2,3}
           --#SEVERITY     INFORMATIONAL
           --#TIMEINDEX    99
           --#STATE        OK
       ::= { fluidFSEventsHardware 110 } 
    
    
    fluidFSEventHardwareProcessorCoresCountFailed NOTIFICATION-TYPE
       OBJECTS { sysName, fluidFSEventsParamsHardwareContextBasedServiceTag, fluidFSEventsParamsHardwareFirstNodeId, fluidFSEventsParamsHardwareSecondNodeId }
       STATUS current
       DESCRIPTION
           "Failed to validate CPU cores count is equal in NAS Controller {{firstNodeId}} and NAS Controller {{secondNodeId}} (service tag: {{contextBasedServiceTag}})."
           --#TYPE         "Normal Event"
           --#SUMMARY      Failed to validate CPU cores count is equal in NAS Controller %d and NAS Controller %d (service tag: %s).
           --#ARGUMENTS    {1,2,3}
           --#SEVERITY     INFORMATIONAL
           --#TIMEINDEX    99
           --#STATE        OK
       ::= { fluidFSEventsHardware 120 } 
    
    
    fluidFSEventHardwareProcessorCoresCountOk NOTIFICATION-TYPE
       OBJECTS { sysName, fluidFSEventsParamsHardwareContextBasedServiceTag, fluidFSEventsParamsHardwareFirstNodeId, fluidFSEventsParamsHardwareSecondNodeId }
       STATUS current
       DESCRIPTION
           "CPU cores count test successful. Count is equal in NAS Controller {{firstNodeId}} and NAS Controller {{secondNodeId}} (service tag: {{contextBasedServiceTag}})."
           --#TYPE         "Normal Event"
           --#SUMMARY      CPU cores count test successful. Count is equal in NAS Controller %d and NAS Controller %d (service tag: %s).
           --#ARGUMENTS    {1,2,3}
           --#SEVERITY     INFORMATIONAL
           --#TIMEINDEX    99
           --#STATE        OK
       ::= { fluidFSEventsHardware 121 } 
    
    
    fluidFSEventHardwareMemoryNotOptimal NOTIFICATION-TYPE
       OBJECTS { sysName, fluidFSEventsParamsHardwareContextBasedServiceTag, fluidFSEventsParamsHardwareNodeId }
       STATUS current
       DESCRIPTION
           "Memory device status in NAS Controller{{nodeId}} is not optimal (service tag: {{contextBasedServiceTag}})."
           --#TYPE         "Normal Event"
           --#SUMMARY      Memory device status in NAS Controller%d is not optimal (service tag: %s).
           --#ARGUMENTS    {1,2}
           --#SEVERITY     MAJOR
           --#TIMEINDEX    99
           --#STATE        OK
       ::= { fluidFSEventsHardware 124 } 
    
    
    fluidFSEventHardwareMemoryError NOTIFICATION-TYPE
       OBJECTS { sysName, fluidFSEventsParamsHardwareContextBasedServiceTag, fluidFSEventsParamsHardwareNodeId }
       STATUS current
       DESCRIPTION
           "Memory device status in NAS Controller{{nodeId}} is critical (service tag: {{contextBasedServiceTag}})."
           --#TYPE         "Normal Event"
           --#SUMMARY      Memory device status in NAS Controller%d is critical (service tag: %s).
           --#ARGUMENTS    {1,2}
           --#SEVERITY     MAJOR
           --#TIMEINDEX    99
           --#STATE        OK
       ::= { fluidFSEventsHardware 125 } 
    
    
    fluidFSEventHardwareMemoryBackToNormal NOTIFICATION-TYPE
       OBJECTS { sysName, fluidFSEventsParamsHardwareContextBasedServiceTag, fluidFSEventsParamsHardwareNodeId }
       STATUS current
       DESCRIPTION
           "Memory device in NAS Controller{{nodeId}} returned to normal operation (service tag: {{contextBasedServiceTag}})."
           --#TYPE         "Normal Event"
           --#SUMMARY      Memory device in NAS Controller%d returned to normal operation (service tag: %s).
           --#ARGUMENTS    {1,2}
           --#SEVERITY     INFORMATIONAL
           --#TIMEINDEX    99
           --#STATE        OK
       ::= { fluidFSEventsHardware 126 } 
    
    
    fluidFSEventHardwareMemoryTempWarn NOTIFICATION-TYPE
       OBJECTS { sysName, fluidFSEventsParamsHardwareContextBasedServiceTag, fluidFSEventsParamsHardwareNodeId, fluidFSEventsParamsHardwareTemperature }
       STATUS current
       DESCRIPTION
           "Memory device temperature sensors in NAS Controller{{nodeId}} report warning status (Ambient temperature: {{temperature}} degrees Celsius) (service tag: {{contextBasedServiceTag}})."
           --#TYPE         "Normal Event"
           --#SUMMARY      Memory device temperature sensors in NAS Controller%d report warning status (Ambient temperature: %d degrees Celsius) (service tag: %s).
           --#ARGUMENTS    {1,2,3}
           --#SEVERITY     INFORMATIONAL
           --#TIMEINDEX    99
           --#STATE        OK
       ::= { fluidFSEventsHardware 127 } 
    
    
    fluidFSEventHardwareMemoryTempNormal NOTIFICATION-TYPE
       OBJECTS { sysName, fluidFSEventsParamsHardwareContextBasedServiceTag, fluidFSEventsParamsHardwareNodeId, fluidFSEventsParamsHardwareTemperature }
       STATUS current
       DESCRIPTION
           "Memory device temperature sensors in NAS Controller{{nodeId}} report normal status (Ambient temperature: {{temperature}} degrees Celsius) (service tag: {{contextBasedServiceTag}})."
           --#TYPE         "Normal Event"
           --#SUMMARY      Memory device temperature sensors in NAS Controller%d report normal status (Ambient temperature: %d degrees Celsius) (service tag: %s).
           --#ARGUMENTS    {1,2,3}
           --#SEVERITY     INFORMATIONAL
           --#TIMEINDEX    99
           --#STATE        OK
       ::= { fluidFSEventsHardware 128 } 
    
    
    fluidFSEventHardwareMemoryTempCritical NOTIFICATION-TYPE
       OBJECTS { sysName, fluidFSEventsParamsHardwareContextBasedServiceTag, fluidFSEventsParamsHardwareNodeId, fluidFSEventsParamsHardwareTemperature }
       STATUS current
       DESCRIPTION
           "Memory device temperature sensors in NAS Controller{{nodeId}} report critical status (Ambient temperature: {{temperature}} degrees Celsius) (service tag: {{contextBasedServiceTag}})."
           --#TYPE         "Normal Event"
           --#SUMMARY      Memory device temperature sensors in NAS Controller%d report critical status (Ambient temperature: %d degrees Celsius) (service tag: %s).
           --#ARGUMENTS    {1,2,3}
           --#SEVERITY     INFORMATIONAL
           --#TIMEINDEX    99
           --#STATE        OK
       ::= { fluidFSEventsHardware 129 } 
    
    
    fluidFSEventHardwareMemorySizeCountFailed NOTIFICATION-TYPE
       OBJECTS { sysName, fluidFSEventsParamsHardwareContextBasedServiceTag, fluidFSEventsParamsHardwareFirstNodeId, fluidFSEventsParamsHardwareSecondNodeId }
       STATUS current
       DESCRIPTION
           "Failed to validate memory size is equal in NAS Controller {{firstNodeId}} and NAS Controller {{secondNodeId}} (service tag: {{contextBasedServiceTag}})."
           --#TYPE         "Normal Event"
           --#SUMMARY      Failed to validate memory size is equal in NAS Controller %d and NAS Controller %d (service tag: %s).
           --#ARGUMENTS    {1,2,3}
           --#SEVERITY     INFORMATIONAL
           --#TIMEINDEX    99
           --#STATE        OK
       ::= { fluidFSEventsHardware 130 } 
    
    
    fluidFSEventHardwareMemorySizeCountOk NOTIFICATION-TYPE
       OBJECTS { sysName, fluidFSEventsParamsHardwareContextBasedServiceTag, fluidFSEventsParamsHardwareFirstNodeId, fluidFSEventsParamsHardwareSecondNodeId }
       STATUS current
       DESCRIPTION
           "Memory size test successful. Size is equal in NAS Controller {{firstNodeId}} and NAS Controller {{secondNodeId}} (service tag: {{contextBasedServiceTag}})."
           --#TYPE         "Normal Event"
           --#SUMMARY      Memory size test successful. Size is equal in NAS Controller %d and NAS Controller %d (service tag: %s).
           --#ARGUMENTS    {1,2,3}
           --#SEVERITY     INFORMATIONAL
           --#TIMEINDEX    99
           --#STATE        OK
       ::= { fluidFSEventsHardware 131 } 
    
    
    fluidFSEventHardwareMemoryInfoNotAvailable NOTIFICATION-TYPE
       OBJECTS { sysName, fluidFSEventsParamsHardwareContextBasedServiceTag, fluidFSEventsParamsHardwareNodeId }
       STATUS current
       DESCRIPTION
           "Memory device status in NAS Controller{{nodeId}} is not available. Internal error in memory monitoring (service tag: {{contextBasedServiceTag}})."
           --#TYPE         "Normal Event"
           --#SUMMARY      Memory device status in NAS Controller%d is not available. Internal error in memory monitoring (service tag: %s).
           --#ARGUMENTS    {1,2}
           --#SEVERITY     MAJOR
           --#TIMEINDEX    99
           --#STATE        OK
       ::= { fluidFSEventsHardware 132 } 
    
    
    fluidFSEventHardwareMemoryInfoIsAvailable NOTIFICATION-TYPE
       OBJECTS { sysName, fluidFSEventsParamsHardwareContextBasedServiceTag, fluidFSEventsParamsHardwareNodeId }
       STATUS current
       DESCRIPTION
           "Memory device status in NAS Controller{{nodeId}} is available again (service tag: {{contextBasedServiceTag}})."
           --#TYPE         "Normal Event"
           --#SUMMARY      Memory device status in NAS Controller%d is available again (service tag: %s).
           --#ARGUMENTS    {1,2}
           --#SEVERITY     INFORMATIONAL
           --#TIMEINDEX    99
           --#STATE        OK
       ::= { fluidFSEventsHardware 133 } 
    
    
    fluidFSEventHardwareControllerStatusNotAvailable NOTIFICATION-TYPE
       OBJECTS { sysName, fluidFSEventsParamsHardwareContextBasedServiceTag, fluidFSEventsParamsHardwareNodeId }
       STATUS current
       DESCRIPTION
           "NAS Controller{{nodeId}} hardware status is not available. Internal error in controller status analysis (service tag: {{contextBasedServiceTag}})."
           --#TYPE         "Normal Event"
           --#SUMMARY      NAS Controller%d hardware status is not available. Internal error in controller status analysis (service tag: %s).
           --#ARGUMENTS    {1,2}
           --#SEVERITY     MAJOR
           --#TIMEINDEX    99
           --#STATE        OK
       ::= { fluidFSEventsHardware 135 } 
    
    
    fluidFSEventHardwareControllerStatusAvailable NOTIFICATION-TYPE
       OBJECTS { sysName, fluidFSEventsParamsHardwareContextBasedServiceTag, fluidFSEventsParamsHardwareNodeId }
       STATUS current
       DESCRIPTION
           "NAS Controller{{nodeId}} hardware status is available again (service tag: {{contextBasedServiceTag}})."
           --#TYPE         "Normal Event"
           --#SUMMARY      NAS Controller%d hardware status is available again (service tag: %s).
           --#ARGUMENTS    {1,2}
           --#SEVERITY     INFORMATIONAL
           --#TIMEINDEX    99
           --#STATE        OK
       ::= { fluidFSEventsHardware 136 } 
    
    
    fluidFSEventHardwareLocalDisksInfoNotAvailable NOTIFICATION-TYPE
       OBJECTS { sysName, fluidFSEventsParamsHardwareContextBasedServiceTag, fluidFSEventsParamsHardwareNodeId }
       STATUS current
       DESCRIPTION
           "Local storage status in NAS Controller{{nodeId}} is not available. S.M.A.R.T. info is not available (service tag: {{contextBasedServiceTag}})."
           --#TYPE         "Normal Event"
           --#SUMMARY      Local storage status in NAS Controller%d is not available. S.M.A.R.T. info is not available (service tag: %s).
           --#ARGUMENTS    {1,2}
           --#SEVERITY     MAJOR
           --#TIMEINDEX    99
           --#STATE        OK
       ::= { fluidFSEventsHardware 143 } 
    
    
    fluidFSEventHardwareLocalDisksInfoIsAvailable NOTIFICATION-TYPE
       OBJECTS { sysName, fluidFSEventsParamsHardwareContextBasedServiceTag, fluidFSEventsParamsHardwareNodeId }
       STATUS current
       DESCRIPTION
           "Local storage status in NAS Controller{{nodeId}} is available again (service tag: {{contextBasedServiceTag}})."
           --#TYPE         "Normal Event"
           --#SUMMARY      Local storage status in NAS Controller%d is available again (service tag: %s).
           --#ARGUMENTS    {1,2}
           --#SEVERITY     INFORMATIONAL
           --#TIMEINDEX    99
           --#STATE        OK
       ::= { fluidFSEventsHardware 144 } 
    
    
    fluidFSEventHardwareApplianceIntrusionWarning NOTIFICATION-TYPE
       OBJECTS { sysName, fluidFSEventsParamsHardwareContextBasedServiceTag, fluidFSEventsParamsHardwareApplianceId }
       STATUS current
       DESCRIPTION
           "Chassis cover for NAS Appliance{{applianceId}} is open (service tag: {{contextBasedServiceTag}})."
           --#TYPE         "Normal Event"
           --#SUMMARY      Chassis cover for NAS Appliance%d is open (service tag: %s).
           --#ARGUMENTS    {1,2}
           --#SEVERITY     MAJOR
           --#TIMEINDEX    99
           --#STATE        OK
       ::= { fluidFSEventsHardware 153 } 
    
    
    fluidFSEventHardwareApplianceIntrusionOk NOTIFICATION-TYPE
       OBJECTS { sysName, fluidFSEventsParamsHardwareContextBasedServiceTag, fluidFSEventsParamsHardwareApplianceId }
       STATUS current
       DESCRIPTION
           "Chassis cover for NAS Controller {{applianceId}} was closed (service tag: {{contextBasedServiceTag}})."
           --#TYPE         "Normal Event"
           --#SUMMARY      Chassis cover for NAS Controller %d was closed (service tag: %s).
           --#ARGUMENTS    {1,2}
           --#SEVERITY     INFORMATIONAL
           --#TIMEINDEX    99
           --#STATE        OK
       ::= { fluidFSEventsHardware 154 } 
    
    
    fluidFSEventHardwareAppFanSystemInfoNotAvailable NOTIFICATION-TYPE
       OBJECTS { sysName, fluidFSEventsParamsHardwareContextBasedServiceTag, fluidFSEventsParamsHardwareApplianceId }
       STATUS current
       DESCRIPTION
           "Fans set overall status in NAS Appliance {{applianceId}} is not available. Internal error in fans monitoring (service tag: {{contextBasedServiceTag}})."
           --#TYPE         "Normal Event"
           --#SUMMARY      Fans set overall status in NAS Appliance %d is not available. Internal error in fans monitoring (service tag: %s).
           --#ARGUMENTS    {1,2}
           --#SEVERITY     MAJOR
           --#TIMEINDEX    99
           --#STATE        OK
       ::= { fluidFSEventsHardware 168 } 
    
    
    fluidFSEventHardwareAppFanSystemInfoIsAvailable NOTIFICATION-TYPE
       OBJECTS { sysName, fluidFSEventsParamsHardwareContextBasedServiceTag, fluidFSEventsParamsHardwareApplianceId }
       STATUS current
       DESCRIPTION
           "Fans set overall status in NAS Appliance {{applianceId}} is available again (service tag: {{contextBasedServiceTag}})."
           --#TYPE         "Normal Event"
           --#SUMMARY      Fans set overall status in NAS Appliance %d is available again (service tag: %s).
           --#ARGUMENTS    {1,2}
           --#SEVERITY     INFORMATIONAL
           --#TIMEINDEX    99
           --#STATE        OK
       ::= { fluidFSEventsHardware 169 } 
    
    
    fluidFSEventHardwareAppFanError NOTIFICATION-TYPE
       OBJECTS { sysName, fluidFSEventsParamsHardwareContextBasedServiceTag, fluidFSEventsParamsHardwareApplianceId, fluidFSEventsParamsHardwareComponentName }
       STATUS current
       DESCRIPTION
           "Fan {{componentName}} in NAS Appliance {{applianceId}} has critical status (service tag: {{contextBasedServiceTag}})."
           --#TYPE         "Normal Event"
           --#SUMMARY      Fan %s in NAS Appliance %d has critical status (service tag: %s).
           --#ARGUMENTS    {1,2,3}
           --#SEVERITY     MAJOR
           --#TIMEINDEX    99
           --#STATE        OK
       ::= { fluidFSEventsHardware 170 } 
    
    
    fluidFSEventHardwareAppFanWarning NOTIFICATION-TYPE
       OBJECTS { sysName, fluidFSEventsParamsHardwareContextBasedServiceTag, fluidFSEventsParamsHardwareApplianceId, fluidFSEventsParamsHardwareComponentName }
       STATUS current
       DESCRIPTION
           "Fan {{componentName}} in NAS Appliance {{applianceId}} has warning status (service tag: {{contextBasedServiceTag}})."
           --#TYPE         "Normal Event"
           --#SUMMARY      Fan %s in NAS Appliance %d has warning status (service tag: %s).
           --#ARGUMENTS    {1,2,3}
           --#SEVERITY     INFORMATIONAL
           --#TIMEINDEX    99
           --#STATE        OK
       ::= { fluidFSEventsHardware 171 } 
    
    
    fluidFSEventHardwareAppFanBackToNormal NOTIFICATION-TYPE
       OBJECTS { sysName, fluidFSEventsParamsHardwareContextBasedServiceTag, fluidFSEventsParamsHardwareApplianceId, fluidFSEventsParamsHardwareComponentName }
       STATUS current
       DESCRIPTION
           "Fan {{componentName}} in NAS Appliance {{applianceId}} returned to normal operation (service tag: {{contextBasedServiceTag}})."
           --#TYPE         "Normal Event"
           --#SUMMARY      Fan %s in NAS Appliance %d returned to normal operation (service tag: %s).
           --#ARGUMENTS    {1,2,3}
           --#SEVERITY     INFORMATIONAL
           --#TIMEINDEX    99
           --#STATE        OK
       ::= { fluidFSEventsHardware 172 } 
    
    
    fluidFSEventHardwareAppFanInfoNotAvailable NOTIFICATION-TYPE
       OBJECTS { sysName, fluidFSEventsParamsHardwareContextBasedServiceTag, fluidFSEventsParamsHardwareApplianceId, fluidFSEventsParamsHardwareComponentName }
       STATUS current
       DESCRIPTION
           "Fan {{componentName}} status in NAS Appliance {{applianceId}} is not available. Internal error in fans monitoring (service tag: {{contextBasedServiceTag}})."
           --#TYPE         "Normal Event"
           --#SUMMARY      Fan %s status in NAS Appliance %d is not available. Internal error in fans monitoring (service tag: %s).
           --#ARGUMENTS    {1,2,3}
           --#SEVERITY     MAJOR
           --#TIMEINDEX    99
           --#STATE        OK
       ::= { fluidFSEventsHardware 173 } 
    
    
    fluidFSEventHardwareAppFanInfoIsAvailable NOTIFICATION-TYPE
       OBJECTS { sysName, fluidFSEventsParamsHardwareContextBasedServiceTag, fluidFSEventsParamsHardwareApplianceId, fluidFSEventsParamsHardwareComponentName }
       STATUS current
       DESCRIPTION
           "Fan {{componentName}} status in NAS Appliance {{applianceId}} is available again (service tag: {{contextBasedServiceTag}})."
           --#TYPE         "Normal Event"
           --#SUMMARY      Fan %s status in NAS Appliance %d is available again (service tag: %s).
           --#ARGUMENTS    {1,2,3}
           --#SEVERITY     INFORMATIONAL
           --#TIMEINDEX    99
           --#STATE        OK
       ::= { fluidFSEventsHardware 174 } 
    
    
    fluidFSEventHardwarePowerSupplyInfoNotAvailable NOTIFICATION-TYPE
       OBJECTS { sysName, fluidFSEventsParamsHardwareContextBasedServiceTag, fluidFSEventsParamsHardwareNodeId }
       STATUS current
       DESCRIPTION
           "Power supply status in NAS Controller{{nodeId}} is not available. Internal error in power supply monitoring (service tag: {{contextBasedServiceTag}})."
           --#TYPE         "Normal Event"
           --#SUMMARY      Power supply status in NAS Controller%d is not available. Internal error in power supply monitoring (service tag: %s).
           --#ARGUMENTS    {1,2}
           --#SEVERITY     MAJOR
           --#TIMEINDEX    99
           --#STATE        OK
       ::= { fluidFSEventsHardware 178 } 
    
    
    fluidFSEventHardwarePowerSupplyInfoIsAvailable NOTIFICATION-TYPE
       OBJECTS { sysName, fluidFSEventsParamsHardwareContextBasedServiceTag, fluidFSEventsParamsHardwareNodeId }
       STATUS current
       DESCRIPTION
           "Power supply status in NAS Controller{{nodeId}} is available again (service tag: {{contextBasedServiceTag}})."
           --#TYPE         "Normal Event"
           --#SUMMARY      Power supply status in NAS Controller%d is available again (service tag: %s).
           --#ARGUMENTS    {1,2}
           --#SEVERITY     INFORMATIONAL
           --#TIMEINDEX    99
           --#STATE        OK
       ::= { fluidFSEventsHardware 179 } 
    
    
    fluidFSEventHardwarePsuError NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} has failure status, power supply redundancy lost (service tag: {{contextBasedServiceTag}})."
           --#TYPE         "Normal Event"
           --#SUMMARY      Power supply unit %s in NAS Controller%d has failure status, power supply redundancy lost (service tag: %s).
           --#ARGUMENTS    {1,2,3}
           --#SEVERITY     MAJOR
           --#TIMEINDEX    99
           --#STATE        OK
       ::= { fluidFSEventsHardware 180 } 
    
    
    fluidFSEventHardwarePsuWarning NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} has warning status (service tag: {{contextBasedServiceTag}})."
           --#TYPE         "Normal Event"
           --#SUMMARY      Power supply unit %s in NAS Controller%d has warning status (service tag: %s).
           --#ARGUMENTS    {1,2,3}
           --#SEVERITY     INFORMATIONAL
           --#TIMEINDEX    99
           --#STATE        OK
       ::= { fluidFSEventsHardware 181 } 
    
    
    fluidFSEventHardwarePsuBackToNormal NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} returned to normal operation (service tag: {{contextBasedServiceTag}})."
           --#TYPE         "Normal Event"
           --#SUMMARY      Power supply unit %s in NAS Controller%d returned to normal operation (service tag: %s).
           --#ARGUMENTS    {1,2,3}
           --#SEVERITY     INFORMATIONAL
           --#TIMEINDEX    99
           --#STATE        OK
       ::= { fluidFSEventsHardware 182 } 
    
    
    fluidFSEventHardwarePsuInfoNotAvailable NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} status in NAS Controller{{nodeId}} is not available. Internal error in power supply monitoring (service tag: {{contextBasedServiceTag}})."
           --#TYPE         "Normal Event"
           --#SUMMARY      Power supply unit %s status in NAS Controller%d is not available. Internal error in power supply monitoring (service tag: %s).
           --#ARGUMENTS    {1,2,3}
           --#SEVERITY     MAJOR
           --#TIMEINDEX    99
           --#STATE        OK
       ::= { fluidFSEventsHardware 183 } 
    
    
    fluidFSEventHardwarePsuInfoIsAvailable NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} status in NAS Controller{{nodeId}} is available again (service tag: {{contextBasedServiceTag}})."
           --#TYPE         "Normal Event"
           --#SUMMARY      Power supply unit %s status in NAS Controller%d is available again (service tag: %s).
           --#ARGUMENTS    {1,2,3}
           --#SEVERITY     INFORMATIONAL
           --#TIMEINDEX    99
           --#STATE        OK
       ::= { fluidFSEventsHardware 184 } 
    
    
    fluidFSEventHardwareAppPowerSupplyInfoNotAvailable NOTIFICATION-TYPE
       OBJECTS { sysName, fluidFSEventsParamsHardwareContextBasedServiceTag, fluidFSEventsParamsHardwareApplianceId }
       STATUS current
       DESCRIPTION
           "Power supply status in NAS Appliance {{applianceId}} is not available. Internal error in power supply monitoring (service tag: {{contextBasedServiceTag}})."
           --#TYPE         "Normal Event"
           --#SUMMARY      Power supply status in NAS Appliance %d is not available. Internal error in power supply monitoring (service tag: %s).
           --#ARGUMENTS    {1,2}
           --#SEVERITY     MAJOR
           --#TIMEINDEX    99
           --#STATE        OK
       ::= { fluidFSEventsHardware 188 } 
    
    
    fluidFSEventHardwareAppPowerSupplyInfoIsAvailable NOTIFICATION-TYPE
       OBJECTS { sysName, fluidFSEventsParamsHardwareContextBasedServiceTag, fluidFSEventsParamsHardwareApplianceId }
       STATUS current
       DESCRIPTION
           "Power supply status in NAS Appliance {{applianceId}} is available again (service tag: {{contextBasedServiceTag}})."
           --#TYPE         "Normal Event"
           --#SUMMARY      Power supply status in NAS Appliance %d is available again (service tag: %s).
           --#ARGUMENTS    {1,2}
           --#SEVERITY     INFORMATIONAL
           --#TIMEINDEX    99
           --#STATE        OK
       ::= { fluidFSEventsHardware 189 } 
    
    
    fluidFSEventHardwareAppPsuError NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} has failure status, power supply redundancy lost (service tag: {{contextBasedServiceTag}})."
           --#TYPE         "Normal Event"
           --#SUMMARY      Power supply unit %s in NAS Appliance %d has failure status, power supply redundancy lost (service tag: %s).
           --#ARGUMENTS    {1,2,3}
           --#SEVERITY     MAJOR
           --#TIMEINDEX    99
           --#STATE        OK
       ::= { fluidFSEventsHardware 190 } 
    
    
    fluidFSEventHardwareAppPsuWarning NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} has warning status (service tag: {{contextBasedServiceTag}})."
           --#TYPE         "Normal Event"
           --#SUMMARY      Power supply unit %s in NAS Appliance %d has warning status (service tag: %s).
           --#ARGUMENTS    {1,2,3}
           --#SEVERITY     INFORMATIONAL
           --#TIMEINDEX    99
           --#STATE        OK
       ::= { fluidFSEventsHardware 191 } 
    
    
    fluidFSEventHardwareAppPsuBackToNormal NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} returned to normal operation (service tag: {{contextBasedServiceTag}})."
           --#TYPE         "Normal Event"
           --#SUMMARY      Power supply unit %s in NAS Appliance %d returned to normal operation (service tag: %s).
           --#ARGUMENTS    {1,2,3}
           --#SEVERITY     INFORMATIONAL
           --#TIMEINDEX    99
           --#STATE        OK
       ::= { fluidFSEventsHardware 192 } 
    
    
    fluidFSEventHardwareAppPsuInfoNotAvailable NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} status in NAS Appliance {{applianceId}} is not available. Internal error in power supply monitoring (service tag: {{contextBasedServiceTag}})."
           --#TYPE         "Normal Event"
           --#SUMMARY      Power supply unit %s status in NAS Appliance %d is not available. Internal error in power supply monitoring (service tag: %s).
           --#ARGUMENTS    {1,2,3}
           --#SEVERITY     MAJOR
           --#TIMEINDEX    99
           --#STATE        OK
       ::= { fluidFSEventsHardware 193 } 
    
    
    fluidFSEventHardwareAppPsuInfoIsAvailable NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} status in NAS Appliance {{applianceId}} is available again (service tag: {{contextBasedServiceTag}})."
           --#TYPE         "Normal Event"
           --#SUMMARY      Power supply unit %s status in NAS Appliance %d is available again (service tag: %s).
           --#ARGUMENTS    {1,2,3}
           --#SEVERITY     INFORMATIONAL
           --#TIMEINDEX    99
           --#STATE        OK
       ::= { fluidFSEventsHardware 194 } 
    
    
    fluidFSEventHardwareAppPsuAmperageError NOTIFICATION-TYPE
       OBJECTS { sysName, fluidFSEventsParamsHardwareContextBasedServiceTag, fluidFSEventsParamsHardwareApplianceId, fluidFSEventsParamsHardwareComponentName }
       STATUS current
       DESCRIPTION
           "Current sensor in power supply unit {{componentName}} in NAS Appliance {{applianceId}} reports critical status (service tag: {{contextBasedServiceTag}})."
           --#TYPE         "Normal Event"
           --#SUMMARY      Current sensor in power supply unit %s in NAS Appliance %d reports critical status (service tag: %s).
           --#ARGUMENTS    {1,2,3}
           --#SEVERITY     INFORMATIONAL
           --#TIMEINDEX    99
           --#STATE        OK
       ::= { fluidFSEventsHardware 195 } 
    
    
    fluidFSEventHardwareAppPsuAmperageWarning NOTIFICATION-TYPE
       OBJECTS { sysName, fluidFSEventsParamsHardwareContextBasedServiceTag, fluidFSEventsParamsHardwareApplianceId, fluidFSEventsParamsHardwareComponentName }
       STATUS current
       DESCRIPTION
           "Current sensor in power supply unit {{componentName}} in NAS Appliance {{applianceId}} reports warning status (service tag: {{contextBasedServiceTag}})."
           --#TYPE         "Normal Event"
           --#SUMMARY      Current sensor in power supply unit %s in NAS Appliance %d reports warning status (service tag: %s).
           --#ARGUMENTS    {1,2,3}
           --#SEVERITY     INFORMATIONAL
           --#TIMEINDEX    99
           --#STATE        OK
       ::= { fluidFSEventsHardware 196 } 
    
    
    fluidFSEventHardwareAppPsuAmperageNormal NOTIFICATION-TYPE
       OBJECTS { sysName, fluidFSEventsParamsHardwareContextBasedServiceTag, fluidFSEventsParamsHardwareApplianceId, fluidFSEventsParamsHardwareComponentName }
       STATUS current
       DESCRIPTION
           "Current sensor in power supply unit {{componentName}} in NAS Appliance {{applianceId}} reports normal status (service tag: {{contextBasedServiceTag}})."
           --#TYPE         "Normal Event"
           --#SUMMARY      Current sensor in power supply unit %s in NAS Appliance %d reports normal status (service tag: %s).
           --#ARGUMENTS    {1,2,3}
           --#SEVERITY     INFORMATIONAL
           --#TIMEINDEX    99
           --#STATE        OK
       ::= { fluidFSEventsHardware 197 } 
    
    
    fluidFSEventHardwareAppPsuTempError NOTIFICATION-TYPE
       OBJECTS { sysName, fluidFSEventsParamsHardwareContextBasedServiceTag, fluidFSEventsParamsHardwareApplianceId, fluidFSEventsParamsHardwareComponentName, fluidFSEventsParamsHardwareTemperature }
       STATUS current
       DESCRIPTION
           "Temperature sensor in power supply unit {{componentName}} in NAS Appliance {{applianceId}} reports critical status (Ambient temperature: {{temperature}} degrees Celsius) (service tag: {{contextBasedServiceTag}})."
           --#TYPE         "Normal Event"
           --#SUMMARY      Temperature sensor in power supply unit %s in NAS Appliance %d reports critical status (Ambient temperature: %d degrees Celsius) (service tag: %s).
           --#ARGUMENTS    {1,2,3,4}
           --#SEVERITY     INFORMATIONAL
           --#TIMEINDEX    99
           --#STATE        OK
       ::= { fluidFSEventsHardware 201 } 
    
    
    fluidFSEventHardwareAppPsuTempWarning NOTIFICATION-TYPE
       OBJECTS { sysName, fluidFSEventsParamsHardwareContextBasedServiceTag, fluidFSEventsParamsHardwareApplianceId, fluidFSEventsParamsHardwareComponentName, fluidFSEventsParamsHardwareTemperature }
       STATUS current
       DESCRIPTION
           "Temperature sensor in power supply unit {{componentName}} in NAS Appliance {{applianceId}} reports warning status (Ambient temperature: {{temperature}} degrees Celsius) (service tag: {{contextBasedServiceTag}})."
           --#TYPE         "Normal Event"
           --#SUMMARY      Temperature sensor in power supply unit %s in NAS Appliance %d reports warning status (Ambient temperature: %d degrees Celsius) (service tag: %s).
           --#ARGUMENTS    {1,2,3,4}
           --#SEVERITY     INFORMATIONAL
           --#TIMEINDEX    99
           --#STATE        OK
       ::= { fluidFSEventsHardware 202 } 
    
    
    fluidFSEventHardwareAppPsuTempNormal NOTIFICATION-TYPE
       OBJECTS { sysName, fluidFSEventsParamsHardwareContextBasedServiceTag, fluidFSEventsParamsHardwareApplianceId, fluidFSEventsParamsHardwareComponentName, fluidFSEventsParamsHardwareTemperature }
       STATUS current
       DESCRIPTION
           "Temperature sensor in power supply unit {{componentName}} in NAS Appliance {{applianceId}} reports normal status (Ambient temperature: {{temperature}} degrees Celsius) (service tag: {{contextBasedServiceTag}})."
           --#TYPE         "Normal Event"
           --#SUMMARY      Temperature sensor in power supply unit %s in NAS Appliance %d reports normal status (Ambient temperature: %d degrees Celsius) (service tag: %s).
           --#ARGUMENTS    {1,2,3,4}
           --#SEVERITY     INFORMATIONAL
           --#TIMEINDEX    99
           --#STATE        OK
       ::= { fluidFSEventsHardware 203 } 
    
    
    fluidFSEventHardwareAppPsuVoltageError NOTIFICATION-TYPE
       OBJECTS { sysName, fluidFSEventsParamsHardwareContextBasedServiceTag, fluidFSEventsParamsHardwareApplianceId, fluidFSEventsParamsHardwareComponentName }
       STATUS current
       DESCRIPTION
           "Voltage sensor in power supply unit {{componentName}} in NAS Appliance {{applianceId}} reports critical status (service tag: {{contextBasedServiceTag}})."
           --#TYPE         "Normal Event"
           --#SUMMARY      Voltage sensor in power supply unit %s in NAS Appliance %d reports critical status (service tag: %s).
           --#ARGUMENTS    {1,2,3}
           --#SEVERITY     INFORMATIONAL
           --#TIMEINDEX    99
           --#STATE        OK
       ::= { fluidFSEventsHardware 207 } 
    
    
    fluidFSEventHardwareAppPsuVoltageWarning NOTIFICATION-TYPE
       OBJECTS { sysName, fluidFSEventsParamsHardwareContextBasedServiceTag, fluidFSEventsParamsHardwareApplianceId, fluidFSEventsParamsHardwareComponentName }
       STATUS current
       DESCRIPTION
           "Voltage sensor in power supply unit {{componentName}} in NAS Appliance {{applianceId}} reports warning status (service tag: {{contextBasedServiceTag}})."
           --#TYPE         "Normal Event"
           --#SUMMARY      Voltage sensor in power supply unit %s in NAS Appliance %d reports warning status (service tag: %s).
           --#ARGUMENTS    {1,2,3}
           --#SEVERITY     INFORMATIONAL
           --#TIMEINDEX    99
           --#STATE        OK
       ::= { fluidFSEventsHardware 208 } 
    
    
    fluidFSEventHardwareAppPsuVoltageNormal NOTIFICATION-TYPE
       OBJECTS { sysName, fluidFSEventsParamsHardwareContextBasedServiceTag, fluidFSEventsParamsHardwareApplianceId, fluidFSEventsParamsHardwareComponentName }
       STATUS current
       DESCRIPTION
           "Voltage sensor in power supply unit {{componentName}} in NAS Appliance {{applianceId}} reports normal status (service tag: {{contextBasedServiceTag}})."
           --#TYPE         "Normal Event"
           --#SUMMARY      Voltage sensor in power supply unit %s in NAS Appliance %d reports normal status (service tag: %s).
           --#ARGUMENTS    {1,2,3}
           --#SEVERITY     INFORMATIONAL
           --#TIMEINDEX    99
           --#STATE        OK
       ::= { fluidFSEventsHardware 209 } 
    
    
    fluidFSEventHardwareMotherBoardAmperageError NOTIFICATION-TYPE
       OBJECTS { sysName, fluidFSEventsParamsHardwareContextBasedServiceTag, fluidFSEventsParamsHardwareNodeId }
       STATUS current
       DESCRIPTION
           "NAS Controller{{nodeId}} system board current sensors report critical status (service tag: {{contextBasedServiceTag}})."
           --#TYPE         "Normal Event"
           --#SUMMARY      NAS Controller%d system board current sensors report critical status (service tag: %s).
           --#ARGUMENTS    {1,2}
           --#SEVERITY     INFORMATIONAL
           --#TIMEINDEX    99
           --#STATE        OK
       ::= { fluidFSEventsHardware 213 } 
    
    
    fluidFSEventHardwareMotherBoardAmperageWarning NOTIFICATION-TYPE
       OBJECTS { sysName, fluidFSEventsParamsHardwareContextBasedServiceTag, fluidFSEventsParamsHardwareNodeId }
       STATUS current
       DESCRIPTION
           "NAS Controller{{nodeId}} system board current sensors report warning status (service tag: {{contextBasedServiceTag}})."
           --#TYPE         "Normal Event"
           --#SUMMARY      NAS Controller%d system board current sensors report warning status (service tag: %s).
           --#ARGUMENTS    {1,2}
           --#SEVERITY     INFORMATIONAL
           --#TIMEINDEX    99
           --#STATE        OK
       ::= { fluidFSEventsHardware 214 } 
    
    
    fluidFSEventHardwareMotherBoardAmperageNormal NOTIFICATION-TYPE
       OBJECTS { sysName, fluidFSEventsParamsHardwareContextBasedServiceTag, fluidFSEventsParamsHardwareNodeId }
       STATUS current
       DESCRIPTION
           "NAS Controller{{nodeId}} system board current sensors report normal status (service tag: {{contextBasedServiceTag}})."
           --#TYPE         "Normal Event"
           --#SUMMARY      NAS Controller%d system board current sensors report normal status (service tag: %s).
           --#ARGUMENTS    {1,2}
           --#SEVERITY     INFORMATIONAL
           --#TIMEINDEX    99
           --#STATE        OK
       ::= { fluidFSEventsHardware 215 } 
    
    
    fluidFSEventHardwareMotherBoardTempError NOTIFICATION-TYPE
       OBJECTS { sysName, fluidFSEventsParamsHardwareContextBasedServiceTag, fluidFSEventsParamsHardwareNodeId, fluidFSEventsParamsHardwareTemperature }
       STATUS current
       DESCRIPTION
           "NAS Controller{{nodeId}} system board temperature sensors report critical status (Ambient temperature: {{temperature}} degrees Celsius) (service tag: {{contextBasedServiceTag}})."
           --#TYPE         "Normal Event"
           --#SUMMARY      NAS Controller%d system board temperature sensors report critical status (Ambient temperature: %d degrees Celsius) (service tag: %s).
           --#ARGUMENTS    {1,2,3}
           --#SEVERITY     INFORMATIONAL
           --#TIMEINDEX    99
           --#STATE        OK
       ::= { fluidFSEventsHardware 216 } 
    
    
    fluidFSEventHardwareMotherBoardTempWarning NOTIFICATION-TYPE
       OBJECTS { sysName, fluidFSEventsParamsHardwareContextBasedServiceTag, fluidFSEventsParamsHardwareNodeId, fluidFSEventsParamsHardwareTemperature }
       STATUS current
       DESCRIPTION
           "NAS Controller{{nodeId}} system board temperature sensors report warning status (Ambient temperature: {{temperature}} degrees Celsius) (service tag: {{contextBasedServiceTag}})."
           --#TYPE         "Normal Event"
           --#SUMMARY      NAS Controller%d system board temperature sensors report warning status (Ambient temperature: %d degrees Celsius) (service tag: %s).
           --#ARGUMENTS    {1,2,3}
           --#SEVERITY     INFORMATIONAL
           --#TIMEINDEX    99
           --#STATE        OK
       ::= { fluidFSEventsHardware 217 } 
    
    
    fluidFSEventHardwareMotherBoardTempNormal NOTIFICATION-TYPE
       OBJECTS { sysName, fluidFSEventsParamsHardwareContextBasedServiceTag, fluidFSEventsParamsHardwareNodeId, fluidFSEventsParamsHardwareTemperature }
       STATUS current
       DESCRIPTION
           "NAS Controller{{nodeId}} system board temperature sensors report normal status (Ambient temperature: {{temperature}} degrees Celsius) (service tag: {{contextBasedServiceTag}})."
           --#TYPE         "Normal Event"
           --#SUMMARY      NAS Controller%d system board temperature sensors report normal status (Ambient temperature: %d degrees Celsius) (service tag: %s).
           --#ARGUMENTS    {1,2,3}
           --#SEVERITY     INFORMATIONAL
           --#TIMEINDEX    99
           --#STATE        OK
       ::= { fluidFSEventsHardware 218 } 
    
    
    fluidFSEventHardwareMotherBoardVoltageError NOTIFICATION-TYPE
       OBJECTS { sysName, fluidFSEventsParamsHardwareContextBasedServiceTag, fluidFSEventsParamsHardwareNodeId }
       STATUS current
       DESCRIPTION
           "NAS Controller{{nodeId}} system board voltage sensors report critical status (service tag: {{contextBasedServiceTag}})."
           --#TYPE         "Normal Event"
           --#SUMMARY      NAS Controller%d system board voltage sensors report critical status (service tag: %s).
           --#ARGUMENTS    {1,2}
           --#SEVERITY     INFORMATIONAL
           --#TIMEINDEX    99
           --#STATE        OK
       ::= { fluidFSEventsHardware 219 } 
    
    
    fluidFSEventHardwareMotherBoardVoltageWarning NOTIFICATION-TYPE
       OBJECTS { sysName, fluidFSEventsParamsHardwareContextBasedServiceTag, fluidFSEventsParamsHardwareNodeId }
       STATUS current
       DESCRIPTION
           "NAS Controller{{nodeId}} system board voltage sensors report warning status (service tag: {{contextBasedServiceTag}})."
           --#TYPE         "Normal Event"
           --#SUMMARY      NAS Controller%d system board voltage sensors report warning status (service tag: %s).
           --#ARGUMENTS    {1,2}
           --#SEVERITY     INFORMATIONAL
           --#TIMEINDEX    99
           --#STATE        OK
       ::= { fluidFSEventsHardware 220 } 
    
    
    fluidFSEventHardwareMotherBoardVoltageNormal NOTIFICATION-TYPE
       OBJECTS { sysName, fluidFSEventsParamsHardwareContextBasedServiceTag, fluidFSEventsParamsHardwareNodeId }
       STATUS current
       DESCRIPTION
           "NAS Controller{{nodeId}} system board voltage sensors report normal status (service tag: {{contextBasedServiceTag}})."
           --#TYPE         "Normal Event"
           --#SUMMARY      NAS Controller%d system board voltage sensors report normal status (service tag: %s).
           --#ARGUMENTS    {1,2}
           --#SEVERITY     INFORMATIONAL
           --#TIMEINDEX    99
           --#STATE        OK
       ::= { fluidFSEventsHardware 221 } 
    
    
    fluidFSEventHardwareMotherBoardInfoNotAvailable NOTIFICATION-TYPE
       OBJECTS { sysName, fluidFSEventsParamsHardwareContextBasedServiceTag, fluidFSEventsParamsHardwareNodeId }
       STATUS current
       DESCRIPTION
           "Controller system board status in NAS Controller{{nodeId}} is not available. Internal error in system board monitoring (service tag: {{contextBasedServiceTag}})."
           --#TYPE         "Normal Event"
           --#SUMMARY      Controller system board status in NAS Controller%d is not available. Internal error in system board monitoring (service tag: %s).
           --#ARGUMENTS    {1,2}
           --#SEVERITY     MAJOR
           --#TIMEINDEX    99
           --#STATE        OK
       ::= { fluidFSEventsHardware 222 } 
    
    
    fluidFSEventHardwareMotherBoardInfoIsAvailable NOTIFICATION-TYPE
       OBJECTS { sysName, fluidFSEventsParamsHardwareContextBasedServiceTag, fluidFSEventsParamsHardwareNodeId }
       STATUS current
       DESCRIPTION
           "Controller system board status in NAS Controller{{nodeId}} is available again (service tag: {{contextBasedServiceTag}})."
           --#TYPE         "Normal Event"
           --#SUMMARY      Controller system board status in NAS Controller%d is available again (service tag: %s).
           --#ARGUMENTS    {1,2}
           --#SEVERITY     INFORMATIONAL
           --#TIMEINDEX    99
           --#STATE        OK
       ::= { fluidFSEventsHardware 223 } 
    
    
    fluidFSEventHardwareNetworksInfoNotAvailable NOTIFICATION-TYPE
       OBJECTS { sysName, fluidFSEventsParamsHardwareContextBasedServiceTag, fluidFSEventsParamsHardwareNodeId }
       STATUS current
       DESCRIPTION
           "Network status in NAS Controller{{nodeId}} is not available. Internal error in network monitoring (service tag: {{contextBasedServiceTag}})."
           --#TYPE         "Normal Event"
           --#SUMMARY      Network status in NAS Controller%d is not available. Internal error in network monitoring (service tag: %s).
           --#ARGUMENTS    {1,2}
           --#SEVERITY     MAJOR
           --#TIMEINDEX    99
           --#STATE        OK
       ::= { fluidFSEventsHardware 224 } 
    
    
    fluidFSEventHardwareNetworksInfoIsAvailable NOTIFICATION-TYPE
       OBJECTS { sysName, fluidFSEventsParamsHardwareContextBasedServiceTag, fluidFSEventsParamsHardwareNodeId }
       STATUS current
       DESCRIPTION
           "Network status in NAS Controller{{nodeId}} is available again (service tag: {{contextBasedServiceTag}})."
           --#TYPE         "Normal Event"
           --#SUMMARY      Network status in NAS Controller%d is available again (service tag: %s).
           --#ARGUMENTS    {1,2}
           --#SEVERITY     INFORMATIONAL
           --#TIMEINDEX    99
           --#STATE        OK
       ::= { fluidFSEventsHardware 225 } 
    
    
    fluidFSEventHardwareNetworkInfoNotAvailable NOTIFICATION-TYPE
       OBJECTS { sysName, fluidFSEventsParamsHardwareContextBasedServiceTag, fluidFSEventsParamsHardwareNodeId, fluidFSEventsParamsHardwareNetworkName }
       STATUS current
       DESCRIPTION
           "{{networkName}} network status in NAS Controller{{nodeId}} is not available. Internal error in network monitoring (service tag: {{contextBasedServiceTag}})."
           --#TYPE         "Normal Event"
           --#SUMMARY      %s network status in NAS Controller%d is not available. Internal error in network monitoring (service tag: %s).
           --#ARGUMENTS    {1,2,3}
           --#SEVERITY     INFORMATIONAL
           --#TIMEINDEX    99
           --#STATE        OK
       ::= { fluidFSEventsHardware 229 } 
    
    
    fluidFSEventHardwareNetworkInfoIsAvailable NOTIFICATION-TYPE
       OBJECTS { sysName, fluidFSEventsParamsHardwareContextBasedServiceTag, fluidFSEventsParamsHardwareNodeId, fluidFSEventsParamsHardwareNetworkName }
       STATUS current
       DESCRIPTION
           "{{networkName}} network status in NAS Controller{{nodeId}} is available again (service tag: {{contextBasedServiceTag}})."
           --#TYPE         "Normal Event"
           --#SUMMARY      %s network status in NAS Controller%d is available again (service tag: %s).
           --#ARGUMENTS    {1,2,3}
           --#SEVERITY     INFORMATIONAL
           --#TIMEINDEX    99
           --#STATE        OK
       ::= { fluidFSEventsHardware 230 } 
    
    
    fluidFSEventHardwareApplianceStatusNotAvailable NOTIFICATION-TYPE
       OBJECTS { sysName, fluidFSEventsParamsHardwareContextBasedServiceTag, fluidFSEventsParamsHardwareApplianceId }
       STATUS current
       DESCRIPTION
           "NAS Appliance {{applianceId}} hardware status is not available. Internal error in appliance status analysis (service tag: {{contextBasedServiceTag}})."
           --#TYPE         "Normal Event"
           --#SUMMARY      NAS Appliance %d hardware status is not available. Internal error in appliance status analysis (service tag: %s).
           --#ARGUMENTS    {1,2}
           --#SEVERITY     MAJOR
           --#TIMEINDEX    99
           --#STATE        OK
       ::= { fluidFSEventsHardware 240 } 
    
    
    fluidFSEventHardwareApplianceStatusAvailable NOTIFICATION-TYPE
       OBJECTS { sysName, fluidFSEventsParamsHardwareContextBasedServiceTag, fluidFSEventsParamsHardwareApplianceId }
       STATUS current
       DESCRIPTION
           "NAS Appliance {{applianceId}} hardware status is available again (service tag: {{contextBasedServiceTag}})."
           --#TYPE         "Normal Event"
           --#SUMMARY      NAS Appliance %d hardware status is available again (service tag: %s).
           --#ARGUMENTS    {1,2}
           --#SEVERITY     INFORMATIONAL
           --#TIMEINDEX    99
           --#STATE        OK
       ::= { fluidFSEventsHardware 241 } 
    
    
    fluidFSEventHardwareLocalIPMIBackToNormal NOTIFICATION-TYPE
       OBJECTS { sysName, fluidFSEventsParamsHardwareContextBasedServiceTag, fluidFSEventsParamsHardwareNodeId }
       STATUS current
       DESCRIPTION
           "NAS Controller{{nodeId}} IPMI is back to normal (service tag: {{contextBasedServiceTag}})."
           --#TYPE         "Normal Event"
           --#SUMMARY      NAS Controller%d IPMI is back to normal (service tag: %s).
           --#ARGUMENTS    {1,2}
           --#SEVERITY     INFORMATIONAL
           --#TIMEINDEX    99
           --#STATE        OK
       ::= { fluidFSEventsHardware 245 } 
    
    
    fluidFSEventHardwarePeerIPMIBackToNormal NOTIFICATION-TYPE
       OBJECTS { sysName, fluidFSEventsParamsHardwareContextBasedServiceTag, fluidFSEventsParamsHardwareNodeId }
       STATUS current
       DESCRIPTION
           "NAS Controller{{nodeId}} peer IPMI is reachable again (service tag: {{contextBasedServiceTag}})."
           --#TYPE         "Normal Event"
           --#SUMMARY      NAS Controller%d peer IPMI is reachable again (service tag: %s).
           --#ARGUMENTS    {1,2}
           --#SEVERITY     INFORMATIONAL
           --#TIMEINDEX    99
           --#STATE        OK
       ::= { fluidFSEventsHardware 246 } 
    
    
    fluidFSEventHardwareLocalIPMIStatusNotAvailable NOTIFICATION-TYPE
       OBJECTS { sysName, fluidFSEventsParamsHardwareContextBasedServiceTag, fluidFSEventsParamsHardwareNodeId }
       STATUS current
       DESCRIPTION
           "NAS Controller{{nodeId}} local IPMI status is not available. Internal error in IPMI status monitoring (service tag: {{contextBasedServiceTag}})."
           --#TYPE         "Normal Event"
           --#SUMMARY      NAS Controller%d local IPMI status is not available. Internal error in IPMI status monitoring (service tag: %s).
           --#ARGUMENTS    {1,2}
           --#SEVERITY     INFORMATIONAL
           --#TIMEINDEX    99
           --#STATE        OK
       ::= { fluidFSEventsHardware 247 } 
    
    
    fluidFSEventHardwareLocalIPMIStatusAvailable NOTIFICATION-TYPE
       OBJECTS { sysName, fluidFSEventsParamsHardwareContextBasedServiceTag, fluidFSEventsParamsHardwareNodeId }
       STATUS current
       DESCRIPTION
           "NAS Controller{{nodeId}} local IPMI status is available again (service tag: {{contextBasedServiceTag}})."
           --#TYPE         "Normal Event"
           --#SUMMARY      NAS Controller%d local IPMI status is available again (service tag: %s).
           --#ARGUMENTS    {1,2}
           --#SEVERITY     INFORMATIONAL
           --#TIMEINDEX    99
           --#STATE        OK
       ::= { fluidFSEventsHardware 248 } 
    
    
    fluidFSEventHardwarePeerIPMIStatusNotAvailable NOTIFICATION-TYPE
       OBJECTS { sysName, fluidFSEventsParamsHardwareContextBasedServiceTag, fluidFSEventsParamsHardwareNodeId }
       STATUS current
       DESCRIPTION
           "NAS Controller{{nodeId}} peer IPMI status is not available. Internal error in IPMI status monitoring (service tag: {{contextBasedServiceTag}})."
           --#TYPE         "Normal Event"
           --#SUMMARY      NAS Controller%d peer IPMI status is not available. Internal error in IPMI status monitoring (service tag: %s).
           --#ARGUMENTS    {1,2}
           --#SEVERITY     INFORMATIONAL
           --#TIMEINDEX    99
           --#STATE        OK
       ::= { fluidFSEventsHardware 249 } 
    
    
    fluidFSEventHardwarePeerIPMIStatusAvailable NOTIFICATION-TYPE
       OBJECTS { sysName, fluidFSEventsParamsHardwareContextBasedServiceTag, fluidFSEventsParamsHardwareNodeId }
       STATUS current
       DESCRIPTION
           "NAS Controller{{nodeId}} peer IPMI status is available again (service tag: {{contextBasedServiceTag}})."
           --#TYPE         "Normal Event"
           --#SUMMARY      NAS Controller%d peer IPMI status is available again (service tag: %s).
           --#ARGUMENTS    {1,2}
           --#SEVERITY     INFORMATIONAL
           --#TIMEINDEX    99
           --#STATE        OK
       ::= { fluidFSEventsHardware 250 } 
    
    
    fluidFSEventHardwarePsuNotDetected NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} is not detected, power supply redundancy lost. Please make sure the unit is attached properly (service tag: {{contextBasedServiceTag}})."
           --#TYPE         "Normal Event"
           --#SUMMARY      Power supply unit %s in NAS Controller%d is not detected, power supply redundancy lost. Please make sure the unit is attached properly (service tag: %s).
           --#ARGUMENTS    {1,2,3}
           --#SEVERITY     MAJOR
           --#TIMEINDEX    99
           --#STATE        OK
       ::= { fluidFSEventsHardware 251 } 
    
    
    fluidFSEventHardwarePsuDetected NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} is detected (service tag: {{contextBasedServiceTag}})."
           --#TYPE         "Normal Event"
           --#SUMMARY      Power supply unit %s in NAS Controller%d is detected (service tag: %s).
           --#ARGUMENTS    {1,2,3}
           --#SEVERITY     INFORMATIONAL
           --#TIMEINDEX    99
           --#STATE        OK
       ::= { fluidFSEventsHardware 252 } 
    
    
    fluidFSEventHardwareAppPsuNotDetected NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} is not detected, power supply redundancy lost. Please make sure the unit is attached properly (service tag: {{contextBasedServiceTag}})."
           --#TYPE         "Normal Event"
           --#SUMMARY      Power supply unit %s in NAS Appliance %d is not detected, power supply redundancy lost. Please make sure the unit is attached properly (service tag: %s).
           --#ARGUMENTS    {1,2,3}
           --#SEVERITY     MAJOR
           --#TIMEINDEX    99
           --#STATE        OK
       ::= { fluidFSEventsHardware 253 } 
    
    
    fluidFSEventHardwareAppPsuDetected NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} is detected (service tag: {{contextBasedServiceTag}})."
           --#TYPE         "Normal Event"
           --#SUMMARY      Power supply unit %s in NAS Appliance %d is detected (service tag: %s).
           --#ARGUMENTS    {1,2,3}
           --#SEVERITY     INFORMATIONAL
           --#TIMEINDEX    99
           --#STATE        OK
       ::= { fluidFSEventsHardware 254 } 
    
    
    fluidFSEventHardwareBpsNotAccessible NOTIFICATION-TYPE
       OBJECTS { sysName, fluidFSEventsParamsHardwareContextBasedServiceTag, fluidFSEventsParamsHardwareNodeId }
       STATUS current
       DESCRIPTION
           "NAS Controller{{nodeId}} failed to reach its BPS (service tag: {{contextBasedServiceTag}})."
           --#TYPE         "Normal Event"
           --#SUMMARY      NAS Controller%d failed to reach its BPS (service tag: %s).
           --#ARGUMENTS    {1,2}
           --#SEVERITY     MAJOR
           --#TIMEINDEX    99
           --#STATE        OK
       ::= { fluidFSEventsHardware 257 } 
    
    
    fluidFSEventHardwareNoLinkInReplicationRelatedEthOnController NOTIFICATION-TYPE
       OBJECTS { sysName, fluidFSEventsParamsHardwareNodeId, fluidFSEventsParamsHardwareEthName }
       STATUS current
       DESCRIPTION
           "Eth{{ethName}} which belongs to NAS Controller{{nodeId}} is down, therefore replication related connectivity may be affected."
           --#TYPE         "Normal Event"
           --#SUMMARY      Eth%s which belongs to NAS Controller%d is down, therefore replication related connectivity may be affected.
           --#ARGUMENTS    {1,2}
           --#SEVERITY     MAJOR
           --#TIMEINDEX    99
           --#STATE        OK
       ::= { fluidFSEventsHardware 258 } 
    
    
    fluidFSEventHardwarePsuNoInput NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} has no input. Please make sure the unit cable is attached properly (service tag: {{contextBasedServiceTag}})."
           --#TYPE         "Normal Event"
           --#SUMMARY      Power supply unit %s in NAS Controller%d has no input. Please make sure the unit cable is attached properly (service tag: %s).
           --#ARGUMENTS    {1,2,3}
           --#SEVERITY     MAJOR
           --#TIMEINDEX    99
           --#STATE        OK
       ::= { fluidFSEventsHardware 259 } 
    
    
    fluidFSEventHardwarePsuInputDetected NOTIFICATION-TYPE
       OBJECTS { sysName, fluidFSEventsParamsHardwareContextBasedServiceTag, fluidFSEventsParamsHardwareNodeId, fluidFSEventsParamsHardwareComponentName }
       STATUS current
       DESCRIPTION
           "Power supply unit {{componentName}} in NAS Controller{{nodeId}} input detected (service tag: {{contextBasedServiceTag}})."
           --#TYPE         "Normal Event"
           --#SUMMARY      Power supply unit %s in NAS Controller%d input detected (service tag: %s).
           --#ARGUMENTS    {1,2,3}
           --#SEVERITY     INFORMATIONAL
           --#TIMEINDEX    99
           --#STATE        OK
       ::= { fluidFSEventsHardware 260 } 
    
    
    fluidFSEventHardwareAppPsuNoInput NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} has no input. Please make sure the unit cable is attached properly (service tag: {{contextBasedServiceTag}})."
           --#TYPE         "Normal Event"
           --#SUMMARY      Power supply unit %s in NAS Appliance %d has no input. Please make sure the unit cable is attached properly (service tag: %s).
           --#ARGUMENTS    {1,2,3}
           --#SEVERITY     MAJOR
           --#TIMEINDEX    99
           --#STATE        OK
       ::= { fluidFSEventsHardware 261 } 
    
    
    fluidFSEventHardwareAppPsuInputDetected NOTIFICATION-TYPE
       OBJECTS { sysName, fluidFSEventsParamsHardwareContextBasedServiceTag, fluidFSEventsParamsHardwareApplianceId, fluidFSEventsParamsHardwareComponentName }
       STATUS current
       DESCRIPTION
           "Power supply unit {{componentName}} in NAS Appliance {{applianceId}} input detected (service tag: {{contextBasedServiceTag}})."
           --#TYPE         "Normal Event"
           --#SUMMARY      Power supply unit %s in NAS Appliance %d input detected (service tag: %s).
           --#ARGUMENTS    {1,2,3}
           --#SEVERITY     INFORMATIONAL
           --#TIMEINDEX    99
           --#STATE        OK
       ::= { fluidFSEventsHardware 262 } 
    
    
    fluidFSEventHardwarePeerIPMIReachability NOTIFICATION-TYPE
       OBJECTS { sysName, fluidFSEventsParamsHardwareContextBasedServiceTag, fluidFSEventsParamsHardwareNodeId }
       STATUS current
       DESCRIPTION
           "NAS Controller{{nodeId}} cannot reach peer IPMI (service tag: {{contextBasedServiceTag}})."
           --#TYPE         "Normal Event"
           --#SUMMARY      NAS Controller%d cannot reach peer IPMI (service tag: %s).
           --#ARGUMENTS    {1,2}
           --#SEVERITY     INFORMATIONAL
           --#TIMEINDEX    99
           --#STATE        OK
       ::= { fluidFSEventsHardware 264 } 
    
    
    fluidFSEventHardwareLocalIPMIReachability NOTIFICATION-TYPE
       OBJECTS { sysName, fluidFSEventsParamsHardwareContextBasedServiceTag, fluidFSEventsParamsHardwareNodeId }
       STATUS current
       DESCRIPTION
           "NAS Controller{{nodeId}} IPMI is not working (service tag: {{contextBasedServiceTag}})."
           --#TYPE         "Normal Event"
           --#SUMMARY      NAS Controller%d IPMI is not working (service tag: %s).
           --#ARGUMENTS    {1,2}
           --#SEVERITY     INFORMATIONAL
           --#TIMEINDEX    99
           --#STATE        OK
       ::= { fluidFSEventsHardware 265 } 
    
    
    fluidFSEventHardwareChassisIntrusionAlert NOTIFICATION-TYPE
       OBJECTS { sysName, fluidFSEventsParamsHardwareContextBasedServiceTag, fluidFSEventsParamsHardwareNodeId }
       STATUS current
       DESCRIPTION
           "Chassis cover for NAS Controller{{nodeId}} is open (service tag: {{contextBasedServiceTag}})."
           --#TYPE         "Normal Event"
           --#SUMMARY      Chassis cover for NAS Controller%d is open (service tag: %s).
           --#ARGUMENTS    {1,2}
           --#SEVERITY     MAJOR
           --#TIMEINDEX    99
           --#STATE        OK
       ::= { fluidFSEventsHardware 267 } 
    
    
    fluidFSEventHardwareChassisIntrusionBackToNormal NOTIFICATION-TYPE
       OBJECTS { sysName, fluidFSEventsParamsHardwareContextBasedServiceTag, fluidFSEventsParamsHardwareNodeId }
       STATUS current
       DESCRIPTION
           "Chassis cover for NAS Controller{{nodeId}} was closed (service tag: {{contextBasedServiceTag}})."
           --#TYPE         "Normal Event"
           --#SUMMARY      Chassis cover for NAS Controller%d was closed (service tag: %s).
           --#ARGUMENTS    {1,2}
           --#SEVERITY     INFORMATIONAL
           --#TIMEINDEX    99
           --#STATE        OK
       ::= { fluidFSEventsHardware 268 } 
    
    
    fluidFSEventHardwareBpsCalibrationCycleNotAvailable NOTIFICATION-TYPE
       OBJECTS { sysName, fluidFSEventsParamsHardwareContextBasedServiceTag, fluidFSEventsParamsHardwareNodeId }
       STATUS current
       DESCRIPTION
           "Battery Calibration Cycle status in NAS Controller{{nodeId}} is not available. Internal error in Battery monitoring (service tag: {{contextBasedServiceTag}})."
           --#TYPE         "Normal Event"
           --#SUMMARY      Battery Calibration Cycle status in NAS Controller%d is not available. Internal error in Battery monitoring (service tag: %s).
           --#ARGUMENTS    {1,2}
           --#SEVERITY     INFORMATIONAL
           --#TIMEINDEX    99
           --#STATE        OK
       ::= { fluidFSEventsHardware 269 } 
    
    
    fluidFSEventHardwareBpsCalibrationCycleIsAvailable NOTIFICATION-TYPE
       OBJECTS { sysName, fluidFSEventsParamsHardwareContextBasedServiceTag, fluidFSEventsParamsHardwareNodeId }
       STATUS current
       DESCRIPTION
           "Battery Calibration Cycle status in NAS Controller{{nodeId}} is available again (service tag: {{contextBasedServiceTag}})."
           --#TYPE         "Normal Event"
           --#SUMMARY      Battery Calibration Cycle status in NAS Controller%d is available again (service tag: %s).
           --#ARGUMENTS    {1,2}
           --#SEVERITY     INFORMATIONAL
           --#TIMEINDEX    99
           --#STATE        OK
       ::= { fluidFSEventsHardware 270 } 
    
    
    fluidFSEventHardwareBpsCalibrationCycleInProgress NOTIFICATION-TYPE
       OBJECTS { sysName, fluidFSEventsParamsHardwareContextBasedServiceTag, fluidFSEventsParamsHardwareNodeId }
       STATUS current
       DESCRIPTION
           "Battery Calibration Cycle is in progress.   Description:  A Battery Calibration Cycle in NAS Controller{{nodeId}} is in progress. The Battery Pack will go through charge and discharge cycles, therefore battery error events during this process are normal. This process may take up to 7 days from first notification to complete. (service tag: {{contextBasedServiceTag}})."
           --#TYPE         "Normal Event"
           --#SUMMARY      Battery Calibration Cycle is in progress.   Description:  A Battery Calibration Cycle in NAS Controller%d is in progress. The Battery Pack will go through charge and discharge cycles, therefore battery error events during this process are normal. This process may take up to 7 days from first notification to complete. (service tag: %s).
           --#ARGUMENTS    {1,2}
           --#SEVERITY     INFORMATIONAL
           --#TIMEINDEX    99
           --#STATE        OK
       ::= { fluidFSEventsHardware 271 } 
    
    
    fluidFSEventHardwareBpsForcedCalibrationCyclePending NOTIFICATION-TYPE
       OBJECTS { sysName, fluidFSEventsParamsHardwareContextBasedServiceTag, fluidFSEventsParamsHardwareNodeId }
       STATUS current
       DESCRIPTION
           "Forced BPS Calibration pending, performance impact expected.   Description:  Calibration Cycle will be forced in 30 days from first notification. Could not perform normal battery calibration cycle in NAS Controller{{nodeId}} since peer controller battery is not in an optimal condition. If peer battery is not repaired before the Calibration Cycle is forced, then during portions of the Calibration Cycle the file system will move to journaling mode, which may cause a performance impact (service tag: {{contextBasedServiceTag}})."
           --#TYPE         "Normal Event"
           --#SUMMARY      Forced BPS Calibration pending, performance impact expected.   Description:  Calibration Cycle will be forced in 30 days from first notification. Could not perform normal battery calibration cycle in NAS Controller%d since peer controller battery is not in an optimal condition. If peer battery is not repaired before the Calibration Cycle is forced, then during portions of the Calibration Cycle the file system will move to journaling mode, which may cause a performance impact (service tag: %s).
           --#ARGUMENTS    {1,2}
           --#SEVERITY     MAJOR
           --#TIMEINDEX    99
           --#STATE        OK
       ::= { fluidFSEventsHardware 272 } 
    
    
    fluidFSEventHardwareBpsForcedCalibrationCycleNotNeeded NOTIFICATION-TYPE
       OBJECTS { sysName, fluidFSEventsParamsHardwareContextBasedServiceTag, fluidFSEventsParamsHardwareNodeId }
       STATUS current
       DESCRIPTION
           "The Forced Battery Calibration Cycle in NAS Controller{{nodeId}} is no longer required (service tag: {{contextBasedServiceTag}})."
           --#TYPE         "Normal Event"
           --#SUMMARY      The Forced Battery Calibration Cycle in NAS Controller%d is no longer required (service tag: %s).
           --#ARGUMENTS    {1,2}
           --#SEVERITY     INFORMATIONAL
           --#TIMEINDEX    99
           --#STATE        OK
       ::= { fluidFSEventsHardware 273 } 
    
    
    fluidFSEventHardwareBpsCalibrationCycleIdle NOTIFICATION-TYPE
       OBJECTS { sysName, fluidFSEventsParamsHardwareContextBasedServiceTag, fluidFSEventsParamsHardwareNodeId }
       STATUS current
       DESCRIPTION
           "The Battery Calibration Cycle in NAS Controller{{nodeId}} is idle (service tag: {{contextBasedServiceTag}})."
           --#TYPE         "Normal Event"
           --#SUMMARY      The Battery Calibration Cycle in NAS Controller%d is idle (service tag: %s).
           --#ARGUMENTS    {1,2}
           --#SEVERITY     INFORMATIONAL
           --#TIMEINDEX    99
           --#STATE        OK
       ::= { fluidFSEventsHardware 274 } 
    
    
    fluidFSEventHardwareBpsCalibrationLowBattery NOTIFICATION-TYPE
       OBJECTS { sysName, fluidFSEventsParamsHardwareContextBasedServiceTag, fluidFSEventsParamsHardwareNodeId, fluidFSEventsParamsHardwareBpsBatteryCharge }
       STATUS current
       DESCRIPTION
           "BPS on NAS Controller{{nodeId}} is not operating properly. This is expected as the battery is under calibration cycle. Charge is {{bpsBatteryCharge}}% (service tag: {{contextBasedServiceTag}})."
           --#TYPE         "Normal Event"
           --#SUMMARY      BPS on NAS Controller%d is not operating properly. This is expected as the battery is under calibration cycle. Charge is %d% (service tag: %s).
           --#ARGUMENTS    {1,2,3}
           --#SEVERITY     INFORMATIONAL
           --#TIMEINDEX    99
           --#STATE        OK
       ::= { fluidFSEventsHardware 275 } 
    
    
    fluidFSEventHardwareStandardFrameDisconnected NOTIFICATION-TYPE
       OBJECTS { sysName, fluidFSEventsParamsHardwareContextBasedServiceTag, fluidFSEventsParamsHardwareFirstNodeId, fluidFSEventsParamsHardwareSecondNodeId, fluidFSEventsParamsHardwareEthName, fluidFSEventsParamsHardwareTargetEthName }
       STATUS current
       DESCRIPTION
           "{{ethName}} on NAS Controller{{firstNodeId}} cannot access {{targetEthName}} on NAS Controller{{secondNodeId}} (service tag: {{contextBasedServiceTag}}). Check that these interfaces are connected to the same switch, and are properly tagged."
           --#TYPE         "Normal Event"
           --#SUMMARY      %s on NAS Controller%d cannot access %s on NAS Controller%d (service tag: %s). Check that these interfaces are connected to the same switch, and are properly tagged.
           --#ARGUMENTS    {1,2,3,4,5}
           --#SEVERITY     MAJOR
           --#TIMEINDEX    99
           --#STATE        OK
       ::= { fluidFSEventsHardware 276 } 
    
    
    fluidFSEventHardwareStandardFrameConnected NOTIFICATION-TYPE
       OBJECTS { sysName, fluidFSEventsParamsHardwareContextBasedServiceTag, fluidFSEventsParamsHardwareFirstNodeId, fluidFSEventsParamsHardwareSecondNodeId, fluidFSEventsParamsHardwareEthName, fluidFSEventsParamsHardwareTargetEthName }
       STATUS current
       DESCRIPTION
           "{{ethName}} on NAS Controller{{firstNodeId}} can access {{targetEthName}} on NAS Controller{{secondNodeId}} (service tag: {{contextBasedServiceTag}})."
           --#TYPE         "Normal Event"
           --#SUMMARY      %s on NAS Controller%d can access %s on NAS Controller%d (service tag: %s).
           --#ARGUMENTS    {1,2,3,4,5}
           --#SEVERITY     INFORMATIONAL
           --#TIMEINDEX    99
           --#STATE        OK
       ::= { fluidFSEventsHardware 277 } 
    
    
    fluidFSEventHardwareLargeFrameLDisconnected NOTIFICATION-TYPE
       OBJECTS { sysName, fluidFSEventsParamsHardwareContextBasedServiceTag, fluidFSEventsParamsHardwareFirstNodeId, fluidFSEventsParamsHardwareSecondNodeId, fluidFSEventsParamsHardwareEthName, fluidFSEventsParamsHardwareTargetEthName }
       STATUS current
       DESCRIPTION
           "{{ethName}} on NAS Controller{{firstNodeId}} cannot access {{targetEthName}} on NAS Controller{{secondNodeId}} using large frames (service tag: {{contextBasedServiceTag}}). Check that jumbo-frames are enabled for these interfaces in the switch."
           --#TYPE         "Normal Event"
           --#SUMMARY      %s on NAS Controller%d cannot access %s on NAS Controller%d using large frames (service tag: %s). Check that jumbo-frames are enabled for these interfaces in the switch.
           --#ARGUMENTS    {1,2,3,4,5}
           --#SEVERITY     MAJOR
           --#TIMEINDEX    99
           --#STATE        OK
       ::= { fluidFSEventsHardware 278 } 
    
    
    fluidFSEventHardwareLargeFrameConnected NOTIFICATION-TYPE
       OBJECTS { sysName, fluidFSEventsParamsHardwareContextBasedServiceTag, fluidFSEventsParamsHardwareFirstNodeId, fluidFSEventsParamsHardwareSecondNodeId, fluidFSEventsParamsHardwareEthName, fluidFSEventsParamsHardwareTargetEthName }
       STATUS current
       DESCRIPTION
           "{{ethName}} on NAS Controller {{firstNodeId}} can access {{targetEthName}} on NAS Controller {{secondNodeId}} using large frames (service tag: {{contextBasedServiceTag}})."
           --#TYPE         "Normal Event"
           --#SUMMARY      %s on NAS Controller %d can access %s on NAS Controller %d using large frames (service tag: %s).
           --#ARGUMENTS    {1,2,3,4,5}
           --#SEVERITY     INFORMATIONAL
           --#TIMEINDEX    99
           --#STATE        OK
       ::= { fluidFSEventsHardware 279 } 
    
    
    fluidFSEventHardwareBpsLowBattery NOTIFICATION-TYPE
       OBJECTS { sysName, fluidFSEventsParamsHardwareContextBasedServiceTag, fluidFSEventsParamsHardwareNodeId, fluidFSEventsParamsHardwareBpsBatteryCharge }
       STATUS current
       DESCRIPTION
           "BPS charge on NAS Controller{{nodeId}} is too low ({{bpsBatteryCharge}}%). BPS is not operating properly (service tag: {{contextBasedServiceTag}})."
           --#TYPE         "Normal Event"
           --#SUMMARY      BPS charge on NAS Controller%d is too low (%d%). BPS is not operating properly (service tag: %s).
           --#ARGUMENTS    {1,2,3}
           --#SEVERITY     MAJOR
           --#TIMEINDEX    99
           --#STATE        OK
       ::= { fluidFSEventsHardware 282 } 
    
    
    fluidFSEventHardwareExtServerJumboFramePacketLoss NOTIFICATION-TYPE
       OBJECTS { sysName, fluidFSEventsParamsHardwareNodeId, fluidFSEventsParamsHardwarePacketLoss, fluidFSEventsParamsHardwareIp, fluidFSEventsParamsHardwareExtSrvType }
       STATUS current
       DESCRIPTION
           "NAS Controller{{nodeId}} had {{packetLoss}}% packet loss to {{extSrvType}} {{ip}}. Please make sure the {{extSrvType}} allows jumbo frames."
           --#TYPE         "Normal Event"
           --#SUMMARY      NAS Controller%d had %d% packet loss to %s %s. Please make sure the %s allows jumbo frames.
           --#ARGUMENTS    {1,2,3,4}
           --#SEVERITY     INFORMATIONAL
           --#TIMEINDEX    99
           --#STATE        OK
       ::= { fluidFSEventsHardware 283 } 
    
    
    fluidFSEventHardwareCantReachExtServeJumboFrame NOTIFICATION-TYPE
       OBJECTS { sysName, fluidFSEventsParamsHardwareNodeId, fluidFSEventsParamsHardwareIp, fluidFSEventsParamsHardwareExtSrvType }
       STATUS current
       DESCRIPTION
           "NAS Controller{{nodeId}} cannot reach {{extSrvType}} {{ip}}. Please make sure the {{extSrvType}} allows jumbo frames."
           --#TYPE         "Normal Event"
           --#SUMMARY      NAS Controller%d cannot reach %s %s. Please make sure the %s allows jumbo frames.
           --#ARGUMENTS    {1,2,3}
           --#SEVERITY     MAJOR
           --#TIMEINDEX    99
           --#STATE        OK
       ::= { fluidFSEventsHardware 284 } 
    
    
    fluidFSEventHardwareCantReachStaticRoute NOTIFICATION-TYPE
       OBJECTS { sysName, fluidFSEventsParamsHardwareNodeId, fluidFSEventsParamsHardwareIp, fluidFSEventsParamsHardwareDestinationNetwork }
       STATUS current
       DESCRIPTION
           "NAS Controller{{nodeId}} cannot reach the gateway {{ip}} to network {{destinationNetwork}}."
           --#TYPE         "Normal Event"
           --#SUMMARY      NAS Controller%d cannot reach the gateway %s to network %s.
           --#ARGUMENTS    {1,2,3}
           --#SEVERITY     MAJOR
           --#TIMEINDEX    99
           --#STATE        OK
       ::= { fluidFSEventsHardware 285 } 
    
    
    fluidFSEventHardwareCanReachStaticRoute NOTIFICATION-TYPE
       OBJECTS { sysName, fluidFSEventsParamsHardwareNodeId, fluidFSEventsParamsHardwareIp, fluidFSEventsParamsHardwareDestinationNetwork }
       STATUS current
       DESCRIPTION
           "NAS Controller{{nodeId}} can reach the gateway {{ip}} to network {{destinationNetwork}}."
           --#TYPE         "Normal Event"
           --#SUMMARY      NAS Controller%d can reach the gateway %s to network %s.
           --#ARGUMENTS    {1,2,3}
           --#SEVERITY     INFORMATIONAL
           --#TIMEINDEX    99
           --#STATE        OK
       ::= { fluidFSEventsHardware 286 } 
    
    
    fluidFSEventHardwareClusterCantSeeAllFormattedLuns NOTIFICATION-TYPE
       OBJECTS { sysName }
       STATUS current
       DESCRIPTION
           "FluidFS cannot access any formatted LUN. Please make sure the backend storage is on and appropriately connected to FluidFS."
           --#TYPE         "Normal Event"
           --#SUMMARY      FluidFS cannot access any formatted LUN. Please make sure the backend storage is on and appropriately connected to FluidFS.
           --#ARGUMENTS    {}
           --#SEVERITY     MAJOR
           --#TIMEINDEX    99
           --#STATE        OK
       ::= { fluidFSEventsHardware 287 } 
    
    
    fluidFSEventHardwareClusterSeesAllFormattedLuns NOTIFICATION-TYPE
       OBJECTS { sysName }
       STATUS current
       DESCRIPTION
           "FluidFS connection to all the formatted LUNs is fully restored."
           --#TYPE         "Normal Event"
           --#SUMMARY      FluidFS connection to all the formatted LUNs is fully restored.
           --#ARGUMENTS    {}
           --#SEVERITY     INFORMATIONAL
           --#TIMEINDEX    99
           --#STATE        OK
       ::= { fluidFSEventsHardware 288 } 
    
    
    fluidFSEventHardwareNodeCantSeeFormattedLunsMajor NOTIFICATION-TYPE
       OBJECTS { sysName, fluidFSEventsParamsHardwareNodeId }
       STATUS current
       DESCRIPTION
           "NAS Controller{{nodeId}} cannot reach all the formatted LUNs. The system may not be serving. Please make sure that this Controller is properly connected to a storage."
           --#TYPE         "Normal Event"
           --#SUMMARY      NAS Controller%d cannot reach all the formatted LUNs. The system may not be serving. Please make sure that this Controller is properly connected to a storage.
           --#ARGUMENTS    {1}
           --#SEVERITY     MAJOR
           --#TIMEINDEX    99
           --#STATE        OK
       ::= { fluidFSEventsHardware 289 } 
    
    
    fluidFSEventHardwareNodeCantSeeFormattedLunsWarning NOTIFICATION-TYPE
       OBJECTS { sysName, fluidFSEventsParamsHardwareNodeId }
       STATUS current
       DESCRIPTION
           "NAS Controller{{nodeId}} cannot reach all the formatted LUNs. The performance may be degraded. Please make sure that this Controller is properly connected to a storage."
           --#TYPE         "Normal Event"
           --#SUMMARY      NAS Controller%d cannot reach all the formatted LUNs. The performance may be degraded. Please make sure that this Controller is properly connected to a storage.
           --#ARGUMENTS    {1}
           --#SEVERITY     INFORMATIONAL
           --#TIMEINDEX    99
           --#STATE        OK
       ::= { fluidFSEventsHardware 290 } 
    
    
    fluidFSEventHardwareNodeSeesFormattedLuns NOTIFICATION-TYPE
       OBJECTS { sysName, fluidFSEventsParamsHardwareNodeId }
       STATUS current
       DESCRIPTION
           "NAS Controller{{nodeId}} restored connection to all the formatted LUNs."
           --#TYPE         "Normal Event"
           --#SUMMARY      NAS Controller%d restored connection to all the formatted LUNs.
           --#ARGUMENTS    {1}
           --#SEVERITY     INFORMATIONAL
           --#TIMEINDEX    99
           --#STATE        OK
       ::= { fluidFSEventsHardware 291 } 
    
    
    fluidFSEventHardwareClusterCantSeeFormattedLun NOTIFICATION-TYPE
       OBJECTS { sysName, fluidFSEventsParamsHardwareLunId }
       STATUS current
       DESCRIPTION
           "LUN {{lunId}} is not reachable from FluidFS. Please make sure the LUN exists and is properly mapped from the backend storage."
           --#TYPE         "Normal Event"
           --#SUMMARY      LUN %s is not reachable from FluidFS. Please make sure the LUN exists and is properly mapped from the backend storage.
           --#ARGUMENTS    {1}
           --#SEVERITY     MAJOR
           --#TIMEINDEX    99
           --#STATE        OK
       ::= { fluidFSEventsHardware 292 } 
    
    
    fluidFSEventHardwareClusterSeesFormattedLun NOTIFICATION-TYPE
       OBJECTS { sysName, fluidFSEventsParamsHardwareLunId }
       STATUS current
       DESCRIPTION
           "LUN {{lunId}} is now fully reachable from FluidFS."
           --#TYPE         "Normal Event"
           --#SUMMARY      LUN %s is now fully reachable from FluidFS.
           --#ARGUMENTS    {1}
           --#SEVERITY     INFORMATIONAL
           --#TIMEINDEX    99
           --#STATE        OK
       ::= { fluidFSEventsHardware 293 } 
    
    
    fluidFSEventHardwareNodeCantSeeLunMajor NOTIFICATION-TYPE
       OBJECTS { sysName, fluidFSEventsParamsHardwareNodeId, fluidFSEventsParamsHardwareLunId }
       STATUS current
       DESCRIPTION
           "FluidFS Controller{{nodeId}} can not reach formatted LUN {{lunId}}. The system may not be serving. Please check that this LUN has appropriate permissions to be seen by this FluidFS Controller."
           --#TYPE         "Normal Event"
           --#SUMMARY      FluidFS Controller%d can not reach formatted LUN %s. The system may not be serving. Please check that this LUN has appropriate permissions to be seen by this FluidFS Controller.
           --#ARGUMENTS    {1,2}
           --#SEVERITY     MAJOR
           --#TIMEINDEX    99
           --#STATE        OK
       ::= { fluidFSEventsHardware 294 } 
    
    
    fluidFSEventHardwareNodeCantSeeLunWarning NOTIFICATION-TYPE
       OBJECTS { sysName, fluidFSEventsParamsHardwareNodeId, fluidFSEventsParamsHardwareLunId }
       STATUS current
       DESCRIPTION
           "FluidFS Controller{{nodeId}} can not reach formatted LUN {{lunId}}. The performance may be degraded. Please check that this LUN has appropriate permissions to be seen by this FluidFS Controller."
           --#TYPE         "Normal Event"
           --#SUMMARY      FluidFS Controller%d can not reach formatted LUN %s. The performance may be degraded. Please check that this LUN has appropriate permissions to be seen by this FluidFS Controller.
           --#ARGUMENTS    {1,2}
           --#SEVERITY     INFORMATIONAL
           --#TIMEINDEX    99
           --#STATE        OK
       ::= { fluidFSEventsHardware 295 } 
    
    
    fluidFSEventHardwareMeshDisconnected NOTIFICATION-TYPE
       OBJECTS { sysName, fluidFSEventsParamsHardwareFromNode, fluidFSEventsParamsHardwareToNode, fluidFSEventsParamsHardwareFromEth, fluidFSEventsParamsHardwareToEth, fluidFSEventsParamsHardwareVlanTag }
       STATUS current
       DESCRIPTION
           "node{{fromNode}}.{{fromEth}} cannot reach node{{toNode}}.{{toEth}} in vlan {{vlanTag}}   Description:  {{fromEth}} on NAS Controller{{fromNode}} cannot access {{toEth}} on NAS Controller{{toNode}} with vlan tag {{vlanTag}}.   Action Items:  Check that these interfaces are connected to the same switch, and are properly tagged."
           --#TYPE         "Normal Event"
           --#SUMMARY      node%d.%s cannot reach node%d.%s in vlan %d   Description:  %s on NAS Controller%d cannot access %s on NAS Controller%d with vlan tag %d.   Action Items:  Check that these interfaces are connected to the same switch, and are properly tagged.
           --#ARGUMENTS    {1,2,3,4,5}
           --#SEVERITY     MAJOR
           --#TIMEINDEX    99
           --#STATE        OK
       ::= { fluidFSEventsHardware 296 } 
    
    
    fluidFSEventHardwareMeshConnected NOTIFICATION-TYPE
       OBJECTS { sysName, fluidFSEventsParamsHardwareFromNode, fluidFSEventsParamsHardwareToNode, fluidFSEventsParamsHardwareFromEth, fluidFSEventsParamsHardwareToEth, fluidFSEventsParamsHardwareVlanTag }
       STATUS current
       DESCRIPTION
           "node{{fromNode}}.{{fromEth}} can reach node{{toNode}}.{{toEth}} in vlan {{vlanTag}}   Description:  {{fromEth}} on NAS Controller{{fromNode}} can access {{toEth}} on NAS Controller{{toNode}} with vlan tag {{vlanTag}}."
           --#TYPE         "Normal Event"
           --#SUMMARY      node%d.%s can reach node%d.%s in vlan %d   Description:  %s on NAS Controller%d can access %s on NAS Controller%d with vlan tag %d.
           --#ARGUMENTS    {1,2,3,4,5}
           --#SEVERITY     INFORMATIONAL
           --#TIMEINDEX    99
           --#STATE        OK
       ::= { fluidFSEventsHardware 297 } 
    
    
    fluidFSEventHardwareTapeDeviceNotAccessibleFromNode NOTIFICATION-TYPE
       OBJECTS { sysName, fluidFSEventsParamsHardwareNodeId, fluidFSEventsParamsHardwareTapeName }
       STATUS current
       DESCRIPTION
           "Tape device {{tapeName}} is not accessible from NAS Controller{{nodeId}}."
           --#TYPE         "Normal Event"
           --#SUMMARY      Tape device %s is not accessible from NAS Controller%d.
           --#ARGUMENTS    {1,2}
           --#SEVERITY     MAJOR
           --#TIMEINDEX    99
           --#STATE        OK
       ::= { fluidFSEventsHardware 298 } 
    
    
    fluidFSEventHardwareTapeDeviceNotAccessibleFromAllNodes NOTIFICATION-TYPE
       OBJECTS { sysName, fluidFSEventsParamsHardwareTapeName }
       STATUS current
       DESCRIPTION
           "Tape device {{tapeName}} is not accessible from all NAS Controllers."
           --#TYPE         "Normal Event"
           --#SUMMARY      Tape device %s is not accessible from all NAS Controllers.
           --#ARGUMENTS    {1}
           --#SEVERITY     MAJOR
           --#TIMEINDEX    99
           --#STATE        OK
       ::= { fluidFSEventsHardware 299 } 
    
    
    fluidFSEventHardwareTapeDeviceAccessibleFromNode NOTIFICATION-TYPE
       OBJECTS { sysName, fluidFSEventsParamsHardwareNodeId, fluidFSEventsParamsHardwareTapeName }
       STATUS current
       DESCRIPTION
           "Tape device {{tapeName}} is accessible from NAS Controller{{nodeId}}."
           --#TYPE         "Normal Event"
           --#SUMMARY      Tape device %s is accessible from NAS Controller%d.
           --#ARGUMENTS    {1,2}
           --#SEVERITY     INFORMATIONAL
           --#TIMEINDEX    99
           --#STATE        OK
       ::= { fluidFSEventsHardware 300 } 
    
    
    fluidFSEventHardwareDifferentFcHbaSpeedOnController NOTIFICATION-TYPE
       OBJECTS { sysName, fluidFSEventsParamsHardwareNodeId }
       STATUS current
       DESCRIPTION
           "Fibre Channel port speeds in NAS Controller{{nodeId}} are not identical."
           --#TYPE         "Normal Event"
           --#SUMMARY      Fibre Channel port speeds in NAS Controller%d are not identical.
           --#ARGUMENTS    {1}
           --#SEVERITY     INFORMATIONAL
           --#TIMEINDEX    99
           --#STATE        OK
       ::= { fluidFSEventsHardware 301 } 
    
    
    fluidFSEventHardwareBpsAccessibilityNotAvailable NOTIFICATION-TYPE
       OBJECTS { sysName, fluidFSEventsParamsHardwareContextBasedServiceTag, fluidFSEventsParamsHardwareNodeId }
       STATUS current
       DESCRIPTION
           "BPS reachability in NAS Controller{{nodeId}} is not available (service tag: {{contextBasedServiceTag}})."
           --#TYPE         "Normal Event"
           --#SUMMARY      BPS reachability in NAS Controller%d is not available (service tag: %s).
           --#ARGUMENTS    {1,2}
           --#SEVERITY     INFORMATIONAL
           --#TIMEINDEX    99
           --#STATE        OK
       ::= { fluidFSEventsHardware 302 } 
    
    
    fluidFSEventHardwareBpsAccessibilityIsAvailable NOTIFICATION-TYPE
       OBJECTS { sysName, fluidFSEventsParamsHardwareContextBasedServiceTag, fluidFSEventsParamsHardwareNodeId }
       STATUS current
       DESCRIPTION
           "BPS reachability in NAS Controller{{nodeId}} is available again (service tag: {{contextBasedServiceTag}})."
           --#TYPE         "Normal Event"
           --#SUMMARY      BPS reachability in NAS Controller%d is available again (service tag: %s).
           --#ARGUMENTS    {1,2}
           --#SEVERITY     INFORMATIONAL
           --#TIMEINDEX    99
           --#STATE        OK
       ::= { fluidFSEventsHardware 303 } 
    
    
    fluidFSEventHardwareBpsInfoNotAvailable NOTIFICATION-TYPE
       OBJECTS { sysName, fluidFSEventsParamsHardwareContextBasedServiceTag, fluidFSEventsParamsHardwareNodeId }
       STATUS current
       DESCRIPTION
           "BPS status info in NAS Controller{{nodeId}} is not available (service tag: {{contextBasedServiceTag}})."
           --#TYPE         "Normal Event"
           --#SUMMARY      BPS status info in NAS Controller%d is not available (service tag: %s).
           --#ARGUMENTS    {1,2}
           --#SEVERITY     INFORMATIONAL
           --#TIMEINDEX    99
           --#STATE        OK
       ::= { fluidFSEventsHardware 304 } 
    
    
    fluidFSEventHardwareBpsInfoIsAvailable NOTIFICATION-TYPE
       OBJECTS { sysName, fluidFSEventsParamsHardwareContextBasedServiceTag, fluidFSEventsParamsHardwareNodeId }
       STATUS current
       DESCRIPTION
           "BPS status info in NAS Controller{{nodeId}} is available again (service tag: {{contextBasedServiceTag}})."
           --#TYPE         "Normal Event"
           --#SUMMARY      BPS status info in NAS Controller%d is available again (service tag: %s).
           --#ARGUMENTS    {1,2}
           --#SEVERITY     INFORMATIONAL
           --#TIMEINDEX    99
           --#STATE        OK
       ::= { fluidFSEventsHardware 305 } 
    
    
    fluidFSEventHardwareProcessorNotOptimal NOTIFICATION-TYPE
       OBJECTS { sysName, fluidFSEventsParamsHardwareContextBasedServiceTag, fluidFSEventsParamsHardwareNodeId, fluidFSEventsParamsHardwareCpuName }
       STATUS current
       DESCRIPTION
           "Processor {{cpuName}} status in NAS Controller{{nodeId}} is not optimal (service tag: {{contextBasedServiceTag}})."
           --#TYPE         "Normal Event"
           --#SUMMARY      Processor %s status in NAS Controller%d is not optimal (service tag: %s).
           --#ARGUMENTS    {1,2,3}
           --#SEVERITY     MAJOR
           --#TIMEINDEX    99
           --#STATE        OK
       ::= { fluidFSEventsHardware 306 } 
    
    
    fluidFSEventHardwareProcessorError NOTIFICATION-TYPE
       OBJECTS { sysName, fluidFSEventsParamsHardwareContextBasedServiceTag, fluidFSEventsParamsHardwareNodeId, fluidFSEventsParamsHardwareCpuName }
       STATUS current
       DESCRIPTION
           "Processor {{cpuName}} status in NAS Controller{{nodeId}} is critical (service tag: {{contextBasedServiceTag}})."
           --#TYPE         "Normal Event"
           --#SUMMARY      Processor %s status in NAS Controller%d is critical (service tag: %s).
           --#ARGUMENTS    {1,2,3}
           --#SEVERITY     MAJOR
           --#TIMEINDEX    99
           --#STATE        OK
       ::= { fluidFSEventsHardware 307 } 
    
    
    fluidFSEventHardwareProcessorBackToNormal NOTIFICATION-TYPE
       OBJECTS { sysName, fluidFSEventsParamsHardwareContextBasedServiceTag, fluidFSEventsParamsHardwareNodeId, fluidFSEventsParamsHardwareCpuName }
       STATUS current
       DESCRIPTION
           "Processor {{cpuName}} in NAS Controller{{nodeId}} returned to normal operation (service tag: {{contextBasedServiceTag}})."
           --#TYPE         "Normal Event"
           --#SUMMARY      Processor %s in NAS Controller%d returned to normal operation (service tag: %s).
           --#ARGUMENTS    {1,2,3}
           --#SEVERITY     INFORMATIONAL
           --#TIMEINDEX    99
           --#STATE        OK
       ::= { fluidFSEventsHardware 308 } 
    
    
    fluidFSEventHardwareProcessorTempNotAvailable NOTIFICATION-TYPE
       OBJECTS { sysName, fluidFSEventsParamsHardwareContextBasedServiceTag, fluidFSEventsParamsHardwareNodeId, fluidFSEventsParamsHardwareCpuName }
       STATUS current
       DESCRIPTION
           "Processor {{cpuName}} temprature sensor info in NAS Controller{{nodeId}} is not available (service tag: {{contextBasedServiceTag}})."
           --#TYPE         "Normal Event"
           --#SUMMARY      Processor %s temprature sensor info in NAS Controller%d is not available (service tag: %s).
           --#ARGUMENTS    {1,2,3}
           --#SEVERITY     INFORMATIONAL
           --#TIMEINDEX    99
           --#STATE        OK
       ::= { fluidFSEventsHardware 309 } 
    
    
    fluidFSEventHardwareProcessorTempIsAvailable NOTIFICATION-TYPE
       OBJECTS { sysName, fluidFSEventsParamsHardwareContextBasedServiceTag, fluidFSEventsParamsHardwareNodeId, fluidFSEventsParamsHardwareCpuName }
       STATUS current
       DESCRIPTION
           "Processor {{cpuName}} temprature sensor info in NAS Controller{{nodeId}} is available again (service tag: {{contextBasedServiceTag}})."
           --#TYPE         "Normal Event"
           --#SUMMARY      Processor %s temprature sensor info in NAS Controller%d is available again (service tag: %s).
           --#ARGUMENTS    {1,2,3}
           --#SEVERITY     INFORMATIONAL
           --#TIMEINDEX    99
           --#STATE        OK
       ::= { fluidFSEventsHardware 310 } 
    
    
    fluidFSEventHardwareProcessorTempWarn NOTIFICATION-TYPE
       OBJECTS { sysName, fluidFSEventsParamsHardwareContextBasedServiceTag, fluidFSEventsParamsHardwareNodeId, fluidFSEventsParamsHardwareCpuName, fluidFSEventsParamsHardwareTemperature }
       STATUS current
       DESCRIPTION
           "Processor {{cpuName}} temperature sensor in NAS Controller{{nodeId}} reports warning status (Ambient temperature: {{temperature}} degrees Celsius) (service tag: {{contextBasedServiceTag}})."
           --#TYPE         "Normal Event"
           --#SUMMARY      Processor %s temperature sensor in NAS Controller%d reports warning status (Ambient temperature: %d degrees Celsius) (service tag: %s).
           --#ARGUMENTS    {1,2,3,4}
           --#SEVERITY     INFORMATIONAL
           --#TIMEINDEX    99
           --#STATE        OK
       ::= { fluidFSEventsHardware 311 } 
    
    
    fluidFSEventHardwareProcessorTempNormal NOTIFICATION-TYPE
       OBJECTS { sysName, fluidFSEventsParamsHardwareContextBasedServiceTag, fluidFSEventsParamsHardwareNodeId, fluidFSEventsParamsHardwareCpuName, fluidFSEventsParamsHardwareTemperature }
       STATUS current
       DESCRIPTION
           "Processor {{cpuName}} temperature sensors in NAS Controller{{nodeId}} report normal status (Ambient temperature: {{temperature}} degrees Celsius) (service tag: {{contextBasedServiceTag}})."
           --#TYPE         "Normal Event"
           --#SUMMARY      Processor %s temperature sensors in NAS Controller%d report normal status (Ambient temperature: %d degrees Celsius) (service tag: %s).
           --#ARGUMENTS    {1,2,3,4}
           --#SEVERITY     INFORMATIONAL
           --#TIMEINDEX    99
           --#STATE        OK
       ::= { fluidFSEventsHardware 312 } 
    
    
    fluidFSEventHardwareProcessorTempCritical NOTIFICATION-TYPE
       OBJECTS { sysName, fluidFSEventsParamsHardwareContextBasedServiceTag, fluidFSEventsParamsHardwareNodeId, fluidFSEventsParamsHardwareCpuName, fluidFSEventsParamsHardwareTemperature }
       STATUS current
       DESCRIPTION
           "Processor {{cpuName}} temperature sensors in NAS Controller{{nodeId}} report critical status (Ambient temperature: {{temperature}} degrees Celsius) (service tag: {{contextBasedServiceTag}})."
           --#TYPE         "Normal Event"
           --#SUMMARY      Processor %s temperature sensors in NAS Controller%d report critical status (Ambient temperature: %d degrees Celsius) (service tag: %s).
           --#ARGUMENTS    {1,2,3,4}
           --#SEVERITY     INFORMATIONAL
           --#TIMEINDEX    99
           --#STATE        OK
       ::= { fluidFSEventsHardware 313 } 
    
    
    fluidFSEventHardwareProcessorVoltageNotAvailable NOTIFICATION-TYPE
       OBJECTS { sysName, fluidFSEventsParamsHardwareContextBasedServiceTag, fluidFSEventsParamsHardwareNodeId, fluidFSEventsParamsHardwareCpuName }
       STATUS current
       DESCRIPTION
           "Processor {{cpuName}} voltage sensor info in NAS Controller{{nodeId}} is not available (service tag: {{contextBasedServiceTag}})."
           --#TYPE         "Normal Event"
           --#SUMMARY      Processor %s voltage sensor info in NAS Controller%d is not available (service tag: %s).
           --#ARGUMENTS    {1,2,3}
           --#SEVERITY     INFORMATIONAL
           --#TIMEINDEX    99
           --#STATE        OK
       ::= { fluidFSEventsHardware 314 } 
    
    
    fluidFSEventHardwareProcessorVoltageIsAvailable NOTIFICATION-TYPE
       OBJECTS { sysName, fluidFSEventsParamsHardwareContextBasedServiceTag, fluidFSEventsParamsHardwareNodeId, fluidFSEventsParamsHardwareCpuName }
       STATUS current
       DESCRIPTION
           "Processor {{cpuName}} voltage sensor info in NAS Controller{{nodeId}} is available again (service tag: {{contextBasedServiceTag}})."
           --#TYPE         "Normal Event"
           --#SUMMARY      Processor %s voltage sensor info in NAS Controller%d is available again (service tag: %s).
           --#ARGUMENTS    {1,2,3}
           --#SEVERITY     INFORMATIONAL
           --#TIMEINDEX    99
           --#STATE        OK
       ::= { fluidFSEventsHardware 315 } 
    
    
    fluidFSEventHardwareProcessorVoltageWarn NOTIFICATION-TYPE
       OBJECTS { sysName, fluidFSEventsParamsHardwareContextBasedServiceTag, fluidFSEventsParamsHardwareNodeId, fluidFSEventsParamsHardwareCpuName }
       STATUS current
       DESCRIPTION
           "Processor {{cpuName}} voltage sensors in NAS Controller{{nodeId}} report warning status (service tag: {{contextBasedServiceTag}})."
           --#TYPE         "Normal Event"
           --#SUMMARY      Processor %s voltage sensors in NAS Controller%d report warning status (service tag: %s).
           --#ARGUMENTS    {1,2,3}
           --#SEVERITY     INFORMATIONAL
           --#TIMEINDEX    99
           --#STATE        OK
       ::= { fluidFSEventsHardware 316 } 
    
    
    fluidFSEventHardwareProcessorVoltageNormal NOTIFICATION-TYPE
       OBJECTS { sysName, fluidFSEventsParamsHardwareContextBasedServiceTag, fluidFSEventsParamsHardwareNodeId, fluidFSEventsParamsHardwareCpuName }
       STATUS current
       DESCRIPTION
           "Processor {{cpuName}} voltage sensors in NAS Controller{{nodeId}} report normal status (service tag: {{contextBasedServiceTag}})."
           --#TYPE         "Normal Event"
           --#SUMMARY      Processor %s voltage sensors in NAS Controller%d report normal status (service tag: %s).
           --#ARGUMENTS    {1,2,3}
           --#SEVERITY     INFORMATIONAL
           --#TIMEINDEX    99
           --#STATE        OK
       ::= { fluidFSEventsHardware 317 } 
    
    
    fluidFSEventHardwareProcessorVoltageCritical NOTIFICATION-TYPE
       OBJECTS { sysName, fluidFSEventsParamsHardwareContextBasedServiceTag, fluidFSEventsParamsHardwareNodeId, fluidFSEventsParamsHardwareCpuName }
       STATUS current
       DESCRIPTION
           "Processor {{cpuName}} voltage sensors in NAS Controller{{nodeId}} report critical status (service tag: {{contextBasedServiceTag}})."
           --#TYPE         "Normal Event"
           --#SUMMARY      Processor %s voltage sensors in NAS Controller%d report critical status (service tag: %s).
           --#ARGUMENTS    {1,2,3}
           --#SEVERITY     INFORMATIONAL
           --#TIMEINDEX    99
           --#STATE        OK
       ::= { fluidFSEventsHardware 318 } 
    
    
    fluidFSEventHardwareProcessorInfoNotAvailable NOTIFICATION-TYPE
       OBJECTS { sysName, fluidFSEventsParamsHardwareContextBasedServiceTag, fluidFSEventsParamsHardwareNodeId, fluidFSEventsParamsHardwareCpuName }
       STATUS current
       DESCRIPTION
           "Processor {{cpuName}} status in NAS Controller{{nodeId}} is not available. Internal error in processor monitoring (service tag: {{contextBasedServiceTag}})."
           --#TYPE         "Normal Event"
           --#SUMMARY      Processor %s status in NAS Controller%d is not available. Internal error in processor monitoring (service tag: %s).
           --#ARGUMENTS    {1,2,3}
           --#SEVERITY     MAJOR
           --#TIMEINDEX    99
           --#STATE        OK
       ::= { fluidFSEventsHardware 319 } 
    
    
    fluidFSEventHardwareProcessorInfoIsAvailable NOTIFICATION-TYPE
       OBJECTS { sysName, fluidFSEventsParamsHardwareContextBasedServiceTag, fluidFSEventsParamsHardwareNodeId, fluidFSEventsParamsHardwareCpuName }
       STATUS current
       DESCRIPTION
           "Processor {{cpuName}} status in NAS Controller{{nodeId}} is available again (service tag: {{contextBasedServiceTag}})."
           --#TYPE         "Normal Event"
           --#SUMMARY      Processor %s status in NAS Controller%d is available again (service tag: %s).
           --#ARGUMENTS    {1,2,3}
           --#SEVERITY     INFORMATIONAL
           --#TIMEINDEX    99
           --#STATE        OK
       ::= { fluidFSEventsHardware 320 } 
    
    
    fluidFSEventHardwareProcessorDisabled NOTIFICATION-TYPE
       OBJECTS { sysName, fluidFSEventsParamsHardwareContextBasedServiceTag, fluidFSEventsParamsHardwareNodeId, fluidFSEventsParamsHardwareCpuName }
       STATUS current
       DESCRIPTION
           "Processor {{cpuName}} in NAS Controller{{nodeId}} is disabled (service tag: {{contextBasedServiceTag}})."
           --#TYPE         "Normal Event"
           --#SUMMARY      Processor %s in NAS Controller%d is disabled (service tag: %s).
           --#ARGUMENTS    {1,2,3}
           --#SEVERITY     MAJOR
           --#TIMEINDEX    99
           --#STATE        OK
       ::= { fluidFSEventsHardware 321 } 
    
    
    fluidFSEventHardwareProcessorEnabled NOTIFICATION-TYPE
       OBJECTS { sysName, fluidFSEventsParamsHardwareContextBasedServiceTag, fluidFSEventsParamsHardwareNodeId, fluidFSEventsParamsHardwareCpuName }
       STATUS current
       DESCRIPTION
           "Processor {{cpuName}} in NAS Controller{{nodeId}} is enabled again (service tag: {{contextBasedServiceTag}})."
           --#TYPE         "Normal Event"
           --#SUMMARY      Processor %s in NAS Controller%d is enabled again (service tag: %s).
           --#ARGUMENTS    {1,2,3}
           --#SEVERITY     INFORMATIONAL
           --#TIMEINDEX    99
           --#STATE        OK
       ::= { fluidFSEventsHardware 322 } 
    
    
    fluidFSEventHardwareMemoryTempNotAvailable NOTIFICATION-TYPE
       OBJECTS { sysName, fluidFSEventsParamsHardwareContextBasedServiceTag, fluidFSEventsParamsHardwareNodeId }
       STATUS current
       DESCRIPTION
           "Memory device temperature sensors info in NAS Controller{{nodeId}} is not available (service tag: {{contextBasedServiceTag}})."
           --#TYPE         "Normal Event"
           --#SUMMARY      Memory device temperature sensors info in NAS Controller%d is not available (service tag: %s).
           --#ARGUMENTS    {1,2}
           --#SEVERITY     INFORMATIONAL
           --#TIMEINDEX    99
           --#STATE        OK
       ::= { fluidFSEventsHardware 323 } 
    
    
    fluidFSEventHardwareMemoryTempIsAvailable NOTIFICATION-TYPE
       OBJECTS { sysName, fluidFSEventsParamsHardwareContextBasedServiceTag, fluidFSEventsParamsHardwareNodeId }
       STATUS current
       DESCRIPTION
           "Memory device temperature sensors info in NAS Controller{{nodeId}} is available again (service tag: {{contextBasedServiceTag}})."
           --#TYPE         "Normal Event"
           --#SUMMARY      Memory device temperature sensors info in NAS Controller%d is available again (service tag: %s).
           --#ARGUMENTS    {1,2}
           --#SEVERITY     INFORMATIONAL
           --#TIMEINDEX    99
           --#STATE        OK
       ::= { fluidFSEventsHardware 324 } 
    
    
    fluidFSEventHardwareBpsError NOTIFICATION-TYPE
       OBJECTS { sysName, fluidFSEventsParamsHardwareContextBasedServiceTag, fluidFSEventsParamsHardwareNodeId, fluidFSEventsParamsHardwareBpsBatteryCharge }
       STATUS current
       DESCRIPTION
           "BPS on Controller{{nodeId}} (service tag: {{contextBasedServiceTag}}) is not operating properly - battery reports failed state (charge: {{bpsBatteryCharge}}%).   Description:  BPS on NAS Controller{{nodeId}} (service tag: {{contextBasedServiceTag}}) is not operating properly - battery reports failed state (charge: {{bpsBatteryCharge}}%). This could be the result of a recent calibration process - if you receive this event again after a few days for this specific controller, please contact Support."
           --#TYPE         "Normal Event"
           --#SUMMARY      BPS on Controller%d (service tag: %s) is not operating properly - battery reports failed state (charge: %d%).   Description:  BPS on NAS Controller%d (service tag: %s) is not operating properly - battery reports failed state (charge: %d%). This could be the result of a recent calibration process - if you receive this event again after a few days for this specific controller, please contact Support.
           --#ARGUMENTS    {1,2,3}
           --#SEVERITY     MAJOR
           --#TIMEINDEX    99
           --#STATE        OK
       ::= { fluidFSEventsHardware 325 } 
    
    
    fluidFSEventHardwareLocalDiskWearingOut NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial, fluidFSEventsParamsHardwareDiskOverallReads, fluidFSEventsParamsHardwareDiskOverallWrites }
       STATUS current
       DESCRIPTION
           "Local storage disk drive {{diskName}} (Model: {{diskModel}}; Serial: {{diskSerial}}) in NAS Controller{{nodeId}} is wearing out. Consider disk replacement. Overall reads/writes: {{diskOverallReads}} / {{diskOverallWrites}} MB. (service tag: {{contextBasedServiceTag}})"
           --#TYPE         "Normal Event"
           --#SUMMARY      Local storage disk drive %s (Model: %s; Serial: %s) in NAS Controller%d is wearing out. Consider disk replacement. Overall reads/writes: %s / %s MB. (service tag: %s)
           --#ARGUMENTS    {1,2,3,4,5,6,7}
           --#SEVERITY     INFORMATIONAL
           --#TIMEINDEX    99
           --#STATE        OK
       ::= { fluidFSEventsHardware 326 } 
    
    
    fluidFSEventHardwareLocalDiskLotOfBadSectors NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial, fluidFSEventsParamsHardwareBadSectorsCount }
       STATUS current
       DESCRIPTION
           "Local disk {{diskName}} (Model: {{diskModel}}; Serial: {{diskSerial}}) in NAS Controller{{nodeId}} has a lot of bad sectors. Consider disk replacement. Bad sectors count: {{badSectorsCount}} (service tag: {{contextBasedServiceTag}})"
           --#TYPE         "Normal Event"
           --#SUMMARY      Local disk %s (Model: %s; Serial: %s) in NAS Controller%d has a lot of bad sectors. Consider disk replacement. Bad sectors count: %s (service tag: %s)
           --#ARGUMENTS    {1,2,3,4,5,6}
           --#SEVERITY     INFORMATIONAL
           --#TIMEINDEX    99
           --#STATE        OK
       ::= { fluidFSEventsHardware 327 } 
    
    
    fluidFSEventHardwareLocalDiskBadSectorsCount NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial, fluidFSEventsParamsHardwareBadSectorsCount }
       STATUS current
       DESCRIPTION
           "Local storage disk drive {{diskName}} (Model: {{diskModel}}; Serial: {{diskSerial}}) in NAS Controller{{nodeId}} bad sectors count: {{badSectorsCount}} (service tag: {{contextBasedServiceTag}})"
           --#TYPE         "Normal Event"
           --#SUMMARY      Local storage disk drive %s (Model: %s; Serial: %s) in NAS Controller%d bad sectors count: %s (service tag: %s)
           --#ARGUMENTS    {1,2,3,4,5,6}
           --#SEVERITY     INFORMATIONAL
           --#TIMEINDEX    99
           --#STATE        OK
       ::= { fluidFSEventsHardware 328 } 
    
    
    fluidFSEventHardwareLocalDiskLotOfFailedWrites NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial, fluidFSEventsParamsHardwareFailedWritesCount }
       STATUS current
       DESCRIPTION
           "Local storage disk drive {{diskName}} (Model: {{diskModel}}; Serial: {{diskSerial}}) in NAS Controller{{nodeId}} has a lot of failed writes. Consider disk replacement. Failed writes count: {{failedWritesCount}} (service tag: {{contextBasedServiceTag}})"
           --#TYPE         "Normal Event"
           --#SUMMARY      Local storage disk drive %s (Model: %s; Serial: %s) in NAS Controller%d has a lot of failed writes. Consider disk replacement. Failed writes count: %s (service tag: %s)
           --#ARGUMENTS    {1,2,3,4,5,6}
           --#SEVERITY     INFORMATIONAL
           --#TIMEINDEX    99
           --#STATE        OK
       ::= { fluidFSEventsHardware 329 } 
    
    
    fluidFSEventHardwareLocalDiskFailedWritesCount NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial, fluidFSEventsParamsHardwareFailedWritesCount }
       STATUS current
       DESCRIPTION
           "Local storage disk drive {{diskName}} (Model: {{diskModel}}; Serial: {{diskSerial}}) in NAS Controller{{nodeId}} failed writes count: {{failedWritesCount}} (service tag: {{contextBasedServiceTag}})"
           --#TYPE         "Normal Event"
           --#SUMMARY      Local storage disk drive %s (Model: %s; Serial: %s) in NAS Controller%d failed writes count: %s (service tag: %s)
           --#ARGUMENTS    {1,2,3,4,5,6}
           --#SEVERITY     INFORMATIONAL
           --#TIMEINDEX    99
           --#STATE        OK
       ::= { fluidFSEventsHardware 330 } 
    
    
    fluidFSEventHardwareLocalDiskBad NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial }
       STATUS current
       DESCRIPTION
           "S.M.A.R.T. self test is failed for local storage disk drive {{diskName}} (Model: {{diskModel}}; Serial: {{diskSerial}}) in NAS Controller{{nodeId}}. Disk may need a replacement. (service tag: {{contextBasedServiceTag}})"
           --#TYPE         "Normal Event"
           --#SUMMARY      S.M.A.R.T. self test is failed for local storage disk drive %s (Model: %s; Serial: %s) in NAS Controller%d. Disk may need a replacement. (service tag: %s)
           --#ARGUMENTS    {1,2,3,4,5}
           --#SEVERITY     MAJOR
           --#TIMEINDEX    99
           --#STATE        OK
       ::= { fluidFSEventsHardware 331 } 
    
    
    fluidFSEventHardwareLocalDiskBackToNormal NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial }
       STATUS current
       DESCRIPTION
           "Local storage disk drive {{diskName}} (Model: {{diskModel}}; Serial: {{diskSerial}}) in NAS Controller{{nodeId}} returned to normal operation (service tag: {{contextBasedServiceTag}})."
           --#TYPE         "Normal Event"
           --#SUMMARY      Local storage disk drive %s (Model: %s; Serial: %s) in NAS Controller%d returned to normal operation (service tag: %s).
           --#ARGUMENTS    {1,2,3,4,5}
           --#SEVERITY     INFORMATIONAL
           --#TIMEINDEX    99
           --#STATE        OK
       ::= { fluidFSEventsHardware 332 } 
    
    
    fluidFSEventHardwareLocalDiskModelNotSupported NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial, fluidFSEventsParamsHardwareSupportedModels }
       STATUS current
       DESCRIPTION
           "Local storage disk drive {{diskName}} (Model: {{diskModel}}; Serial: {{diskSerial}}) is not supported in NAS Controller{{nodeId}}. Disk monitoring may not work properly. Suppoerted modles are: {{supportedModels}}. (service tag: {{contextBasedServiceTag}})"
           --#TYPE         "Normal Event"
           --#SUMMARY      Local storage disk drive %s (Model: %s; Serial: %s) is not supported in NAS Controller%d. Disk monitoring may not work properly. Suppoerted modles are: %s. (service tag: %s)
           --#ARGUMENTS    {1,2,3,4,5,6}
           --#SEVERITY     MAJOR
           --#TIMEINDEX    99
           --#STATE        OK
       ::= { fluidFSEventsHardware 333 } 
    
    
    fluidFSEventHardwareLocalDiskInfoNotAvailable NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial }
       STATUS current
       DESCRIPTION
           "Local storage disk drive {{diskName}} (Model: {{diskModel}}; Serial: {{diskSerial}}) status in NAS Controller{{nodeId}} is not available. Internal error in local storage monitoring (service tag: {{contextBasedServiceTag}})."
           --#TYPE         "Normal Event"
           --#SUMMARY      Local storage disk drive %s (Model: %s; Serial: %s) status in NAS Controller%d is not available. Internal error in local storage monitoring (service tag: %s).
           --#ARGUMENTS    {1,2,3,4,5}
           --#SEVERITY     MAJOR
           --#TIMEINDEX    99
           --#STATE        OK
       ::= { fluidFSEventsHardware 334 } 
    
    
    fluidFSEventHardwareLocalDiskInfoIsAvailable NOTIFICATION-TYPE
       OBJECTS { sysName, fluidFSEventsParamsHardwareContextBasedServiceTag, fluidFSEventsParamsHardwareNodeId, fluidFSEventsParamsHardwareDiskName, fluidFSEventsParamsHardwareDiskModel, fluidFSEventsParamsHardwareDiskSerial }
       STATUS current
       DESCRIPTION
           "Local storage disk drive {{diskName}} (Model: {{diskModel}}; Serial: {{diskSerial}}) status in NAS Controller{{nodeId}} is available again (service tag: {{contextBasedServiceTag}})."
           --#TYPE         "Normal Event"
           --#SUMMARY      Local storage disk drive %s (Model: %s; Serial: %s) status in NAS Controller%d is available again (service tag: %s).
           --#ARGUMENTS    {1,2,3,4,5}
           --#SEVERITY     INFORMATIONAL
           --#TIMEINDEX    99
           --#STATE        OK
       ::= { fluidFSEventsHardware 335 } 
    
    
    fluidFSEventHardwareApplianceIntrusionNotAvailable NOTIFICATION-TYPE
       OBJECTS { sysName, fluidFSEventsParamsHardwareContextBasedServiceTag, fluidFSEventsParamsHardwareApplianceId }
       STATUS current
       DESCRIPTION
           "Intrusion info for NAS Appliance{{applianceId}} is not available (service tag: {{contextBasedServiceTag}})."
           --#TYPE         "Normal Event"
           --#SUMMARY      Intrusion info for NAS Appliance%d is not available (service tag: %s).
           --#ARGUMENTS    {1,2}
           --#SEVERITY     MAJOR
           --#TIMEINDEX    99
           --#STATE        OK
       ::= { fluidFSEventsHardware 336 } 
    
    
    fluidFSEventHardwareApplianceIntrusionIsAvailable NOTIFICATION-TYPE
       OBJECTS { sysName, fluidFSEventsParamsHardwareContextBasedServiceTag, fluidFSEventsParamsHardwareApplianceId }
       STATUS current
       DESCRIPTION
           "Intrusion info for NAS Appliance{{applianceId}} is available again (service tag: {{contextBasedServiceTag}})."
           --#TYPE         "Normal Event"
           --#SUMMARY      Intrusion info for NAS Appliance%d is available again (service tag: %s).
           --#ARGUMENTS    {1,2}
           --#SEVERITY     INFORMATIONAL
           --#TIMEINDEX    99
           --#STATE        OK
       ::= { fluidFSEventsHardware 337 } 
    
    
    fluidFSEventHardwareAppPsuAmperageNotAvailable NOTIFICATION-TYPE
       OBJECTS { sysName, fluidFSEventsParamsHardwareContextBasedServiceTag, fluidFSEventsParamsHardwareApplianceId, fluidFSEventsParamsHardwareComponentName }
       STATUS current
       DESCRIPTION
           "Current sensor info in power supply unit {{componentName}} in NAS Appliance {{applianceId}} is not available (service tag: {{contextBasedServiceTag}})."
           --#TYPE         "Normal Event"
           --#SUMMARY      Current sensor info in power supply unit %s in NAS Appliance %d is not available (service tag: %s).
           --#ARGUMENTS    {1,2,3}
           --#SEVERITY     INFORMATIONAL
           --#TIMEINDEX    99
           --#STATE        OK
       ::= { fluidFSEventsHardware 338 } 
    
    
    fluidFSEventHardwareAppPsuAmperageIsAvailable NOTIFICATION-TYPE
       OBJECTS { sysName, fluidFSEventsParamsHardwareContextBasedServiceTag, fluidFSEventsParamsHardwareApplianceId, fluidFSEventsParamsHardwareComponentName }
       STATUS current
       DESCRIPTION
           "Current sensor info in power supply unit {{componentName}} in NAS Appliance {{applianceId}} is available again (service tag: {{contextBasedServiceTag}})."
           --#TYPE         "Normal Event"
           --#SUMMARY      Current sensor info in power supply unit %s in NAS Appliance %d is available again (service tag: %s).
           --#ARGUMENTS    {1,2,3}
           --#SEVERITY     INFORMATIONAL
           --#TIMEINDEX    99
           --#STATE        OK
       ::= { fluidFSEventsHardware 339 } 
    
    
    fluidFSEventHardwareAppPsuTempNotAvailable NOTIFICATION-TYPE
       OBJECTS { sysName, fluidFSEventsParamsHardwareContextBasedServiceTag, fluidFSEventsParamsHardwareApplianceId, fluidFSEventsParamsHardwareComponentName }
       STATUS current
       DESCRIPTION
           "Temperature sensor info in power supply unit {{componentName}} in NAS Appliance {{applianceId}} is not available (service tag: {{contextBasedServiceTag}})."
           --#TYPE         "Normal Event"
           --#SUMMARY      Temperature sensor info in power supply unit %s in NAS Appliance %d is not available (service tag: %s).
           --#ARGUMENTS    {1,2,3}
           --#SEVERITY     INFORMATIONAL
           --#TIMEINDEX    99
           --#STATE        OK
       ::= { fluidFSEventsHardware 340 } 
    
    
    fluidFSEventHardwareAppPsuTempIsAvailable NOTIFICATION-TYPE
       OBJECTS { sysName, fluidFSEventsParamsHardwareContextBasedServiceTag, fluidFSEventsParamsHardwareApplianceId, fluidFSEventsParamsHardwareComponentName }
       STATUS current
       DESCRIPTION
           "Temperature sensor info in power supply unit {{componentName}} in NAS Appliance {{applianceId}} is available again (service tag: {{contextBasedServiceTag}})."
           --#TYPE         "Normal Event"
           --#SUMMARY      Temperature sensor info in power supply unit %s in NAS Appliance %d is available again (service tag: %s).
           --#ARGUMENTS    {1,2,3}
           --#SEVERITY     INFORMATIONAL
           --#TIMEINDEX    99
           --#STATE        OK
       ::= { fluidFSEventsHardware 341 } 
    
    
    fluidFSEventHardwareAppPsuVoltageNotAvailable NOTIFICATION-TYPE
       OBJECTS { sysName, fluidFSEventsParamsHardwareContextBasedServiceTag, fluidFSEventsParamsHardwareApplianceId, fluidFSEventsParamsHardwareComponentName }
       STATUS current
       DESCRIPTION
           "Voltage sensor info in power supply unit {{componentName}} in NAS Appliance {{applianceId}} is not available (service tag: {{contextBasedServiceTag}})."
           --#TYPE         "Normal Event"
           --#SUMMARY      Voltage sensor info in power supply unit %s in NAS Appliance %d is not available (service tag: %s).
           --#ARGUMENTS    {1,2,3}
           --#SEVERITY     INFORMATIONAL
           --#TIMEINDEX    99
           --#STATE        OK
       ::= { fluidFSEventsHardware 342 } 
    
    
    fluidFSEventHardwareAppPsuVoltageIsAvailable NOTIFICATION-TYPE
       OBJECTS { sysName, fluidFSEventsParamsHardwareContextBasedServiceTag, fluidFSEventsParamsHardwareApplianceId, fluidFSEventsParamsHardwareComponentName }
       STATUS current
       DESCRIPTION
           "Voltage sensor info in power supply unit {{componentName}} in NAS Appliance {{applianceId}} is available again (service tag: {{contextBasedServiceTag}})."
           --#TYPE         "Normal Event"
           --#SUMMARY      Voltage sensor info in power supply unit %s in NAS Appliance %d is available again (service tag: %s).
           --#ARGUMENTS    {1,2,3}
           --#SEVERITY     INFORMATIONAL
           --#TIMEINDEX    99
           --#STATE        OK
       ::= { fluidFSEventsHardware 343 } 
    
    
    fluidFSEventHardwareAppTopControllerTempNotAvailable NOTIFICATION-TYPE
       OBJECTS { sysName, fluidFSEventsParamsHardwareContextBasedServiceTag, fluidFSEventsParamsHardwareApplianceId }
       STATUS current
       DESCRIPTION
           "Temperature sensor info in top controller in NAS Appliance {{applianceId}} is not available (service tag: {{contextBasedServiceTag}})."
           --#TYPE         "Normal Event"
           --#SUMMARY      Temperature sensor info in top controller in NAS Appliance %d is not available (service tag: %s).
           --#ARGUMENTS    {1,2}
           --#SEVERITY     INFORMATIONAL
           --#TIMEINDEX    99
           --#STATE        OK
       ::= { fluidFSEventsHardware 344 } 
    
    
    fluidFSEventHardwareAppTopControllerTempIsAvailable NOTIFICATION-TYPE
       OBJECTS { sysName, fluidFSEventsParamsHardwareContextBasedServiceTag, fluidFSEventsParamsHardwareApplianceId }
       STATUS current
       DESCRIPTION
           "Temperature sensor info in top controller in NAS Appliance {{applianceId}} is available again (service tag: {{contextBasedServiceTag}})."
           --#TYPE         "Normal Event"
           --#SUMMARY      Temperature sensor info in top controller in NAS Appliance %d is available again (service tag: %s).
           --#ARGUMENTS    {1,2}
           --#SEVERITY     INFORMATIONAL
           --#TIMEINDEX    99
           --#STATE        OK
       ::= { fluidFSEventsHardware 345 } 
    
    
    fluidFSEventHardwareAppTopControllerTempNormal NOTIFICATION-TYPE
       OBJECTS { sysName, fluidFSEventsParamsHardwareContextBasedServiceTag, fluidFSEventsParamsHardwareApplianceId, fluidFSEventsParamsHardwareTemperature }
       STATUS current
       DESCRIPTION
           "Temperature sensor in top controller in NAS Appliance {{applianceId}} reports normal status (Ambient temperature: {{temperature}} degrees Celsius) (service tag: {{contextBasedServiceTag}})."
           --#TYPE         "Normal Event"
           --#SUMMARY      Temperature sensor in top controller in NAS Appliance %d reports normal status (Ambient temperature: %d degrees Celsius) (service tag: %s).
           --#ARGUMENTS    {1,2,3}
           --#SEVERITY     INFORMATIONAL
           --#TIMEINDEX    99
           --#STATE        OK
       ::= { fluidFSEventsHardware 346 } 
    
    
    fluidFSEventHardwareAppTopControllerTempWarning NOTIFICATION-TYPE
       OBJECTS { sysName, fluidFSEventsParamsHardwareContextBasedServiceTag, fluidFSEventsParamsHardwareApplianceId, fluidFSEventsParamsHardwareTemperature }
       STATUS current
       DESCRIPTION
           "Temperature sensor in top controller in NAS Appliance {{applianceId}} reports warning status (Ambient temperature: {{temperature}} degrees Celsius) (service tag: {{contextBasedServiceTag}})."
           --#TYPE         "Normal Event"
           --#SUMMARY      Temperature sensor in top controller in NAS Appliance %d reports warning status (Ambient temperature: %d degrees Celsius) (service tag: %s).
           --#ARGUMENTS    {1,2,3}
           --#SEVERITY     INFORMATIONAL
           --#TIMEINDEX    99
           --#STATE        OK
       ::= { fluidFSEventsHardware 347 } 
    
    
    fluidFSEventHardwareAppTopControllerTempError NOTIFICATION-TYPE
       OBJECTS { sysName, fluidFSEventsParamsHardwareContextBasedServiceTag, fluidFSEventsParamsHardwareApplianceId, fluidFSEventsParamsHardwareTemperature }
       STATUS current
       DESCRIPTION
           "Temperature sensor in top controller in NAS Appliance {{applianceId}} reports critical status (Ambient temperature: {{temperature}} degrees Celsius) (service tag: {{contextBasedServiceTag}})."
           --#TYPE         "Normal Event"
           --#SUMMARY      Temperature sensor in top controller in NAS Appliance %d reports critical status (Ambient temperature: %d degrees Celsius) (service tag: %s).
           --#ARGUMENTS    {1,2,3}
           --#SEVERITY     INFORMATIONAL
           --#TIMEINDEX    99
           --#STATE        OK
       ::= { fluidFSEventsHardware 348 } 
    
    
    fluidFSEventHardwareAppBottomControllerTempNotAvailable NOTIFICATION-TYPE
       OBJECTS { sysName, fluidFSEventsParamsHardwareContextBasedServiceTag, fluidFSEventsParamsHardwareApplianceId }
       STATUS current
       DESCRIPTION
           "Temperature sensor info in bottom controller in NAS Appliance {{applianceId}} is not available (service tag: {{contextBasedServiceTag}})."
           --#TYPE         "Normal Event"
           --#SUMMARY      Temperature sensor info in bottom controller in NAS Appliance %d is not available (service tag: %s).
           --#ARGUMENTS    {1,2}
           --#SEVERITY     INFORMATIONAL
           --#TIMEINDEX    99
           --#STATE        OK
       ::= { fluidFSEventsHardware 349 } 
    
    
    fluidFSEventHardwareAppBottomControllerTempIsAvailable NOTIFICATION-TYPE
       OBJECTS { sysName, fluidFSEventsParamsHardwareContextBasedServiceTag, fluidFSEventsParamsHardwareApplianceId }
       STATUS current
       DESCRIPTION
           "Temperature sensor info in bottom controller in NAS Appliance {{applianceId}} is available again (service tag: {{contextBasedServiceTag}})."
           --#TYPE         "Normal Event"
           --#SUMMARY      Temperature sensor info in bottom controller in NAS Appliance %d is available again (service tag: %s).
           --#ARGUMENTS    {1,2}
           --#SEVERITY     INFORMATIONAL
           --#TIMEINDEX    99
           --#STATE        OK
       ::= { fluidFSEventsHardware 350 } 
    
    
    fluidFSEventHardwareAppBottomControllerTempNormal NOTIFICATION-TYPE
       OBJECTS { sysName, fluidFSEventsParamsHardwareContextBasedServiceTag, fluidFSEventsParamsHardwareApplianceId, fluidFSEventsParamsHardwareTemperature }
       STATUS current
       DESCRIPTION
           "Temperature sensor in bottom controller in NAS Appliance {{applianceId}} reports normal status (Ambient temperature: {{temperature}} degrees Celsius) (service tag: {{contextBasedServiceTag}})."
           --#TYPE         "Normal Event"
           --#SUMMARY      Temperature sensor in bottom controller in NAS Appliance %d reports normal status (Ambient temperature: %d degrees Celsius) (service tag: %s).
           --#ARGUMENTS    {1,2,3}
           --#SEVERITY     INFORMATIONAL
           --#TIMEINDEX    99
           --#STATE        OK
       ::= { fluidFSEventsHardware 351 } 
    
    
    fluidFSEventHardwareAppBottomControllerTempWarning NOTIFICATION-TYPE
       OBJECTS { sysName, fluidFSEventsParamsHardwareContextBasedServiceTag, fluidFSEventsParamsHardwareApplianceId, fluidFSEventsParamsHardwareTemperature }
       STATUS current
       DESCRIPTION
           "Temperature sensor in bottom controller in NAS Appliance {{applianceId}} reports warning status (Ambient temperature: {{temperature}} degrees Celsius) (service tag: {{contextBasedServiceTag}})."
           --#TYPE         "Normal Event"
           --#SUMMARY      Temperature sensor in bottom controller in NAS Appliance %d reports warning status (Ambient temperature: %d degrees Celsius) (service tag: %s).
           --#ARGUMENTS    {1,2,3}
           --#SEVERITY     INFORMATIONAL
           --#TIMEINDEX    99
           --#STATE        OK
       ::= { fluidFSEventsHardware 352 } 
    
    
    fluidFSEventHardwareAppBottomControllerTempError NOTIFICATION-TYPE
       OBJECTS { sysName, fluidFSEventsParamsHardwareContextBasedServiceTag, fluidFSEventsParamsHardwareApplianceId, fluidFSEventsParamsHardwareTemperature }
       STATUS current
       DESCRIPTION
           "Temperature sensor in bottom controller in NAS Appliance {{applianceId}} reports critical status (Ambient temperature: {{temperature}} degrees Celsius) (service tag: {{contextBasedServiceTag}})."
           --#TYPE         "Normal Event"
           --#SUMMARY      Temperature sensor in bottom controller in NAS Appliance %d reports critical status (Ambient temperature: %d degrees Celsius) (service tag: %s).
           --#ARGUMENTS    {1,2,3}
           --#SEVERITY     INFORMATIONAL
           --#TIMEINDEX    99
           --#STATE        OK
       ::= { fluidFSEventsHardware 353 } 
    
    
    fluidFSEventHardwareAppLeftRaiserCardTempNotAvailable NOTIFICATION-TYPE
       OBJECTS { sysName, fluidFSEventsParamsHardwareContextBasedServiceTag, fluidFSEventsParamsHardwareApplianceId }
       STATUS current
       DESCRIPTION
           "Temperature sensor info in left raiser card in NAS Appliance {{applianceId}} is not available (service tag: {{contextBasedServiceTag}})."
           --#TYPE         "Normal Event"
           --#SUMMARY      Temperature sensor info in left raiser card in NAS Appliance %d is not available (service tag: %s).
           --#ARGUMENTS    {1,2}
           --#SEVERITY     INFORMATIONAL
           --#TIMEINDEX    99
           --#STATE        OK
       ::= { fluidFSEventsHardware 354 } 
    
    
    fluidFSEventHardwareAppLeftRaiserCardTempIsAvailable NOTIFICATION-TYPE
       OBJECTS { sysName, fluidFSEventsParamsHardwareContextBasedServiceTag, fluidFSEventsParamsHardwareApplianceId }
       STATUS current
       DESCRIPTION
           "Temperature sensor info in left raiser card in NAS Appliance {{applianceId}} is available again (service tag: {{contextBasedServiceTag}})."
           --#TYPE         "Normal Event"
           --#SUMMARY      Temperature sensor info in left raiser card in NAS Appliance %d is available again (service tag: %s).
           --#ARGUMENTS    {1,2}
           --#SEVERITY     INFORMATIONAL
           --#TIMEINDEX    99
           --#STATE        OK
       ::= { fluidFSEventsHardware 355 } 
    
    
    fluidFSEventHardwareAppLeftRaiserCardTempNormal NOTIFICATION-TYPE
       OBJECTS { sysName, fluidFSEventsParamsHardwareContextBasedServiceTag, fluidFSEventsParamsHardwareApplianceId, fluidFSEventsParamsHardwareTemperature }
       STATUS current
       DESCRIPTION
           "Temperature sensor in left raiser card in NAS Appliance {{applianceId}} reports normal status (Ambient temperature: {{temperature}} degrees Celsius) (service tag: {{contextBasedServiceTag}})."
           --#TYPE         "Normal Event"
           --#SUMMARY      Temperature sensor in left raiser card in NAS Appliance %d reports normal status (Ambient temperature: %d degrees Celsius) (service tag: %s).
           --#ARGUMENTS    {1,2,3}
           --#SEVERITY     INFORMATIONAL
           --#TIMEINDEX    99
           --#STATE        OK
       ::= { fluidFSEventsHardware 356 } 
    
    
    fluidFSEventHardwareAppLeftRaiserCardTempWarning NOTIFICATION-TYPE
       OBJECTS { sysName, fluidFSEventsParamsHardwareContextBasedServiceTag, fluidFSEventsParamsHardwareApplianceId, fluidFSEventsParamsHardwareTemperature }
       STATUS current
       DESCRIPTION
           "Temperature sensor in left raiser card in NAS Appliance {{applianceId}} reports warning status (Ambient temperature: {{temperature}} degrees Celsius) (service tag: {{contextBasedServiceTag}})."
           --#TYPE         "Normal Event"
           --#SUMMARY      Temperature sensor in left raiser card in NAS Appliance %d reports warning status (Ambient temperature: %d degrees Celsius) (service tag: %s).
           --#ARGUMENTS    {1,2,3}
           --#SEVERITY     INFORMATIONAL
           --#TIMEINDEX    99
           --#STATE        OK
       ::= { fluidFSEventsHardware 357 } 
    
    
    fluidFSEventHardwareAppLeftRaiserCardTempError NOTIFICATION-TYPE
       OBJECTS { sysName, fluidFSEventsParamsHardwareContextBasedServiceTag, fluidFSEventsParamsHardwareApplianceId, fluidFSEventsParamsHardwareTemperature }
       STATUS current
       DESCRIPTION
           "Temperature sensor in left raiser card in NAS Appliance {{applianceId}} reports critical status (Ambient temperature: {{temperature}} degrees Celsius) (service tag: {{contextBasedServiceTag}})."
           --#TYPE         "Normal Event"
           --#SUMMARY      Temperature sensor in left raiser card in NAS Appliance %d reports critical status (Ambient temperature: %d degrees Celsius) (service tag: %s).
           --#ARGUMENTS    {1,2,3}
           --#SEVERITY     INFORMATIONAL
           --#TIMEINDEX    99
           --#STATE        OK
       ::= { fluidFSEventsHardware 358 } 
    
    
    fluidFSEventHardwareAppRightRaiserCardTempNotAvailable NOTIFICATION-TYPE
       OBJECTS { sysName, fluidFSEventsParamsHardwareContextBasedServiceTag, fluidFSEventsParamsHardwareApplianceId }
       STATUS current
       DESCRIPTION
           "Temperature sensor info in right raiser card in NAS Appliance {{applianceId}} is not available (service tag: {{contextBasedServiceTag}})."
           --#TYPE         "Normal Event"
           --#SUMMARY      Temperature sensor info in right raiser card in NAS Appliance %d is not available (service tag: %s).
           --#ARGUMENTS    {1,2}
           --#SEVERITY     INFORMATIONAL
           --#TIMEINDEX    99
           --#STATE        OK
       ::= { fluidFSEventsHardware 359 } 
    
    
    fluidFSEventHardwareAppRightRaiserCardTempIsAvailable NOTIFICATION-TYPE
       OBJECTS { sysName, fluidFSEventsParamsHardwareContextBasedServiceTag, fluidFSEventsParamsHardwareApplianceId }
       STATUS current
       DESCRIPTION
           "Temperature sensor info in right raiser card in NAS Appliance {{applianceId}} is available again (service tag: {{contextBasedServiceTag}})."
           --#TYPE         "Normal Event"
           --#SUMMARY      Temperature sensor info in right raiser card in NAS Appliance %d is available again (service tag: %s).
           --#ARGUMENTS    {1,2}
           --#SEVERITY     INFORMATIONAL
           --#TIMEINDEX    99
           --#STATE        OK
       ::= { fluidFSEventsHardware 360 } 
    
    
    fluidFSEventHardwareAppRightRaiserCardTempNormal NOTIFICATION-TYPE
       OBJECTS { sysName, fluidFSEventsParamsHardwareContextBasedServiceTag, fluidFSEventsParamsHardwareApplianceId, fluidFSEventsParamsHardwareTemperature }
       STATUS current
       DESCRIPTION
           "Temperature sensor in right raiser card in NAS Appliance {{applianceId}} reports normal status (Ambient temperature: {{temperature}} degrees Celsius) (service tag: {{contextBasedServiceTag}})."
           --#TYPE         "Normal Event"
           --#SUMMARY      Temperature sensor in right raiser card in NAS Appliance %d reports normal status (Ambient temperature: %d degrees Celsius) (service tag: %s).
           --#ARGUMENTS    {1,2,3}
           --#SEVERITY     INFORMATIONAL
           --#TIMEINDEX    99
           --#STATE        OK
       ::= { fluidFSEventsHardware 361 } 
    
    
    fluidFSEventHardwareAppRightRaiserCardTempWarning NOTIFICATION-TYPE
       OBJECTS { sysName, fluidFSEventsParamsHardwareContextBasedServiceTag, fluidFSEventsParamsHardwareApplianceId, fluidFSEventsParamsHardwareTemperature }
       STATUS current
       DESCRIPTION
           "Temperature sensor in right raiser card in NAS Appliance {{applianceId}} reports warning status (Ambient temperature: {{temperature}} degrees Celsius) (service tag: {{contextBasedServiceTag}})."
           --#TYPE         "Normal Event"
           --#SUMMARY      Temperature sensor in right raiser card in NAS Appliance %d reports warning status (Ambient temperature: %d degrees Celsius) (service tag: %s).
           --#ARGUMENTS    {1,2,3}
           --#SEVERITY     INFORMATIONAL
           --#TIMEINDEX    99
           --#STATE        OK
       ::= { fluidFSEventsHardware 362 } 
    
    
    fluidFSEventHardwareAppRightRaiserCardTempError NOTIFICATION-TYPE
       OBJECTS { sysName, fluidFSEventsParamsHardwareContextBasedServiceTag, fluidFSEventsParamsHardwareApplianceId, fluidFSEventsParamsHardwareTemperature }
       STATUS current
       DESCRIPTION
           "Temperature sensor in right raiser card in NAS Appliance {{applianceId}} reports critical status (Ambient temperature: {{temperature}} degrees Celsius) (service tag: {{contextBasedServiceTag}})."
           --#TYPE         "Normal Event"
           --#SUMMARY      Temperature sensor in right raiser card in NAS Appliance %d reports critical status (Ambient temperature: %d degrees Celsius) (service tag: %s).
           --#ARGUMENTS    {1,2,3}
           --#SEVERITY     INFORMATIONAL
           --#TIMEINDEX    99
           --#STATE        OK
       ::= { fluidFSEventsHardware 363 } 
    
    
    fluidFSEventHardwareMotherBoardAmperageNotAvailable NOTIFICATION-TYPE
       OBJECTS { sysName, fluidFSEventsParamsHardwareContextBasedServiceTag, fluidFSEventsParamsHardwareNodeId }
       STATUS current
       DESCRIPTION
           "NAS Controller{{nodeId}} system board current sensors info is not available (service tag: {{contextBasedServiceTag}})."
           --#TYPE         "Normal Event"
           --#SUMMARY      NAS Controller%d system board current sensors info is not available (service tag: %s).
           --#ARGUMENTS    {1,2}
           --#SEVERITY     INFORMATIONAL
           --#TIMEINDEX    99
           --#STATE        OK
       ::= { fluidFSEventsHardware 364 } 
    
    
    fluidFSEventHardwareMotherBoardAmperageIsAvailable NOTIFICATION-TYPE
       OBJECTS { sysName, fluidFSEventsParamsHardwareContextBasedServiceTag, fluidFSEventsParamsHardwareNodeId }
       STATUS current
       DESCRIPTION
           "NAS Controller{{nodeId}} system board current sensors info is available again (service tag: {{contextBasedServiceTag}})."
           --#TYPE         "Normal Event"
           --#SUMMARY      NAS Controller%d system board current sensors info is available again (service tag: %s).
           --#ARGUMENTS    {1,2}
           --#SEVERITY     INFORMATIONAL
           --#TIMEINDEX    99
           --#STATE        OK
       ::= { fluidFSEventsHardware 365 } 
    
    
    fluidFSEventHardwareMotherBoardTempNotAvailable NOTIFICATION-TYPE
       OBJECTS { sysName, fluidFSEventsParamsHardwareContextBasedServiceTag, fluidFSEventsParamsHardwareNodeId }
       STATUS current
       DESCRIPTION
           "NAS Controller{{nodeId}} system board temprature sensors info is not available (service tag: {{contextBasedServiceTag}})."
           --#TYPE         "Normal Event"
           --#SUMMARY      NAS Controller%d system board temprature sensors info is not available (service tag: %s).
           --#ARGUMENTS    {1,2}
           --#SEVERITY     INFORMATIONAL
           --#TIMEINDEX    99
           --#STATE        OK
       ::= { fluidFSEventsHardware 366 } 
    
    
    fluidFSEventHardwareMotherBoardTempIsAvailable NOTIFICATION-TYPE
       OBJECTS { sysName, fluidFSEventsParamsHardwareContextBasedServiceTag, fluidFSEventsParamsHardwareNodeId }
       STATUS current
       DESCRIPTION
           "NAS Controller{{nodeId}} system board temprature sensors info is available again (service tag: {{contextBasedServiceTag}})."
           --#TYPE         "Normal Event"
           --#SUMMARY      NAS Controller%d system board temprature sensors info is available again (service tag: %s).
           --#ARGUMENTS    {1,2}
           --#SEVERITY     INFORMATIONAL
           --#TIMEINDEX    99
           --#STATE        OK
       ::= { fluidFSEventsHardware 367 } 
    
    
    fluidFSEventHardwareMotherBoardVoltageNotAvailable NOTIFICATION-TYPE
       OBJECTS { sysName, fluidFSEventsParamsHardwareContextBasedServiceTag, fluidFSEventsParamsHardwareNodeId }
       STATUS current
       DESCRIPTION
           "NAS Controller{{nodeId}} system board voltage sensors info is not available (service tag: {{contextBasedServiceTag}})."
           --#TYPE         "Normal Event"
           --#SUMMARY      NAS Controller%d system board voltage sensors info is not available (service tag: %s).
           --#ARGUMENTS    {1,2}
           --#SEVERITY     INFORMATIONAL
           --#TIMEINDEX    99
           --#STATE        OK
       ::= { fluidFSEventsHardware 368 } 
    
    
    fluidFSEventHardwareMotherBoardVoltageIsAvailable NOTIFICATION-TYPE
       OBJECTS { sysName, fluidFSEventsParamsHardwareContextBasedServiceTag, fluidFSEventsParamsHardwareNodeId }
       STATUS current
       DESCRIPTION
           "NAS Controller{{nodeId}} system board voltage sensors info is available again (service tag: {{contextBasedServiceTag}})."
           --#TYPE         "Normal Event"
           --#SUMMARY      NAS Controller%d system board voltage sensors info is available again (service tag: %s).
           --#ARGUMENTS    {1,2}
           --#SEVERITY     INFORMATIONAL
           --#TIMEINDEX    99
           --#STATE        OK
       ::= { fluidFSEventsHardware 369 } 
    
    
    fluidFSEventHardwareNetworkInterfaceDown NOTIFICATION-TYPE
       OBJECTS { sysName, fluidFSEventsParamsHardwareNodeId, fluidFSEventsParamsHardwareNetworkName, fluidFSEventsParamsHardwareEthName }
       STATUS current
       DESCRIPTION
           "{{networkName}} network interface {{ethName}} in NAS Controller{{nodeId}} is down."
           --#TYPE         "Normal Event"
           --#SUMMARY      %s network interface %s in NAS Controller%d is down.
           --#ARGUMENTS    {1,2,3}
           --#SEVERITY     MAJOR
           --#TIMEINDEX    99
           --#STATE        OK
       ::= { fluidFSEventsHardware 370 } 
    
    
    fluidFSEventHardwareNetworkInterfaceBackUp NOTIFICATION-TYPE
       OBJECTS { sysName, fluidFSEventsParamsHardwareNodeId, fluidFSEventsParamsHardwareNetworkName, fluidFSEventsParamsHardwareEthName }
       STATUS current
       DESCRIPTION
           "{{networkName}} network interface {{ethName}} in NAS Controller{{nodeId}} is back up."
           --#TYPE         "Normal Event"
           --#SUMMARY      %s network interface %s in NAS Controller%d is back up.
           --#ARGUMENTS    {1,2,3}
           --#SEVERITY     INFORMATIONAL
           --#TIMEINDEX    99
           --#STATE        OK
       ::= { fluidFSEventsHardware 371 } 
    
    
    fluidFSEventHardwareNetworkInterfaceUnknown NOTIFICATION-TYPE
       OBJECTS { sysName, fluidFSEventsParamsHardwareNodeId, fluidFSEventsParamsHardwareNetworkName, fluidFSEventsParamsHardwareEthName }
       STATUS current
       DESCRIPTION
           "{{networkName}} network interface {{ethName}} in NAS Controller{{nodeId}} has unknown status."
           --#TYPE         "Normal Event"
           --#SUMMARY      %s network interface %s in NAS Controller%d has unknown status.
           --#ARGUMENTS    {1,2,3}
           --#SEVERITY     MAJOR
           --#TIMEINDEX    99
           --#STATE        OK
       ::= { fluidFSEventsHardware 372 } 
    
    
    fluidFSEventHardwareFibreChannelPortDown NOTIFICATION-TYPE
       OBJECTS { sysName, fluidFSEventsParamsHardwareNodeId, fluidFSEventsParamsHardwareEthName }
       STATUS current
       DESCRIPTION
           "Fibre Channel port {{ethName}} in NAS Controller{{nodeId}} is down."
           --#TYPE         "Normal Event"
           --#SUMMARY      Fibre Channel port %s in NAS Controller%d is down.
           --#ARGUMENTS    {1,2}
           --#SEVERITY     MAJOR
           --#TIMEINDEX    99
           --#STATE        OK
       ::= { fluidFSEventsHardware 373 } 
    
    
    fluidFSEventHardwareFibreChannelPortUp NOTIFICATION-TYPE
       OBJECTS { sysName, fluidFSEventsParamsHardwareNodeId, fluidFSEventsParamsHardwareEthName }
       STATUS current
       DESCRIPTION
           "Fibre Channel port {{ethName}} in NAS Controller{{nodeId}} is back up."
           --#TYPE         "Normal Event"
           --#SUMMARY      Fibre Channel port %s in NAS Controller%d is back up.
           --#ARGUMENTS    {1,2}
           --#SEVERITY     INFORMATIONAL
           --#TIMEINDEX    99
           --#STATE        OK
       ::= { fluidFSEventsHardware 374 } 
    
    
    fluidFSEventHardwareFibreChannelPortUnknown NOTIFICATION-TYPE
       OBJECTS { sysName, fluidFSEventsParamsHardwareNodeId, fluidFSEventsParamsHardwareEthName }
       STATUS current
       DESCRIPTION
           "Fibre Channel port {{ethName}} in NAS Controller{{nodeId}} has unknown status."
           --#TYPE         "Normal Event"
           --#SUMMARY      Fibre Channel port %s in NAS Controller%d has unknown status.
           --#ARGUMENTS    {1,2}
           --#SEVERITY     MAJOR
           --#TIMEINDEX    99
           --#STATE        OK
       ::= { fluidFSEventsHardware 375 } 
    
    
    fluidFSEventHardwareSameFcHbaSpeedOnController NOTIFICATION-TYPE
       OBJECTS { sysName, fluidFSEventsParamsHardwareNodeId }
       STATUS current
       DESCRIPTION
           "Fibre Channel port speeds in NAS Controller{{nodeId}} are identical again."
           --#TYPE         "Normal Event"
           --#SUMMARY      Fibre Channel port speeds in NAS Controller%d are identical again.
           --#ARGUMENTS    {1}
           --#SEVERITY     INFORMATIONAL
           --#TIMEINDEX    99
           --#STATE        OK
       ::= { fluidFSEventsHardware 376 } 
    
    
    fluidFSEventHardwareSameEthSpeedOnNetworkNode NOTIFICATION-TYPE
       OBJECTS { sysName, fluidFSEventsParamsHardwareNodeId, fluidFSEventsParamsHardwareNetworkName }
       STATUS current
       DESCRIPTION
           "Eth speeds on {{networkName}} network in NAS Controller{{nodeId}} are identical again."
           --#TYPE         "Normal Event"
           --#SUMMARY      Eth speeds on %s network in NAS Controller%d are identical again.
           --#ARGUMENTS    {1,2}
           --#SEVERITY     INFORMATIONAL
           --#TIMEINDEX    99
           --#STATE        OK
       ::= { fluidFSEventsHardware 377 } 
    
    
    fluidFSEventHardwareAllIfsAreDown NOTIFICATION-TYPE
       OBJECTS { sysName, fluidFSEventsParamsHardwareNodeId, fluidFSEventsParamsHardwareSubnetName }
       STATUS current
       DESCRIPTION
           "All {{subnetName}} network interfaces on NAS Controller{{nodeId}} are down."
           --#TYPE         "Normal Event"
           --#SUMMARY      All %s network interfaces on NAS Controller%d are down.
           --#ARGUMENTS    {1,2}
           --#SEVERITY     MAJOR
           --#TIMEINDEX    99
           --#STATE        OK
       ::= { fluidFSEventsHardware 378 } 
    
    
    fluidFSEventHardwareEthSpeedOnSubnetNodeNotEqual NOTIFICATION-TYPE
       OBJECTS { sysName, fluidFSEventsParamsHardwareNodeId, fluidFSEventsParamsHardwareSubnetName }
       STATUS current
       DESCRIPTION
           "Eth speeds on {{subnetName}} network in NAS Controller{{nodeId}} are not identical."
           --#TYPE         "Normal Event"
           --#SUMMARY      Eth speeds on %s network in NAS Controller%d are not identical.
           --#ARGUMENTS    {1,2}
           --#SEVERITY     INFORMATIONAL
           --#TIMEINDEX    99
           --#STATE        OK
       ::= { fluidFSEventsHardware 379 } 
    
    
    fluidFSEventHardwareBpsTempNotAvailable NOTIFICATION-TYPE
       OBJECTS { sysName, fluidFSEventsParamsHardwareContextBasedServiceTag, fluidFSEventsParamsHardwareNodeId }
       STATUS current
       DESCRIPTION
           "BPS temperature sensor info in NAS Controller{{nodeId}} is not available (service tag: {{contextBasedServiceTag}})."
           --#TYPE         "Normal Event"
           --#SUMMARY      BPS temperature sensor info in NAS Controller%d is not available (service tag: %s).
           --#ARGUMENTS    {1,2}
           --#SEVERITY     INFORMATIONAL
           --#TIMEINDEX    99
           --#STATE        OK
       ::= { fluidFSEventsHardware 380 } 
    
    
    fluidFSEventHardwareBpsTempIsAvailable NOTIFICATION-TYPE
       OBJECTS { sysName, fluidFSEventsParamsHardwareContextBasedServiceTag, fluidFSEventsParamsHardwareNodeId }
       STATUS current
       DESCRIPTION
           "BPS temperature sensor info in NAS Controller{{nodeId}} is not available again (service tag: {{contextBasedServiceTag}})."
           --#TYPE         "Normal Event"
           --#SUMMARY      BPS temperature sensor info in NAS Controller%d is not available again (service tag: %s).
           --#ARGUMENTS    {1,2}
           --#SEVERITY     INFORMATIONAL
           --#TIMEINDEX    99
           --#STATE        OK
       ::= { fluidFSEventsHardware 381 } 
    
    
    fluidFSEventHardwareBpsTempNormal NOTIFICATION-TYPE
       OBJECTS { sysName, fluidFSEventsParamsHardwareContextBasedServiceTag, fluidFSEventsParamsHardwareNodeId, fluidFSEventsParamsHardwareTemperature }
       STATUS current
       DESCRIPTION
           "Temperature sensor in BPS in NAS Controller{{nodeId}} reports normal status (Ambient temperature: {{temperature}} degrees Celsius) (service tag: {{contextBasedServiceTag}})."
           --#TYPE         "Normal Event"
           --#SUMMARY      Temperature sensor in BPS in NAS Controller%d reports normal status (Ambient temperature: %d degrees Celsius) (service tag: %s).
           --#ARGUMENTS    {1,2,3}
           --#SEVERITY     INFORMATIONAL
           --#TIMEINDEX    99
           --#STATE        OK
       ::= { fluidFSEventsHardware 382 } 
    
    
    fluidFSEventHardwareBpsTempWarning NOTIFICATION-TYPE
       OBJECTS { sysName, fluidFSEventsParamsHardwareContextBasedServiceTag, fluidFSEventsParamsHardwareNodeId, fluidFSEventsParamsHardwareTemperature }
       STATUS current
       DESCRIPTION
           "Temperature sensor in BPS in NAS Controller{{nodeId}} reports warning status (Ambient temperature: {{temperature}} degrees Celsius) (service tag: {{contextBasedServiceTag}})."
           --#TYPE         "Normal Event"
           --#SUMMARY      Temperature sensor in BPS in NAS Controller%d reports warning status (Ambient temperature: %d degrees Celsius) (service tag: %s).
           --#ARGUMENTS    {1,2,3}
           --#SEVERITY     INFORMATIONAL
           --#TIMEINDEX    99
           --#STATE        OK
       ::= { fluidFSEventsHardware 383 } 
    
    
    fluidFSEventHardwareBpsTempError NOTIFICATION-TYPE
       OBJECTS { sysName, fluidFSEventsParamsHardwareContextBasedServiceTag, fluidFSEventsParamsHardwareNodeId, fluidFSEventsParamsHardwareTemperature }
       STATUS current
       DESCRIPTION
           "Temperature sensor in BPS in NAS Controller{{nodeId}} reports error status (Ambient temperature: {{temperature}} degrees Celsius) (service tag: {{contextBasedServiceTag}})."
           --#TYPE         "Normal Event"
           --#SUMMARY      Temperature sensor in BPS in NAS Controller%d reports error status (Ambient temperature: %d degrees Celsius) (service tag: %s).
           --#ARGUMENTS    {1,2,3}
           --#SEVERITY     INFORMATIONAL
           --#TIMEINDEX    99
           --#STATE        OK
       ::= { fluidFSEventsHardware 384 } 
    
    
    fluidFSEventHardwarePSUfirmwareUpgradeFail NOTIFICATION-TYPE
       OBJECTS { sysName, fluidFSEventsParamsHardwareId }
       STATUS current
       DESCRIPTION
           "Firmware upgarade for {{id}} failed"
           --#TYPE         "Normal Event"
           --#SUMMARY      Firmware upgarade for %s failed
           --#ARGUMENTS    {1}
           --#SEVERITY     MAJOR
           --#TIMEINDEX    99
           --#STATE        OK
       ::= { fluidFSEventsHardware 385 } 
    
    
    fluidFSEventHardwarePSUfirmwareUpgradeSuccess NOTIFICATION-TYPE
       OBJECTS { sysName, fluidFSEventsParamsHardwareId }
       STATUS current
       DESCRIPTION
           "Firmware upgrade for {{id}} finished successfuly"
           --#TYPE         "Normal Event"
           --#SUMMARY      Firmware upgrade for %s finished successfuly
           --#ARGUMENTS    {1}
           --#SEVERITY     INFORMATIONAL
           --#TIMEINDEX    99
           --#STATE        OK
       ::= { fluidFSEventsHardware 386 } 
    
    
    fluidFSEventHardwareUnsupportedNic NOTIFICATION-TYPE
       OBJECTS { sysName, fluidFSEventsParamsHardwareNodeId, fluidFSEventsParamsHardwarePciSlot, fluidFSEventsParamsHardwarePciCard }
       STATUS current
       DESCRIPTION
           "Unsupported card installed on Controller{{nodeId}}.   Description:  An unsupported PCI card was detected in slot {{pciSlot}} on NAS Controller{{nodeId}}: {{pciCard}}."
           --#TYPE         "Normal Event"
           --#SUMMARY      Unsupported card installed on Controller%d.   Description:  An unsupported PCI card was detected in slot %d on NAS Controller%d: %s.
           --#ARGUMENTS    {1,2,3}
           --#SEVERITY     MAJOR
           --#TIMEINDEX    99
           --#STATE        OK
       ::= { fluidFSEventsHardware 387 } 
    
    
    fluidFSEventsParamsNdmp OBJECT IDENTIFIER ::= { fluidFSEventsParams 3 } 
    
    
    fluidFSEventsNdmp OBJECT IDENTIFIER ::= { fluidFSEvents 3 } 
    
    
    fluidFSEventsParamsNdmpSessionId OBJECT-TYPE
       SYNTAX  INTEGER
       MAX-ACCESS  read-only
       STATUS  current
       DESCRIPTION
           "NDMP job session id"
       ::= { fluidFSEventsParamsNdmp 1 }
    
    
    fluidFSEventsParamsNdmpJobType OBJECT-TYPE
       SYNTAX  DisplayString
       MAX-ACCESS  read-only
       STATUS  current
       DESCRIPTION
           "NDMP job type (backup/restore)"
       ::= { fluidFSEventsParamsNdmp 2 }
    
    
    fluidFSEventsParamsNdmpPath OBJECT-TYPE
       SYNTAX  DisplayString
       MAX-ACCESS  read-only
       STATUS  current
       DESCRIPTION
           "Target path"
       ::= { fluidFSEventsParamsNdmp 3 }
    
    
    fluidFSEventsParamsNdmpStartTimestamp OBJECT-TYPE
       SYNTAX  DisplayString
       MAX-ACCESS  read-only
       STATUS  current
       DESCRIPTION
           "NDMP session start timestamp"
       ::= { fluidFSEventsParamsNdmp 4 }
    
    
    fluidFSEventsParamsNdmpInitiatorDMAServer OBJECT-TYPE
       SYNTAX  DisplayString
       MAX-ACCESS  read-only
       STATUS  current
       DESCRIPTION
           "DMA server that initiated the session"
       ::= { fluidFSEventsParamsNdmp 5 }
    
    
    fluidFSEventsParamsNdmpExecutedOnNode OBJECT-TYPE
       SYNTAX  INTEGER
       MAX-ACCESS  read-only
       STATUS  current
       DESCRIPTION
           "Node that executes the job"
       ::= { fluidFSEventsParamsNdmp 6 }
    
    
    fluidFSEventsParamsNdmpNDMPMessage OBJECT-TYPE
       SYNTAX  DisplayString
       MAX-ACCESS  read-only
       STATUS  current
       DESCRIPTION
           "Event message sent from NDMP"
       ::= { fluidFSEventsParamsNdmp 7 }
    
    
    fluidFSEventsParamsNdmpDetail OBJECT-TYPE
       SYNTAX  DisplayString
       MAX-ACCESS  read-only
       STATUS  current
       DESCRIPTION
           "Event message sent from NDMP"
       ::= { fluidFSEventsParamsNdmp 8 }
    
    
    fluidFSEventNdmpNdmpError NOTIFICATION-TYPE
       OBJECTS { sysName, fluidFSEventsParamsNdmpDetail }
       STATUS current
       DESCRIPTION
           "{{Detail}}"
           --#TYPE         "Normal Event"
           --#SUMMARY      %s
           --#ARGUMENTS    {1}
           --#SEVERITY     MAJOR
           --#TIMEINDEX    99
           --#STATE        OK
       ::= { fluidFSEventsNdmp 6 } 
    
    
    fluidFSEventNdmpNdmpWarn NOTIFICATION-TYPE
       OBJECTS { sysName, fluidFSEventsParamsNdmpDetail }
       STATUS current
       DESCRIPTION
           "{{Detail}}"
           --#TYPE         "Normal Event"
           --#SUMMARY      %s
           --#ARGUMENTS    {1}
           --#SEVERITY     INFORMATIONAL
           --#TIMEINDEX    99
           --#STATE        OK
       ::= { fluidFSEventsNdmp 7 } 
    
    
    fluidFSEventNdmpNdmpInfo NOTIFICATION-TYPE
       OBJECTS { sysName, fluidFSEventsParamsNdmpDetail }
       STATUS current
       DESCRIPTION
           "{{Detail}}"
           --#TYPE         "Normal Event"
           --#SUMMARY      %s
           --#ARGUMENTS    {1}
           --#SEVERITY     INFORMATIONAL
           --#TIMEINDEX    99
           --#STATE        OK
       ::= { fluidFSEventsNdmp 8 } 
    
    
    fluidFSEventNdmpAuthenticationFailure NOTIFICATION-TYPE
       OBJECTS { sysName, fluidFSEventsParamsNdmpDetail }
       STATUS current
       DESCRIPTION
           "Failed to authenticate: {{Detail}}."
           --#TYPE         "Normal Event"
           --#SUMMARY      Failed to authenticate: %s.
           --#ARGUMENTS    {1}
           --#SEVERITY     MAJOR
           --#TIMEINDEX    99
           --#STATE        OK
       ::= { fluidFSEventsNdmp 9 } 
    
    
    fluidFSEventNdmpBackupStarted NOTIFICATION-TYPE
       OBJECTS { sysName, fluidFSEventsParamsNdmpSessionId, fluidFSEventsParamsNdmpInitiatorDMAServer, fluidFSEventsParamsNdmpStartTimestamp, fluidFSEventsParamsNdmpPath, fluidFSEventsParamsNdmpExecutedOnNode }
       STATUS current
       DESCRIPTION
           "The backup session by ID {{SessionId}} initiated by DMA {{InitiatorDMAServer}} on {{StartTimestamp}} started.   Description:  The backup session by ID {{SessionId}} initiated by DMA {{InitiatorDMAServer}} on {{StartTimestamp}} started. The source path is {{Path}} and it is executed on controller {{ExecutedOnNode}}."
           --#TYPE         "Normal Event"
           --#SUMMARY      The backup session by ID %d initiated by DMA %s on %s started.   Description:  The backup session by ID %d initiated by DMA %s on %s started. The source path is %s and it is executed on controller %d.
           --#ARGUMENTS    {1,2,3,4,5}
           --#SEVERITY     INFORMATIONAL
           --#TIMEINDEX    99
           --#STATE        OK
       ::= { fluidFSEventsNdmp 10 } 
    
    
    fluidFSEventNdmpBackupFinished NOTIFICATION-TYPE
       OBJECTS { sysName, fluidFSEventsParamsNdmpSessionId, fluidFSEventsParamsNdmpInitiatorDMAServer, fluidFSEventsParamsNdmpStartTimestamp, fluidFSEventsParamsNdmpPath, fluidFSEventsParamsNdmpExecutedOnNode }
       STATUS current
       DESCRIPTION
           "The backup session by ID {{SessionId}} initiated by DMA {{InitiatorDMAServer}} on {{StartTimestamp}} finished.   Description:  The backup session by ID {{SessionId}} initiated by DMA {{InitiatorDMAServer}} on {{StartTimestamp}} finished. The source path is {{Path}} and it is executed on controller {{ExecutedOnNode}}."
           --#TYPE         "Normal Event"
           --#SUMMARY      The backup session by ID %d initiated by DMA %s on %s finished.   Description:  The backup session by ID %d initiated by DMA %s on %s finished. The source path is %s and it is executed on controller %d.
           --#ARGUMENTS    {1,2,3,4,5}
           --#SEVERITY     INFORMATIONAL
           --#TIMEINDEX    99
           --#STATE        OK
       ::= { fluidFSEventsNdmp 11 } 
    
    
    fluidFSEventNdmpRestoreStarted NOTIFICATION-TYPE
       OBJECTS { sysName, fluidFSEventsParamsNdmpSessionId, fluidFSEventsParamsNdmpInitiatorDMAServer, fluidFSEventsParamsNdmpStartTimestamp, fluidFSEventsParamsNdmpPath, fluidFSEventsParamsNdmpExecutedOnNode }
       STATUS current
       DESCRIPTION
           "The restore session by ID {{SessionId}} initiated by DMA {{InitiatorDMAServer}} on {{StartTimestamp}} started.   Description:  The restore session by ID {{SessionId}} initiated by DMA {{InitiatorDMAServer}} on {{StartTimestamp}} started. The target path is {{Path}} and it is executed on controller {{ExecutedOnNode}}."
           --#TYPE         "Normal Event"
           --#SUMMARY      The restore session by ID %d initiated by DMA %s on %s started.   Description:  The restore session by ID %d initiated by DMA %s on %s started. The target path is %s and it is executed on controller %d.
           --#ARGUMENTS    {1,2,3,4,5}
           --#SEVERITY     INFORMATIONAL
           --#TIMEINDEX    99
           --#STATE        OK
       ::= { fluidFSEventsNdmp 12 } 
    
    
    fluidFSEventNdmpRestoreFinished NOTIFICATION-TYPE
       OBJECTS { sysName, fluidFSEventsParamsNdmpSessionId, fluidFSEventsParamsNdmpInitiatorDMAServer, fluidFSEventsParamsNdmpStartTimestamp, fluidFSEventsParamsNdmpPath, fluidFSEventsParamsNdmpExecutedOnNode }
       STATUS current
       DESCRIPTION
           "The restore session by ID {{SessionId}} initiated by DMA {{InitiatorDMAServer}} on {{StartTimestamp}} finished.   Description:  The restore session by ID {{SessionId}} initiated by DMA {{InitiatorDMAServer}} on {{StartTimestamp}} finished. The target path is {{Path}} and it is executed on controller {{ExecutedOnNode}}."
           --#TYPE         "Normal Event"
           --#SUMMARY      The restore session by ID %d initiated by DMA %s on %s finished.   Description:  The restore session by ID %d initiated by DMA %s on %s finished. The target path is %s and it is executed on controller %d.
           --#ARGUMENTS    {1,2,3,4,5}
           --#SEVERITY     INFORMATIONAL
           --#TIMEINDEX    99
           --#STATE        OK
       ::= { fluidFSEventsNdmp 13 } 
    
    
    fluidFSEventNdmpSessionFailed NOTIFICATION-TYPE
       OBJECTS { sysName, fluidFSEventsParamsNdmpSessionId, fluidFSEventsParamsNdmpDetail }
       STATUS current
       DESCRIPTION
           "The session by ID {{SessionId}} failed: {{Detail}}."
           --#TYPE         "Normal Event"
           --#SUMMARY      The session by ID %d failed: %s.
           --#ARGUMENTS    {1,2}
           --#SEVERITY     MAJOR
           --#TIMEINDEX    99
           --#STATE        OK
       ::= { fluidFSEventsNdmp 14 } 
    
    
    fluidFSEventNdmpSessionTerminated NOTIFICATION-TYPE
       OBJECTS { sysName, fluidFSEventsParamsNdmpSessionId, fluidFSEventsParamsNdmpDetail }
       STATUS current
       DESCRIPTION
           "The session by ID {{SessionId}} was terminated: {{Detail}}."
           --#TYPE         "Normal Event"
           --#SUMMARY      The session by ID %d was terminated: %s.
           --#ARGUMENTS    {1,2}
           --#SEVERITY     INFORMATIONAL
           --#TIMEINDEX    99
           --#STATE        OK
       ::= { fluidFSEventsNdmp 15 } 
    
    
    fluidFSEventNdmpConfigurationValidationError NOTIFICATION-TYPE
       OBJECTS { sysName, fluidFSEventsParamsNdmpDetail }
       STATUS current
       DESCRIPTION
           "Failed to validate configuration: {{Detail}}."
           --#TYPE         "Normal Event"
           --#SUMMARY      Failed to validate configuration: %s.
           --#ARGUMENTS    {1}
           --#SEVERITY     MAJOR
           --#TIMEINDEX    99
           --#STATE        OK
       ::= { fluidFSEventsNdmp 16 } 
    
    
    fluidFSEventNdmpIOError NOTIFICATION-TYPE
       OBJECTS { sysName, fluidFSEventsParamsNdmpDetail }
       STATUS current
       DESCRIPTION
           "IO error: {{Detail}}."
           --#TYPE         "Normal Event"
           --#SUMMARY      IO error: %s.
           --#ARGUMENTS    {1}
           --#SEVERITY     MAJOR
           --#TIMEINDEX    99
           --#STATE        OK
       ::= { fluidFSEventsNdmp 17 } 
    
    
    fluidFSEventNdmpNetworkError NOTIFICATION-TYPE
       OBJECTS { sysName, fluidFSEventsParamsNdmpDetail }
       STATUS current
       DESCRIPTION
           "Network error: {{Detail}}."
           --#TYPE         "Normal Event"
           --#SUMMARY      Network error: %s.
           --#ARGUMENTS    {1}
           --#SEVERITY     MAJOR
           --#TIMEINDEX    99
           --#STATE        OK
       ::= { fluidFSEventsNdmp 18 } 
    
    
    fluidFSEventNdmpSnapshotError NOTIFICATION-TYPE
       OBJECTS { sysName, fluidFSEventsParamsNdmpDetail }
       STATUS current
       DESCRIPTION
           "Snapshot error: {{Detail}}."
           --#TYPE         "Normal Event"
           --#SUMMARY      Snapshot error: %s.
           --#ARGUMENTS    {1}
           --#SEVERITY     MAJOR
           --#TIMEINDEX    99
           --#STATE        OK
       ::= { fluidFSEventsNdmp 19 } 
    
    
    fluidFSEventsParamsQuota OBJECT IDENTIFIER ::= { fluidFSEventsParams 4 } 
    
    
    fluidFSEventsQuota OBJECT IDENTIFIER ::= { fluidFSEvents 4 } 
    
    
    fluidFSEventsParamsQuotaVirtualVolume OBJECT-TYPE
       SYNTAX  DisplayString
       MAX-ACCESS  read-only
       STATUS  current
       DESCRIPTION
           "NAS volume FSID"
       ::= { fluidFSEventsParamsQuota 1 }
    
    
    fluidFSEventsParamsQuotaUserName OBJECT-TYPE
       SYNTAX  DisplayString
       MAX-ACCESS  read-only
       STATUS  current
       DESCRIPTION
           "User name"
       ::= { fluidFSEventsParamsQuota 2 }
    
    
    fluidFSEventsParamsQuotaGroupName OBJECT-TYPE
       SYNTAX  DisplayString
       MAX-ACCESS  read-only
       STATUS  current
       DESCRIPTION
           "Group name"
       ::= { fluidFSEventsParamsQuota 3 }
    
    
    fluidFSEventsParamsQuotaVolumeSize OBJECT-TYPE
       SYNTAX  DisplayString
       MAX-ACCESS  read-only
       STATUS  current
       DESCRIPTION
           "Volume size"
       ::= { fluidFSEventsParamsQuota 4 }
    
    
    fluidFSEventsParamsQuotaVolumeSpaceThreshold OBJECT-TYPE
       SYNTAX  DisplayString
       MAX-ACCESS  read-only
       STATUS  current
       DESCRIPTION
           "Volume space threshold"
       ::= { fluidFSEventsParamsQuota 5 }
    
    
    fluidFSEventsParamsQuotaSnapshotsSpaceThreshold OBJECT-TYPE
       SYNTAX  DisplayString
       MAX-ACCESS  read-only
       STATUS  current
       DESCRIPTION
           "Snapshots space threshold"
       ::= { fluidFSEventsParamsQuota 6 }
    
    
    fluidFSEventsParamsQuotaQuotaThreshold OBJECT-TYPE
       SYNTAX  DisplayString
       MAX-ACCESS  read-only
       STATUS  current
       DESCRIPTION
           "Quota threshold for user or group"
       ::= { fluidFSEventsParamsQuota 7 }
    
    
    fluidFSEventsParamsQuotaVolumeFreeSpace OBJECT-TYPE
       SYNTAX  DisplayString
       MAX-ACCESS  read-only
       STATUS  current
       DESCRIPTION
           "Volume free space"
       ::= { fluidFSEventsParamsQuota 8 }
    
    
    fluidFSEventsParamsQuotaSystemCapacity OBJECT-TYPE
       SYNTAX  DisplayString
       MAX-ACCESS  read-only
       STATUS  current
       DESCRIPTION
           "Capacity of the system"
       ::= { fluidFSEventsParamsQuota 9 }
    
    
    fluidFSEventsParamsQuotaSystemThreshold OBJECT-TYPE
       SYNTAX  DisplayString
       MAX-ACCESS  read-only
       STATUS  current
       DESCRIPTION
           "System threshold"
       ::= { fluidFSEventsParamsQuota 10 }
    
    
    fluidFSEventsParamsQuotaQuotaDirPath OBJECT-TYPE
       SYNTAX  DisplayString
       MAX-ACCESS  read-only
       STATUS  current
       DESCRIPTION
           "The path of the Directory Quota"
       ::= { fluidFSEventsParamsQuota 11 }
    
    
    fluidFSEventsParamsQuotaVirtualVolume OBJECT-TYPE
       SYNTAX  INTEGER
       MAX-ACCESS  read-only
       STATUS  current
       DESCRIPTION
           "NAS volume FSID"
       ::= { fluidFSEventsParamsQuota 12 }
    
    
    fluidFSEventsParamsQuotaVirtualVolumeName OBJECT-TYPE
       SYNTAX  DisplayString
       MAX-ACCESS  read-only
       STATUS  current
       DESCRIPTION
           ""
       ::= { fluidFSEventsParamsQuota 13 }
    
    
    fluidFSEventsParamsQuotaUserNameName OBJECT-TYPE
       SYNTAX  DisplayString
       MAX-ACCESS  read-only
       STATUS  current
       DESCRIPTION
           ""
       ::= { fluidFSEventsParamsQuota 14 }
    
    
    fluidFSEventsParamsQuotaGroupNameName OBJECT-TYPE
       SYNTAX  DisplayString
       MAX-ACCESS  read-only
       STATUS  current
       DESCRIPTION
           ""
       ::= { fluidFSEventsParamsQuota 15 }
    
    
    fluidFSEventQuotaSystemFreeSpaceThresholdExceeded NOTIFICATION-TYPE
       OBJECTS { sysName, fluidFSEventsParamsQuotaSystemThreshold }
       STATUS current
       DESCRIPTION
           "Low system available space.   Description:  System available space is less than {{systemThreshold}}.   Action Items:  Add more storage to your system."
           --#TYPE         "Normal Event"
           --#SUMMARY      Low system available space.   Description:  System available space is less than %s.   Action Items:  Add more storage to your system.
           --#ARGUMENTS    {1}
           --#SEVERITY     MAJOR
           --#TIMEINDEX    99
           --#STATE        OK
       ::= { fluidFSEventsQuota 7 } 
    
    
    fluidFSEventQuotaSystemUsedSpaceThresholdExceeded NOTIFICATION-TYPE
       OBJECTS { sysName, fluidFSEventsParamsQuotaSystemThreshold, fluidFSEventsParamsQuotaSystemCapacity }
       STATUS current
       DESCRIPTION
           "System usage is higher than {{systemThreshold}}%.   Description:  System usage is higher than threshold {{systemThreshold}}% of system capacity {{systemCapacity}}.   Action Items:  Add more storage to your system."
           --#TYPE         "Normal Event"
           --#SUMMARY      System usage is higher than %s%.   Description:  System usage is higher than threshold %s% of system capacity %s.   Action Items:  Add more storage to your system.
           --#ARGUMENTS    {1,2}
           --#SEVERITY     MAJOR
           --#TIMEINDEX    99
           --#STATE        OK
       ::= { fluidFSEventsQuota 8 } 
    
    
    fluidFSEventQuotaSystemLeakageBufferThresholdExceeded NOTIFICATION-TYPE
       OBJECTS { sysName, fluidFSEventsParamsQuotaSystemCapacity }
       STATUS current
       DESCRIPTION
           "Internal storage reservation is running low.   Description:  Internal storage reservation is running low. The system capacity is {{systemCapacity}}. Please contact Support. "
           --#TYPE         "Normal Event"
           --#SUMMARY      Internal storage reservation is running low.   Description:  Internal storage reservation is running low. The system capacity is %s. Please contact Support. 
           --#ARGUMENTS    {1}
           --#SEVERITY     MAJOR
           --#TIMEINDEX    99
           --#STATE        OK
       ::= { fluidFSEventsQuota 10 } 
    
    
    fluidFSEventQuotaSystemOutOfFreeSpace NOTIFICATION-TYPE
       OBJECTS { sysName }
       STATUS current
       DESCRIPTION
           "System is out of available space.   Description:  System is out of available space.   Action Items:  Add more storage to your system."
           --#TYPE         "Normal Event"
           --#SUMMARY      System is out of available space.   Description:  System is out of available space.   Action Items:  Add more storage to your system.
           --#ARGUMENTS    {}
           --#SEVERITY     MAJOR
           --#TIMEINDEX    99
           --#STATE        OK
       ::= { fluidFSEventsQuota 13 } 
    
    
    fluidFSEventQuotaSystemUsedSpaceOverwhelmed NOTIFICATION-TYPE
       OBJECTS { sysName, fluidFSEventsParamsQuotaSystemCapacity }
       STATUS current
       DESCRIPTION
           "System usage reached system capacity of {{systemCapacity}}.   Description:  System usage reached system capacity of {{systemCapacity}}.   Action Items:  Add more storage to your system."
           --#TYPE         "Normal Event"
           --#SUMMARY      System usage reached system capacity of %s.   Description:  System usage reached system capacity of %s.   Action Items:  Add more storage to your system.
           --#ARGUMENTS    {1}
           --#SEVERITY     MAJOR
           --#TIMEINDEX    99
           --#STATE        OK
       ::= { fluidFSEventsQuota 14 } 
    
    
    fluidFSEventQuotaSnapshotThresholdExceeded NOTIFICATION-TYPE
       OBJECTS { sysName, fluidFSEventsParamsQuotaVirtualVolume, fluidFSEventsParamsQuotaSnapshotsSpaceThreshold, fluidFSEventsParamsQuotaVolumeSize }
       STATUS current
       DESCRIPTION
           "Snapshots space exceeded threshold for NAS volume {{virtualVolumeName}}.   Description:  NAS volume {{virtualVolumeName}} - Snapshots space exceeded the defined snapshots threshold {{snapshotsSpaceThreshold}}% of the total size {{volumeSize}}."
           --#TYPE         "Normal Event"
           --#SUMMARY      Snapshots space exceeded threshold for NAS volume %s.   Description:  NAS volume %s - Snapshots space exceeded the defined snapshots threshold %s% of the total size %s.
           --#ARGUMENTS    {1,2,3}
           --#SEVERITY     MAJOR
           --#TIMEINDEX    99
           --#STATE        OK
       ::= { fluidFSEventsQuota 16 } 
    
    
    fluidFSEventQuotaSnapshotAvailableSpaceBelowThreshold NOTIFICATION-TYPE
       OBJECTS { sysName, fluidFSEventsParamsQuotaVirtualVolume, fluidFSEventsParamsQuotaSnapshotsSpaceThreshold, fluidFSEventsParamsQuotaVolumeSize }
       STATUS current
       DESCRIPTION
           "Low space is available for snapshots in NAS Volume {{virtualVolumeName}}.   Description:  NAS Volume {{virtualVolumeName}} - Space available for snapshots is less than {{snapshotsSpaceThreshold}}% of the total size {{volumeSize}}."
           --#TYPE         "Normal Event"
           --#SUMMARY      Low space is available for snapshots in NAS Volume %s.   Description:  NAS Volume %s - Space available for snapshots is less than %s% of the total size %s.
           --#ARGUMENTS    {1,2,3}
           --#SEVERITY     MAJOR
           --#TIMEINDEX    99
           --#STATE        OK
       ::= { fluidFSEventsQuota 17 } 
    
    
    fluidFSEventQuotaUserQuotaExceeded NOTIFICATION-TYPE
       OBJECTS { sysName, fluidFSEventsParamsQuotaUserName, fluidFSEventsParamsQuotaVirtualVolume, fluidFSEventsParamsQuotaQuotaThreshold }
       STATUS current
       DESCRIPTION
           "User soft quota exceeded. User {{userNameName}}, NAS volume {{virtualVolumeName}}.   Description:  User {{userNameName}} on NAS volume {{virtualVolumeName}} has exceeded its soft limit. Soft limit is {{quotaThreshold}} MB.   Action Items:  First determine whether this is the outcome of default quota or specific user quota defined for this NAS volume. If there is a fit between the current definition and the required quota enforcement, contact the user and warn him/her that future writes might be denied due to quota violation. If there is a special user requirement, and this is the outcome of a default quota definition, you might consider defining specific user quota for this user."
           --#TYPE         "Normal Event"
           --#SUMMARY      User soft quota exceeded. User %s, NAS volume %s.   Description:  User %s on NAS volume %s has exceeded its soft limit. Soft limit is %s MB.   Action Items:  First determine whether this is the outcome of default quota or specific user quota defined for this NAS volume. If there is a fit between the current definition and the required quota enforcement, contact the user and warn him/her that future writes might be denied due to quota violation. If there is a special user requirement, and this is the outcome of a default quota definition, you might consider defining specific user quota for this user.
           --#ARGUMENTS    {1,2,3}
           --#SEVERITY     INFORMATIONAL
           --#TIMEINDEX    99
           --#STATE        OK
       ::= { fluidFSEventsQuota 18 } 
    
    
    fluidFSEventQuotaGroupQuotaExceeded NOTIFICATION-TYPE
       OBJECTS { sysName, fluidFSEventsParamsQuotaGroupName, fluidFSEventsParamsQuotaVirtualVolume, fluidFSEventsParamsQuotaQuotaThreshold }
       STATUS current
       DESCRIPTION
           "Group soft quota exceeded. Group {{groupNameName}}, NAS volume {{virtualVolumeName}}.   Description:  Group {{groupNameName}} on NAS volume {{virtualVolumeName}} has exceeded its soft limit. Soft limit is {{quotaThreshold}} MB.   Action Items:  First determine whether this is the outcome of default quota or specific group quota defined for this NAS volume. If there is a fit between the current definition and the required quota enforcement, contact the group manager and warn him/her that future writes might be denied due to quota violation. If there is a special group requirement, and this is the outcome of a default quota definition, you might consider defining specific group quota for this group."
           --#TYPE         "Normal Event"
           --#SUMMARY      Group soft quota exceeded. Group %s, NAS volume %s.   Description:  Group %s on NAS volume %s has exceeded its soft limit. Soft limit is %s MB.   Action Items:  First determine whether this is the outcome of default quota or specific group quota defined for this NAS volume. If there is a fit between the current definition and the required quota enforcement, contact the group manager and warn him/her that future writes might be denied due to quota violation. If there is a special group requirement, and this is the outcome of a default quota definition, you might consider defining specific group quota for this group.
           --#ARGUMENTS    {1,2,3}
           --#SEVERITY     INFORMATIONAL
           --#TIMEINDEX    99
           --#STATE        OK
       ::= { fluidFSEventsQuota 19 } 
    
    
    fluidFSEventQuotaVolumeFreeSpaceThresholdExceeded NOTIFICATION-TYPE
       OBJECTS { sysName, fluidFSEventsParamsQuotaVirtualVolume, fluidFSEventsParamsQuotaVolumeSpaceThreshold }
       STATUS current
       DESCRIPTION
           "Available space on NAS volume {{virtualVolumeName}} is running low.   Description:  NAS volume {{virtualVolumeName}} - Volume available space is less than {{volumeSpaceThreshold}}. Please note that writes to the NAS volume's clones will fail if its base Volume reaches full capacity.   Action Items:  See if the space shortage is caused by system space shortage or the volume is almost full. If the volume is thick or the shortage is at the volume level, you should consider removing old snapshots, cleanup the volume or increase the volume size. If the volume is thin and it is far from being full, consider removing snapshots and files in other thin volumes that are using unreserved space, purchase more storage and expand LUNs."
           --#TYPE         "Normal Event"
           --#SUMMARY      Available space on NAS volume %s is running low.   Description:  NAS volume %s - Volume available space is less than %s. Please note that writes to the NAS volume's clones will fail if its base Volume reaches full capacity.   Action Items:  See if the space shortage is caused by system space shortage or the volume is almost full. If the volume is thick or the shortage is at the volume level, you should consider removing old snapshots, cleanup the volume or increase the volume size. If the volume is thin and it is far from being full, consider removing snapshots and files in other thin volumes that are using unreserved space, purchase more storage and expand LUNs.
           --#ARGUMENTS    {1,2}
           --#SEVERITY     MAJOR
           --#TIMEINDEX    99
           --#STATE        OK
       ::= { fluidFSEventsQuota 20 } 
    
    
    fluidFSEventQuotaVolumeUsedSpaceThresholdExceeded NOTIFICATION-TYPE
       OBJECTS { sysName, fluidFSEventsParamsQuotaVirtualVolume, fluidFSEventsParamsQuotaVolumeSpaceThreshold, fluidFSEventsParamsQuotaVolumeSize }
       STATUS current
       DESCRIPTION
           "NAS volume {{virtualVolumeName}} exceeded used space threshold.   Description:  NAS volume {{virtualVolumeName}} - Used space exceeded {{volumeSpaceThreshold}}% of the total size {{volumeSize}}. Please note that writes to the NAS volume's clones will fail if its base volume reaches full capacity."
           --#TYPE         "Normal Event"
           --#SUMMARY      NAS volume %s exceeded used space threshold.   Description:  NAS volume %s - Used space exceeded %s% of the total size %s. Please note that writes to the NAS volume's clones will fail if its base volume reaches full capacity.
           --#ARGUMENTS    {1,2,3}
           --#SEVERITY     MAJOR
           --#TIMEINDEX    99
           --#STATE        OK
       ::= { fluidFSEventsQuota 21 } 
    
    
    fluidFSEventQuotaVolumeOutOfFreeSpace NOTIFICATION-TYPE
       OBJECTS { sysName, fluidFSEventsParamsQuotaVirtualVolume }
       STATUS current
       DESCRIPTION
           "NAS volume {{virtualVolumeName}} is out of available space.   Description:  NAS volume {{virtualVolumeName}} - Volume is out of available space. Please note that writes to the NAS volume and its clones will fail.   Action Items:  See if the space shortage is caused by system space shortage or the volume is full. If the volume is thick or the shortage is at the volume level, you should consider removing old snapshots, cleanup the volume or increase the volume size. If the volume is thin and it is far from being full, consider removing snapshots and files in other thin volumes that are using unreserved space, purchase more storage and expand LUNs."
           --#TYPE         "Normal Event"
           --#SUMMARY      NAS volume %s is out of available space.   Description:  NAS volume %s - Volume is out of available space. Please note that writes to the NAS volume and its clones will fail.   Action Items:  See if the space shortage is caused by system space shortage or the volume is full. If the volume is thick or the shortage is at the volume level, you should consider removing old snapshots, cleanup the volume or increase the volume size. If the volume is thin and it is far from being full, consider removing snapshots and files in other thin volumes that are using unreserved space, purchase more storage and expand LUNs.
           --#ARGUMENTS    {1}
           --#SEVERITY     MAJOR
           --#TIMEINDEX    99
           --#STATE        OK
       ::= { fluidFSEventsQuota 22 } 
    
    
    fluidFSEventQuotaVolumeUsedSpaceOverwhelmed NOTIFICATION-TYPE
       OBJECTS { sysName, fluidFSEventsParamsQuotaVirtualVolume, fluidFSEventsParamsQuotaVolumeSize }
       STATUS current
       DESCRIPTION
           "NAS volume {{virtualVolumeName}} used space reached the volume size (no space).   Description:  NAS volume {{virtualVolumeName}} - Used space reached the volume size {{volumeSize}}. Please note that writes to the NAS volume and its clones will fail.   Action Items:  See if the space shortage is caused by system space shortage or the volume is full. If the volume is thick or the shortage is at the volume level, you should consider removing old snapshots, cleanup the volume or increase the volume size. If the volume is thin and it is far from being full, consider removing snapshots and files in other thin volumes that are using unreserved space, purchase more storage and expand LUNs."
           --#TYPE         "Normal Event"
           --#SUMMARY      NAS volume %s used space reached the volume size (no space).   Description:  NAS volume %s - Used space reached the volume size %s. Please note that writes to the NAS volume and its clones will fail.   Action Items:  See if the space shortage is caused by system space shortage or the volume is full. If the volume is thick or the shortage is at the volume level, you should consider removing old snapshots, cleanup the volume or increase the volume size. If the volume is thin and it is far from being full, consider removing snapshots and files in other thin volumes that are using unreserved space, purchase more storage and expand LUNs.
           --#ARGUMENTS    {1,2}
           --#SEVERITY     MAJOR
           --#TIMEINDEX    99
           --#STATE        OK
       ::= { fluidFSEventsQuota 23 } 
    
    
    fluidFSEventQuotaDirectoryQuotaExceeded NOTIFICATION-TYPE
       OBJECTS { sysName, fluidFSEventsParamsQuotaQuotaDirPath, fluidFSEventsParamsQuotaVirtualVolume, fluidFSEventsParamsQuotaQuotaThreshold }
       STATUS current
       DESCRIPTION
           "Directory Quota '{{quotaDirPath}}' in volume {{virtualVolumeName}} exceeded the soft limit   Description:  Directory Quota '{{quotaDirPath}}' in volume {{virtualVolumeName}} exceeded the soft limit of {{quotaThreshold}} MB.   Action Items:  Advise the users to clear some space from the directory or consider extending the quota limit."
           --#TYPE         "Normal Event"
           --#SUMMARY      Directory Quota '%s' in volume %s exceeded the soft limit   Description:  Directory Quota '%s' in volume %s exceeded the soft limit of %s MB.   Action Items:  Advise the users to clear some space from the directory or consider extending the quota limit.
           --#ARGUMENTS    {1,2,3}
           --#SEVERITY     INFORMATIONAL
           --#TIMEINDEX    99
           --#STATE        OK
       ::= { fluidFSEventsQuota 24 } 
    
    
    fluidFSEventsParamsReplication OBJECT IDENTIFIER ::= { fluidFSEventsParams 5 } 
    
    
    fluidFSEventsReplication OBJECT IDENTIFIER ::= { fluidFSEvents 5 } 
    
    
    fluidFSEventsParamsReplicationSourceVolume OBJECT-TYPE
       SYNTAX  DisplayString
       MAX-ACCESS  read-only
       STATUS  current
       DESCRIPTION
           "Source NAS volume FSID"
       ::= { fluidFSEventsParamsReplication 1 }
    
    
    fluidFSEventsParamsReplicationSourceCluster OBJECT-TYPE
       SYNTAX  DisplayString
       MAX-ACCESS  read-only
       STATUS  current
       DESCRIPTION
           "Source cluster"
       ::= { fluidFSEventsParamsReplication 2 }
    
    
    fluidFSEventsParamsReplicationDestinationVolume OBJECT-TYPE
       SYNTAX  DisplayString
       MAX-ACCESS  read-only
       STATUS  current
       DESCRIPTION
           "Destination NAS volume"
       ::= { fluidFSEventsParamsReplication 3 }
    
    
    fluidFSEventsParamsReplicationDestinationCluster OBJECT-TYPE
       SYNTAX  DisplayString
       MAX-ACCESS  read-only
       STATUS  current
       DESCRIPTION
           "Destination cluster"
       ::= { fluidFSEventsParamsReplication 4 }
    
    
    fluidFSEventsParamsReplicationErrorCode OBJECT-TYPE
       SYNTAX  INTEGER
       MAX-ACCESS  read-only
       STATUS  current
       DESCRIPTION
           "Error code"
       ::= { fluidFSEventsParamsReplication 5 }
    
    
    fluidFSEventsParamsReplicationTaskName OBJECT-TYPE
       SYNTAX  DisplayString
       MAX-ACCESS  read-only
       STATUS  current
       DESCRIPTION
           "Task name of file level replication"
       ::= { fluidFSEventsParamsReplication 6 }
    
    
    fluidFSEventsParamsReplicationErrorDesc OBJECT-TYPE
       SYNTAX  DisplayString
       MAX-ACCESS  read-only
       STATUS  current
       DESCRIPTION
           "Error description"
       ::= { fluidFSEventsParamsReplication 7 }
    
    
    fluidFSEventsParamsReplicationOldMngConVip OBJECT-TYPE
       SYNTAX  DisplayString
       MAX-ACCESS  read-only
       STATUS  current
       DESCRIPTION
           "Old manage console VIP"
       ::= { fluidFSEventsParamsReplication 8 }
    
    
    fluidFSEventsParamsReplicationNewMngConVip OBJECT-TYPE
       SYNTAX  DisplayString
       MAX-ACCESS  read-only
       STATUS  current
       DESCRIPTION
           "New manage console VIP"
       ::= { fluidFSEventsParamsReplication 9 }
    
    
    fluidFSEventsParamsReplicationStartTime OBJECT-TYPE
       SYNTAX  DisplayString
       MAX-ACCESS  read-only
       STATUS  current
       DESCRIPTION
           "replication start time"
       ::= { fluidFSEventsParamsReplication 10 }
    
    
    fluidFSEventsParamsReplicationEndTime OBJECT-TYPE
       SYNTAX  DisplayString
       MAX-ACCESS  read-only
       STATUS  current
       DESCRIPTION
           "replication end time"
       ::= { fluidFSEventsParamsReplication 11 }
    
    
    fluidFSEventsParamsReplicationTotalTransferredSize OBJECT-TYPE
       SYNTAX  DisplayString
       MAX-ACCESS  read-only
       STATUS  current
       DESCRIPTION
           "total transferred size"
       ::= { fluidFSEventsParamsReplication 12 }
    
    
    fluidFSEventsParamsReplicationRehydratedVolumeSize OBJECT-TYPE
       SYNTAX  DisplayString
       MAX-ACCESS  read-only
       STATUS  current
       DESCRIPTION
           "rehydrated volume size"
       ::= { fluidFSEventsParamsReplication 13 }
    
    
    fluidFSEventsParamsReplicationSourceVolume OBJECT-TYPE
       SYNTAX  INTEGER
       MAX-ACCESS  read-only
       STATUS  current
       DESCRIPTION
           "Source NAS volume FSID"
       ::= { fluidFSEventsParamsReplication 14 }
    
    
    fluidFSEventsParamsReplicationDestinationVolume OBJECT-TYPE
       SYNTAX  INTEGER
       MAX-ACCESS  read-only
       STATUS  current
       DESCRIPTION
           "Destination NAS volume"
       ::= { fluidFSEventsParamsReplication 15 }
    
    
    fluidFSEventsParamsReplicationDomainId OBJECT-TYPE
       SYNTAX  DisplayString
       MAX-ACCESS  read-only
       STATUS  current
       DESCRIPTION
           "domain Id"
       ::= { fluidFSEventsParamsReplication 16 }
    
    
    fluidFSEventsParamsReplicationSnapshotId OBJECT-TYPE
       SYNTAX  DisplayString
       MAX-ACCESS  read-only
       STATUS  current
       DESCRIPTION
           "snapshot Id"
       ::= { fluidFSEventsParamsReplication 17 }
    
    
    fluidFSEventsParamsReplicationDomainReplicationStats OBJECT-TYPE
       SYNTAX  DisplayString
       MAX-ACCESS  read-only
       STATUS  current
       DESCRIPTION
           "domain replication stats"
       ::= { fluidFSEventsParamsReplication 18 }
    
    
    fluidFSEventsParamsReplicationSavingsPercent OBJECT-TYPE
       SYNTAX  DisplayString
       MAX-ACCESS  read-only
       STATUS  current
       DESCRIPTION
           ""
       ::= { fluidFSEventsParamsReplication 19 }
    
    
    fluidFSEventsParamsReplicationSourceVolumeName OBJECT-TYPE
       SYNTAX  DisplayString
       MAX-ACCESS  read-only
       STATUS  current
       DESCRIPTION
           ""
       ::= { fluidFSEventsParamsReplication 20 }
    
    
    fluidFSEventsParamsReplicationDestinationVolumeName OBJECT-TYPE
       SYNTAX  DisplayString
       MAX-ACCESS  read-only
       STATUS  current
       DESCRIPTION
           ""
       ::= { fluidFSEventsParamsReplication 21 }
    
    
    fluidFSEventReplicationDisconnection NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The connection between source and destination systems was lost. The replication will continue automatically when the connection is restored."
           --#TYPE         "Normal Event"
           --#SUMMARY      Replication between NAS volume %s@%s and NAS volume %s@%s failed.   Description:  Replication between NAS volume %s@%s and NAS volume %s@%s failed because of the following reason: The connection between source and destination systems was lost. The replication will continue automatically when the connection is restored.
           --#ARGUMENTS    {1,2,3,4}
           --#SEVERITY     INFORMATIONAL
           --#TIMEINDEX    99
           --#STATE        OK
       ::= { fluidFSEventsReplication 14 } 
    
    
    fluidFSEventReplicationInternalError NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationErrorCode }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: There was an internal error (err: {{errorCode}}), please contact Support."
           --#TYPE         "Normal Event"
           --#SUMMARY      Replication between NAS volume %s@%s and NAS volume %s@%s failed.   Description:  Replication between NAS volume %s@%s and NAS volume %s@%s failed because of the following reason: There was an internal error (err: %d), please contact Support.
           --#ARGUMENTS    {1,2,3,4,5}
           --#SEVERITY     MAJOR
           --#TIMEINDEX    99
           --#STATE        OK
       ::= { fluidFSEventsReplication 15 } 
    
    
    fluidFSEventReplicationSourceFSIsDown NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The file system of source NAS volume is down. The replication will continue automatically when the file-system is started."
           --#TYPE         "Normal Event"
           --#SUMMARY      Replication between NAS volume %s@%s and NAS volume %s@%s failed.   Description:  Replication between NAS volume %s@%s and NAS volume %s@%s failed because of the following reason: The file system of source NAS volume is down. The replication will continue automatically when the file-system is started.
           --#ARGUMENTS    {1,2,3,4}
           --#SEVERITY     MAJOR
           --#TIMEINDEX    99
           --#STATE        OK
       ::= { fluidFSEventsReplication 16 } 
    
    
    fluidFSEventReplicationSourceFSIsNotOptimal NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The file-system of the source NAS volume is not optimal. The replication will continue automatically when the file-system recovers."
           --#TYPE         "Normal Event"
           --#SUMMARY      Replication between NAS volume %s@%s and NAS volume %s@%s failed.   Description:  Replication between NAS volume %s@%s and NAS volume %s@%s failed because of the following reason: The file-system of the source NAS volume is not optimal. The replication will continue automatically when the file-system recovers.
           --#ARGUMENTS    {1,2,3,4}
           --#SEVERITY     MAJOR
           --#TIMEINDEX    99
           --#STATE        OK
       ::= { fluidFSEventsReplication 17 } 
    
    
    fluidFSEventReplicationDestinationFSIsNotOptimal NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The file-system of the destination NAS volume is not optimal. The replication will continue automatically when the file-system recovers."
           --#TYPE         "Normal Event"
           --#SUMMARY      Replication between NAS volume %s@%s and NAS volume %s@%s failed.   Description:  Replication between NAS volume %s@%s and NAS volume %s@%s failed because of the following reason: The file-system of the destination NAS volume is not optimal. The replication will continue automatically when the file-system recovers.
           --#ARGUMENTS    {1,2,3,4}
           --#SEVERITY     MAJOR
           --#TIMEINDEX    99
           --#STATE        OK
       ::= { fluidFSEventsReplication 18 } 
    
    
    fluidFSEventReplicationDestinationFSIsDown NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The file system of destination NAS volume is down. The replication will continue automatically when the file-system is started."
           --#TYPE         "Normal Event"
           --#SUMMARY      Replication between NAS volume %s@%s and NAS volume %s@%s failed.   Description:  Replication between NAS volume %s@%s and NAS volume %s@%s failed because of the following reason: The file system of destination NAS volume is down. The replication will continue automatically when the file-system is started.
           --#ARGUMENTS    {1,2,3,4}
           --#SEVERITY     MAJOR
           --#TIMEINDEX    99
           --#STATE        OK
       ::= { fluidFSEventsReplication 19 } 
    
    
    fluidFSEventReplicationConfigurationError NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The source and destination systems resources are not balanced. Please consider to add new applience to the destination system."
           --#TYPE         "Normal Event"
           --#SUMMARY      Replication between NAS volume %s@%s and NAS volume %s@%s failed.   Description:  Replication between NAS volume %s@%s and NAS volume %s@%s failed because of the following reason: The source and destination systems resources are not balanced. Please consider to add new applience to the destination system.
           --#ARGUMENTS    {1,2,3,4}
           --#SEVERITY     MAJOR
           --#TIMEINDEX    99
           --#STATE        OK
       ::= { fluidFSEventsReplication 20 } 
    
    
    fluidFSEventReplicationMngConVipChanged NOTIFICATION-TYPE
       OBJECTS { sysName, fluidFSEventsParamsReplicationOldMngConVip, fluidFSEventsParamsReplicationNewMngConVip }
       STATUS current
       DESCRIPTION
           "Cluster VIP {{oldMngConVip}} was changed to {{newMngConVip}}. Please update partnership systems with this change."
           --#TYPE         "Normal Event"
           --#SUMMARY      Cluster VIP %s was changed to %s. Please update partnership systems with this change.
           --#ARGUMENTS    {1,2}
           --#SEVERITY     INFORMATIONAL
           --#TIMEINDEX    99
           --#STATE        OK
       ::= { fluidFSEventsReplication 26 } 
    
    
    fluidFSEventReplicationMngConVipChangedDestination NOTIFICATION-TYPE
       OBJECTS { sysName, fluidFSEventsParamsReplicationOldMngConVip, fluidFSEventsParamsReplicationNewMngConVip }
       STATUS current
       DESCRIPTION
           "Manage console VIP {{oldMngConVip}} was changed to {{newMngConVip}}. Please, update partnership systems with this change."
           --#TYPE         "Normal Event"
           --#SUMMARY      Manage console VIP %s was changed to %s. Please, update partnership systems with this change.
           --#ARGUMENTS    {1,2}
           --#SEVERITY     INFORMATIONAL
           --#TIMEINDEX    99
           --#STATE        OK
       ::= { fluidFSEventsReplication 49 } 
    
    
    fluidFSEventReplicationDestinationVolumeIsDetached NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The destination NAS volume disconnected from the source NAS volume. Please perform the disconnect action also from the source NAS volume, and if you would like, reconnect the NAS volumes again to allow replication."
           --#TYPE         "Normal Event"
           --#SUMMARY      Replication between NAS volume %s@%s and NAS volume %s@%s failed.   Description:  Replication between NAS volume %s@%s and NAS volume %s@%s failed because of the following reason: The destination NAS volume disconnected from the source NAS volume. Please perform the disconnect action also from the source NAS volume, and if you would like, reconnect the NAS volumes again to allow replication.
           --#ARGUMENTS    {1,2,3,4}
           --#SEVERITY     MAJOR
           --#TIMEINDEX    99
           --#STATE        OK
       ::= { fluidFSEventsReplication 55 } 
    
    
    fluidFSEventReplicationDestinationClusterIsBusy NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: Temporarily the destination cluster is not available to serve the required replication."
           --#TYPE         "Normal Event"
           --#SUMMARY      Replication between NAS volume %s@%s and NAS volume %s@%s failed.   Description:  Replication between NAS volume %s@%s and NAS volume %s@%s failed because of the following reason: Temporarily the destination cluster is not available to serve the required replication.
           --#ARGUMENTS    {1,2,3,4}
           --#SEVERITY     INFORMATIONAL
           --#TIMEINDEX    99
           --#STATE        OK
       ::= { fluidFSEventsReplication 56 } 
    
    
    fluidFSEventReplicationIncompatibleVersions NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The system version of source NAS volume is higher than the system version of the destination system. Please upgrade the destination system to same version as source system."
           --#TYPE         "Normal Event"
           --#SUMMARY      Replication between NAS volume %s@%s and NAS volume %s@%s failed.   Description:  Replication between NAS volume %s@%s and NAS volume %s@%s failed because of the following reason: The system version of source NAS volume is higher than the system version of the destination system. Please upgrade the destination system to same version as source system.
           --#ARGUMENTS    {1,2,3,4}
           --#SEVERITY     MAJOR
           --#TIMEINDEX    99
           --#STATE        OK
       ::= { fluidFSEventsReplication 57 } 
    
    
    fluidFSEventReplicationNotEnoughSpaceInDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: There is not enough space in the destination NAS volume. Please increase the destination NAS volume size."
           --#TYPE         "Normal Event"
           --#SUMMARY      Replication between NAS volume %s@%s and NAS volume %s@%s failed.   Description:  Replication between NAS volume %s@%s and NAS volume %s@%s failed because of the following reason: There is not enough space in the destination NAS volume. Please increase the destination NAS volume size.
           --#ARGUMENTS    {1,2,3,4}
           --#SEVERITY     MAJOR
           --#TIMEINDEX    99
           --#STATE        OK
       ::= { fluidFSEventsReplication 58 } 
    
    
    fluidFSEventReplicationSourceVolumeBusyWithReclaiming NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between {{sourceVolumeName}}@{{sourceCluster}} and {{destinationVolume}}@{{destinationCluster}} experienced a temporary failure.   Description:  Replication between NAS volume {{sourceVolumeName}}@{{sourceCluster}} and NAS volume {{destinationVolume}}@{{destinationCluster}} experienced a temporary failure because of the following reason: The source NAS volume is busy freeing space. The replication will continue automatically when space is available."
           --#TYPE         "Normal Event"
           --#SUMMARY      Replication between %s@%s and %s@%s experienced a temporary failure.   Description:  Replication between NAS volume %s@%s and NAS volume %s@%s experienced a temporary failure because of the following reason: The source NAS volume is busy freeing space. The replication will continue automatically when space is available.
           --#ARGUMENTS    {1,2,3,4}
           --#SEVERITY     INFORMATIONAL
           --#TIMEINDEX    99
           --#STATE        OK
       ::= { fluidFSEventsReplication 59 } 
    
    
    fluidFSEventReplicationDestinationVolumeBusyWithReclaiming NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between {{sourceVolumeName}}@{{sourceCluster}} and {{destinationVolume}}@{{destinationCluster}} experienced a temporary failure.   Description:  Replication between NAS volume {{sourceVolumeName}}@{{sourceCluster}} and NAS volume {{destinationVolume}}@{{destinationCluster}} experienced a temporary failure because of the following reason: The destination NAS volume is busy freeing space. The replication will continue automatically when space is available."
           --#TYPE         "Normal Event"
           --#SUMMARY      Replication between %s@%s and %s@%s experienced a temporary failure.   Description:  Replication between NAS volume %s@%s and NAS volume %s@%s experienced a temporary failure because of the following reason: The destination NAS volume is busy freeing space. The replication will continue automatically when space is available.
           --#ARGUMENTS    {1,2,3,4}
           --#SEVERITY     INFORMATIONAL
           --#TIMEINDEX    99
           --#STATE        OK
       ::= { fluidFSEventsReplication 60 } 
    
    
    fluidFSEventReplicationSourceFSIsBusy NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The file-system of the source NAS volume is busy with replication of other NAS volumes. The replication will continue automatically when the file-system releases part of the resources."
           --#TYPE         "Normal Event"
           --#SUMMARY      Replication between NAS volume %s@%s and NAS volume %s@%s failed.   Description:  Replication between NAS volume %s@%s and NAS volume %s@%s failed because of the following reason: The file-system of the source NAS volume is busy with replication of other NAS volumes. The replication will continue automatically when the file-system releases part of the resources.
           --#ARGUMENTS    {1,2,3,4}
           --#SEVERITY     INFORMATIONAL
           --#TIMEINDEX    99
           --#STATE        OK
       ::= { fluidFSEventsReplication 61 } 
    
    
    fluidFSEventReplicationDestinationFSIsBusy NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The file-system of the destination NAS volume is busy with replication of other NAS volumes. The replication will continue automatically when the file-system releases part of the resources."
           --#TYPE         "Normal Event"
           --#SUMMARY      Replication between NAS volume %s@%s and NAS volume %s@%s failed.   Description:  Replication between NAS volume %s@%s and NAS volume %s@%s failed because of the following reason: The file-system of the destination NAS volume is busy with replication of other NAS volumes. The replication will continue automatically when the file-system releases part of the resources.
           --#ARGUMENTS    {1,2,3,4}
           --#SEVERITY     INFORMATIONAL
           --#TIMEINDEX    99
           --#STATE        OK
       ::= { fluidFSEventsReplication 62 } 
    
    
    fluidFSEventReplicationJumboFramesBlocked NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: Jumbo frames are blocked over the network."
           --#TYPE         "Normal Event"
           --#SUMMARY      Replication between NAS volume %s@%s and NAS volume %s@%s failed.   Description:  Replication between NAS volume %s@%s and NAS volume %s@%s failed because of the following reason: Jumbo frames are blocked over the network.
           --#ARGUMENTS    {1,2,3,4}
           --#SEVERITY     MAJOR
           --#TIMEINDEX    99
           --#STATE        OK
       ::= { fluidFSEventsReplication 63 } 
    
    
    fluidFSEventReplicationRecoveredReplication NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} finished.   Description:  Replication between NAS volume {{sourceVolumeName}}@{{sourceCluster}} and NAS volume {{destinationVolume}}@{{destinationCluster}} successfully recovered from the problem and finished."
           --#TYPE         "Normal Event"
           --#SUMMARY      Replication between NAS volume %s@%s and NAS volume %s@%s finished.   Description:  Replication between NAS volume %s@%s and NAS volume %s@%s successfully recovered from the problem and finished.
           --#ARGUMENTS    {1,2,3,4}
           --#SEVERITY     INFORMATIONAL
           --#TIMEINDEX    99
           --#STATE        OK
       ::= { fluidFSEventsReplication 64 } 
    
    
    fluidFSEventReplicationDestinationVolumeShrink NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} succeeded.   Description:  Replication between NAS volume {{sourceVolumeName}}@{{sourceCluster}} and NAS volume {{destinationVolume}}@{{destinationCluster}} succeeded but resizing of the destination volume failed."
           --#TYPE         "Normal Event"
           --#SUMMARY      Replication between NAS volume %s@%s and NAS volume %s@%s succeeded.   Description:  Replication between NAS volume %s@%s and NAS volume %s@%s succeeded but resizing of the destination volume failed.
           --#ARGUMENTS    {1,2,3,4}
           --#SEVERITY     INFORMATIONAL
           --#TIMEINDEX    99
           --#STATE        OK
       ::= { fluidFSEventsReplication 65 } 
    
    
    fluidFSEventReplicationDestinationVolumeIsDisabled NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The replication policy status on the destination volume is currently promoted. Please perform the promote action also from the source NAS volume, and demote to allow replication."
           --#TYPE         "Normal Event"
           --#SUMMARY      Replication between NAS volume %s@%s and NAS volume %s@%s failed.   Description:  Replication between NAS volume %s@%s and NAS volume %s@%s failed because of the following reason: The replication policy status on the destination volume is currently promoted. Please perform the promote action also from the source NAS volume, and demote to allow replication.
           --#ARGUMENTS    {1,2,3,4}
           --#SEVERITY     MAJOR
           --#TIMEINDEX    99
           --#STATE        OK
       ::= { fluidFSEventsReplication 66 } 
    
    
    fluidFSEventReplicationDestinationVolumeDedupParams NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Optimization policy configuration is not updated.   Description:  As part of replication between NAS volume {{sourceVolumeName}}@{{sourceCluster}} and NAS volume {{destinationVolume}}@{{destinationCluster}} the optimization policy configuration has failed to update."
           --#TYPE         "Normal Event"
           --#SUMMARY      Optimization policy configuration is not updated.   Description:  As part of replication between NAS volume %s@%s and NAS volume %s@%s the optimization policy configuration has failed to update.
           --#ARGUMENTS    {1,2,3,4}
           --#SEVERITY     MAJOR
           --#TIMEINDEX    99
           --#STATE        OK
       ::= { fluidFSEventsReplication 67 } 
    
    
    fluidFSEventReplicationRollbackSnapCloneBase NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: rollback snapshot failed due to clone snapshot base."
           --#TYPE         "Normal Event"
           --#SUMMARY      Replication between NAS volume %s@%s and NAS volume %s@%s failed.   Description:  Replication between NAS volume %s@%s and NAS volume %s@%s failed because of the following reason: rollback snapshot failed due to clone snapshot base.
           --#ARGUMENTS    {1,2,3,4}
           --#SEVERITY     MAJOR
           --#TIMEINDEX    99
           --#STATE        OK
       ::= { fluidFSEventsReplication 68 } 
    
    
    fluidFSEventReplicationReplicationFinished NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationStartTime, fluidFSEventsParamsReplicationEndTime, fluidFSEventsParamsReplicationTotalTransferredSize }
       STATUS current
       DESCRIPTION
           "Replication between NAS volume {{sourceVolumeName}}@{{sourceCluster}} and NAS volume {{destinationVolume}}@{{destinationCluster}} finished.   Description:  Replication between NAS volume {{sourceVolumeName}}@{{sourceCluster}} and NAS volume {{destinationVolume}}@{{destinationCluster}} which start at {{startTime}} has transferred {{totalTransferredSize}} MB of data and finished successfully at {{endTime}}. "
           --#TYPE         "Normal Event"
           --#SUMMARY      Replication between NAS volume %s@%s and NAS volume %s@%s finished.   Description:  Replication between NAS volume %s@%s and NAS volume %s@%s which start at %s has transferred %s MB of data and finished successfully at %s. 
           --#ARGUMENTS    {1,2,3,4,5,6,7}
           --#SEVERITY     INFORMATIONAL
           --#TIMEINDEX    99
           --#STATE        OK
       ::= { fluidFSEventsReplication 69 } 
    
    
    fluidFSEventReplicationDisconnectionDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The connection between source and destination systems was lost. The replication will continue automatically when the connection is restored."
           --#TYPE         "Normal Event"
           --#SUMMARY      Replication between NAS volume %s@%s and NAS volume %s@%s failed   Description:  Replication between NAS volume %s@%s and NAS volume %s@%s failed because of the following reason: The connection between source and destination systems was lost. The replication will continue automatically when the connection is restored.
           --#ARGUMENTS    {1,2,3,4}
           --#SEVERITY     INFORMATIONAL
           --#TIMEINDEX    99
           --#STATE        OK
       ::= { fluidFSEventsReplication 70 } 
    
    
    fluidFSEventReplicationInternalErrorDestination NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationErrorCode }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: There was an internal error (err: {{errorCode}}), please contact the support team"
           --#TYPE         "Normal Event"
           --#SUMMARY      Replication between NAS volume %s@%s and NAS volume %s@%s failed   Description:  Replication between NAS volume %s@%s and NAS volume %s@%s failed because of the following reason: There was an internal error (err: %d), please contact the support team
           --#ARGUMENTS    {1,2,3,4,5}
           --#SEVERITY     MAJOR
           --#TIMEINDEX    99
           --#STATE        OK
       ::= { fluidFSEventsReplication 71 } 
    
    
    fluidFSEventReplicationSourceFSIsDownDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The file system of source NAS volume is down. The replication will continue automatically when the file-system is started."
           --#TYPE         "Normal Event"
           --#SUMMARY      Replication between NAS volume %s@%s and NAS volume %s@%s failed   Description:  Replication between NAS volume %s@%s and NAS volume %s@%s failed because of the following reason: The file system of source NAS volume is down. The replication will continue automatically when the file-system is started.
           --#ARGUMENTS    {1,2,3,4}
           --#SEVERITY     MAJOR
           --#TIMEINDEX    99
           --#STATE        OK
       ::= { fluidFSEventsReplication 72 } 
    
    
    fluidFSEventReplicationSourceFSIsNotOptimalDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The file-system of the source NAS volume is not optimal. The replication will continue automatically when the file-system recovers."
           --#TYPE         "Normal Event"
           --#SUMMARY      Replication between NAS volume %s@%s and NAS volume %s@%s failed   Description:  Replication between NAS volume %s@%s and NAS volume %s@%s failed because of the following reason: The file-system of the source NAS volume is not optimal. The replication will continue automatically when the file-system recovers.
           --#ARGUMENTS    {1,2,3,4}
           --#SEVERITY     MAJOR
           --#TIMEINDEX    99
           --#STATE        OK
       ::= { fluidFSEventsReplication 73 } 
    
    
    fluidFSEventReplicationDestinationFSIsNotOptimalDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The file-system of the destination NAS volume is not optimal. The replication will continue automatically when the file-system recovers."
           --#TYPE         "Normal Event"
           --#SUMMARY      Replication between NAS volume %s@%s and NAS volume %s@%s failed   Description:  Replication between NAS volume %s@%s and NAS volume %s@%s failed because of the following reason: The file-system of the destination NAS volume is not optimal. The replication will continue automatically when the file-system recovers.
           --#ARGUMENTS    {1,2,3,4}
           --#SEVERITY     MAJOR
           --#TIMEINDEX    99
           --#STATE        OK
       ::= { fluidFSEventsReplication 74 } 
    
    
    fluidFSEventReplicationDestinationFSIsDownDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The file system of destination NAS volume is down. The replication will continue automatically when the file-system is started."
           --#TYPE         "Normal Event"
           --#SUMMARY      Replication between NAS volume %s@%s and NAS volume %s@%s failed   Description:  Replication between NAS volume %s@%s and NAS volume %s@%s failed because of the following reason: The file system of destination NAS volume is down. The replication will continue automatically when the file-system is started.
           --#ARGUMENTS    {1,2,3,4}
           --#SEVERITY     MAJOR
           --#TIMEINDEX    99
           --#STATE        OK
       ::= { fluidFSEventsReplication 75 } 
    
    
    fluidFSEventReplicationConfigurationErrorDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The source and destination systems resources are not balanced. Please consider to add new applience to the destination system."
           --#TYPE         "Normal Event"
           --#SUMMARY      Replication between NAS volume %s@%s and NAS volume %s@%s failed   Description:  Replication between NAS volume %s@%s and NAS volume %s@%s failed because of the following reason: The source and destination systems resources are not balanced. Please consider to add new applience to the destination system.
           --#ARGUMENTS    {1,2,3,4}
           --#SEVERITY     MAJOR
           --#TIMEINDEX    99
           --#STATE        OK
       ::= { fluidFSEventsReplication 76 } 
    
    
    fluidFSEventReplicationDestinationVolumeIsDetachedDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The destination NAS volume disconnected from the source NAS volume, please perform the disconnect action also from the source NAS volume and if you would like reconnect the NAS volumes again."
           --#TYPE         "Normal Event"
           --#SUMMARY      Replication between NAS volume %s@%s and NAS volume %s@%s failed   Description:  Replication between NAS volume %s@%s and NAS volume %s@%s failed because of the following reason: The destination NAS volume disconnected from the source NAS volume, please perform the disconnect action also from the source NAS volume and if you would like reconnect the NAS volumes again.
           --#ARGUMENTS    {1,2,3,4}
           --#SEVERITY     MAJOR
           --#TIMEINDEX    99
           --#STATE        OK
       ::= { fluidFSEventsReplication 77 } 
    
    
    fluidFSEventReplicationDestinationClusterIsBusyDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: Temporarily the destination cluster is not available to serve the required replication."
           --#TYPE         "Normal Event"
           --#SUMMARY      Replication between NAS volume %s@%s and NAS volume %s@%s failed   Description:  Replication between NAS volume %s@%s and NAS volume %s@%s failed because of the following reason: Temporarily the destination cluster is not available to serve the required replication.
           --#ARGUMENTS    {1,2,3,4}
           --#SEVERITY     INFORMATIONAL
           --#TIMEINDEX    99
           --#STATE        OK
       ::= { fluidFSEventsReplication 78 } 
    
    
    fluidFSEventReplicationIncompatibleVersionsDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The system version of source NAS volume is higher than the system version of the destination system. Please upgrade the destination system to same version as source system."
           --#TYPE         "Normal Event"
           --#SUMMARY      Replication between NAS volume %s@%s and NAS volume %s@%s failed   Description:  Replication between NAS volume %s@%s and NAS volume %s@%s failed because of the following reason: The system version of source NAS volume is higher than the system version of the destination system. Please upgrade the destination system to same version as source system.
           --#ARGUMENTS    {1,2,3,4}
           --#SEVERITY     MAJOR
           --#TIMEINDEX    99
           --#STATE        OK
       ::= { fluidFSEventsReplication 79 } 
    
    
    fluidFSEventReplicationNotEnoughSpaceInDestinationDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: There is not enough space in the destination NAS volume, Please increase the destination NAS volume size."
           --#TYPE         "Normal Event"
           --#SUMMARY      Replication between NAS volume %s@%s and NAS volume %s@%s failed   Description:  Replication between NAS volume %s@%s and NAS volume %s@%s failed because of the following reason: There is not enough space in the destination NAS volume, Please increase the destination NAS volume size.
           --#ARGUMENTS    {1,2,3,4}
           --#SEVERITY     MAJOR
           --#TIMEINDEX    99
           --#STATE        OK
       ::= { fluidFSEventsReplication 80 } 
    
    
    fluidFSEventReplicationSourceVolumeBusyWithReclaimingDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between {{sourceVolume}}@{{sourceCluster}} and {{destinationVolumeName}}@{{destinationCluster}} experienced a temporary failure   Description:  Replication between NAS volume {{sourceVolume}}@{{sourceCluster}} and NAS volume {{destinationVolumeName}}@{{destinationCluster}} experienced a temporary failure because of the following reason: The source NAS volume is busy freeing space. The replication will continue automatically when space is available."
           --#TYPE         "Normal Event"
           --#SUMMARY      Replication between %s@%s and %s@%s experienced a temporary failure   Description:  Replication between NAS volume %s@%s and NAS volume %s@%s experienced a temporary failure because of the following reason: The source NAS volume is busy freeing space. The replication will continue automatically when space is available.
           --#ARGUMENTS    {1,2,3,4}
           --#SEVERITY     INFORMATIONAL
           --#TIMEINDEX    99
           --#STATE        OK
       ::= { fluidFSEventsReplication 81 } 
    
    
    fluidFSEventReplicationDestinationVolumeBusyWithReclaimingDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between {{sourceVolume}}@{{sourceCluster}} and {{destinationVolumeName}}@{{destinationCluster}} experienced a temporary failure   Description:  Replication between NAS volume {{sourceVolume}}@{{sourceCluster}} and NAS volume {{destinationVolumeName}}@{{destinationCluster}} experienced a temporary failure because of the following reason: The destination NAS volume is busy freeing space. The replication will continue automatically when space is available."
           --#TYPE         "Normal Event"
           --#SUMMARY      Replication between %s@%s and %s@%s experienced a temporary failure   Description:  Replication between NAS volume %s@%s and NAS volume %s@%s experienced a temporary failure because of the following reason: The destination NAS volume is busy freeing space. The replication will continue automatically when space is available.
           --#ARGUMENTS    {1,2,3,4}
           --#SEVERITY     INFORMATIONAL
           --#TIMEINDEX    99
           --#STATE        OK
       ::= { fluidFSEventsReplication 82 } 
    
    
    fluidFSEventReplicationSourceFSIsBusyDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The file-system of the source NAS volume is busy with replication of other NAS volumes. The replication will continue automatically when the file-system releases part of the resources ."
           --#TYPE         "Normal Event"
           --#SUMMARY      Replication between NAS volume %s@%s and NAS volume %s@%s failed   Description:  Replication between NAS volume %s@%s and NAS volume %s@%s failed because of the following reason: The file-system of the source NAS volume is busy with replication of other NAS volumes. The replication will continue automatically when the file-system releases part of the resources .
           --#ARGUMENTS    {1,2,3,4}
           --#SEVERITY     INFORMATIONAL
           --#TIMEINDEX    99
           --#STATE        OK
       ::= { fluidFSEventsReplication 83 } 
    
    
    fluidFSEventReplicationDestinationFSIsBusyDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The file-system of the destination NAS volume does not have enough resources to proceed with replication of other NAS volumes. The replication will continue automatically when the file-system releases part of the resources."
           --#TYPE         "Normal Event"
           --#SUMMARY      Replication between NAS volume %s@%s and NAS volume %s@%s failed   Description:  Replication between NAS volume %s@%s and NAS volume %s@%s failed because of the following reason: The file-system of the destination NAS volume does not have enough resources to proceed with replication of other NAS volumes. The replication will continue automatically when the file-system releases part of the resources.
           --#ARGUMENTS    {1,2,3,4}
           --#SEVERITY     INFORMATIONAL
           --#TIMEINDEX    99
           --#STATE        OK
       ::= { fluidFSEventsReplication 84 } 
    
    
    fluidFSEventReplicationJumboFramesBlockedDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: Jumbo frames are blocked over the network."
           --#TYPE         "Normal Event"
           --#SUMMARY      Replication between NAS volume %s@%s and NAS volume %s@%s failed   Description:  Replication between NAS volume %s@%s and NAS volume %s@%s failed because of the following reason: Jumbo frames are blocked over the network.
           --#ARGUMENTS    {1,2,3,4}
           --#SEVERITY     MAJOR
           --#TIMEINDEX    99
           --#STATE        OK
       ::= { fluidFSEventsReplication 85 } 
    
    
    fluidFSEventReplicationRecoveredReplicationDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} finished.   Description:  Replication between NAS volume {{sourceVolume}}@{{sourceCluster}} and NAS volume {{destinationVolumeName}}@{{destinationCluster}} successfully recovered from the problem and finished."
           --#TYPE         "Normal Event"
           --#SUMMARY      Replication between NAS volume %s@%s and NAS volume %s@%s finished.   Description:  Replication between NAS volume %s@%s and NAS volume %s@%s successfully recovered from the problem and finished.
           --#ARGUMENTS    {1,2,3,4}
           --#SEVERITY     INFORMATIONAL
           --#TIMEINDEX    99
           --#STATE        OK
       ::= { fluidFSEventsReplication 86 } 
    
    
    fluidFSEventReplicationDestinationVolumeShrinkDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} succeeded   Description:  Replication between NAS volume {{sourceVolume}}@{{sourceCluster}} and NAS volume {{destinationVolumeName}}@{{destinationCluster}} succeeded but resizing of the desination volume failed."
           --#TYPE         "Normal Event"
           --#SUMMARY      Replication between NAS volume %s@%s and NAS volume %s@%s succeeded   Description:  Replication between NAS volume %s@%s and NAS volume %s@%s succeeded but resizing of the desination volume failed.
           --#ARGUMENTS    {1,2,3,4}
           --#SEVERITY     INFORMATIONAL
           --#TIMEINDEX    99
           --#STATE        OK
       ::= { fluidFSEventsReplication 87 } 
    
    
    fluidFSEventReplicationDestinationVolumeIsDisabledDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: The replication policy status on the destination volume is currently promoted, please perform the promote action also from the source NAS volume, and demote allow replication."
           --#TYPE         "Normal Event"
           --#SUMMARY      Replication between NAS volume %s@%s and NAS volume %s@%s failed   Description:  Replication between NAS volume %s@%s and NAS volume %s@%s failed because of the following reason: The replication policy status on the destination volume is currently promoted, please perform the promote action also from the source NAS volume, and demote allow replication.
           --#ARGUMENTS    {1,2,3,4}
           --#SEVERITY     MAJOR
           --#TIMEINDEX    99
           --#STATE        OK
       ::= { fluidFSEventsReplication 88 } 
    
    
    fluidFSEventReplicationDestinationVolumeDedupParamsDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Optimization policy configuration is not updated   Description:  As part of replication between NAS volume {{sourceVolume}}@{{sourceCluster}} and NAS volume {{destinationVolumeName}}@{{destinationCluster}} the optimization policy configuration has failed to update."
           --#TYPE         "Normal Event"
           --#SUMMARY      Optimization policy configuration is not updated   Description:  As part of replication between NAS volume %s@%s and NAS volume %s@%s the optimization policy configuration has failed to update.
           --#ARGUMENTS    {1,2,3,4}
           --#SEVERITY     MAJOR
           --#TIMEINDEX    99
           --#STATE        OK
       ::= { fluidFSEventsReplication 89 } 
    
    
    fluidFSEventReplicationRollbackSnapCloneBaseDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed   Description:  Replication between NAS volume {{sourceVolume}}@{{sourceCluster}} and NAS volume {{destinationVolumeName}}@{{destinationCluster}} failed because of the following reason: rollback snapshot failed due to clone snapshot base."
           --#TYPE         "Normal Event"
           --#SUMMARY      Replication between NAS volume %s@%s and NAS volume %s@%s failed   Description:  Replication between NAS volume %s@%s and NAS volume %s@%s failed because of the following reason: rollback snapshot failed due to clone snapshot base.
           --#ARGUMENTS    {1,2,3,4}
           --#SEVERITY     MAJOR
           --#TIMEINDEX    99
           --#STATE        OK
       ::= { fluidFSEventsReplication 90 } 
    
    
    fluidFSEventReplicationReplicationFinishedDestination NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationStartTime, fluidFSEventsParamsReplicationEndTime, fluidFSEventsParamsReplicationTotalTransferredSize }
       STATUS current
       DESCRIPTION
           "Replication between NAS volume {{sourceVolume}}@{{sourceCluster}} and NAS volume {{destinationVolumeName}}@{{destinationCluster}} finished.   Description:  Replication between NAS volume {{sourceVolume}}@{{sourceCluster}} and NAS volume {{destinationVolumeName}}@{{destinationCluster}} which start at {{startTime}} has transferred {{totalTransferredSize}} MB of data and finished successfully at {{endTime}}. "
           --#TYPE         "Normal Event"
           --#SUMMARY      Replication between NAS volume %s@%s and NAS volume %s@%s finished.   Description:  Replication between NAS volume %s@%s and NAS volume %s@%s which start at %s has transferred %s MB of data and finished successfully at %s. 
           --#ARGUMENTS    {1,2,3,4,5,6,7}
           --#SEVERITY     INFORMATIONAL
           --#TIMEINDEX    99
           --#STATE        OK
       ::= { fluidFSEventsReplication 91 } 
    
    
    fluidFSEventReplicationNotEnoughSpaceInDestinationRehydSrcVolSize NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationRehydratedVolumeSize }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: There is not enough space in the destination NAS volume. Please increase the destination NAS volume size to be at least {{rehydratedVolumeSize}} MBs."
           --#TYPE         "Normal Event"
           --#SUMMARY      Replication between NAS volume %s@%s and NAS volume %s@%s failed.   Description:  Replication between NAS volume %s@%s and NAS volume %s@%s failed because of the following reason: There is not enough space in the destination NAS volume. Please increase the destination NAS volume size to be at least %s MBs.
           --#ARGUMENTS    {1,2,3,4,5}
           --#SEVERITY     MAJOR
           --#TIMEINDEX    99
           --#STATE        OK
       ::= { fluidFSEventsReplication 92 } 
    
    
    fluidFSEventReplicationReplicationFinishedInDomain NOTIFICATION-TYPE
       OBJECTS { sysName, fluidFSEventsParamsReplicationSourceVolume, fluidFSEventsParamsReplicationDestinationVolume, fluidFSEventsParamsReplicationDestinationCluster, fluidFSEventsParamsReplicationDomainId, fluidFSEventsParamsReplicationSnapshotId, fluidFSEventsParamsReplicationDomainReplicationStats }
       STATUS current
       DESCRIPTION
           "Replication {{sourceVolumeName}}, {{destinationVolume}}@{{destinationCluster}} finished in domain {{domainId}} s-{{snapshotId}}.   Description:  Replication {{sourceVolumeName}}, {{destinationVolume}}@{{destinationCluster}} finished in domain {{domainId}} s-{{snapshotId}}. {{domainReplicationStats}} "
           --#TYPE         "Normal Event"
           --#SUMMARY      Replication %s, %s@%s finished in domain %s s-%s.   Description:  Replication %s, %s@%s finished in domain %s s-%s. %s 
           --#ARGUMENTS    {1,2,3,4,5,6}
           --#SEVERITY     INFORMATIONAL
           --#TIMEINDEX    99
           --#STATE        OK
       ::= { fluidFSEventsReplication 93 } 
    
    
    fluidFSEventReplicationDestinationVolumeIsReplicating NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolumeName}}@{{sourceCluster}} and NAS volume {{destinationVolume}}@{{destinationCluster}} failed.   Description:  Replication between NAS volume {{sourceVolumeName}}@{{sourceCluster}} and NAS volume {{destinationVolume}}@{{destinationCluster}} failed because of the following reason: The destination NAS volume is in the middle of replicating to another NAS volume. Please temporarily disable the outgoing replications from the destination NAS volume."
           --#TYPE         "Normal Event"
           --#SUMMARY      Replication between NAS volume %s@%s and NAS volume %s@%s failed.   Description:  Replication between NAS volume %s@%s and NAS volume %s@%s failed because of the following reason: The destination NAS volume is in the middle of replicating to another NAS volume. Please temporarily disable the outgoing replications from the destination NAS volume.
           --#ARGUMENTS    {1,2,3,4}
           --#SEVERITY     INFORMATIONAL
           --#TIMEINDEX    99
           --#STATE        OK
       ::= { fluidFSEventsReplication 94 } 
    
    
    fluidFSEventReplicationDestinationVolumeIsReplicatingDestination NOTIFICATION-TYPE
       OBJECTS { sysName, fluidFSEventsParamsReplicationSourceVolume, fluidFSEventsParamsReplicationSourceCluster, fluidFSEventsParamsReplicationDestinationVolume, fluidFSEventsParamsReplicationDestinationCluster }
       STATUS current
       DESCRIPTION
           "Replication between NAS volume {{sourceVolume}}@{{sourceCluster}} and NAS volume {{destinationVolumeName}}@{{destinationCluster}} failed.   Description:  Replication between NAS volume {{sourceVolume}}@{{sourceCluster}} and NAS volume {{destinationVolumeName}}@{{destinationCluster}} failed because of the following reason: The destination NAS volume is in the middle of replicating to another NAS volume. Please temporarily disable the outgoing replications from the destination NAS volume."
           --#TYPE         "Normal Event"
           --#SUMMARY      Replication between NAS volume %s@%s and NAS volume %s@%s failed.   Description:  Replication between NAS volume %s@%s and NAS volume %s@%s failed because of the following reason: The destination NAS volume is in the middle of replicating to another NAS volume. Please temporarily disable the outgoing replications from the destination NAS volume.
           --#ARGUMENTS    {1,2,3,4}
           --#SEVERITY     INFORMATIONAL
           --#TIMEINDEX    99
           --#STATE        OK
       ::= { fluidFSEventsReplication 95 } 
    
    
    fluidFSEventReplicationReplicationFinishedWithCompression NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationStartTime, fluidFSEventsParamsReplicationEndTime, fluidFSEventsParamsReplicationTotalTransferredSize, fluidFSEventsParamsReplicationSavingsPercent }
       STATUS current
       DESCRIPTION
           "Replication between NAS volume {{sourceVolumeName}}@{{sourceCluster}} and NAS volume {{destinationVolume}}@{{destinationCluster}} finished.   Description:  Replication between NAS volume {{sourceVolumeName}}@{{sourceCluster}} and NAS volume {{destinationVolume}}@{{destinationCluster}} which start at {{startTime}} has transferred {{totalTransferredSize}} MB of data with {{savingsPercent}}% savings due to data reduction and finished successfully at {{endTime}}. "
           --#TYPE         "Normal Event"
           --#SUMMARY      Replication between NAS volume %s@%s and NAS volume %s@%s finished.   Description:  Replication between NAS volume %s@%s and NAS volume %s@%s which start at %s has transferred %s MB of data with %s% savings due to data reduction and finished successfully at %s. 
           --#ARGUMENTS    {1,2,3,4,5,6,7,8}
           --#SEVERITY     INFORMATIONAL
           --#TIMEINDEX    99
           --#STATE        OK
       ::= { fluidFSEventsReplication 96 } 
    
    
    fluidFSEventReplicationReplicationFinishedWithCompressionDestination NOTIFICATION-TYPE
       OBJECTS { sysName, fluidFSEventsParamsReplicationSourceVolume, fluidFSEventsParamsReplicationSourceCluster, fluidFSEventsParamsReplicationDestinationVolume, fluidFSEventsParamsReplicationDestinationCluster, fluidFSEventsParamsReplicationStartTime, fluidFSEventsParamsReplicationEndTime, fluidFSEventsParamsReplicationTotalTransferredSize, fluidFSEventsParamsReplicationSavingsPercent }
       STATUS current
       DESCRIPTION
           "Replication between NAS volume {{sourceVolume}}@{{sourceCluster}} and NAS volume {{destinationVolumeName}}@{{destinationCluster}} finished.   Description:  Replication between NAS volume {{sourceVolume}}@{{sourceCluster}} and NAS volume {{destinationVolumeName}}@{{destinationCluster}} which start at {{startTime}} has transferred {{totalTransferredSize}} MB of data with {{savingsPercent}}% savings due to data reduction and finished successfully at {{endTime}}. "
           --#TYPE         "Normal Event"
           --#SUMMARY      Replication between NAS volume %s@%s and NAS volume %s@%s finished.   Description:  Replication between NAS volume %s@%s and NAS volume %s@%s which start at %s has transferred %s MB of data with %s% savings due to data reduction and finished successfully at %s. 
           --#ARGUMENTS    {1,2,3,4,5,6,7,8}
           --#SEVERITY     INFORMATIONAL
           --#TIMEINDEX    99
           --#STATE        OK
       ::= { fluidFSEventsReplication 97 } 
    
    
    fluidFSEventsParamsSnapshot OBJECT IDENTIFIER ::= { fluidFSEventsParams 7 } 
    
    
    fluidFSEventsSnapshot OBJECT IDENTIFIER ::= { fluidFSEvents 7 } 
    
    
    fluidFSEventsParamsSnapshotSnapshotName OBJECT-TYPE
       SYNTAX  DisplayString
       MAX-ACCESS  read-only
       STATUS  current
       DESCRIPTION
           "Snapshot name"
       ::= { fluidFSEventsParamsSnapshot 1 }
    
    
    fluidFSEventsParamsSnapshotVolumeName OBJECT-TYPE
       SYNTAX  DisplayString
       MAX-ACCESS  read-only
       STATUS  current
       DESCRIPTION
           "Volume name"
       ::= { fluidFSEventsParamsSnapshot 2 }
    
    
    fluidFSEventsParamsSnapshotFSID OBJECT-TYPE
       SYNTAX  INTEGER
       MAX-ACCESS  read-only
       STATUS  current
       DESCRIPTION
           "NAS volume id"
       ::= { fluidFSEventsParamsSnapshot 3 }
    
    
    fluidFSEventsParamsSnapshotOutputFileName OBJECT-TYPE
       SYNTAX  DisplayString
       MAX-ACCESS  read-only
       STATUS  current
       DESCRIPTION
           ""
       ::= { fluidFSEventsParamsSnapshot 4 }
    
    
    fluidFSEventsParamsSnapshotOutputFSID OBJECT-TYPE
       SYNTAX  INTEGER
       MAX-ACCESS  read-only
       STATUS  current
       DESCRIPTION
           ""
       ::= { fluidFSEventsParamsSnapshot 5 }
    
    
    fluidFSEventsParamsSnapshotOutputPath OBJECT-TYPE
       SYNTAX  DisplayString
       MAX-ACCESS  read-only
       STATUS  current
       DESCRIPTION
           ""
       ::= { fluidFSEventsParamsSnapshot 6 }
    
    
    fluidFSEventsParamsSnapshotFSIDName OBJECT-TYPE
       SYNTAX  DisplayString
       MAX-ACCESS  read-only
       STATUS  current
       DESCRIPTION
           ""
       ::= { fluidFSEventsParamsSnapshot 7 }
    
    
    fluidFSEventsParamsSnapshotOutputFSIDName OBJECT-TYPE
       SYNTAX  DisplayString
       MAX-ACCESS  read-only
       STATUS  current
       DESCRIPTION
           ""
       ::= { fluidFSEventsParamsSnapshot 8 }
    
    
    fluidFSEventSnapshotFailedCreateSnapshot NOTIFICATION-TYPE
       OBJECTS { sysName, fluidFSEventsParamsSnapshotSnapshotName, fluidFSEventsParamsSnapshotVolumeName }
       STATUS current
       DESCRIPTION
           "The snapshot scheduler failed to create {{snapshotName}} snapshot in volume {{volumeName}}."
           --#TYPE         "Normal Event"
           --#SUMMARY      The snapshot scheduler failed to create %s snapshot in volume %s.
           --#ARGUMENTS    {1,2}
           --#SEVERITY     MAJOR
           --#TIMEINDEX    99
           --#STATE        OK
       ::= { fluidFSEventsSnapshot 1 } 
    
    
    fluidFSEventSnapshotFailedDeleteSnapshot NOTIFICATION-TYPE
       OBJECTS { sysName, fluidFSEventsParamsSnapshotVolumeName }
       STATUS current
       DESCRIPTION
           "The snapshot scheduler failed to delete snapshots in volume {{volumeName}}."
           --#TYPE         "Normal Event"
           --#SUMMARY      The snapshot scheduler failed to delete snapshots in volume %s.
           --#ARGUMENTS    {1}
           --#SEVERITY     MAJOR
           --#TIMEINDEX    99
           --#STATE        OK
       ::= { fluidFSEventsSnapshot 2 } 
    
    
    fluidFSEventSnapshotScheduleDeleteSnapshotBySpace NOTIFICATION-TYPE
       OBJECTS { sysName, fluidFSEventsParamsSnapshotSnapshotName, fluidFSEventsParamsSnapshotVolumeName }
       STATUS current
       DESCRIPTION
           "The snapshot named {{snapshotName}} on {{volumeName}} NAS volume was scheduled for deletion by snapshots space auto-deletion mechanism."
           --#TYPE         "Normal Event"
           --#SUMMARY      The snapshot named %s on %s NAS volume was scheduled for deletion by snapshots space auto-deletion mechanism.
           --#ARGUMENTS    {1,2}
           --#SEVERITY     INFORMATIONAL
           --#TIMEINDEX    99
           --#STATE        OK
       ::= { fluidFSEventsSnapshot 3 } 
    
    
    fluidFSEventSnapshotFailedToInitVMSnapshotsCreation NOTIFICATION-TYPE
       OBJECTS { sysName, fluidFSEventsParamsSnapshotSnapshotName, fluidFSEventsParamsSnapshotFSID }
       STATUS current
       DESCRIPTION
           "Failed initializing the VM snapshot(s) creation   Description:  Failed to initiate VM snapshot(s) creation on VMWare server(s), thus {{snapshotName}} snapshot of {{FSIDName}} NAS volume will not be consistent from VMWare perspective   Action Items:  Please check network availability and current load on related VMWare server(s)   Internal Information:  One (or more) VMWare servers may be unavailable or responds with errors to FluidFS requests"
           --#TYPE         "Normal Event"
           --#SUMMARY      Failed initializing the VM snapshot(s) creation   Description:  Failed to initiate VM snapshot(s) creation on VMWare server(s), thus %s snapshot of %s NAS volume will not be consistent from VMWare perspective   Action Items:  Please check network availability and current load on related VMWare server(s)   Internal Information:  One (or more) VMWare servers may be unavailable or responds with errors to FluidFS requests
           --#ARGUMENTS    {1,2}
           --#SEVERITY     MAJOR
           --#TIMEINDEX    99
           --#STATE        OK
       ::= { fluidFSEventsSnapshot 8 } 
    
    
    fluidFSEventSnapshotFailedToPerformVMSnapshotsCreation NOTIFICATION-TYPE
       OBJECTS { sysName, fluidFSEventsParamsSnapshotSnapshotName, fluidFSEventsParamsSnapshotFSID }
       STATUS current
       DESCRIPTION
           "Failed to create VM snapshot(s) on VMWare server(s)   Description:  Failed to create VM snapshot(s), thus {{snapshotName}} snapshot of {{FSIDName}} NAS volume will not be consistent from VMWare perspective   Action Items:  Please check network availability and current load on related VMWare server(s)   Internal Information:  One (or more) VMWare servers may be unavailable or responds with errors to FluidFS requests"
           --#TYPE         "Normal Event"
           --#SUMMARY      Failed to create VM snapshot(s) on VMWare server(s)   Description:  Failed to create VM snapshot(s), thus %s snapshot of %s NAS volume will not be consistent from VMWare perspective   Action Items:  Please check network availability and current load on related VMWare server(s)   Internal Information:  One (or more) VMWare servers may be unavailable or responds with errors to FluidFS requests
           --#ARGUMENTS    {1,2}
           --#SEVERITY     MAJOR
           --#TIMEINDEX    99
           --#STATE        OK
       ::= { fluidFSEventsSnapshot 9 } 
    
    
    fluidFSEventSnapshotFailedToPerformVMSnapshotsCleanup NOTIFICATION-TYPE
       OBJECTS { sysName, fluidFSEventsParamsSnapshotSnapshotName, fluidFSEventsParamsSnapshotFSID }
       STATUS current
       DESCRIPTION
           "Failed removing the VM snapshot(s), created by FluidFS   Description:  Failed to perform a cleanup of VM snapshot(s), previously created by FluidFS on VMWare server(s) during {{snapshotName}} snapshot of {{FSIDName}} NAS volume creation   Action Items:  Please check network availability and current load on related VMWare server(s). Try to delete the redundant VM snapshot(s) manually in the vSphere user interface   Internal Information:  One (or more) VMWare servers may be unavailable or responds with errors to FluidFS requests"
           --#TYPE         "Normal Event"
           --#SUMMARY      Failed removing the VM snapshot(s), created by FluidFS   Description:  Failed to perform a cleanup of VM snapshot(s), previously created by FluidFS on VMWare server(s) during %s snapshot of %s NAS volume creation   Action Items:  Please check network availability and current load on related VMWare server(s). Try to delete the redundant VM snapshot(s) manually in the vSphere user interface   Internal Information:  One (or more) VMWare servers may be unavailable or responds with errors to FluidFS requests
           --#ARGUMENTS    {1,2}
           --#SEVERITY     INFORMATIONAL
           --#TIMEINDEX    99
           --#STATE        OK
       ::= { fluidFSEventsSnapshot 10 } 
    
    
    fluidFSEventSnapshotSnapshotIsNotVMConsistent NOTIFICATION-TYPE
       OBJECTS { sysName, fluidFSEventsParamsSnapshotSnapshotName, fluidFSEventsParamsSnapshotFSID }
       STATUS current
       DESCRIPTION
           "The {{snapshotName}} snapshot is not consistent from VMWare perspective   Description:  NAS volume {{FSIDName}} had been restored to the {{snapshotName}} snapshot recovery point, which is not consistent from VMWare perspective   Action Items:  In case {{FSIDName}} NAS volume indeed serves as VMWare Datastore, please try to restore the volume to a consistent snapshot recovery point"
           --#TYPE         "Normal Event"
           --#SUMMARY      The %s snapshot is not consistent from VMWare perspective   Description:  NAS volume %s had been restored to the %s snapshot recovery point, which is not consistent from VMWare perspective   Action Items:  In case %s NAS volume indeed serves as VMWare Datastore, please try to restore the volume to a consistent snapshot recovery point
           --#ARGUMENTS    {1,2}
           --#SEVERITY     INFORMATIONAL
           --#TIMEINDEX    99
           --#STATE        OK
       ::= { fluidFSEventsSnapshot 11 } 
    
    
    fluidFSEventSnapshotSnapshotDeltaFailed NOTIFICATION-TYPE
       OBJECTS { sysName, fluidFSEventsParamsSnapshotFSID }
       STATUS current
       DESCRIPTION
           "Snapshot delta process on volume {{FSIDName}}  failed   Description:  NAS volume {{FSIDName}} did not finish properly and therefore aborted   Action Items:  Please restart the process"
           --#TYPE         "Normal Event"
           --#SUMMARY      Snapshot delta process on volume %s  failed   Description:  NAS volume %s did not finish properly and therefore aborted   Action Items:  Please restart the process
           --#ARGUMENTS    {1}
           --#SEVERITY     INFORMATIONAL
           --#TIMEINDEX    99
           --#STATE        OK
       ::= { fluidFSEventsSnapshot 12 } 
    
    
    fluidFSEventSnapshotSnapshotDeltaSucceded NOTIFICATION-TYPE
       OBJECTS { sysName, fluidFSEventsParamsSnapshotFSID, fluidFSEventsParamsSnapshotOutputFileName, fluidFSEventsParamsSnapshotOutputFSID, fluidFSEventsParamsSnapshotOutputPath }
       STATUS current
       DESCRIPTION
           "Snapshot delta process on volume {{FSIDName}}  succeded   Description:  NAS volume {{FSIDName}} has finished properly and file {{outputFileName}} was created in path {{outputPath}} on volume {{outputFSIDName}}   Action Items:  file {{outputFileName}} was created in path {{outputPath}} on volume {{outputFSIDName}} and is available now for reading"
           --#TYPE         "Normal Event"
           --#SUMMARY      Snapshot delta process on volume %s  succeded   Description:  NAS volume %s has finished properly and file %s was created in path %s on volume %s   Action Items:  file %s was created in path %s on volume %s and is available now for reading
           --#ARGUMENTS    {1,2,3,4}
           --#SEVERITY     INFORMATIONAL
           --#TIMEINDEX    99
           --#STATE        OK
       ::= { fluidFSEventsSnapshot 13 } 
    
    
    fluidFSEventSnapshotSnapshotDeltaStarted NOTIFICATION-TYPE
       OBJECTS { sysName, fluidFSEventsParamsSnapshotFSID, fluidFSEventsParamsSnapshotOutputFileName, fluidFSEventsParamsSnapshotOutputFSID, fluidFSEventsParamsSnapshotOutputPath }
       STATUS current
       DESCRIPTION
           "Snapshot delta process on volume {{FSIDName}}  started   Description:  NAS volume {{FSIDName}} has started with output file {{outputFileName}} in path {{outputPath}} on volume {{outputFSIDName}}   Action Items:  file {{outputFileName}} will be created in path {{outputPath}} on volume {{outputFSIDName}} "
           --#TYPE         "Normal Event"
           --#SUMMARY      Snapshot delta process on volume %s  started   Description:  NAS volume %s has started with output file %s in path %s on volume %s   Action Items:  file %s will be created in path %s on volume %s 
           --#ARGUMENTS    {1,2,3,4}
           --#SEVERITY     INFORMATIONAL
           --#TIMEINDEX    99
           --#STATE        OK
       ::= { fluidFSEventsSnapshot 14 } 
    
    
    fluidFSEventsParamsHealth OBJECT IDENTIFIER ::= { fluidFSEventsParams 9 } 
    
    
    fluidFSEventsHealth OBJECT IDENTIFIER ::= { fluidFSEvents 9 } 
    
    
    fluidFSEventsParamsHealthPercentOfUsedSpace OBJECT-TYPE
       SYNTAX  DisplayString
       MAX-ACCESS  read-only
       STATUS  current
       DESCRIPTION
           "Percentage of system used space"
       ::= { fluidFSEventsParamsHealth 1 }
    
    
    fluidFSEventsParamsHealthNodeName OBJECT-TYPE
       SYNTAX  DisplayString
       MAX-ACCESS  read-only
       STATUS  current
       DESCRIPTION
           "Node name"
       ::= { fluidFSEventsParamsHealth 2 }
    
    
    fluidFSEventsParamsHealthService OBJECT-TYPE
       SYNTAX  DisplayString
       MAX-ACCESS  read-only
       STATUS  current
       DESCRIPTION
           "Service name"
       ::= { fluidFSEventsParamsHealth 3 }
    
    
    fluidFSEventsParamsHealthPartitionName OBJECT-TYPE
       SYNTAX  DisplayString
       MAX-ACCESS  read-only
       STATUS  current
       DESCRIPTION
           "Local partition name"
       ::= { fluidFSEventsParamsHealth 4 }
    
    
    fluidFSEventsParamsHealthPercentOfUsedSwap OBJECT-TYPE
       SYNTAX  INTEGER
       MAX-ACCESS  read-only
       STATUS  current
       DESCRIPTION
           "Percent of used swap memory"
       ::= { fluidFSEventsParamsHealth 5 }
    
    
    fluidFSEventsParamsHealthNodeIds OBJECT-TYPE
       SYNTAX  DisplayString
       MAX-ACCESS  read-only
       STATUS  current
       DESCRIPTION
           ""
       ::= { fluidFSEventsParamsHealth 6 }
    
    
    fluidFSEventsParamsHealthPercentOfUsedFileDescriptors OBJECT-TYPE
       SYNTAX  INTEGER
       MAX-ACCESS  read-only
       STATUS  current
       DESCRIPTION
           "Percent of used file descriptors"
       ::= { fluidFSEventsParamsHealth 7 }
    
    
    fluidFSEventsParamsHealthThisNodeId OBJECT-TYPE
       SYNTAX  DisplayString
       MAX-ACCESS  read-only
       STATUS  current
       DESCRIPTION
           "Node id of the current node"
       ::= { fluidFSEventsParamsHealth 8 }
    
    
    fluidFSEventsParamsHealthPeerNodeId OBJECT-TYPE
       SYNTAX  DisplayString
       MAX-ACCESS  read-only
       STATUS  current
       DESCRIPTION
           "Node id of the peer node"
       ::= { fluidFSEventsParamsHealth 9 }
    
    
    fluidFSEventsParamsHealthVirtualVolume OBJECT-TYPE
       SYNTAX  DisplayString
       MAX-ACCESS  read-only
       STATUS  current
       DESCRIPTION
           "NAS volume name"
       ::= { fluidFSEventsParamsHealth 10 }
    
    
    fluidFSEventsParamsHealthFSID OBJECT-TYPE
       SYNTAX  INTEGER
       MAX-ACCESS  read-only
       STATUS  current
       DESCRIPTION
           "NAS volume id"
       ::= { fluidFSEventsParamsHealth 11 }
    
    
    fluidFSEventsParamsHealthMinFreeSpaceInBytes OBJECT-TYPE
       SYNTAX  INTEGER
       MAX-ACCESS  read-only
       STATUS  current
       DESCRIPTION
           "Free space in bytes"
       ::= { fluidFSEventsParamsHealth 12 }
    
    
    fluidFSEventsParamsHealthModuleName OBJECT-TYPE
       SYNTAX  DisplayString
       MAX-ACCESS  read-only
       STATUS  current
       DESCRIPTION
           "The BMR module name"
       ::= { fluidFSEventsParamsHealth 13 }
    
    
    fluidFSEventsParamsHealthNumberOfClients OBJECT-TYPE
       SYNTAX  INTEGER
       MAX-ACCESS  read-only
       STATUS  current
       DESCRIPTION
           "Number of clients"
       ::= { fluidFSEventsParamsHealth 14 }
    
    
    fluidFSEventsParamsHealthDomainId OBJECT-TYPE
       SYNTAX  INTEGER
       MAX-ACCESS  read-only
       STATUS  current
       DESCRIPTION
           "Id of the domain from which the event was raised"
       ::= { fluidFSEventsParamsHealth 15 }
    
    
    fluidFSEventsParamsHealthServiceName OBJECT-TYPE
       SYNTAX  DisplayString
       MAX-ACCESS  read-only
       STATUS  current
       DESCRIPTION
           "The name of the service"
       ::= { fluidFSEventsParamsHealth 16 }
    
    
    fluidFSEventsParamsHealthSynchronizedServiceName OBJECT-TYPE
       SYNTAX  DisplayString
       MAX-ACCESS  read-only
       STATUS  current
       DESCRIPTION
           "The name of the service being synchronized"
       ::= { fluidFSEventsParamsHealth 17 }
    
    
    fluidFSEventsParamsHealthTimeout OBJECT-TYPE
       SYNTAX  INTEGER
       MAX-ACCESS  read-only
       STATUS  current
       DESCRIPTION
           "The timeout in minutes"
       ::= { fluidFSEventsParamsHealth 18 }
    
    
    fluidFSEventsParamsHealthStorageId OBJECT-TYPE
       SYNTAX  INTEGER
       MAX-ACCESS  read-only
       STATUS  current
       DESCRIPTION
           "Internal id of a storage"
       ::= { fluidFSEventsParamsHealth 19 }
    
    
    fluidFSEventsParamsHealthSynchronizedStorageId OBJECT-TYPE
       SYNTAX  INTEGER
       MAX-ACCESS  read-only
       STATUS  current
       DESCRIPTION
           "Internal id of a storage being synchronized"
       ::= { fluidFSEventsParamsHealth 20 }
    
    
    fluidFSEventsParamsHealthNodeId OBJECT-TYPE
       SYNTAX  INTEGER
       MAX-ACCESS  read-only
       STATUS  current
       DESCRIPTION
           "Id of a node"
       ::= { fluidFSEventsParamsHealth 21 }
    
    
    fluidFSEventsParamsHealthSetId OBJECT-TYPE
       SYNTAX  INTEGER
       MAX-ACCESS  read-only
       STATUS  current
       DESCRIPTION
           "Id of a LUNs' set"
       ::= { fluidFSEventsParamsHealth 22 }
    
    
    fluidFSEventsParamsHealthLunId OBJECT-TYPE
       SYNTAX  INTEGER
       MAX-ACCESS  read-only
       STATUS  current
       DESCRIPTION
           "Id of a LUN"
       ::= { fluidFSEventsParamsHealth 23 }
    
    
    fluidFSEventsParamsHealthHealthyNodeId OBJECT-TYPE
       SYNTAX  DisplayString
       MAX-ACCESS  read-only
       STATUS  current
       DESCRIPTION
           "Healthy NAS controller id"
       ::= { fluidFSEventsParamsHealth 24 }
    
    
    fluidFSEventsParamsHealthFaultyNodeId OBJECT-TYPE
       SYNTAX  DisplayString
       MAX-ACCESS  read-only
       STATUS  current
       DESCRIPTION
           "Faulty NAS controller id"
       ::= { fluidFSEventsParamsHealth 25 }
    
    
    fluidFSEventsParamsHealthFmsAdminCmd OBJECT-TYPE
       SYNTAX  DisplayString
       MAX-ACCESS  read-only
       STATUS  current
       DESCRIPTION
           "FMS Admin command"
       ::= { fluidFSEventsParamsHealth 26 }
    
    
    fluidFSEventsParamsHealthQuorumIP OBJECT-TYPE
       SYNTAX  DisplayString
       MAX-ACCESS  read-only
       STATUS  current
       DESCRIPTION
           "FMS Quorum IP"
       ::= { fluidFSEventsParamsHealth 27 }
    
    
    fluidFSEventsParamsHealthFmsState OBJECT-TYPE
       SYNTAX  DisplayString
       MAX-ACCESS  read-only
       STATUS  current
       DESCRIPTION
           "FMS NAS controller State"
       ::= { fluidFSEventsParamsHealth 28 }
    
    
    fluidFSEventsParamsHealthFsdInstance OBJECT-TYPE
       SYNTAX  INTEGER
       MAX-ACCESS  read-only
       STATUS  current
       DESCRIPTION
           "FS Daemon instance in the node"
       ::= { fluidFSEventsParamsHealth 29 }
    
    
    fluidFSEventsParamsHealthErrorDescription OBJECT-TYPE
       SYNTAX  DisplayString
       MAX-ACCESS  read-only
       STATUS  current
       DESCRIPTION
           "Description of the error"
       ::= { fluidFSEventsParamsHealth 30 }
    
    
    fluidFSEventsParamsHealthBacktrace OBJECT-TYPE
       SYNTAX  DisplayString
       MAX-ACCESS  read-only
       STATUS  current
       DESCRIPTION
           "Debug backtrace information"
       ::= { fluidFSEventsParamsHealth 31 }
    
    
    fluidFSEventsParamsHealthDsid OBJECT-TYPE
       SYNTAX  DisplayString
       MAX-ACCESS  read-only
       STATUS  current
       DESCRIPTION
           "DSID (internal filesystem ID) of file or directory. Use dsid2name utility to translate dsid to path via command line, also dsid2path translator is designed to do it automatically for events"
       ::= { fluidFSEventsParamsHealth 32 }
    
    
    fluidFSEventsParamsHealthFileMapping OBJECT-TYPE
       SYNTAX  DisplayString
       MAX-ACCESS  read-only
       STATUS  current
       DESCRIPTION
           "FS mapping from file range to disk range (hex offsets)"
       ::= { fluidFSEventsParamsHealth 33 }
    
    
    fluidFSEventsParamsHealthParentDirDsid OBJECT-TYPE
       SYNTAX  DisplayString
       MAX-ACCESS  read-only
       STATUS  current
       DESCRIPTION
           "Parent directory file id"
       ::= { fluidFSEventsParamsHealth 34 }
    
    
    fluidFSEventsParamsHealthDirEntry OBJECT-TYPE
       SYNTAX  DisplayString
       MAX-ACCESS  read-only
       STATUS  current
       DESCRIPTION
           "Directory entry pointing to a file"
       ::= { fluidFSEventsParamsHealth 35 }
    
    
    fluidFSEventsParamsHealthPacketLossThresholdPercent OBJECT-TYPE
       SYNTAX  INTEGER
       MAX-ACCESS  read-only
       STATUS  current
       DESCRIPTION
           "Percents threashold for interconnect packet loss"
       ::= { fluidFSEventsParamsHealth 36 }
    
    
    fluidFSEventsParamsHealthFsLogicalErrorDescription OBJECT-TYPE
       SYNTAX  DisplayString
       MAX-ACCESS  read-only
       STATUS  current
       DESCRIPTION
           "Internal description of logical error found in the FS layout"
       ::= { fluidFSEventsParamsHealth 37 }
    
    
    fluidFSEventsParamsHealthLowCacheThresholdPercent OBJECT-TYPE
       SYNTAX  INTEGER
       MAX-ACCESS  read-only
       STATUS  current
       DESCRIPTION
           "Percents threashold for low on cache"
       ::= { fluidFSEventsParamsHealth 38 }
    
    
    fluidFSEventsParamsHealthProtocol OBJECT-TYPE
       SYNTAX  DisplayString
       MAX-ACCESS  read-only
       STATUS  current
       DESCRIPTION
           "Protocol"
       ::= { fluidFSEventsParamsHealth 39 }
    
    
    fluidFSEventsParamsHealthConnectionsVector OBJECT-TYPE
       SYNTAX  DisplayString
       MAX-ACCESS  read-only
       STATUS  current
       DESCRIPTION
           "Connections per nodes"
       ::= { fluidFSEventsParamsHealth 40 }
    
    
    fluidFSEventsParamsHealthAdClockSkew OBJECT-TYPE
       SYNTAX  INTEGER
       MAX-ACCESS  read-only
       STATUS  current
       DESCRIPTION
           "Skew between NAS controller and AD clocks"
       ::= { fluidFSEventsParamsHealth 41 }
    
    
    fluidFSEventsParamsHealthMaxAdClockSkew OBJECT-TYPE
       SYNTAX  INTEGER
       MAX-ACCESS  read-only
       STATUS  current
       DESCRIPTION
           "Critical skew between NAS controller and AD clocks"
       ::= { fluidFSEventsParamsHealth 42 }
    
    
    fluidFSEventsParamsHealthServerKind OBJECT-TYPE
       SYNTAX  DisplayString
       MAX-ACCESS  read-only
       STATUS  current
       DESCRIPTION
           "Server kind"
       ::= { fluidFSEventsParamsHealth 43 }
    
    
    fluidFSEventsParamsHealthResponseTime OBJECT-TYPE
       SYNTAX  DisplayString
       MAX-ACCESS  read-only
       STATUS  current
       DESCRIPTION
           "Response time"
       ::= { fluidFSEventsParamsHealth 44 }
    
    
    fluidFSEventsParamsHealthCriticalResponseTime OBJECT-TYPE
       SYNTAX  DisplayString
       MAX-ACCESS  read-only
       STATUS  current
       DESCRIPTION
           "Critical response time"
       ::= { fluidFSEventsParamsHealth 45 }
    
    
    fluidFSEventsParamsHealthInternalInfo OBJECT-TYPE
       SYNTAX  DisplayString
       MAX-ACCESS  read-only
       STATUS  current
       DESCRIPTION
           "Internal failure info for RnD troubleshooting, for example slow request details"
       ::= { fluidFSEventsParamsHealth 46 }
    
    
    fluidFSEventsParamsHealthServerIps OBJECT-TYPE
       SYNTAX  DisplayString
       MAX-ACCESS  read-only
       STATUS  current
       DESCRIPTION
           "List of server IPs"
       ::= { fluidFSEventsParamsHealth 47 }
    
    
    fluidFSEventsParamsHealthOldQuorumIP OBJECT-TYPE
       SYNTAX  DisplayString
       MAX-ACCESS  read-only
       STATUS  current
       DESCRIPTION
           "FMS old Quorum IP"
       ::= { fluidFSEventsParamsHealth 48 }
    
    
    fluidFSEventsParamsHealthDedupSpaceMarginMb OBJECT-TYPE
       SYNTAX  INTEGER
       MAX-ACCESS  read-only
       STATUS  current
       DESCRIPTION
           "Free space needed for optimization of a volume, in Megabytes"
       ::= { fluidFSEventsParamsHealth 49 }
    
    
    fluidFSEventsParamsHealthOldNumberOfVirtualDomains OBJECT-TYPE
       SYNTAX  INTEGER
       MAX-ACCESS  read-only
       STATUS  current
       DESCRIPTION
           "Old number of Virtual Domains"
       ::= { fluidFSEventsParamsHealth 50 }
    
    
    fluidFSEventsParamsHealthNewNumberOfVirtualDomains OBJECT-TYPE
       SYNTAX  INTEGER
       MAX-ACCESS  read-only
       STATUS  current
       DESCRIPTION
           "New number of Virtual Domains"
       ::= { fluidFSEventsParamsHealth 51 }
    
    
    fluidFSEventsParamsHealthNumberOfDomainsInPreviousDistribution OBJECT-TYPE
       SYNTAX  INTEGER
       MAX-ACCESS  read-only
       STATUS  current
       DESCRIPTION
           "Number of virtual domains in the file's previous distribution"
       ::= { fluidFSEventsParamsHealth 52 }
    
    
    fluidFSEventsParamsHealthNumberOfDomainsInNewDistribution OBJECT-TYPE
       SYNTAX  INTEGER
       MAX-ACCESS  read-only
       STATUS  current
       DESCRIPTION
           "Number of virtual domains in the file's new distribution"
       ::= { fluidFSEventsParamsHealth 53 }
    
    
    fluidFSEventsParamsHealthVirtualDomain OBJECT-TYPE
       SYNTAX  INTEGER
       MAX-ACCESS  read-only
       STATUS  current
       DESCRIPTION
           "The number of the virtual domain"
       ::= { fluidFSEventsParamsHealth 54 }
    
    
    fluidFSEventsParamsHealthCurrentPhysicalDomain OBJECT-TYPE
       SYNTAX  INTEGER
       MAX-ACCESS  read-only
       STATUS  current
       DESCRIPTION
           "The number of the physical domain that is currently holds the virtual domain"
       ::= { fluidFSEventsParamsHealth 55 }
    
    
    fluidFSEventsParamsHealthNewPhysicalDomain OBJECT-TYPE
       SYNTAX  INTEGER
       MAX-ACCESS  read-only
       STATUS  current
       DESCRIPTION
           "The number of the physical domain that will hold the virtual domain after the hot migration process ends"
       ::= { fluidFSEventsParamsHealth 56 }
    
    
    fluidFSEventsParamsHealthIpAddr OBJECT-TYPE
       SYNTAX  DisplayString
       MAX-ACCESS  read-only
       STATUS  current
       DESCRIPTION
           "IP Address"
       ::= { fluidFSEventsParamsHealth 57 }
    
    
    fluidFSEventsParamsHealthMacAddr OBJECT-TYPE
       SYNTAX  DisplayString
       MAX-ACCESS  read-only
       STATUS  current
       DESCRIPTION
           "mac address"
       ::= { fluidFSEventsParamsHealth 58 }
    
    
    fluidFSEventsParamsHealthLunsList OBJECT-TYPE
       SYNTAX  DisplayString
       MAX-ACCESS  read-only
       STATUS  current
       DESCRIPTION
           "A list of LUNs, comma separated"
       ::= { fluidFSEventsParamsHealth 59 }
    
    
    fluidFSEventsParamsHealthTenantId OBJECT-TYPE
       SYNTAX  DisplayString
       MAX-ACCESS  read-only
       STATUS  current
       DESCRIPTION
           "Tenant unique identifier"
       ::= { fluidFSEventsParamsHealth 60 }
    
    
    fluidFSEventsParamsHealthServerNames OBJECT-TYPE
       SYNTAX  DisplayString
       MAX-ACCESS  read-only
       STATUS  current
       DESCRIPTION
           ""
       ::= { fluidFSEventsParamsHealth 61 }
    
    
    fluidFSEventsParamsHealthDomainName OBJECT-TYPE
       SYNTAX  DisplayString
       MAX-ACCESS  read-only
       STATUS  current
       DESCRIPTION
           ""
       ::= { fluidFSEventsParamsHealth 62 }
    
    
    fluidFSEventsParamsHealthServerList OBJECT-TYPE
       SYNTAX  DisplayString
       MAX-ACCESS  read-only
       STATUS  current
       DESCRIPTION
           ""
       ::= { fluidFSEventsParamsHealth 63 }
    
    
    fluidFSEventsParamsHealthDomainControllerName OBJECT-TYPE
       SYNTAX  DisplayString
       MAX-ACCESS  read-only
       STATUS  current
       DESCRIPTION
           "Active Directory domain name"
       ::= { fluidFSEventsParamsHealth 64 }
    
    
    fluidFSEventsParamsHealthFsid OBJECT-TYPE
       SYNTAX  INTEGER
       MAX-ACCESS  read-only
       STATUS  current
       DESCRIPTION
           ""
       ::= { fluidFSEventsParamsHealth 65 }
    
    
    fluidFSEventsParamsHealthTimeDiffSec OBJECT-TYPE
       SYNTAX  INTEGER
       MAX-ACCESS  read-only
       STATUS  current
       DESCRIPTION
           ""
       ::= { fluidFSEventsParamsHealth 66 }
    
    
    fluidFSEventsParamsHealthFSIDName OBJECT-TYPE
       SYNTAX  DisplayString
       MAX-ACCESS  read-only
       STATUS  current
       DESCRIPTION
           ""
       ::= { fluidFSEventsParamsHealth 67 }
    
    
    fluidFSEventsParamsHealthParentDirDsidPath OBJECT-TYPE
       SYNTAX  DisplayString
       MAX-ACCESS  read-only
       STATUS  current
       DESCRIPTION
           ""
       ::= { fluidFSEventsParamsHealth 68 }
    
    
    fluidFSEventsParamsHealthTenantName OBJECT-TYPE
       SYNTAX  DisplayString
       MAX-ACCESS  read-only
       STATUS  current
       DESCRIPTION
           ""
       ::= { fluidFSEventsParamsHealth 69 }
    
    
    fluidFSEventsParamsHealthDsidPath OBJECT-TYPE
       SYNTAX  DisplayString
       MAX-ACCESS  read-only
       STATUS  current
       DESCRIPTION
           ""
       ::= { fluidFSEventsParamsHealth 70 }
    
    
    fluidFSEventHealthNodeFailed NOTIFICATION-TYPE
       OBJECTS { sysName, fluidFSEventsParamsHealthNodeName }
       STATUS current
       DESCRIPTION
           "NAS controller {{nodeName}} is unavailable."
           --#TYPE         "Normal Event"
           --#SUMMARY      NAS controller %s is unavailable.
           --#ARGUMENTS    {1}
           --#SEVERITY     MAJOR
           --#TIMEINDEX    99
           --#STATE        OK
       ::= { fluidFSEventsHealth 4 } 
    
    
    fluidFSEventHealthNodeOK NOTIFICATION-TYPE
       OBJECTS { sysName, fluidFSEventsParamsHealthNodeName }
       STATUS current
       DESCRIPTION
           "NAS controller {{nodeName}} is available."
           --#TYPE         "Normal Event"
           --#SUMMARY      NAS controller %s is available.
           --#ARGUMENTS    {1}
           --#SEVERITY     INFORMATIONAL
           --#TIMEINDEX    99
           --#STATE        OK
       ::= { fluidFSEventsHealth 5 } 
    
    
    fluidFSEventHealthLocalPartitionIsFull NOTIFICATION-TYPE
       OBJECTS { sysName, fluidFSEventsParamsHealthNodeName, fluidFSEventsParamsHealthPartitionName, fluidFSEventsParamsHealthPercentOfUsedSpace }
       STATUS current
       DESCRIPTION
           "The used space of local file system partition {{partitionName}} on NAS controller {{nodeName}} is high ({{percentOfUsedSpace}}%). Please contact support."
           --#TYPE         "Normal Event"
           --#SUMMARY      The used space of local file system partition %s on NAS controller %s is high (%s%). Please contact support.
           --#ARGUMENTS    {1,2,3}
           --#SEVERITY     MAJOR
           --#TIMEINDEX    99
           --#STATE        OK
       ::= { fluidFSEventsHealth 6 } 
    
    
    fluidFSEventHealthHighUseOfSwap NOTIFICATION-TYPE
       OBJECTS { sysName, fluidFSEventsParamsHealthNodeName, fluidFSEventsParamsHealthPercentOfUsedSwap }
       STATUS current
       DESCRIPTION
           "The usage of swap memory on NAS controller {{nodeName}} is high ({{percentOfUsedSwap}}%)."
           --#TYPE         "Normal Event"
           --#SUMMARY      The usage of swap memory on NAS controller %s is high (%d%).
           --#ARGUMENTS    {1,2}
           --#SEVERITY     INFORMATIONAL
           --#TIMEINDEX    99
           --#STATE        OK
       ::= { fluidFSEventsHealth 7 } 
    
    
    fluidFSEventHealthHighUseOfMemory NOTIFICATION-TYPE
       OBJECTS { sysName, fluidFSEventsParamsHealthNodeName }
       STATUS current
       DESCRIPTION
           "The memory usage on NAS controller {{nodeName}} is high."
           --#TYPE         "Normal Event"
           --#SUMMARY      The memory usage on NAS controller %s is high.
           --#ARGUMENTS    {1}
           --#SEVERITY     INFORMATIONAL
           --#TIMEINDEX    99
           --#STATE        OK
       ::= { fluidFSEventsHealth 8 } 
    
    
    fluidFSEventHealthHighUseOfFileDescriptors NOTIFICATION-TYPE
       OBJECTS { sysName, fluidFSEventsParamsHealthNodeName, fluidFSEventsParamsHealthPercentOfUsedFileDescriptors }
       STATUS current
       DESCRIPTION
           "File descriptors usage on NAS controller {{nodeName}} is high ({{percentOfUsedFileDescriptors}}%)."
           --#TYPE         "Normal Event"
           --#SUMMARY      File descriptors usage on NAS controller %s is high (%d%).
           --#ARGUMENTS    {1,2}
           --#SEVERITY     INFORMATIONAL
           --#TIMEINDEX    99
           --#STATE        OK
       ::= { fluidFSEventsHealth 9 } 
    
    
    fluidFSEventHealthPairPowerProblem NOTIFICATION-TYPE
       OBJECTS { sysName, fluidFSEventsParamsHealthThisNodeId, fluidFSEventsParamsHealthPeerNodeId }
       STATUS current
       DESCRIPTION
           "The system switched Write-Through mode on (journaling).   Description:  NAS controller {{thisNodeId}} BPS is not functioning properly and its peer controller {{peerNodeId}} has health problems as well. Switched Write-Through mode on (journaling)."
           --#TYPE         "Normal Event"
           --#SUMMARY      The system switched Write-Through mode on (journaling).   Description:  NAS controller %s BPS is not functioning properly and its peer controller %s has health problems as well. Switched Write-Through mode on (journaling).
           --#ARGUMENTS    {1,2}
           --#SEVERITY     MAJOR
           --#TIMEINDEX    99
           --#STATE        OK
       ::= { fluidFSEventsHealth 10 } 
    
    
    fluidFSEventHealthPairPowerProblemRecovered NOTIFICATION-TYPE
       OBJECTS { sysName, fluidFSEventsParamsHealthThisNodeId }
       STATUS current
       DESCRIPTION
           "The system switched Write-Through mode off (mirroring).   Description:  NAS controller {{thisNodeId}} verified the power system reliability and switched Write-Through mode off (mirroring)."
           --#TYPE         "Normal Event"
           --#SUMMARY      The system switched Write-Through mode off (mirroring).   Description:  NAS controller %s verified the power system reliability and switched Write-Through mode off (mirroring).
           --#ARGUMENTS    {1}
           --#SEVERITY     INFORMATIONAL
           --#TIMEINDEX    99
           --#STATE        OK
       ::= { fluidFSEventsHealth 11 } 
    
    
    fluidFSEventHealthSafeShutdownBegins NOTIFICATION-TYPE
       OBJECTS { sysName, fluidFSEventsParamsHealthThisNodeId }
       STATUS current
       DESCRIPTION
           "The power button of NAS controller {{thisNodeId}} was pressed.   Description:  The power button of NAS controller {{thisNodeId}} was pressed. The NAS controller's cache is being flushed and will orderly shut down in approximately 5 minutes. Please allow it to finish.   Action Items:  If this process takes longer than expected, don't try to workaround by manually shutting down the NAS controller. Please contact Support."
           --#TYPE         "Normal Event"
           --#SUMMARY      The power button of NAS controller %s was pressed.   Description:  The power button of NAS controller %s was pressed. The NAS controller's cache is being flushed and will orderly shut down in approximately 5 minutes. Please allow it to finish.   Action Items:  If this process takes longer than expected, don't try to workaround by manually shutting down the NAS controller. Please contact Support.
           --#ARGUMENTS    {1}
           --#SEVERITY     MAJOR
           --#TIMEINDEX    99
           --#STATE        OK
       ::= { fluidFSEventsHealth 12 } 
    
    
    fluidFSEventHealthSafeShutdownEnds NOTIFICATION-TYPE
       OBJECTS { sysName, fluidFSEventsParamsHealthThisNodeId }
       STATUS current
       DESCRIPTION
           "NAS controller {{thisNodeId}} cache was flushed and it is shutting down."
           --#TYPE         "Normal Event"
           --#SUMMARY      NAS controller %s cache was flushed and it is shutting down.
           --#ARGUMENTS    {1}
           --#SEVERITY     INFORMATIONAL
           --#TIMEINDEX    99
           --#STATE        OK
       ::= { fluidFSEventsHealth 13 } 
    
    
    fluidFSEventHealthPairTemperatureProblem NOTIFICATION-TYPE
       OBJECTS { sysName, fluidFSEventsParamsHealthThisNodeId, fluidFSEventsParamsHealthPeerNodeId }
       STATUS current
       DESCRIPTION
           "The system switched Write-Through mode on (journaling).   Description:  The system switched Write-Through mode on (journaling) because both NAS controllers' temperature appears high (or cannot be verified), on the controller pair with IDS {{thisNodeId}} and {{peerNodeId}}."
           --#TYPE         "Normal Event"
           --#SUMMARY      The system switched Write-Through mode on (journaling).   Description:  The system switched Write-Through mode on (journaling) because both NAS controllers' temperature appears high (or cannot be verified), on the controller pair with IDS %s and %s.
           --#ARGUMENTS    {1,2}
           --#SEVERITY     MAJOR
           --#TIMEINDEX    99
           --#STATE        OK
       ::= { fluidFSEventsHealth 14 } 
    
    
    fluidFSEventHealthPairTemperatureProblemRecovered NOTIFICATION-TYPE
       OBJECTS { sysName, fluidFSEventsParamsHealthThisNodeId }
       STATUS current
       DESCRIPTION
           "The system switched Write-Through mode off (mirroring).   Description:  NAS controller {{thisNodeId}} verified the temperature system reliability and switched Write-Through mode off (mirroring)."
           --#TYPE         "Normal Event"
           --#SUMMARY      The system switched Write-Through mode off (mirroring).   Description:  NAS controller %s verified the temperature system reliability and switched Write-Through mode off (mirroring).
           --#ARGUMENTS    {1}
           --#SEVERITY     INFORMATIONAL
           --#TIMEINDEX    99
           --#STATE        OK
       ::= { fluidFSEventsHealth 15 } 
    
    
    fluidFSEventHealthClientsOnFailback NOTIFICATION-TYPE
       OBJECTS { sysName, fluidFSEventsParamsHealthNumberOfClients }
       STATUS current
       DESCRIPTION
           "There are clients ({{numberOfClients}}) that are waiting for manual failback."
           --#TYPE         "Normal Event"
           --#SUMMARY      There are clients (%d) that are waiting for manual failback.
           --#ARGUMENTS    {1}
           --#SEVERITY     INFORMATIONAL
           --#TIMEINDEX    99
           --#STATE        OK
       ::= { fluidFSEventsHealth 16 } 
    
    
    fluidFSEventHealthCacheLossOfUserFiles NOTIFICATION-TYPE
       OBJECTS { sysName, fluidFSEventsParamsHealthDomainId }
       STATUS current
       DESCRIPTION
           "Latest user writes might have been lost.   Description:  The system identified that some of the latest user writes might have been lost. This might have been caused by a reboot of two NAS controllers in the same NAS appliance simultaneously. The system will start an automatic recovery procedure and in few minutes you should receive a completion event. During that time you will have partial or no service, SMB clients will be disconnected and NFS clients will be forced to remount. After the system is fully functional, please check your applications integrity and repeat the latest writes if needed.   Action Items:  In case repeating the latest writes is not possible or you still experience any difficulties, consider recovering the data from the latest snapshots or from backup.   Internal Information:  Domain {{domainId}}"
           --#TYPE         "Normal Event"
           --#SUMMARY      Latest user writes might have been lost.   Description:  The system identified that some of the latest user writes might have been lost. This might have been caused by a reboot of two NAS controllers in the same NAS appliance simultaneously. The system will start an automatic recovery procedure and in few minutes you should receive a completion event. During that time you will have partial or no service, SMB clients will be disconnected and NFS clients will be forced to remount. After the system is fully functional, please check your applications integrity and repeat the latest writes if needed.   Action Items:  In case repeating the latest writes is not possible or you still experience any difficulties, consider recovering the data from the latest snapshots or from backup.   Internal Information:  Domain %d
           --#ARGUMENTS    {1}
           --#SEVERITY     MAJOR
           --#TIMEINDEX    99
           --#STATE        OK
       ::= { fluidFSEventsHealth 21 } 
    
    
    fluidFSEventHealthCacheLossOfMetadata NOTIFICATION-TYPE
       OBJECTS { sysName, fluidFSEventsParamsHealthDomainId }
       STATUS current
       DESCRIPTION
           "File System process failed to recover.   Description:  The system identified that at least one of its File System processes has restarted and failed to recover it. The system will provide limited service. Please contact Support for further assistance.     Action Items:  Search product Knowledge Base for further information.   Internal Information:  Domain {{domainId}}"
           --#TYPE         "Normal Event"
           --#SUMMARY      File System process failed to recover.   Description:  The system identified that at least one of its File System processes has restarted and failed to recover it. The system will provide limited service. Please contact Support for further assistance.     Action Items:  Search product Knowledge Base for further information.   Internal Information:  Domain %d
           --#ARGUMENTS    {1}
           --#SEVERITY     MAJOR
           --#TIMEINDEX    99
           --#STATE        OK
       ::= { fluidFSEventsHealth 22 } 
    
    
    fluidFSEventHealthCacheLossRecovered NOTIFICATION-TYPE
       OBJECTS { sysName }
       STATUS current
       DESCRIPTION
           "File system recovery successfully finished.   Description:  File system recovery successfully finished.   Action Items:  Data written in the day prior to the event might be compromised and should be verified."
           --#TYPE         "Normal Event"
           --#SUMMARY      File system recovery successfully finished.   Description:  File system recovery successfully finished.   Action Items:  Data written in the day prior to the event might be compromised and should be verified.
           --#ARGUMENTS    {}
           --#SEVERITY     INFORMATIONAL
           --#TIMEINDEX    99
           --#STATE        OK
       ::= { fluidFSEventsHealth 23 } 
    
    
    fluidFSEventHealthStoreAccessProblem NOTIFICATION-TYPE
       OBJECTS { sysName, fluidFSEventsParamsHealthDomainId, fluidFSEventsParamsHealthNodeId, fluidFSEventsParamsHealthSetId }
       STATUS current
       DESCRIPTION
           "Lost communication to storage from NAS controller {{nodeId}}.   Description:  The system identified a communication problem between NAS controller {{nodeId}} and the storage controllers which may affect system performance.   Action Items:  The system constantly monitors the validity of communication between NAS controllers and Storage controller. This event is issued once the system identifies a communication issue. If the system was recently deployed or any of its components were recently moved, verify that all connections and configurations are according to the recommendations. If the system was functioning optimally for a while and this is a new event it is most likely due to a physical problem (like a bad/loose cable) or a change in network configuration which affects the components communication. Verify that all the network cables are correctly connected to the relevant NAS controller. Verify that all the iSCSI switches are up and running. If any change was introduced to the environment (new physical switch, new switch configuration), try to revert this change in order to understand the cause of the problem. Verify that the iSCSI switch is configured according to the recommendation. If the problem is persistent after verifying all the above, it is recommended to power cycle the problematic NAS controller using the UI.   Internal Information:  Domain {{domainId}} setId {{setId}}"
           --#TYPE         "Normal Event"
           --#SUMMARY      Lost communication to storage from NAS controller %d.   Description:  The system identified a communication problem between NAS controller %d and the storage controllers which may affect system performance.   Action Items:  The system constantly monitors the validity of communication between NAS controllers and Storage controller. This event is issued once the system identifies a communication issue. If the system was recently deployed or any of its components were recently moved, verify that all connections and configurations are according to the recommendations. If the system was functioning optimally for a while and this is a new event it is most likely due to a physical problem (like a bad/loose cable) or a change in network configuration which affects the components communication. Verify that all the network cables are correctly connected to the relevant NAS controller. Verify that all the iSCSI switches are up and running. If any change was introduced to the environment (new physical switch, new switch configuration), try to revert this change in order to understand the cause of the problem. Verify that the iSCSI switch is configured according to the recommendation. If the problem is persistent after verifying all the above, it is recommended to power cycle the problematic NAS controller using the UI.   Internal Information:  Domain %d setId %d
           --#ARGUMENTS    {1,2,3}
           --#SEVERITY     INFORMATIONAL
           --#TIMEINDEX    99
           --#STATE        OK
       ::= { fluidFSEventsHealth 24 } 
    
    
    fluidFSEventHealthLunVerificationFailure NOTIFICATION-TYPE
       OBJECTS { sysName, fluidFSEventsParamsHealthDomainId, fluidFSEventsParamsHealthNodeId, fluidFSEventsParamsHealthLunId }
       STATUS current
       DESCRIPTION
           "NAS controller {{nodeId}} encountered a problem accessing a NAS storage pool.   Action Items:  Please contact Support.   Internal Information:  Domain {{domainId}} LUN {{lunId}}"
           --#TYPE         "Normal Event"
           --#SUMMARY      NAS controller %d encountered a problem accessing a NAS storage pool.   Action Items:  Please contact Support.   Internal Information:  Domain %d LUN %d
           --#ARGUMENTS    {1,2,3}
           --#SEVERITY     MAJOR
           --#TIMEINDEX    99
           --#STATE        OK
       ::= { fluidFSEventsHealth 25 } 
    
    
    fluidFSEventHealthFileSystemMajorAccessibilityProblem NOTIFICATION-TYPE
       OBJECTS { sysName, fluidFSEventsParamsHealthTimeout }
       STATUS current
       DESCRIPTION
           "Clients may encounter a long period of partial data access.   Description:  The file system identified that clients may have partial data access in the last {{timeout}} minutes.   Action Items:  The NAS file system constantly verifies that it is accessible for read/write operations. This event is issued once it identifies that some operations took more time than expected or failed completely in the last {{timeout}} minutes. This could be caused by an intermittent issue of a HW failure like failed disk or disconnected network port. Verify that no RAID is being rebuilt and you do not have a recently failed drive. Verify that the cluster is connected according to the recommended cabling method and switch configuration."
           --#TYPE         "Normal Event"
           --#SUMMARY      Clients may encounter a long period of partial data access.   Description:  The file system identified that clients may have partial data access in the last %d minutes.   Action Items:  The NAS file system constantly verifies that it is accessible for read/write operations. This event is issued once it identifies that some operations took more time than expected or failed completely in the last %d minutes. This could be caused by an intermittent issue of a HW failure like failed disk or disconnected network port. Verify that no RAID is being rebuilt and you do not have a recently failed drive. Verify that the cluster is connected according to the recommended cabling method and switch configuration.
           --#ARGUMENTS    {1}
           --#SEVERITY     MAJOR
           --#TIMEINDEX    99
           --#STATE        OK
       ::= { fluidFSEventsHealth 27 } 
    
    
    fluidFSEventHealthFileSystemAccessibilityRevival NOTIFICATION-TYPE
       OBJECTS { sysName }
       STATUS current
       DESCRIPTION
           "File system back to optimal state.   Description:  The File System has overcome its accessibility problem and returned back to full functionality."
           --#TYPE         "Normal Event"
           --#SUMMARY      File system back to optimal state.   Description:  The File System has overcome its accessibility problem and returned back to full functionality.
           --#ARGUMENTS    {}
           --#SEVERITY     INFORMATIONAL
           --#TIMEINDEX    99
           --#STATE        OK
       ::= { fluidFSEventsHealth 28 } 
    
    
    fluidFSEventHealthFSMultipleRmapChecksumError NOTIFICATION-TYPE
       OBJECTS { sysName }
       STATUS current
       DESCRIPTION
           "Multiple erroneous file system blocks were identified and fixed.   Action Items:  If the problem recurs, verify system hardware health."
           --#TYPE         "Normal Event"
           --#SUMMARY      Multiple erroneous file system blocks were identified and fixed.   Action Items:  If the problem recurs, verify system hardware health.
           --#ARGUMENTS    {}
           --#SEVERITY     INFORMATIONAL
           --#TIMEINDEX    99
           --#STATE        OK
       ::= { fluidFSEventsHealth 47 } 
    
    
    fluidFSEventHealthFSSystemUnrecoverableRmapChecksumError NOTIFICATION-TYPE
       OBJECTS { sysName, fluidFSEventsParamsHealthDsid, fluidFSEventsParamsHealthFileMapping }
       STATUS current
       DESCRIPTION
           "Unrecoverable erroneous block was identified.   Description:  Unrecoverable erroneous block was identified. The file system is partially serving.   Action Items:  Contact Support.   Internal Information:  File {{dsid}} mapping {{fileMapping}}"
           --#TYPE         "Normal Event"
           --#SUMMARY      Unrecoverable erroneous block was identified.   Description:  Unrecoverable erroneous block was identified. The file system is partially serving.   Action Items:  Contact Support.   Internal Information:  File %s mapping %s
           --#ARGUMENTS    {1,2}
           --#SEVERITY     MAJOR
           --#TIMEINDEX    99
           --#STATE        OK
       ::= { fluidFSEventsHealth 48 } 
    
    
    fluidFSEventHealthFSMultipleUserMetaDataMissing NOTIFICATION-TYPE
       OBJECTS { sysName }
       STATUS current
       DESCRIPTION
           "Multiple directory entries were identified as missing.   Action Items:  Recover them from backup."
           --#TYPE         "Normal Event"
           --#SUMMARY      Multiple directory entries were identified as missing.   Action Items:  Recover them from backup.
           --#ARGUMENTS    {}
           --#SEVERITY     MAJOR
           --#TIMEINDEX    99
           --#STATE        OK
       ::= { fluidFSEventsHealth 50 } 
    
    
    fluidFSEventHealthFSLowOnLunSpace NOTIFICATION-TYPE
       OBJECTS { sysName }
       STATUS current
       DESCRIPTION
           "High NAS pool capacity. Performance might be affected.   Description:  NAS pool capacity usage has reached high watermark which will affect performance.   Action Items:  Expand the NAS pool capacity, or free some space."
           --#TYPE         "Normal Event"
           --#SUMMARY      High NAS pool capacity. Performance might be affected.   Description:  NAS pool capacity usage has reached high watermark which will affect performance.   Action Items:  Expand the NAS pool capacity, or free some space.
           --#ARGUMENTS    {}
           --#SEVERITY     MAJOR
           --#TIMEINDEX    99
           --#STATE        OK
       ::= { fluidFSEventsHealth 53 } 
    
    
    fluidFSEventHealthBadClientLoadBalancing NOTIFICATION-TYPE
       OBJECTS { sysName, fluidFSEventsParamsHealthProtocol, fluidFSEventsParamsHealthConnectionsVector }
       STATUS current
       DESCRIPTION
           "Bad {{protocol}} clients distribution: ({{connectionsVector}}).   Description:  Bad {{protocol}} clients distribution: ({{connectionsVector}}). Each pair in this set represents NAS controller ID and number of connections separated by a colon. Use the mass rebalance feature available via the clients connections screen."
           --#TYPE         "Normal Event"
           --#SUMMARY      Bad %s clients distribution: (%s).   Description:  Bad %s clients distribution: (%s). Each pair in this set represents NAS controller ID and number of connections separated by a colon. Use the mass rebalance feature available via the clients connections screen.
           --#ARGUMENTS    {1,2}
           --#SEVERITY     INFORMATIONAL
           --#TIMEINDEX    99
           --#STATE        OK
       ::= { fluidFSEventsHealth 65 } 
    
    
    fluidFSEventHealthCifsLockingInconsistancy NOTIFICATION-TYPE
       OBJECTS { sysName, fluidFSEventsParamsHealthDomainId }
       STATUS current
       DESCRIPTION
           "Inconsistent locks interrupted SMB service.   Description:  SMB service is interrupted due to inconsistencies in locking mechanism, starting recovery process.   Internal Information:  Domain {{domainId}}"
           --#TYPE         "Normal Event"
           --#SUMMARY      Inconsistent locks interrupted SMB service.   Description:  SMB service is interrupted due to inconsistencies in locking mechanism, starting recovery process.   Internal Information:  Domain %d
           --#ARGUMENTS    {1}
           --#SEVERITY     MAJOR
           --#TIMEINDEX    99
           --#STATE        OK
       ::= { fluidFSEventsHealth 66 } 
    
    
    fluidFSEventHealthCifsLockingInconsistancyRecovered NOTIFICATION-TYPE
       OBJECTS { sysName }
       STATUS current
       DESCRIPTION
           "Inconsistent locks recovered.   Description:  SMB locking inconsistencies recovery was successfully finished."
           --#TYPE         "Normal Event"
           --#SUMMARY      Inconsistent locks recovered.   Description:  SMB locking inconsistencies recovery was successfully finished.
           --#ARGUMENTS    {}
           --#SEVERITY     INFORMATIONAL
           --#TIMEINDEX    99
           --#STATE        OK
       ::= { fluidFSEventsHealth 67 } 
    
    
    fluidFSEventHealthFSReclaimerOverload NOTIFICATION-TYPE
       OBJECTS { sysName, fluidFSEventsParamsHealthDomainId }
       STATUS current
       DESCRIPTION
           "High load in snapshots space reclaiming process.   Description:  The file system has been recently engaged in reclaiming the space of deleted snapshots or NAS volumes. This could be the result of the deletion of a NAS volume and/or multiple snapshots.   Action Items:  If this event recurs on a daily basis, the file system performance can be improved; Reducing the frequency of snapshot scheduling will make more resources available for clients activity.   Internal Information:  Domain {{domainId}}"
           --#TYPE         "Normal Event"
           --#SUMMARY      High load in snapshots space reclaiming process.   Description:  The file system has been recently engaged in reclaiming the space of deleted snapshots or NAS volumes. This could be the result of the deletion of a NAS volume and/or multiple snapshots.   Action Items:  If this event recurs on a daily basis, the file system performance can be improved; Reducing the frequency of snapshot scheduling will make more resources available for clients activity.   Internal Information:  Domain %d
           --#ARGUMENTS    {1}
           --#SEVERITY     INFORMATIONAL
           --#TIMEINDEX    99
           --#STATE        OK
       ::= { fluidFSEventsHealth 72 } 
    
    
    fluidFSEventHealthPairStoreSetProblem NOTIFICATION-TYPE
       OBJECTS { sysName, fluidFSEventsParamsHealthThisNodeId, fluidFSEventsParamsHealthPeerNodeId }
       STATUS current
       DESCRIPTION
           "System switched Write-Through mode on (journaling).   Description:  NAS controller {{thisNodeId}} has lost connection to storage subsystem and its peer NAS controller {{peerNodeId}} has health problems as well. Switched Write-Through mode on (journaling)."
           --#TYPE         "Normal Event"
           --#SUMMARY      System switched Write-Through mode on (journaling).   Description:  NAS controller %s has lost connection to storage subsystem and its peer NAS controller %s has health problems as well. Switched Write-Through mode on (journaling).
           --#ARGUMENTS    {1,2}
           --#SEVERITY     MAJOR
           --#TIMEINDEX    99
           --#STATE        OK
       ::= { fluidFSEventsHealth 75 } 
    
    
    fluidFSEventHealthPairStoreSetProblemRecovered NOTIFICATION-TYPE
       OBJECTS { sysName, fluidFSEventsParamsHealthThisNodeId }
       STATUS current
       DESCRIPTION
           "System switched Write-Through mode off (mirroring).   Description:  NAS controller {{thisNodeId}} verified connection to storage subsystem and switched Write-Through mode off (mirroring)."
           --#TYPE         "Normal Event"
           --#SUMMARY      System switched Write-Through mode off (mirroring).   Description:  NAS controller %s verified connection to storage subsystem and switched Write-Through mode off (mirroring).
           --#ARGUMENTS    {1}
           --#SEVERITY     INFORMATIONAL
           --#TIMEINDEX    99
           --#STATE        OK
       ::= { fluidFSEventsHealth 76 } 
    
    
    fluidFSEventHealthPairPowerSuppliesProblem NOTIFICATION-TYPE
       OBJECTS { sysName, fluidFSEventsParamsHealthThisNodeId, fluidFSEventsParamsHealthPeerNodeId }
       STATUS current
       DESCRIPTION
           "The system switched Write-Through mode on (journaling).   Description:  NAS controller {{thisNodeId}} has lost full power supplies redundancy and its peer NAS controller {{peerNodeId}} has health problems as well. Switched Write-Through mode on (journaling)."
           --#TYPE         "Normal Event"
           --#SUMMARY      The system switched Write-Through mode on (journaling).   Description:  NAS controller %s has lost full power supplies redundancy and its peer NAS controller %s has health problems as well. Switched Write-Through mode on (journaling).
           --#ARGUMENTS    {1,2}
           --#SEVERITY     MAJOR
           --#TIMEINDEX    99
           --#STATE        OK
       ::= { fluidFSEventsHealth 77 } 
    
    
    fluidFSEventHealthPairPowerSuppliesRecovered NOTIFICATION-TYPE
       OBJECTS { sysName, fluidFSEventsParamsHealthThisNodeId }
       STATUS current
       DESCRIPTION
           "The system switched Write-Through mode off (mirroring).   Description:  NAS controller {{thisNodeId}} full power supplies redundancy was restored and switched Write-Through mode off (mirroring)."
           --#TYPE         "Normal Event"
           --#SUMMARY      The system switched Write-Through mode off (mirroring).   Description:  NAS controller %s full power supplies redundancy was restored and switched Write-Through mode off (mirroring).
           --#ARGUMENTS    {1}
           --#SEVERITY     INFORMATIONAL
           --#TIMEINDEX    99
           --#STATE        OK
       ::= { fluidFSEventsHealth 78 } 
    
    
    fluidFSEventHealthPairFansProblem NOTIFICATION-TYPE
       OBJECTS { sysName, fluidFSEventsParamsHealthThisNodeId, fluidFSEventsParamsHealthPeerNodeId }
       STATUS current
       DESCRIPTION
           "The system switched Write-Through mode on (journaling).   Description:  NAS controller {{thisNodeId}} fans are not working properly and its peer NAS controller {{peerNodeId}} has health problems as well. Switched Write-Through mode on (journaling)."
           --#TYPE         "Normal Event"
           --#SUMMARY      The system switched Write-Through mode on (journaling).   Description:  NAS controller %s fans are not working properly and its peer NAS controller %s has health problems as well. Switched Write-Through mode on (journaling).
           --#ARGUMENTS    {1,2}
           --#SEVERITY     MAJOR
           --#TIMEINDEX    99
           --#STATE        OK
       ::= { fluidFSEventsHealth 85 } 
    
    
    fluidFSEventHealthPairFansRecovered NOTIFICATION-TYPE
       OBJECTS { sysName, fluidFSEventsParamsHealthThisNodeId }
       STATUS current
       DESCRIPTION
           "The system switched Write-Through mode off (mirroring).   Description:  NAS controller {{thisNodeId}} fans are working properly. Switched Write-Through mode off (mirroring)."
           --#TYPE         "Normal Event"
           --#SUMMARY      The system switched Write-Through mode off (mirroring).   Description:  NAS controller %s fans are working properly. Switched Write-Through mode off (mirroring).
           --#ARGUMENTS    {1}
           --#SEVERITY     INFORMATIONAL
           --#TIMEINDEX    99
           --#STATE        OK
       ::= { fluidFSEventsHealth 86 } 
    
    
    fluidFSEventHealthProtocolsStateInconsistancy NOTIFICATION-TYPE
       OBJECTS { sysName, fluidFSEventsParamsHealthDomainId }
       STATUS current
       DESCRIPTION
           "Inconsistent state interrupted SMB/NFSv4 service.   Description:  SMB/NFSv4 services are interrupted due to inconsistencies in locking mechanism, starting recovery process.   Internal Information:  Domain {{domainId}}"
           --#TYPE         "Normal Event"
           --#SUMMARY      Inconsistent state interrupted SMB/NFSv4 service.   Description:  SMB/NFSv4 services are interrupted due to inconsistencies in locking mechanism, starting recovery process.   Internal Information:  Domain %d
           --#ARGUMENTS    {1}
           --#SEVERITY     MAJOR
           --#TIMEINDEX    99
           --#STATE        OK
       ::= { fluidFSEventsHealth 87 } 
    
    
    fluidFSEventHealthProtocolsStateInconsistancyRecovered NOTIFICATION-TYPE
       OBJECTS { sysName }
       STATUS current
       DESCRIPTION
           "Inconsistent locks recovered.   Description:  SMB/NFSv4 locking inconsistencies recovery was successfully finished."
           --#TYPE         "Normal Event"
           --#SUMMARY      Inconsistent locks recovered.   Description:  SMB/NFSv4 locking inconsistencies recovery was successfully finished.
           --#ARGUMENTS    {}
           --#SEVERITY     INFORMATIONAL
           --#TIMEINDEX    99
           --#STATE        OK
       ::= { fluidFSEventsHealth 88 } 
    
    
    fluidFSEventHealthFSDedupSpaceMarginReached NOTIFICATION-TYPE
       OBJECTS { sysName, fluidFSEventsParamsHealthVirtualVolume, fluidFSEventsParamsHealthDedupSpaceMarginMb }
       STATUS current
       DESCRIPTION
           "Optimization paused on volume {{virtualVolume}} - insufficient space.   Description:  Volume {{virtualVolume}} doesn't have the required free {{dedupSpaceMarginMb}} MB needed for optimization.   Action Items:  Make sure volume {{virtualVolume}} has at least {{dedupSpaceMarginMb}} MB free."
           --#TYPE         "Normal Event"
           --#SUMMARY      Optimization paused on volume %s - insufficient space.   Description:  Volume %s doesn't have the required free %d MB needed for optimization.   Action Items:  Make sure volume %s has at least %d MB free.
           --#ARGUMENTS    {1,2}
           --#SEVERITY     INFORMATIONAL
           --#TIMEINDEX    99
           --#STATE        OK
       ::= { fluidFSEventsHealth 91 } 
    
    
    fluidFSEventHealthStoreAccessRestored NOTIFICATION-TYPE
       OBJECTS { sysName, fluidFSEventsParamsHealthDomainId, fluidFSEventsParamsHealthNodeId, fluidFSEventsParamsHealthSetId }
       STATUS current
       DESCRIPTION
           "Restored communication to storage from NAS controller {{nodeId}}.   Description:  The system identified that a communication problem between NAS controller {{nodeId}} and the storage controllers was resolved.   Internal Information:  Domain {{domainId}} setId {{setId}}"
           --#TYPE         "Normal Event"
           --#SUMMARY      Restored communication to storage from NAS controller %d.   Description:  The system identified that a communication problem between NAS controller %d and the storage controllers was resolved.   Internal Information:  Domain %d setId %d
           --#ARGUMENTS    {1,2,3}
           --#SEVERITY     INFORMATIONAL
           --#TIMEINDEX    99
           --#STATE        OK
       ::= { fluidFSEventsHealth 92 } 
    
    
    fluidFSEventHealthDuplicateIp NOTIFICATION-TYPE
       OBJECTS { sysName, fluidFSEventsParamsHealthNodeId, fluidFSEventsParamsHealthMacAddr, fluidFSEventsParamsHealthIpAddr }
       STATUS current
       DESCRIPTION
           "Duplicate IP address {{ipAddr}} in use on the node {{nodeId}}.   Description:  On node {{nodeId}} an ip address {{ipAddr}} in use on this system is being used by another system with mac address {{macAddr}}.   Action Items:  Either change the address {{ipAddr}} on node {{nodeId}}, or on the other device."
           --#TYPE         "Normal Event"
           --#SUMMARY      Duplicate IP address %s in use on the node %d.   Description:  On node %d an ip address %s in use on this system is being used by another system with mac address %s.   Action Items:  Either change the address %s on node %d, or on the other device.
           --#ARGUMENTS    {1,2,3}
           --#SEVERITY     INFORMATIONAL
           --#TIMEINDEX    99
           --#STATE        OK
       ::= { fluidFSEventsHealth 102 } 
    
    
    fluidFSEventHealthUnmapIsNotSupportedOnLuns NOTIFICATION-TYPE
       OBJECTS { sysName, fluidFSEventsParamsHealthLunsList }
       STATUS current
       DESCRIPTION
           "Unmap is not supported by some of the LUNs   Description:  The following LUNs doesn't support the unmap functionallity: {{LunsList}}.   Action Items:  Please consider to upgrade the listed LUNs to the newest version."
           --#TYPE         "Normal Event"
           --#SUMMARY      Unmap is not supported by some of the LUNs   Description:  The following LUNs doesn't support the unmap functionallity: %s.   Action Items:  Please consider to upgrade the listed LUNs to the newest version.
           --#ARGUMENTS    {1}
           --#SEVERITY     INFORMATIONAL
           --#TIMEINDEX    99
           --#STATE        OK
       ::= { fluidFSEventsHealth 103 } 
    
    
    fluidFSEventHealthPairHWProblem NOTIFICATION-TYPE
       OBJECTS { sysName, fluidFSEventsParamsHealthThisNodeId, fluidFSEventsParamsHealthPeerNodeId }
       STATUS current
       DESCRIPTION
           "The system switched Write-Through mode on (journaling).   Description:  NAS controller {{thisNodeId}} hardware is not working properly and its peer NAS controller {{peerNodeId}} has health problems as well. Switched Write-Through mode on (journaling)."
           --#TYPE         "Normal Event"
           --#SUMMARY      The system switched Write-Through mode on (journaling).   Description:  NAS controller %s hardware is not working properly and its peer NAS controller %s has health problems as well. Switched Write-Through mode on (journaling).
           --#ARGUMENTS    {1,2}
           --#SEVERITY     MAJOR
           --#TIMEINDEX    99
           --#STATE        OK
       ::= { fluidFSEventsHealth 110 } 
    
    
    fluidFSEventHealthPairHWRecovered NOTIFICATION-TYPE
       OBJECTS { sysName, fluidFSEventsParamsHealthThisNodeId }
       STATUS current
       DESCRIPTION
           "The system switched Write-Through mode off (mirroring).   Description:  NAS controller {{thisNodeId}} hardware is working properly. Switched Write-Through mode off (mirroring)."
           --#TYPE         "Normal Event"
           --#SUMMARY      The system switched Write-Through mode off (mirroring).   Description:  NAS controller %s hardware is working properly. Switched Write-Through mode off (mirroring).
           --#ARGUMENTS    {1}
           --#SEVERITY     INFORMATIONAL
           --#TIMEINDEX    99
           --#STATE        OK
       ::= { fluidFSEventsHealth 111 } 
    
    
    fluidFSEventHealthUnresponsiveVmwareServerOnAllNodes NOTIFICATION-TYPE
       OBJECTS { sysName }
       STATUS current
       DESCRIPTION
           "VMWare service is unavailable on all NAS-Controllers"
           --#TYPE         "Normal Event"
           --#SUMMARY      VMWare service is unavailable on all NAS-Controllers
           --#ARGUMENTS    {}
           --#SEVERITY     INFORMATIONAL
           --#TIMEINDEX    99
           --#STATE        OK
       ::= { fluidFSEventsHealth 112 } 
    
    
    fluidFSEventHealthUnresponsiveVmwareServerOnNodes NOTIFICATION-TYPE
       OBJECTS { sysName, fluidFSEventsParamsHealthNodeIds }
       STATUS current
       DESCRIPTION
           "VMWare service is unavailable on all NAS-Controllers {{nodeIds}}"
           --#TYPE         "Normal Event"
           --#SUMMARY      VMWare service is unavailable on all NAS-Controllers %s
           --#ARGUMENTS    {1}
           --#SEVERITY     INFORMATIONAL
           --#TIMEINDEX    99
           --#STATE        OK
       ::= { fluidFSEventsHealth 113 } 
    
    
    fluidFSEventHealthResponsiveVmwareServerOnAllNodes NOTIFICATION-TYPE
       OBJECTS { sysName }
       STATUS current
       DESCRIPTION
           "VMWare service is available on all NAS-Controlles"
           --#TYPE         "Normal Event"
           --#SUMMARY      VMWare service is available on all NAS-Controlles
           --#ARGUMENTS    {}
           --#SEVERITY     INFORMATIONAL
           --#TIMEINDEX    99
           --#STATE        OK
       ::= { fluidFSEventsHealth 114 } 
    
    
    fluidFSEventHealthCouldNotAllocateProtectedMemory NOTIFICATION-TYPE
       OBJECTS { sysName }
       STATUS current
       DESCRIPTION
           "Problem with allocating protected memory   Description:  Memory detector could not allocate the protected memory   Action Items:  Please contact support"
           --#TYPE         "Normal Event"
           --#SUMMARY      Problem with allocating protected memory   Description:  Memory detector could not allocate the protected memory   Action Items:  Please contact support
           --#ARGUMENTS    {}
           --#SEVERITY     MAJOR
           --#TIMEINDEX    99
           --#STATE        OK
       ::= { fluidFSEventsHealth 115 } 
    
    
    fluidFSEventHealthInvalidSizeOfProtectedMemory NOTIFICATION-TYPE
       OBJECTS { sysName }
       STATUS current
       DESCRIPTION
           "Problem with allocating protected memory   Description:  The model's predefined size of protected memory is not equal to allocated   Action Items:  Please contact support"
           --#TYPE         "Normal Event"
           --#SUMMARY      Problem with allocating protected memory   Description:  The model's predefined size of protected memory is not equal to allocated   Action Items:  Please contact support
           --#ARGUMENTS    {}
           --#SEVERITY     MAJOR
           --#TIMEINDEX    99
           --#STATE        OK
       ::= { fluidFSEventsHealth 116 } 
    
    
    fluidFSEventHealthCouldNotAllocateUnProtectedMemory NOTIFICATION-TYPE
       OBJECTS { sysName }
       STATUS current
       DESCRIPTION
           "Problem with allocating unprotected memory   Description:  Preallocation script could not allocate the unprotected memory   Action Items:  Please contact support"
           --#TYPE         "Normal Event"
           --#SUMMARY      Problem with allocating unprotected memory   Description:  Preallocation script could not allocate the unprotected memory   Action Items:  Please contact support
           --#ARGUMENTS    {}
           --#SEVERITY     MAJOR
           --#TIMEINDEX    99
           --#STATE        OK
       ::= { fluidFSEventsHealth 117 } 
    
    
    fluidFSEventHealthUnresponsiveIscsiPortalsOnAllNodes NOTIFICATION-TYPE
       OBJECTS { sysName }
       STATUS current
       DESCRIPTION
           "iSCSI portals are unavailable on all NAS Controllers"
           --#TYPE         "Normal Event"
           --#SUMMARY      iSCSI portals are unavailable on all NAS Controllers
           --#ARGUMENTS    {}
           --#SEVERITY     INFORMATIONAL
           --#TIMEINDEX    99
           --#STATE        OK
       ::= { fluidFSEventsHealth 118 } 
    
    
    fluidFSEventHealthUnresponsiveIscsiPortalsOnNodes NOTIFICATION-TYPE
       OBJECTS { sysName, fluidFSEventsParamsHealthNodeIds }
       STATUS current
       DESCRIPTION
           "iSCSI portals are unavailable on NAS Controllers {{nodeIds}}"
           --#TYPE         "Normal Event"
           --#SUMMARY      iSCSI portals are unavailable on NAS Controllers %s
           --#ARGUMENTS    {1}
           --#SEVERITY     INFORMATIONAL
           --#TIMEINDEX    99
           --#STATE        OK
       ::= { fluidFSEventsHealth 119 } 
    
    
    fluidFSEventHealthResponsiveIscsiPortalsOnAllNodes NOTIFICATION-TYPE
       OBJECTS { sysName }
       STATUS current
       DESCRIPTION
           "iSCSI portals are available on all NAS Controllers"
           --#TYPE         "Normal Event"
           --#SUMMARY      iSCSI portals are available on all NAS Controllers
           --#ARGUMENTS    {}
           --#SEVERITY     INFORMATIONAL
           --#TIMEINDEX    99
           --#STATE        OK
       ::= { fluidFSEventsHealth 120 } 
    
    
    fluidFSEventHealthUnavailableNtpServiceOnAllNodes NOTIFICATION-TYPE
       OBJECTS { sysName }
       STATUS current
       DESCRIPTION
           "NTP service is unavailable on all NAS Controllers"
           --#TYPE         "Normal Event"
           --#SUMMARY      NTP service is unavailable on all NAS Controllers
           --#ARGUMENTS    {}
           --#SEVERITY     MAJOR
           --#TIMEINDEX    99
           --#STATE        OK
       ::= { fluidFSEventsHealth 121 } 
    
    
    fluidFSEventHealthAvailableNtpServiceOnAllNodes NOTIFICATION-TYPE
       OBJECTS { sysName }
       STATUS current
       DESCRIPTION
           "NTP service become available on all NAS Controllers"
           --#TYPE         "Normal Event"
           --#SUMMARY      NTP service become available on all NAS Controllers
           --#ARGUMENTS    {}
           --#SEVERITY     INFORMATIONAL
           --#TIMEINDEX    99
           --#STATE        OK
       ::= { fluidFSEventsHealth 122 } 
    
    
    fluidFSEventHealthUnavailableNtpServiceOnNodes NOTIFICATION-TYPE
       OBJECTS { sysName, fluidFSEventsParamsHealthNodeIds }
       STATUS current
       DESCRIPTION
           "NTP service is unavailable on NAS Controllers {{nodeIds}}"
           --#TYPE         "Normal Event"
           --#SUMMARY      NTP service is unavailable on NAS Controllers %s
           --#ARGUMENTS    {1}
           --#SEVERITY     INFORMATIONAL
           --#TIMEINDEX    99
           --#STATE        OK
       ::= { fluidFSEventsHealth 123 } 
    
    
    fluidFSEventHealthUnavailableAntivirusOnAllNodes NOTIFICATION-TYPE
       OBJECTS { sysName }
       STATUS current
       DESCRIPTION
           "Antivirus is unavailable on all NAS Controllers"
           --#TYPE         "Normal Event"
           --#SUMMARY      Antivirus is unavailable on all NAS Controllers
           --#ARGUMENTS    {}
           --#SEVERITY     MAJOR
           --#TIMEINDEX    99
           --#STATE        OK
       ::= { fluidFSEventsHealth 124 } 
    
    
    fluidFSEventHealthAvailableAntivirusOnAllNodes NOTIFICATION-TYPE
       OBJECTS { sysName }
       STATUS current
       DESCRIPTION
           "Antivirus become available on all NAS Controllers"
           --#TYPE         "Normal Event"
           --#SUMMARY      Antivirus become available on all NAS Controllers
           --#ARGUMENTS    {}
           --#SEVERITY     INFORMATIONAL
           --#TIMEINDEX    99
           --#STATE        OK
       ::= { fluidFSEventsHealth 125 } 
    
    
    fluidFSEventHealthUnavailableAntivirusOnNodes NOTIFICATION-TYPE
       OBJECTS { sysName, fluidFSEventsParamsHealthNodeIds }
       STATUS current
       DESCRIPTION
           "Antivirus is unavailable on NAS Controllers {{nodeIds}}"
           --#TYPE         "Normal Event"
           --#SUMMARY      Antivirus is unavailable on NAS Controllers %s
           --#ARGUMENTS    {1}
           --#SEVERITY     INFORMATIONAL
           --#TIMEINDEX    99
           --#STATE        OK
       ::= { fluidFSEventsHealth 126 } 
    
    
    fluidFSEventHealthUnavailableAuditingServicesOnAllNodes NOTIFICATION-TYPE
       OBJECTS { sysName }
       STATUS current
       DESCRIPTION
           "Auditing subscribers became unavailable for all NAS Controllers"
           --#TYPE         "Normal Event"
           --#SUMMARY      Auditing subscribers became unavailable for all NAS Controllers
           --#ARGUMENTS    {}
           --#SEVERITY     MAJOR
           --#TIMEINDEX    99
           --#STATE        OK
       ::= { fluidFSEventsHealth 127 } 
    
    
    fluidFSEventHealthAvailableAuditingServicesOnAllNodes NOTIFICATION-TYPE
       OBJECTS { sysName }
       STATUS current
       DESCRIPTION
           "Auditing subscribers became available for all NAS Controllers"
           --#TYPE         "Normal Event"
           --#SUMMARY      Auditing subscribers became available for all NAS Controllers
           --#ARGUMENTS    {}
           --#SEVERITY     INFORMATIONAL
           --#TIMEINDEX    99
           --#STATE        OK
       ::= { fluidFSEventsHealth 128 } 
    
    
    fluidFSEventHealthUnavailableAuditingServicesOnNodes NOTIFICATION-TYPE
       OBJECTS { sysName, fluidFSEventsParamsHealthNodeIds }
       STATUS current
       DESCRIPTION
           "Auditing subscribers became unavailable for NAS Controller/s: {{nodeIds}}"
           --#TYPE         "Normal Event"
           --#SUMMARY      Auditing subscribers became unavailable for NAS Controller/s: %s
           --#ARGUMENTS    {1}
           --#SEVERITY     INFORMATIONAL
           --#TIMEINDEX    99
           --#STATE        OK
       ::= { fluidFSEventsHealth 129 } 
    
    
    fluidFSEventHealthPairCacheArmingProblem NOTIFICATION-TYPE
       OBJECTS { sysName, fluidFSEventsParamsHealthThisNodeId }
       STATUS current
       DESCRIPTION
           "System switched Write-Through mode on (journaling).   Description:  NAS controller {{thisNodeId}} has problems with arming the protected memory, as well as it's peer. Switched Write-Through mode on (journaling)."
           --#TYPE         "Normal Event"
           --#SUMMARY      System switched Write-Through mode on (journaling).   Description:  NAS controller %s has problems with arming the protected memory, as well as it's peer. Switched Write-Through mode on (journaling).
           --#ARGUMENTS    {1}
           --#SEVERITY     MAJOR
           --#TIMEINDEX    99
           --#STATE        OK
       ::= { fluidFSEventsHealth 130 } 
    
    
    fluidFSEventHealthPairCacheArmingProblemRecovered NOTIFICATION-TYPE
       OBJECTS { sysName, fluidFSEventsParamsHealthThisNodeId }
       STATUS current
       DESCRIPTION
           "System switched Write-Through mode off (mirroring).   Description:  NAS controller {{thisNodeId}} succeeded arming the protected memory, and switched Write-Through mode off (mirroring) ."
           --#TYPE         "Normal Event"
           --#SUMMARY      System switched Write-Through mode off (mirroring).   Description:  NAS controller %s succeeded arming the protected memory, and switched Write-Through mode off (mirroring) .
           --#ARGUMENTS    {1}
           --#SEVERITY     INFORMATIONAL
           --#TIMEINDEX    99
           --#STATE        OK
       ::= { fluidFSEventsHealth 131 } 
    
    
    fluidFSEventHealthCouldNotArmProtectedMemoryRegion NOTIFICATION-TYPE
       OBJECTS { sysName }
       STATUS current
       DESCRIPTION
           "Problem with arming of protected memory regions   Description:  Memory detector could not arm protected memory region   Action Items:  Please contact support"
           --#TYPE         "Normal Event"
           --#SUMMARY      Problem with arming of protected memory regions   Description:  Memory detector could not arm protected memory region   Action Items:  Please contact support
           --#ARGUMENTS    {}
           --#SEVERITY     MAJOR
           --#TIMEINDEX    99
           --#STATE        OK
       ::= { fluidFSEventsHealth 132 } 
    
    
    fluidFSEventHealthFSUserMetaDataMissing NOTIFICATION-TYPE
       OBJECTS { sysName, fluidFSEventsParamsHealthFSID, fluidFSEventsParamsHealthDsid, fluidFSEventsParamsHealthParentDirDsid, fluidFSEventsParamsHealthDirEntry }
       STATUS current
       DESCRIPTION
           "Directory entry was identified as missing; Entry {{dirEntry}} in {{parentDirDsidPath}}.   Action Items:  Recover it from backup.   Internal Information:  File {{dsid}} volume {{FSIDName}}"
           --#TYPE         "Normal Event"
           --#SUMMARY      Directory entry was identified as missing; Entry %s in %s.   Action Items:  Recover it from backup.   Internal Information:  File %s volume %s
           --#ARGUMENTS    {1,2,3,4}
           --#SEVERITY     INFORMATIONAL
           --#TIMEINDEX    99
           --#STATE        OK
       ::= { fluidFSEventsHealth 133 } 
    
    
    fluidFSEventHealthUnresponsiveLdapServersOnAllNodes NOTIFICATION-TYPE
       OBJECTS { sysName, fluidFSEventsParamsHealthTenantId, fluidFSEventsParamsHealthServerNames }
       STATUS current
       DESCRIPTION
           "LDAP servers, used by {{TenantName}}, are not responding.   Description:  All LDAP servers ({{serverNames}}), used by {{TenantName}}, are not responding on all NAS Controllers. For each server please check: its server logs for any event that caused it not to respond to requests; that it responds to ping requests from clients on the same subnetwork; that it responds to LDAP requests from clients on the same subnetwork."
           --#TYPE         "Normal Event"
           --#SUMMARY      LDAP servers, used by %s, are not responding.   Description:  All LDAP servers (%s), used by %s, are not responding on all NAS Controllers. For each server please check: its server logs for any event that caused it not to respond to requests; that it responds to ping requests from clients on the same subnetwork; that it responds to LDAP requests from clients on the same subnetwork.
           --#ARGUMENTS    {1,2}
           --#SEVERITY     MAJOR
           --#TIMEINDEX    99
           --#STATE        OK
       ::= { fluidFSEventsHealth 134 } 
    
    
    fluidFSEventHealthUnresponsiveLdapServersOnSomeNodes NOTIFICATION-TYPE
       OBJECTS { sysName, fluidFSEventsParamsHealthTenantId, fluidFSEventsParamsHealthServerNames, fluidFSEventsParamsHealthNodeIds }
       STATUS current
       DESCRIPTION
           "All LDAP servers ({{serverNames}}), used by {{TenantName}}, are unresponsive on some NAS Controllers: {{nodeIds}}."
           --#TYPE         "Normal Event"
           --#SUMMARY      All LDAP servers (%s), used by %s, are unresponsive on some NAS Controllers: %s.
           --#ARGUMENTS    {1,2,3}
           --#SEVERITY     INFORMATIONAL
           --#TIMEINDEX    99
           --#STATE        OK
       ::= { fluidFSEventsHealth 135 } 
    
    
    fluidFSEventHealthResponsiveLdapServerOnAllNodes NOTIFICATION-TYPE
       OBJECTS { sysName, fluidFSEventsParamsHealthTenantId, fluidFSEventsParamsHealthServerNames }
       STATUS current
       DESCRIPTION
           "Found responsive LDAP server(s) among ({{serverNames}}), used by {{TenantName}}, on all NAS Controllers."
           --#TYPE         "Normal Event"
           --#SUMMARY      Found responsive LDAP server(s) among (%s), used by %s, on all NAS Controllers.
           --#ARGUMENTS    {1,2}
           --#SEVERITY     INFORMATIONAL
           --#TIMEINDEX    99
           --#STATE        OK
       ::= { fluidFSEventsHealth 136 } 
    
    
    fluidFSEventHealthUnresponsiveNisServersOnAllNodes NOTIFICATION-TYPE
       OBJECTS { sysName, fluidFSEventsParamsHealthTenantId, fluidFSEventsParamsHealthServerNames }
       STATUS current
       DESCRIPTION
           "NIS servers, used by {{TenantName}}, are not responding.   Description:  All NIS servers ({{serverNames}}), used by {{TenantName}}, are not responding on all NAS Controllers. For each server please check: its server logs for any event that caused it not to respond to requests; that it responds to ping requests from clients on the same subnetwork; that it responds to NIS requests from clients on the same subnetwork."
           --#TYPE         "Normal Event"
           --#SUMMARY      NIS servers, used by %s, are not responding.   Description:  All NIS servers (%s), used by %s, are not responding on all NAS Controllers. For each server please check: its server logs for any event that caused it not to respond to requests; that it responds to ping requests from clients on the same subnetwork; that it responds to NIS requests from clients on the same subnetwork.
           --#ARGUMENTS    {1,2}
           --#SEVERITY     MAJOR
           --#TIMEINDEX    99
           --#STATE        OK
       ::= { fluidFSEventsHealth 137 } 
    
    
    fluidFSEventHealthResponsiveNisServerOnAllNodes NOTIFICATION-TYPE
       OBJECTS { sysName, fluidFSEventsParamsHealthTenantId, fluidFSEventsParamsHealthServerNames }
       STATUS current
       DESCRIPTION
           "Found responsive NIS server(s) among ({{serverNames}}), used by {{TenantName}}, on all NAS Controllers."
           --#TYPE         "Normal Event"
           --#SUMMARY      Found responsive NIS server(s) among (%s), used by %s, on all NAS Controllers.
           --#ARGUMENTS    {1,2}
           --#SEVERITY     INFORMATIONAL
           --#TIMEINDEX    99
           --#STATE        OK
       ::= { fluidFSEventsHealth 138 } 
    
    
    fluidFSEventHealthUnresponsiveNisServersOnSomeNodes NOTIFICATION-TYPE
       OBJECTS { sysName, fluidFSEventsParamsHealthTenantId, fluidFSEventsParamsHealthServerNames, fluidFSEventsParamsHealthNodeIds }
       STATUS current
       DESCRIPTION
           "All NIS servers ({{serverNames}}), used by {{TenantName}}, are unresponsive on some NAS Controllers: {{nodeIds}}."
           --#TYPE         "Normal Event"
           --#SUMMARY      All NIS servers (%s), used by %s, are unresponsive on some NAS Controllers: %s.
           --#ARGUMENTS    {1,2,3}
           --#SEVERITY     INFORMATIONAL
           --#TIMEINDEX    99
           --#STATE        OK
       ::= { fluidFSEventsHealth 139 } 
    
    
    fluidFSEventHealthUnresponsiveDnsServersOnAllNodes NOTIFICATION-TYPE
       OBJECTS { sysName, fluidFSEventsParamsHealthTenantId, fluidFSEventsParamsHealthServerIps }
       STATUS current
       DESCRIPTION
           "DNS servers, used by {{TenantName}}, are not responding.   Description:  All DNS servers ({{serverIps}}), used by {{TenantName}}, are not responding on all NAS Controllers.  For each server please check: its server logs for any event that caused it not to respond to requests; that it responds to ping requests from clients on the same subnetwork; that it responds to DNS requests from clients on the same subnetwork."
           --#TYPE         "Normal Event"
           --#SUMMARY      DNS servers, used by %s, are not responding.   Description:  All DNS servers (%s), used by %s, are not responding on all NAS Controllers.  For each server please check: its server logs for any event that caused it not to respond to requests; that it responds to ping requests from clients on the same subnetwork; that it responds to DNS requests from clients on the same subnetwork.
           --#ARGUMENTS    {1,2}
           --#SEVERITY     MAJOR
           --#TIMEINDEX    99
           --#STATE        OK
       ::= { fluidFSEventsHealth 140 } 
    
    
    fluidFSEventHealthResponsiveDnsServerOnAllNodes NOTIFICATION-TYPE
       OBJECTS { sysName, fluidFSEventsParamsHealthTenantId, fluidFSEventsParamsHealthServerIps }
       STATUS current
       DESCRIPTION
           "Found responsive DNS server(s) among ({{serverIps}}), used by {{TenantName}}, on all NAS Controllers."
           --#TYPE         "Normal Event"
           --#SUMMARY      Found responsive DNS server(s) among (%s), used by %s, on all NAS Controllers.
           --#ARGUMENTS    {1,2}
           --#SEVERITY     INFORMATIONAL
           --#TIMEINDEX    99
           --#STATE        OK
       ::= { fluidFSEventsHealth 141 } 
    
    
    fluidFSEventHealthUnresponsiveDnsServersOnSomeNodes NOTIFICATION-TYPE
       OBJECTS { sysName, fluidFSEventsParamsHealthTenantId, fluidFSEventsParamsHealthServerIps, fluidFSEventsParamsHealthNodeIds }
       STATUS current
       DESCRIPTION
           "All DNS servers ({{serverIps}}), used by {{TenantName}}, are unresponsive on some NAS Controllers: {{nodeIds}}."
           --#TYPE         "Normal Event"
           --#SUMMARY      All DNS servers (%s), used by %s, are unresponsive on some NAS Controllers: %s.
           --#ARGUMENTS    {1,2,3}
           --#SEVERITY     INFORMATIONAL
           --#TIMEINDEX    99
           --#STATE        OK
       ::= { fluidFSEventsHealth 142 } 
    
    
    fluidFSEventHealthUnresponsiveAdServer NOTIFICATION-TYPE
       OBJECTS { sysName, fluidFSEventsParamsHealthTenantId, fluidFSEventsParamsHealthDomainName }
       STATUS current
       DESCRIPTION
           "Active Directory, used by {{TenantName}}, is not responsive.   Description:  Active Directory domain {{domainName}}, used by {{TenantName}}, is not reachable. For each domain controller please check: its logs for any event that caused it not to respond to requests; that it responds to ping requests from clients on the same subnetwork; that it responds to AD requests from clients on the same subnetwork."
           --#TYPE         "Normal Event"
           --#SUMMARY      Active Directory, used by %s, is not responsive.   Description:  Active Directory domain %s, used by %s, is not reachable. For each domain controller please check: its logs for any event that caused it not to respond to requests; that it responds to ping requests from clients on the same subnetwork; that it responds to AD requests from clients on the same subnetwork.
           --#ARGUMENTS    {1,2}
           --#SEVERITY     MAJOR
           --#TIMEINDEX    99
           --#STATE        OK
       ::= { fluidFSEventsHealth 143 } 
    
    
    fluidFSEventHealthResponsiveAdServer NOTIFICATION-TYPE
       OBJECTS { sysName, fluidFSEventsParamsHealthTenantId, fluidFSEventsParamsHealthDomainName }
       STATUS current
       DESCRIPTION
           "Active Directory domain {{domainName}}, used by {{TenantName}}, is reachable."
           --#TYPE         "Normal Event"
           --#SUMMARY      Active Directory domain %s, used by %s, is reachable.
           --#ARGUMENTS    {1,2}
           --#SEVERITY     INFORMATIONAL
           --#TIMEINDEX    99
           --#STATE        OK
       ::= { fluidFSEventsHealth 144 } 
    
    
    fluidFSEventHealthSlowResponse NOTIFICATION-TYPE
       OBJECTS { sysName, fluidFSEventsParamsHealthTenantId, fluidFSEventsParamsHealthServerKind, fluidFSEventsParamsHealthServerList, fluidFSEventsParamsHealthResponseTime, fluidFSEventsParamsHealthCriticalResponseTime, fluidFSEventsParamsHealthInternalInfo }
       STATUS current
       DESCRIPTION
           "Slow response time from {{serverKind}} to {{TenantName}}.   Description:  Response time from {{serverKind}} servers ({{serverList}}) of {{responseTime}} seconds exceeds {{criticalResponseTime}} seconds on {{TenantName}}.   Action Items:  Check availability of all {{serverKind}} servers. This error is usually the outcome of a communication error between the NAS and the external server. It could be caused by a network issue, external server overload or a software malfunction in one of environment components.   Internal Information:  {{internalInfo}}"
           --#TYPE         "Normal Event"
           --#SUMMARY      Slow response time from %s to %s.   Description:  Response time from %s servers (%s) of %s seconds exceeds %s seconds on %s.   Action Items:  Check availability of all %s servers. This error is usually the outcome of a communication error between the NAS and the external server. It could be caused by a network issue, external server overload or a software malfunction in one of environment components.   Internal Information:  %s
           --#ARGUMENTS    {1,2,3,4,5,6}
           --#SEVERITY     INFORMATIONAL
           --#TIMEINDEX    99
           --#STATE        OK
       ::= { fluidFSEventsHealth 145 } 
    
    
    fluidFSEventHealthAdCriticalClockSkew NOTIFICATION-TYPE
       OBJECTS { sysName, fluidFSEventsParamsHealthNodeId, fluidFSEventsParamsHealthTenantId, fluidFSEventsParamsHealthDomainControllerName, fluidFSEventsParamsHealthAdClockSkew, fluidFSEventsParamsHealthMaxAdClockSkew }
       STATUS current
       DESCRIPTION
           "AD (used by {{TenantName}}) and NAS controller {{nodeId}} clocks aren't synchronized   Description:  Clock of NAS controller {{nodeId}} and AD clock, used by {{TenantName}} (domain {{DomainControllerName}}), are not synchronized (skew of {{adClockSkew}} seconds exceeds critical threshold of {{maxAdClockSkew}} seconds). Kerberos authentication may fail. Fix system clock/Fix AD clock. Enter the time configuration screen and get the configured NTP host. If no NTP is configured, it is recommended to configure one by either using the organization's NTP or the same IP/name used for joining the NAS to the AD."
           --#TYPE         "Normal Event"
           --#SUMMARY      AD (used by %s) and NAS controller %d clocks aren't synchronized   Description:  Clock of NAS controller %d and AD clock, used by %s (domain %s), are not synchronized (skew of %d seconds exceeds critical threshold of %d seconds). Kerberos authentication may fail. Fix system clock/Fix AD clock. Enter the time configuration screen and get the configured NTP host. If no NTP is configured, it is recommended to configure one by either using the organization's NTP or the same IP/name used for joining the NAS to the AD.
           --#ARGUMENTS    {1,2,3,4,5}
           --#SEVERITY     INFORMATIONAL
           --#TIMEINDEX    99
           --#STATE        OK
       ::= { fluidFSEventsHealth 146 } 
    
    
    fluidFSEventHealthCIFSAttachedACLCorruption NOTIFICATION-TYPE
       OBJECTS { sysName, fluidFSEventsParamsHealthFsid, fluidFSEventsParamsHealthDsid }
       STATUS current
       DESCRIPTION
           "Failed to read a file ACL's.   Description:   ACL of file {{dsidPath}} can not be read. Access will be denied to all users.   Action Items:  Please reset the file ACL"
           --#TYPE         "Normal Event"
           --#SUMMARY      Failed to read a file ACL's.   Description:   ACL of file %s can not be read. Access will be denied to all users.   Action Items:  Please reset the file ACL
           --#ARGUMENTS    {1,2}
           --#SEVERITY     INFORMATIONAL
           --#TIMEINDEX    99
           --#STATE        OK
       ::= { fluidFSEventsHealth 147 } 
    
    
    fluidFSEventHealthFSUserUnrecoverableRmapChecksumError NOTIFICATION-TYPE
       OBJECTS { sysName, fluidFSEventsParamsHealthDsid, fluidFSEventsParamsHealthFileMapping }
       STATUS current
       DESCRIPTION
           "Unrecoverable erroneous block in user file.   Description:  Unrecoverable erroneous block was identified in {{dsidPath}} and it is inaccessible.   Action Items:  Move this file/directory to a different name, and recover it from backup.   Internal Information:  Mapping {{fileMapping}}"
           --#TYPE         "Normal Event"
           --#SUMMARY      Unrecoverable erroneous block in user file.   Description:  Unrecoverable erroneous block was identified in %s and it is inaccessible.   Action Items:  Move this file/directory to a different name, and recover it from backup.   Internal Information:  Mapping %s
           --#ARGUMENTS    {1,2}
           --#SEVERITY     INFORMATIONAL
           --#TIMEINDEX    99
           --#STATE        OK
       ::= { fluidFSEventsHealth 149 } 
    
    
    fluidFSEventHealthFSVolumeUnrecoverableRmapChecksumError NOTIFICATION-TYPE
       OBJECTS { sysName, fluidFSEventsParamsHealthFSID, fluidFSEventsParamsHealthDsid, fluidFSEventsParamsHealthFileMapping }
       STATUS current
       DESCRIPTION
           "NAS Volume {{FSIDName}} is partially serving.   Description:  Unrecoverable erroneous block was identified in volume {{FSIDName}}. This volume is partially serving.   Action Items:  Run the file system diagnostics and contact Support.   Internal Information:  File {{dsid}} mapping {{fileMapping}}"
           --#TYPE         "Normal Event"
           --#SUMMARY      NAS Volume %s is partially serving.   Description:  Unrecoverable erroneous block was identified in volume %s. This volume is partially serving.   Action Items:  Run the file system diagnostics and contact Support.   Internal Information:  File %s mapping %s
           --#ARGUMENTS    {1,2,3}
           --#SEVERITY     MAJOR
           --#TIMEINDEX    99
           --#STATE        OK
       ::= { fluidFSEventsHealth 150 } 
    
    
    fluidFSEventHealthFSRehydrationSpaceMarginReached NOTIFICATION-TYPE
       OBJECTS { sysName, fluidFSEventsParamsHealthFSID, fluidFSEventsParamsHealthDedupSpaceMarginMb }
       STATUS current
       DESCRIPTION
           "Rehydration paused on volume {{FSIDName}} - insufficient space.   Description:  Volume {{FSIDName}} doesn't have the required free {{dedupSpaceMarginMb}} MB needed for rehydration.   Action Items:  Make sure volume {{FSIDName}} has at least {{dedupSpaceMarginMb}} MB free."
           --#TYPE         "Normal Event"
           --#SUMMARY      Rehydration paused on volume %s - insufficient space.   Description:  Volume %s doesn't have the required free %d MB needed for rehydration.   Action Items:  Make sure volume %s has at least %d MB free.
           --#ARGUMENTS    {1,2}
           --#SEVERITY     INFORMATIONAL
           --#TIMEINDEX    99
           --#STATE        OK
       ::= { fluidFSEventsHealth 151 } 
    
    
    fluidFSEventHealthFSLowOnLunSpaceDedupPostponed NOTIFICATION-TYPE
       OBJECTS { sysName }
       STATUS current
       DESCRIPTION
           "High NAS pool space usage. Data Reduction paused on cluster.   Description:  Cluster does not have the required NAS pool free space needed for Data Reduction   Action Items:  Please perform one of the following actions to increase NAS pool free space : expand your NAS pool; Delete old Snapshots; Delete redundant NAS volumes."
           --#TYPE         "Normal Event"
           --#SUMMARY      High NAS pool space usage. Data Reduction paused on cluster.   Description:  Cluster does not have the required NAS pool free space needed for Data Reduction   Action Items:  Please perform one of the following actions to increase NAS pool free space : expand your NAS pool; Delete old Snapshots; Delete redundant NAS volumes.
           --#ARGUMENTS    {}
           --#SEVERITY     MAJOR
           --#TIMEINDEX    99
           --#STATE        OK
       ::= { fluidFSEventsHealth 154 } 
    
    
    fluidFSEventHealthFSLowOnLunSpaceDedupResumed NOTIFICATION-TYPE
       OBJECTS { sysName }
       STATUS current
       DESCRIPTION
           "Data Reduction resumed on cluster.   Description:  NAS pool free space increased. Data reduction is resumed"
           --#TYPE         "Normal Event"
           --#SUMMARY      Data Reduction resumed on cluster.   Description:  NAS pool free space increased. Data reduction is resumed
           --#ARGUMENTS    {}
           --#SEVERITY     INFORMATIONAL
           --#TIMEINDEX    99
           --#STATE        OK
       ::= { fluidFSEventsHealth 155 } 
    
    
    fluidFSEventHealthFSLowOnLunSpaceFSNotAccessible NOTIFICATION-TYPE
       OBJECTS { sysName }
       STATUS current
       DESCRIPTION
           "High NAS pool space usage. File system access is limited   Description:  High NAS pool space usage. File system is accessible only using NFS3.   Action Items:  Please perform one of the following actions to increase NAS pool free space : expand your NAS pool; Delete old Snapshots; Delete redundant NAS volumes."
           --#TYPE         "Normal Event"
           --#SUMMARY      High NAS pool space usage. File system access is limited   Description:  High NAS pool space usage. File system is accessible only using NFS3.   Action Items:  Please perform one of the following actions to increase NAS pool free space : expand your NAS pool; Delete old Snapshots; Delete redundant NAS volumes.
           --#ARGUMENTS    {}
           --#SEVERITY     MAJOR
           --#TIMEINDEX    99
           --#STATE        OK
       ::= { fluidFSEventsHealth 156 } 
    
    
    fluidFSEventHealthFSLowOnLunSpaceFSAccessible NOTIFICATION-TYPE
       OBJECTS { sysName }
       STATUS current
       DESCRIPTION
           "File system access is back to normal.   Description:  NAS pool free space increased. File system can be accessed by all protocols "
           --#TYPE         "Normal Event"
           --#SUMMARY      File system access is back to normal.   Description:  NAS pool free space increased. File system can be accessed by all protocols 
           --#ARGUMENTS    {}
           --#SEVERITY     INFORMATIONAL
           --#TIMEINDEX    99
           --#STATE        OK
       ::= { fluidFSEventsHealth 157 } 
    
    
    fluidFSEventHealthLocalTimeDesynchronizedToNtp NOTIFICATION-TYPE
       OBJECTS { sysName, fluidFSEventsParamsHealthNodeId, fluidFSEventsParamsHealthTimeDiffSec }
       STATUS current
       DESCRIPTION
           "Local time on node {{nodeId}} is desynchronized by {{timeDiffSec}} seconds."
           --#TYPE         "Normal Event"
           --#SUMMARY      Local time on node %d is desynchronized by %d seconds.
           --#ARGUMENTS    {1,2}
           --#SEVERITY     MAJOR
           --#TIMEINDEX    99
           --#STATE        OK
       ::= { fluidFSEventsHealth 158 } 
    
    
    fluidFSEventsParamsAntivirus OBJECT IDENTIFIER ::= { fluidFSEventsParams 10 } 
    
    
    fluidFSEventsAntivirus OBJECT IDENTIFIER ::= { fluidFSEvents 10 } 
    
    
    fluidFSEventsParamsAntivirusShareName OBJECT-TYPE
       SYNTAX  DisplayString
       MAX-ACCESS  read-only
       STATUS  current
       DESCRIPTION
           "cifs share where scanning occurs"
       ::= { fluidFSEventsParamsAntivirus 1 }
    
    
    fluidFSEventsParamsAntivirusVirusDescription OBJECT-TYPE
       SYNTAX  DisplayString
       MAX-ACCESS  read-only
       STATUS  current
       DESCRIPTION
           "brief virus description"
       ::= { fluidFSEventsParamsAntivirus 2 }
    
    
    fluidFSEventsParamsAntivirusFilePath OBJECT-TYPE
       SYNTAX  DisplayString
       MAX-ACCESS  read-only
       STATUS  current
       DESCRIPTION
           "path of the scanned file"
       ::= { fluidFSEventsParamsAntivirus 3 }
    
    
    fluidFSEventsParamsAntivirusQuarantinedPath OBJECT-TYPE
       SYNTAX  DisplayString
       MAX-ACCESS  read-only
       STATUS  current
       DESCRIPTION
           "path of the quarantined file"
       ::= { fluidFSEventsParamsAntivirus 4 }
    
    
    fluidFSEventsParamsAntivirusInfectedAction OBJECT-TYPE
       SYNTAX  DisplayString
       MAX-ACCESS  read-only
       STATUS  current
       DESCRIPTION
           "action applied to infected file"
       ::= { fluidFSEventsParamsAntivirus 5 }
    
    
    fluidFSEventsParamsAntivirusAdsName OBJECT-TYPE
       SYNTAX  DisplayString
       MAX-ACCESS  read-only
       STATUS  current
       DESCRIPTION
           "name of the ADS"
       ::= { fluidFSEventsParamsAntivirus 6 }
    
    
    fluidFSEventsParamsAntivirusSnapName OBJECT-TYPE
       SYNTAX  DisplayString
       MAX-ACCESS  read-only
       STATUS  current
       DESCRIPTION
           "name of the snapshot for previous version"
       ::= { fluidFSEventsParamsAntivirus 7 }
    
    
    fluidFSEventsParamsAntivirusHost OBJECT-TYPE
       SYNTAX  DisplayString
       MAX-ACCESS  read-only
       STATUS  current
       DESCRIPTION
           "antivirus host hostname or IP address"
       ::= { fluidFSEventsParamsAntivirus 8 }
    
    
    fluidFSEventsParamsAntivirusPort OBJECT-TYPE
       SYNTAX  INTEGER
       MAX-ACCESS  read-only
       STATUS  current
       DESCRIPTION
           "antivirus host port"
       ::= { fluidFSEventsParamsAntivirus 9 }
    
    
    fluidFSEventsParamsAntivirusScanningFacility OBJECT-TYPE
       SYNTAX  DisplayString
       MAX-ACCESS  read-only
       STATUS  current
       DESCRIPTION
           "actual antivirus host and port used for scanning"
       ::= { fluidFSEventsParamsAntivirus 10 }
    
    
    fluidFSEventsParamsAntivirusScanningDuration OBJECT-TYPE
       SYNTAX  DisplayString
       MAX-ACCESS  read-only
       STATUS  current
       DESCRIPTION
           "scanning duration, real number in seconds with enough precision"
       ::= { fluidFSEventsParamsAntivirus 11 }
    
    
    fluidFSEventsParamsAntivirusScanningDurationThreshold OBJECT-TYPE
       SYNTAX  INTEGER
       MAX-ACCESS  read-only
       STATUS  current
       DESCRIPTION
           "critical scanning duration in seconds used as the threshold for event"
       ::= { fluidFSEventsParamsAntivirus 12 }
    
    
    fluidFSEventsParamsAntivirusDsid OBJECT-TYPE
       SYNTAX  DisplayString
       MAX-ACCESS  read-only
       STATUS  current
       DESCRIPTION
           "DSID (internal filesystem ID) of file or directory. Use dsid2name utility to translate dsid to path via command line, also dsid2path translator is designed to do it automatically for events"
       ::= { fluidFSEventsParamsAntivirus 13 }
    
    
    fluidFSEventsParamsAntivirusFSID OBJECT-TYPE
       SYNTAX  INTEGER
       MAX-ACCESS  read-only
       STATUS  current
       DESCRIPTION
           "NAS volume id"
       ::= { fluidFSEventsParamsAntivirus 14 }
    
    
    fluidFSEventsParamsAntivirusAccessDeniedReason OBJECT-TYPE
       SYNTAX  DisplayString
       MAX-ACCESS  read-only
       STATUS  current
       DESCRIPTION
           "Extended details about reason of returned ACCESS_DENIED error"
       ::= { fluidFSEventsParamsAntivirus 15 }
    
    
    fluidFSEventsParamsAntivirusFileSizeMb OBJECT-TYPE
       SYNTAX  INTEGER
       MAX-ACCESS  read-only
       STATUS  current
       DESCRIPTION
           "Size (in Megabytes) of the file to be scanned for viruses"
       ::= { fluidFSEventsParamsAntivirus 16 }
    
    
    fluidFSEventsParamsAntivirusLargeFileSizeLimitMb OBJECT-TYPE
       SYNTAX  INTEGER
       MAX-ACCESS  read-only
       STATUS  current
       DESCRIPTION
           "Limit of the file size (in Megabytes) of the file to be scanned for viruses. Larger files are not scanned."
       ::= { fluidFSEventsParamsAntivirus 17 }
    
    
    fluidFSEventsParamsAntivirusIcapStatus OBJECT-TYPE
       SYNTAX  DisplayString
       MAX-ACCESS  read-only
       STATUS  current
       DESCRIPTION
           ""
       ::= { fluidFSEventsParamsAntivirus 18 }
    
    
    fluidFSEventsParamsAntivirusServer OBJECT-TYPE
       SYNTAX  DisplayString
       MAX-ACCESS  read-only
       STATUS  current
       DESCRIPTION
           ""
       ::= { fluidFSEventsParamsAntivirus 19 }
    
    
    fluidFSEventsParamsAntivirusPort OBJECT-TYPE
       SYNTAX  DisplayString
       MAX-ACCESS  read-only
       STATUS  current
       DESCRIPTION
           "antivirus host port"
       ::= { fluidFSEventsParamsAntivirus 20 }
    
    
    fluidFSEventsParamsAntivirusFSIDName OBJECT-TYPE
       SYNTAX  DisplayString
       MAX-ACCESS  read-only
       STATUS  current
       DESCRIPTION
           ""
       ::= { fluidFSEventsParamsAntivirus 21 }
    
    
    fluidFSEventsParamsAntivirusDsidPath OBJECT-TYPE
       SYNTAX  DisplayString
       MAX-ACCESS  read-only
       STATUS  current
       DESCRIPTION
           ""
       ::= { fluidFSEventsParamsAntivirus 22 }
    
    
    fluidFSEventAntivirusAntivirusHostUp NOTIFICATION-TYPE
       OBJECTS { sysName, fluidFSEventsParamsAntivirusHost, fluidFSEventsParamsAntivirusPort }
       STATUS current
       DESCRIPTION
           "Antivirus host {{host}}:{{port}} accessibility is restored.   Description:  Antivirus host {{host}}:{{port}} accessibility is restored."
           --#TYPE         "Normal Event"
           --#SUMMARY      Antivirus host %s:%d accessibility is restored.   Description:  Antivirus host %s:%d accessibility is restored.
           --#ARGUMENTS    {1,2}
           --#SEVERITY     INFORMATIONAL
           --#TIMEINDEX    99
           --#STATE        OK
       ::= { fluidFSEventsAntivirus 16 } 
    
    
    fluidFSEventAntivirusAntivirusHostDown NOTIFICATION-TYPE
       OBJECTS { sysName, fluidFSEventsParamsAntivirusHost, fluidFSEventsParamsAntivirusPort }
       STATUS current
       DESCRIPTION
           "Antivirus host {{host}}:{{port}} is not accessible.   Description:  Antivirus host {{host}}:{{port}} is not accessible."
           --#TYPE         "Normal Event"
           --#SUMMARY      Antivirus host %s:%d is not accessible.   Description:  Antivirus host %s:%d is not accessible.
           --#ARGUMENTS    {1,2}
           --#SEVERITY     INFORMATIONAL
           --#TIMEINDEX    99
           --#STATE        OK
       ::= { fluidFSEventsAntivirus 17 } 
    
    
    fluidFSEventAntivirusAntivirusLicenseError NOTIFICATION-TYPE
       OBJECTS { sysName, fluidFSEventsParamsAntivirusHost, fluidFSEventsParamsAntivirusPort }
       STATUS current
       DESCRIPTION
           " Antivirus host {{host}}:{{port}} returns license error.   Description:  Antivirus host {{host}}:{{port}} returns license error."
           --#TYPE         "Normal Event"
           --#SUMMARY       Antivirus host %s:%d returns license error.   Description:  Antivirus host %s:%d returns license error.
           --#ARGUMENTS    {1,2}
           --#SEVERITY     INFORMATIONAL
           --#TIMEINDEX    99
           --#STATE        OK
       ::= { fluidFSEventsAntivirus 18 } 
    
    
    fluidFSEventAntivirusAntivirusAllDown NOTIFICATION-TYPE
       OBJECTS { sysName }
       STATUS current
       DESCRIPTION
           "No antivirus hosts are accessible.   Description:  No antivirus hosts are accessible. Virus scanning is not possible. SMB Shares with AV scan configured will not be accessible."
           --#TYPE         "Normal Event"
           --#SUMMARY      No antivirus hosts are accessible.   Description:  No antivirus hosts are accessible. Virus scanning is not possible. SMB Shares with AV scan configured will not be accessible.
           --#ARGUMENTS    {}
           --#SEVERITY     MAJOR
           --#TIMEINDEX    99
           --#STATE        OK
       ::= { fluidFSEventsAntivirus 19 } 
    
    
    fluidFSEventAntivirusAntivirusServersNotConfigured NOTIFICATION-TYPE
       OBJECTS { sysName, fluidFSEventsParamsAntivirusShareName }
       STATUS current
       DESCRIPTION
           "AntiVirus servers are not configured.   Description:  SMB share {{shareName}} is configured to use antivirus checking but no AV servers are configured yet. Access to the files inside the share is denied.   Action Items:  AntiVirus servers must be configured to provide AntiVirus facility"
           --#TYPE         "Normal Event"
           --#SUMMARY      AntiVirus servers are not configured.   Description:  SMB share %s is configured to use antivirus checking but no AV servers are configured yet. Access to the files inside the share is denied.   Action Items:  AntiVirus servers must be configured to provide AntiVirus facility
           --#ARGUMENTS    {1}
           --#SEVERITY     MAJOR
           --#TIMEINDEX    99
           --#STATE        OK
       ::= { fluidFSEventsAntivirus 27 } 
    
    
    fluidFSEventAntivirusAntivirusScanWasTooLong2 NOTIFICATION-TYPE
       OBJECTS { sysName, fluidFSEventsParamsAntivirusFSID, fluidFSEventsParamsAntivirusShareName, fluidFSEventsParamsAntivirusDsid, fluidFSEventsParamsAntivirusScanningFacility, fluidFSEventsParamsAntivirusScanningDuration, fluidFSEventsParamsAntivirusScanningDurationThreshold }
       STATUS current
       DESCRIPTION
           "Antivirus scan for file {{FSIDName}}/{{dsidPath}} took too long   Description:  Scanning for viruses for file {{dsidPath}} on NAS volume {{FSIDName}} accessed via SMB share {{shareName}} took too long: {{scanningDuration}} seconds (must be less than {{scanningDurationThreshold}}), scanning facility '{{scanningFacility}}'.   Action Items:  Please check network availability and current load on problematic AntiVirus facility."
           --#TYPE         "Normal Event"
           --#SUMMARY      Antivirus scan for file %s/%s took too long   Description:  Scanning for viruses for file %s on NAS volume %s accessed via SMB share %s took too long: %s seconds (must be less than %d), scanning facility '%s'.   Action Items:  Please check network availability and current load on problematic AntiVirus facility.
           --#ARGUMENTS    {1,2,3,4,5,6}
           --#SEVERITY     INFORMATIONAL
           --#TIMEINDEX    99
           --#STATE        OK
       ::= { fluidFSEventsAntivirus 31 } 
    
    
    fluidFSEventAntivirusAccessDenied NOTIFICATION-TYPE
       OBJECTS { sysName, fluidFSEventsParamsAntivirusFSID, fluidFSEventsParamsAntivirusShareName, fluidFSEventsParamsAntivirusDsid, fluidFSEventsParamsAntivirusVirusDescription, fluidFSEventsParamsAntivirusAccessDeniedReason }
       STATUS current
       DESCRIPTION
           "Virus was found in file {{FSIDName}}/{{dsidPath}} but quarantine is not applicable.   Description:  Virus ({{virusDescription}}) was found in file {{dsidPath}} on NAS volume {{FSIDName}} accessed via SMB share {{shareName}}. Quarantine action is not possible for this file, access to file is denied.   Internal Information:  Reason why quarantine action is not possible: {{accessDeniedReason}}"
           --#TYPE         "Normal Event"
           --#SUMMARY      Virus was found in file %s/%s but quarantine is not applicable.   Description:  Virus (%s) was found in file %s on NAS volume %s accessed via SMB share %s. Quarantine action is not possible for this file, access to file is denied.   Internal Information:  Reason why quarantine action is not possible: %s
           --#ARGUMENTS    {1,2,3,4,5}
           --#SEVERITY     INFORMATIONAL
           --#TIMEINDEX    99
           --#STATE        OK
       ::= { fluidFSEventsAntivirus 32 } 
    
    
    fluidFSEventAntivirusAccessDeniedDueInternalError NOTIFICATION-TYPE
       OBJECTS { sysName, fluidFSEventsParamsAntivirusFSID, fluidFSEventsParamsAntivirusShareName, fluidFSEventsParamsAntivirusDsid, fluidFSEventsParamsAntivirusAccessDeniedReason }
       STATUS current
       DESCRIPTION
           "An error occurred while scanning the file {{FSIDName}}/{{dsidPath}} for viruses.   Description:  An error occurred during AV scan of the file {{dsidPath}} on NAS volume {{FSIDName}} accessed via SMB share {{shareName}}. Access to file is denied.   Internal Information:  Error details: {{accessDeniedReason}}"
           --#TYPE         "Normal Event"
           --#SUMMARY      An error occurred while scanning the file %s/%s for viruses.   Description:  An error occurred during AV scan of the file %s on NAS volume %s accessed via SMB share %s. Access to file is denied.   Internal Information:  Error details: %s
           --#ARGUMENTS    {1,2,3,4}
           --#SEVERITY     MAJOR
           --#TIMEINDEX    99
           --#STATE        OK
       ::= { fluidFSEventsAntivirus 33 } 
    
    
    fluidFSEventAntivirusUnexpectedAvResponse NOTIFICATION-TYPE
       OBJECTS { sysName, fluidFSEventsParamsAntivirusFSID, fluidFSEventsParamsAntivirusShareName, fluidFSEventsParamsAntivirusDsid, fluidFSEventsParamsAntivirusIcapStatus, fluidFSEventsParamsAntivirusServer, fluidFSEventsParamsAntivirusPort }
       STATUS current
       DESCRIPTION
           "Error occurred while scanning for viruses.   Description:  AV server returned unexpected error during the scan for file {{dsidPath}} on NAS volume {{FSIDName}} accessed via SMB share {{shareName}}. Access is denied.   Internal Information:  ICAP protocol issue: unexpected ICAP status code {{icapStatus}} returned by facility {{server}}:{{port}}"
           --#TYPE         "Normal Event"
           --#SUMMARY      Error occurred while scanning for viruses.   Description:  AV server returned unexpected error during the scan for file %s on NAS volume %s accessed via SMB share %s. Access is denied.   Internal Information:  ICAP protocol issue: unexpected ICAP status code %s returned by facility %s:%s
           --#ARGUMENTS    {1,2,3,4,5,6}
           --#SEVERITY     MAJOR
           --#TIMEINDEX    99
           --#STATE        OK
       ::= { fluidFSEventsAntivirus 34 } 
    
    
    fluidFSEventAntivirusQuarantineActionFailed NOTIFICATION-TYPE
       OBJECTS { sysName, fluidFSEventsParamsAntivirusFSID, fluidFSEventsParamsAntivirusShareName, fluidFSEventsParamsAntivirusDsid, fluidFSEventsParamsAntivirusVirusDescription, fluidFSEventsParamsAntivirusAccessDeniedReason }
       STATUS current
       DESCRIPTION
           "Virus was found in file {{FSIDName}}/{{dsidPath}} but quarantine action has failed.   Description:  Virus ({{virusDescription}}) was found in file {{dsidPath}} on NAS volume {{FSIDName}} accessed via SMB share {{shareName}}. Quarantine action failed for this file, access to file is denied.   Internal Information:  Quarantine action error details: {{accessDeniedReason}}"
           --#TYPE         "Normal Event"
           --#SUMMARY      Virus was found in file %s/%s but quarantine action has failed.   Description:  Virus (%s) was found in file %s on NAS volume %s accessed via SMB share %s. Quarantine action failed for this file, access to file is denied.   Internal Information:  Quarantine action error details: %s
           --#ARGUMENTS    {1,2,3,4,5}
           --#SEVERITY     MAJOR
           --#TIMEINDEX    99
           --#STATE        OK
       ::= { fluidFSEventsAntivirus 35 } 
    
    
    fluidFSEventAntivirusInfectedFileQuarantined2 NOTIFICATION-TYPE
       OBJECTS { sysName, fluidFSEventsParamsAntivirusFSID, fluidFSEventsParamsAntivirusShareName, fluidFSEventsParamsAntivirusDsid, fluidFSEventsParamsAntivirusFilePath, fluidFSEventsParamsAntivirusVirusDescription }
       STATUS current
       DESCRIPTION
           "Virus was found in file {{FSIDName}}/{{filePath}}, quarantine action is applied.   Description:  Virus ({{virusDescription}}) was found in file {{filePath}} on NAS volume {{FSIDName}} accessed via SMB share {{shareName}}. File is moved to quarantine (new path is {{dsidPath}})."
           --#TYPE         "Normal Event"
           --#SUMMARY      Virus was found in file %s/%s, quarantine action is applied.   Description:  Virus (%s) was found in file %s on NAS volume %s accessed via SMB share %s. File is moved to quarantine (new path is %s).
           --#ARGUMENTS    {1,2,3,4,5}
           --#SEVERITY     INFORMATIONAL
           --#TIMEINDEX    99
           --#STATE        OK
       ::= { fluidFSEventsAntivirus 36 } 
    
    
    fluidFSEventAntivirusInfectedFileRepaired NOTIFICATION-TYPE
       OBJECTS { sysName, fluidFSEventsParamsAntivirusFSID, fluidFSEventsParamsAntivirusShareName, fluidFSEventsParamsAntivirusDsid, fluidFSEventsParamsAntivirusVirusDescription }
       STATUS current
       DESCRIPTION
           "Infected file {{FSIDName}}/{{dsidPath}} was repaired.   Description:  Virus ({{virusDescription}}) was found in file {{dsidPath}} on NAS volume {{FSIDName}} accessed via SMB share {{shareName}}. The file was repaired automatically."
           --#TYPE         "Normal Event"
           --#SUMMARY      Infected file %s/%s was repaired.   Description:  Virus (%s) was found in file %s on NAS volume %s accessed via SMB share %s. The file was repaired automatically.
           --#ARGUMENTS    {1,2,3,4}
           --#SEVERITY     INFORMATIONAL
           --#TIMEINDEX    99
           --#STATE        OK
       ::= { fluidFSEventsAntivirus 37 } 
    
    
    fluidFSEventAntivirusAccessDeniedLargeFileNotScanned NOTIFICATION-TYPE
       OBJECTS { sysName, fluidFSEventsParamsAntivirusFSID, fluidFSEventsParamsAntivirusShareName, fluidFSEventsParamsAntivirusDsid, fluidFSEventsParamsAntivirusFileSizeMb, fluidFSEventsParamsAntivirusLargeFileSizeLimitMb }
       STATUS current
       DESCRIPTION
           "Access denied: file {{FSIDName}}/{{dsidPath}} is too large for AV verification.   Description:  File {{dsidPath}} (which is {{fileSizeMb}} MB) on NAS volume {{FSIDName}} accessed via SMB share {{shareName}} cannot be scanned for viruses because it exceeds the maximum scan size ({{largeFileSizeLimitMb}} Mb). This share is configured to block access to un-scanned files.   Action Items:  Increase the maximum scan size for AV scanning or change the policy to allow un-scanned files for access. Please note, Anti-virus scan of large files may delay the initial open request."
           --#TYPE         "Normal Event"
           --#SUMMARY      Access denied: file %s/%s is too large for AV verification.   Description:  File %s (which is %d MB) on NAS volume %s accessed via SMB share %s cannot be scanned for viruses because it exceeds the maximum scan size (%d Mb). This share is configured to block access to un-scanned files.   Action Items:  Increase the maximum scan size for AV scanning or change the policy to allow un-scanned files for access. Please note, Anti-virus scan of large files may delay the initial open request.
           --#ARGUMENTS    {1,2,3,4,5}
           --#SEVERITY     INFORMATIONAL
           --#TIMEINDEX    99
           --#STATE        OK
       ::= { fluidFSEventsAntivirus 38 } 
    
    
    fluidFSEventAntivirusLargeFileNotScanned NOTIFICATION-TYPE
       OBJECTS { sysName, fluidFSEventsParamsAntivirusFSID, fluidFSEventsParamsAntivirusShareName, fluidFSEventsParamsAntivirusDsid, fluidFSEventsParamsAntivirusFileSizeMb, fluidFSEventsParamsAntivirusLargeFileSizeLimitMb }
       STATUS current
       DESCRIPTION
           "Access allowed: file {{FSIDName}}/{{dsidPath}} was opened without AV verification.   Description:  File {{dsidPath}} (which is {{fileSizeMb}} MB) on NAS volume {{FSIDName}} accessed via SMB share {{shareName}} was not scanned for viruses because it exceeds the maximum scan size ({{largeFileSizeLimitMb}} MB).   Action Items:  Increase the maximum file size for AV scan or change the policy to deny un-scanned files for access. Please note, Anti-virus scan of large files may delay the initial open request."
           --#TYPE         "Normal Event"
           --#SUMMARY      Access allowed: file %s/%s was opened without AV verification.   Description:  File %s (which is %d MB) on NAS volume %s accessed via SMB share %s was not scanned for viruses because it exceeds the maximum scan size (%d MB).   Action Items:  Increase the maximum file size for AV scan or change the policy to deny un-scanned files for access. Please note, Anti-virus scan of large files may delay the initial open request.
           --#ARGUMENTS    {1,2,3,4,5}
           --#SEVERITY     INFORMATIONAL
           --#TIMEINDEX    99
           --#STATE        OK
       ::= { fluidFSEventsAntivirus 39 } 
    
    
    fluidFSEventsParamsClientAccess OBJECT IDENTIFIER ::= { fluidFSEventsParams 11 } 
    
    
    fluidFSEventsClientAccess OBJECT IDENTIFIER ::= { fluidFSEvents 11 } 
    
    
    fluidFSEventsParamsClientAccessMaxConnections OBJECT-TYPE
       SYNTAX  INTEGER
       MAX-ACCESS  read-only
       STATUS  current
       DESCRIPTION
           "maximal number of connections"
       ::= { fluidFSEventsParamsClientAccess 1 }
    
    
    fluidFSEventsParamsClientAccessNfsExport OBJECT-TYPE
       SYNTAX  DisplayString
       MAX-ACCESS  read-only
       STATUS  current
       DESCRIPTION
           "NFS export name, as defined on cluster"
       ::= { fluidFSEventsParamsClientAccess 2 }
    
    
    fluidFSEventsParamsClientAccessMountPath OBJECT-TYPE
       SYNTAX  DisplayString
       MAX-ACCESS  read-only
       STATUS  current
       DESCRIPTION
           "NFS mount path as specified by user for mount command"
       ::= { fluidFSEventsParamsClientAccess 3 }
    
    
    fluidFSEventsParamsClientAccessNfsClientPort OBJECT-TYPE
       SYNTAX  INTEGER
       MAX-ACCESS  read-only
       STATUS  current
       DESCRIPTION
           "NFS client port number"
       ::= { fluidFSEventsParamsClientAccess 4 }
    
    
    fluidFSEventsParamsClientAccessNfsExportOptions OBJECT-TYPE
       SYNTAX  DisplayString
       MAX-ACCESS  read-only
       STATUS  current
       DESCRIPTION
           "NFS export options, as defined on cluster"
       ::= { fluidFSEventsParamsClientAccess 5 }
    
    
    fluidFSEventsParamsClientAccessClientIpAddr OBJECT-TYPE
       SYNTAX  DisplayString
       MAX-ACCESS  read-only
       STATUS  current
       DESCRIPTION
           "Client IP address"
       ::= { fluidFSEventsParamsClientAccess 6 }
    
    
    fluidFSEventsParamsClientAccessNfsUser OBJECT-TYPE
       SYNTAX  DisplayString
       MAX-ACCESS  read-only
       STATUS  current
       DESCRIPTION
           "User ID as seen from NFS server, either UID or SID. Will be translated to username by 'uidOrSid2name' translator automatically"
       ::= { fluidFSEventsParamsClientAccess 7 }
    
    
    fluidFSEventsParamsClientAccessCifsUser OBJECT-TYPE
       SYNTAX  INTEGER
       MAX-ACCESS  read-only
       STATUS  current
       DESCRIPTION
           "User ID as seen from Samba - TUID. Will be translated to username by 'tuid2name' translator automatically"
       ::= { fluidFSEventsParamsClientAccess 8 }
    
    
    fluidFSEventsParamsClientAccessUserName OBJECT-TYPE
       SYNTAX  DisplayString
       MAX-ACCESS  read-only
       STATUS  current
       DESCRIPTION
           ""
       ::= { fluidFSEventsParamsClientAccess 9 }
    
    
    fluidFSEventsParamsClientAccessCifsShare OBJECT-TYPE
       SYNTAX  DisplayString
       MAX-ACCESS  read-only
       STATUS  current
       DESCRIPTION
           "SMB share name, as defined on cluster"
       ::= { fluidFSEventsParamsClientAccess 10 }
    
    
    fluidFSEventsParamsClientAccessDsid OBJECT-TYPE
       SYNTAX  DisplayString
       MAX-ACCESS  read-only
       STATUS  current
       DESCRIPTION
           "DSID (internal filesystem ID) of file or directory. Use dsid2name utility to translate dsid to path."
       ::= { fluidFSEventsParamsClientAccess 11 }
    
    
    fluidFSEventsParamsClientAccessNfsOp OBJECT-TYPE
       SYNTAX  DisplayString
       MAX-ACCESS  read-only
       STATUS  current
       DESCRIPTION
           "NFS operation (NFS verb, command, etc)"
       ::= { fluidFSEventsParamsClientAccess 12 }
    
    
    fluidFSEventsParamsClientAccessVolumeStyle OBJECT-TYPE
       SYNTAX  DisplayString
       MAX-ACCESS  read-only
       STATUS  current
       DESCRIPTION
           "Volume style - NTFS, UNIX or MIXED"
       ::= { fluidFSEventsParamsClientAccess 13 }
    
    
    fluidFSEventsParamsClientAccessUserOwner OBJECT-TYPE
       SYNTAX  DisplayString
       MAX-ACCESS  read-only
       STATUS  current
       DESCRIPTION
           "User owner for a file"
       ::= { fluidFSEventsParamsClientAccess 14 }
    
    
    fluidFSEventsParamsClientAccessGroupOwner OBJECT-TYPE
       SYNTAX  DisplayString
       MAX-ACCESS  read-only
       STATUS  current
       DESCRIPTION
           "Group owner for a file"
       ::= { fluidFSEventsParamsClientAccess 15 }
    
    
    fluidFSEventsParamsClientAccessUserIdentityType OBJECT-TYPE
       SYNTAX  DisplayString
       MAX-ACCESS  read-only
       STATUS  current
       DESCRIPTION
           "User type (NTFS or UNIX, i.e. UID or SID)"
       ::= { fluidFSEventsParamsClientAccess 16 }
    
    
    fluidFSEventsParamsClientAccessGroupIdentityType OBJECT-TYPE
       SYNTAX  DisplayString
       MAX-ACCESS  read-only
       STATUS  current
       DESCRIPTION
           "6roup type (NTFS or UNIX, i.e. GID or GSID)"
       ::= { fluidFSEventsParamsClientAccess 17 }
    
    
    fluidFSEventsParamsClientAccessDesiredNfsAccessMask OBJECT-TYPE
       SYNTAX  DisplayString
       MAX-ACCESS  read-only
       STATUS  current
       DESCRIPTION
           "7esired access mask"
       ::= { fluidFSEventsParamsClientAccess 18 }
    
    
    fluidFSEventsParamsClientAccessGrantedNfsAccessMask OBJECT-TYPE
       SYNTAX  DisplayString
       MAX-ACCESS  read-only
       STATUS  current
       DESCRIPTION
           "Granted (maximal) access mask"
       ::= { fluidFSEventsParamsClientAccess 19 }
    
    
    fluidFSEventsParamsClientAccessDesiredCifsAccessMask OBJECT-TYPE
       SYNTAX  INTEGER
       MAX-ACCESS  read-only
       STATUS  current
       DESCRIPTION
           "Desired access mask"
       ::= { fluidFSEventsParamsClientAccess 20 }
    
    
    fluidFSEventsParamsClientAccessGrantedCifsAccessMask OBJECT-TYPE
       SYNTAX  INTEGER
       MAX-ACCESS  read-only
       STATUS  current
       DESCRIPTION
           "Granted (maximal) access mask"
       ::= { fluidFSEventsParamsClientAccess 21 }
    
    
    fluidFSEventsParamsClientAccessMissedCifsAccessBits OBJECT-TYPE
       SYNTAX  INTEGER
       MAX-ACCESS  read-only
       STATUS  current
       DESCRIPTION
           "Missed access bits (mask)"
       ::= { fluidFSEventsParamsClientAccess 22 }
    
    
    fluidFSEventsParamsClientAccessCifsOp OBJECT-TYPE
       SYNTAX  DisplayString
       MAX-ACCESS  read-only
       STATUS  current
       DESCRIPTION
           "SMB operation (SMB verb, VFS verb, generic command, etc)"
       ::= { fluidFSEventsParamsClientAccess 23 }
    
    
    fluidFSEventsParamsClientAccessCifsPrivileges OBJECT-TYPE
       SYNTAX  DisplayString
       MAX-ACCESS  read-only
       STATUS  current
       DESCRIPTION
           "SMB User privileges"
       ::= { fluidFSEventsParamsClientAccess 24 }
    
    
    fluidFSEventsParamsClientAccessCifsGuestAccount OBJECT-TYPE
       SYNTAX  DisplayString
       MAX-ACCESS  read-only
       STATUS  current
       DESCRIPTION
           "SMB guest account as configured on the cluster"
       ::= { fluidFSEventsParamsClientAccess 25 }
    
    
    fluidFSEventsParamsClientAccessNasContainerId OBJECT-TYPE
       SYNTAX  DisplayString
       MAX-ACCESS  read-only
       STATUS  current
       DESCRIPTION
           "NAS Volume (volume name)"
       ::= { fluidFSEventsParamsClientAccess 26 }
    
    
    fluidFSEventsParamsClientAccessNasContainerPath OBJECT-TYPE
       SYNTAX  DisplayString
       MAX-ACCESS  read-only
       STATUS  current
       DESCRIPTION
           "Path related to specified NAS Volume"
       ::= { fluidFSEventsParamsClientAccess 27 }
    
    
    fluidFSEventsParamsClientAccessNasControllerId OBJECT-TYPE
       SYNTAX  DisplayString
       MAX-ACCESS  read-only
       STATUS  current
       DESCRIPTION
           "NAS controller ID (node ID)"
       ::= { fluidFSEventsParamsClientAccess 28 }
    
    
    fluidFSEventsParamsClientAccessNasContainerIdInteger OBJECT-TYPE
       SYNTAX  INTEGER
       MAX-ACCESS  read-only
       STATUS  current
       DESCRIPTION
           "NAS Volume ID (volume ID, i.e. FSID uint32 value). Will be translated to volume name by translator"
       ::= { fluidFSEventsParamsClientAccess 29 }
    
    
    fluidFSEventsParamsClientAccessLockingUser OBJECT-TYPE
       SYNTAX  INTEGER
       MAX-ACCESS  read-only
       STATUS  current
       DESCRIPTION
           "User identity who holds the lock on requested file and causing access conflict"
       ::= { fluidFSEventsParamsClientAccess 30 }
    
    
    fluidFSEventsParamsClientAccessInternalInfo OBJECT-TYPE
       SYNTAX  DisplayString
       MAX-ACCESS  read-only
       STATUS  current
       DESCRIPTION
           "Internal failure info for RnD troubleshooting, for example access decision flow or client disconnection reason"
       ::= { fluidFSEventsParamsClientAccess 31 }
    
    
    fluidFSEventsParamsClientAccessNfsErrorCode OBJECT-TYPE
       SYNTAX  INTEGER
       MAX-ACCESS  read-only
       STATUS  current
       DESCRIPTION
           "NFSERR_x code for troubleshooting purpose (as the part of internal info)"
       ::= { fluidFSEventsParamsClientAccess 32 }
    
    
    fluidFSEventsParamsClientAccessOpenModeAccessBits OBJECT-TYPE
       SYNTAX  INTEGER
       MAX-ACCESS  read-only
       STATUS  current
       DESCRIPTION
           "Open mode access bits(mask) used during file open"
       ::= { fluidFSEventsParamsClientAccess 33 }
    
    
    fluidFSEventsParamsClientAccessShareLevelPermissionsMode OBJECT-TYPE
       SYNTAX  DisplayString
       MAX-ACCESS  read-only
       STATUS  current
       DESCRIPTION
           "Share-level permission mode applied for current connection, like NONE, READ, CHANGE or FULL-CONTROL"
       ::= { fluidFSEventsParamsClientAccess 34 }
    
    
    fluidFSEventsParamsClientAccessOperation OBJECT-TYPE
       SYNTAX  DisplayString
       MAX-ACCESS  read-only
       STATUS  current
       DESCRIPTION
           "operation being executed"
       ::= { fluidFSEventsParamsClientAccess 35 }
    
    
    fluidFSEventsParamsClientAccessUser OBJECT-TYPE
       SYNTAX  DisplayString
       MAX-ACCESS  read-only
       STATUS  current
       DESCRIPTION
           "User ID (will undergo transformation as required)"
       ::= { fluidFSEventsParamsClientAccess 36 }
    
    
    fluidFSEventsParamsClientAccessCifsUser2 OBJECT-TYPE
       SYNTAX  DisplayString
       MAX-ACCESS  read-only
       STATUS  current
       DESCRIPTION
           "User SID as seen by likewise/cifs_server"
       ::= { fluidFSEventsParamsClientAccess 37 }
    
    
    fluidFSEventsParamsClientAccessNetgroupName OBJECT-TYPE
       SYNTAX  DisplayString
       MAX-ACCESS  read-only
       STATUS  current
       DESCRIPTION
           "UNIX external repository netgroup name"
       ::= { fluidFSEventsParamsClientAccess 38 }
    
    
    fluidFSEventsParamsClientAccessParentNetgroupName OBJECT-TYPE
       SYNTAX  DisplayString
       MAX-ACCESS  read-only
       STATUS  current
       DESCRIPTION
           "UNIX external repository netgroup name"
       ::= { fluidFSEventsParamsClientAccess 39 }
    
    
    fluidFSEventsParamsClientAccessNetgroupThreshold OBJECT-TYPE
       SYNTAX  INTEGER
       MAX-ACCESS  read-only
       STATUS  current
       DESCRIPTION
           "Critical threshold of netgroup metric (like size or nesting level)"
       ::= { fluidFSEventsParamsClientAccess 40 }
    
    
    fluidFSEventsParamsClientAccessNodeId OBJECT-TYPE
       SYNTAX  INTEGER
       MAX-ACCESS  read-only
       STATUS  current
       DESCRIPTION
           "Node Id (NAS controller ID)"
       ::= { fluidFSEventsParamsClientAccess 41 }
    
    
    fluidFSEventsParamsClientAccessMaxOpenFilesPerNode OBJECT-TYPE
       SYNTAX  INTEGER
       MAX-ACCESS  read-only
       STATUS  current
       DESCRIPTION
           "maximal number of open files per node"
       ::= { fluidFSEventsParamsClientAccess 42 }
    
    
    fluidFSEventsParamsClientAccessAdProviderName OBJECT-TYPE
       SYNTAX  DisplayString
       MAX-ACCESS  read-only
       STATUS  current
       DESCRIPTION
           "Name of active directory provider"
       ::= { fluidFSEventsParamsClientAccess 43 }
    
    
    fluidFSEventsParamsClientAccessDomainName OBJECT-TYPE
       SYNTAX  DisplayString
       MAX-ACCESS  read-only
       STATUS  current
       DESCRIPTION
           "Domain name"
       ::= { fluidFSEventsParamsClientAccess 44 }
    
    
    fluidFSEventsParamsClientAccessFileExtension OBJECT-TYPE
       SYNTAX  DisplayString
       MAX-ACCESS  read-only
       STATUS  current
       DESCRIPTION
           "File extension"
       ::= { fluidFSEventsParamsClientAccess 45 }
    
    
    fluidFSEventsParamsClientAccessCifsErrorCode OBJECT-TYPE
       SYNTAX  INTEGER
       MAX-ACCESS  read-only
       STATUS  current
       DESCRIPTION
           "Cifs code for troubleshooting purpose (as the part of internal info)"
       ::= { fluidFSEventsParamsClientAccess 46 }
    
    
    fluidFSEventsParamsClientAccessClusterVIP OBJECT-TYPE
       SYNTAX  DisplayString
       MAX-ACCESS  read-only
       STATUS  current
       DESCRIPTION
           "Server VIP address"
       ::= { fluidFSEventsParamsClientAccess 47 }
    
    
    fluidFSEventsParamsClientAccessServerKind OBJECT-TYPE
       SYNTAX  DisplayString
       MAX-ACCESS  read-only
       STATUS  current
       DESCRIPTION
           "Server kind"
       ::= { fluidFSEventsParamsClientAccess 48 }
    
    
    fluidFSEventsParamsClientAccessService OBJECT-TYPE
       SYNTAX  DisplayString
       MAX-ACCESS  read-only
       STATUS  current
       DESCRIPTION
           "Service name"
       ::= { fluidFSEventsParamsClientAccess 49 }
    
    
    fluidFSEventsParamsClientAccessUserEmail OBJECT-TYPE
       SYNTAX  DisplayString
       MAX-ACCESS  read-only
       STATUS  current
       DESCRIPTION
           ""
       ::= { fluidFSEventsParamsClientAccess 50 }
    
    
    fluidFSEventsParamsClientAccessDroppedNotificationsCounter OBJECT-TYPE
       SYNTAX  INTEGER
       MAX-ACCESS  read-only
       STATUS  current
       DESCRIPTION
           "counts how many events were dropped"
       ::= { fluidFSEventsParamsClientAccess 51 }
    
    
    fluidFSEventsParamsClientAccessPolicyName OBJECT-TYPE
       SYNTAX  DisplayString
       MAX-ACCESS  read-only
       STATUS  current
       DESCRIPTION
           "Policy name"
       ::= { fluidFSEventsParamsClientAccess 52 }
    
    
    fluidFSEventsParamsClientAccessPolicyGuid OBJECT-TYPE
       SYNTAX  DisplayString
       MAX-ACCESS  read-only
       STATUS  current
       DESCRIPTION
           "Policy guid"
       ::= { fluidFSEventsParamsClientAccess 53 }
    
    
    fluidFSEventsParamsClientAccessPolicyTargetPath OBJECT-TYPE
       SYNTAX  DisplayString
       MAX-ACCESS  read-only
       STATUS  current
       DESCRIPTION
           "Path"
       ::= { fluidFSEventsParamsClientAccess 54 }
    
    
    fluidFSEventsParamsClientAccessTenantId OBJECT-TYPE
       SYNTAX  DisplayString
       MAX-ACCESS  read-only
       STATUS  current
       DESCRIPTION
           ""
       ::= { fluidFSEventsParamsClientAccess 55 }
    
    
    fluidFSEventsParamsClientAccessTlsVersion OBJECT-TYPE
       SYNTAX  INTEGER
       MAX-ACCESS  read-only
       STATUS  current
       DESCRIPTION
           "Version of TLS protocol"
       ::= { fluidFSEventsParamsClientAccess 56 }
    
    
    fluidFSEventsParamsClientAccessBaseLandingPath OBJECT-TYPE
       SYNTAX  DisplayString
       MAX-ACCESS  read-only
       STATUS  current
       DESCRIPTION
           ""
       ::= { fluidFSEventsParamsClientAccess 57 }
    
    
    fluidFSEventsParamsClientAccessSuffixLandingPath OBJECT-TYPE
       SYNTAX  DisplayString
       MAX-ACCESS  read-only
       STATUS  current
       DESCRIPTION
           ""
       ::= { fluidFSEventsParamsClientAccess 58 }
    
    
    fluidFSEventsParamsClientAccessFilePath OBJECT-TYPE
       SYNTAX  DisplayString
       MAX-ACCESS  read-only
       STATUS  current
       DESCRIPTION
           ""
       ::= { fluidFSEventsParamsClientAccess 59 }
    
    
    fluidFSEventsParamsClientAccessSearchedObjects OBJECT-TYPE
       SYNTAX  DisplayString
       MAX-ACCESS  read-only
       STATUS  current
       DESCRIPTION
           ""
       ::= { fluidFSEventsParamsClientAccess 60 }
    
    
    fluidFSEventsParamsClientAccessRuleDN OBJECT-TYPE
       SYNTAX  DisplayString
       MAX-ACCESS  read-only
       STATUS  current
       DESCRIPTION
           ""
       ::= { fluidFSEventsParamsClientAccess 61 }
    
    
    fluidFSEventsParamsClientAccessPolicyDN OBJECT-TYPE
       SYNTAX  DisplayString
       MAX-ACCESS  read-only
       STATUS  current
       DESCRIPTION
           ""
       ::= { fluidFSEventsParamsClientAccess 62 }
    
    
    fluidFSEventsParamsClientAccessNasContainerIdIntegerName OBJECT-TYPE
       SYNTAX  DisplayString
       MAX-ACCESS  read-only
       STATUS  current
       DESCRIPTION
           ""
       ::= { fluidFSEventsParamsClientAccess 63 }
    
    
    fluidFSEventsParamsClientAccessTenantName OBJECT-TYPE
       SYNTAX  DisplayString
       MAX-ACCESS  read-only
       STATUS  current
       DESCRIPTION
           ""
       ::= { fluidFSEventsParamsClientAccess 64 }
    
    
    fluidFSEventsParamsClientAccessNfsUserName OBJECT-TYPE
       SYNTAX  DisplayString
       MAX-ACCESS  read-only
       STATUS  current
       DESCRIPTION
           ""
       ::= { fluidFSEventsParamsClientAccess 65 }
    
    
    fluidFSEventsParamsClientAccessDsidPath OBJECT-TYPE
       SYNTAX  DisplayString
       MAX-ACCESS  read-only
       STATUS  current
       DESCRIPTION
           ""
       ::= { fluidFSEventsParamsClientAccess 66 }
    
    
    fluidFSEventsParamsClientAccessDesiredNfsAccessMaskHrf OBJECT-TYPE
       SYNTAX  DisplayString
       MAX-ACCESS  read-only
       STATUS  current
       DESCRIPTION
           ""
       ::= { fluidFSEventsParamsClientAccess 67 }
    
    
    fluidFSEventsParamsClientAccessGrantedNfsAccessMaskHrf OBJECT-TYPE
       SYNTAX  DisplayString
       MAX-ACCESS  read-only
       STATUS  current
       DESCRIPTION
           ""
       ::= { fluidFSEventsParamsClientAccess 68 }
    
    
    fluidFSEventsParamsClientAccessUserOwnerName OBJECT-TYPE
       SYNTAX  DisplayString
       MAX-ACCESS  read-only
       STATUS  current
       DESCRIPTION
           ""
       ::= { fluidFSEventsParamsClientAccess 69 }
    
    
    fluidFSEventsParamsClientAccessGroupOwnerName OBJECT-TYPE
       SYNTAX  DisplayString
       MAX-ACCESS  read-only
       STATUS  current
       DESCRIPTION
           ""
       ::= { fluidFSEventsParamsClientAccess 70 }
    
    
    fluidFSEventsParamsClientAccessDesiredCifsAccessMaskName OBJECT-TYPE
       SYNTAX  DisplayString
       MAX-ACCESS  read-only
       STATUS  current
       DESCRIPTION
           ""
       ::= { fluidFSEventsParamsClientAccess 71 }
    
    
    fluidFSEventsParamsClientAccessMissedCifsAccessBitsName OBJECT-TYPE
       SYNTAX  DisplayString
       MAX-ACCESS  read-only
       STATUS  current
       DESCRIPTION
           ""
       ::= { fluidFSEventsParamsClientAccess 72 }
    
    
    fluidFSEventsParamsClientAccessOpenModeAccessBitsName OBJECT-TYPE
       SYNTAX  DisplayString
       MAX-ACCESS  read-only
       STATUS  current
       DESCRIPTION
           ""
       ::= { fluidFSEventsParamsClientAccess 73 }
    
    
    fluidFSEventsParamsClientAccessCifsUser2Name OBJECT-TYPE
       SYNTAX  DisplayString
       MAX-ACCESS  read-only
       STATUS  current
       DESCRIPTION
           ""
       ::= { fluidFSEventsParamsClientAccess 74 }
    
    
    fluidFSEventClientAccessMountFailureInternalError NOTIFICATION-TYPE
       OBJECTS { sysName, fluidFSEventsParamsClientAccessClientIpAddr, fluidFSEventsParamsClientAccessMountPath, fluidFSEventsParamsClientAccessNfsErrorCode }
       STATUS current
       DESCRIPTION
           "NFS mount failure. Internal mount error {{mountPath}}.   Description:  NFS mount failure: Internal mount error for the client {{clientIpAddr}} while mounting path {{mountPath}}.   Internal Information:   NFS error code: {{nfsErrorCode}} "
           --#TYPE         "Normal Event"
           --#SUMMARY      NFS mount failure. Internal mount error %s.   Description:  NFS mount failure: Internal mount error for the client %s while mounting path %s.   Internal Information:   NFS error code: %d 
           --#ARGUMENTS    {1,2,3}
           --#SEVERITY     INFORMATIONAL
           --#TIMEINDEX    99
           --#STATE        OK
       ::= { fluidFSEventsClientAccess 6 } 
    
    
    fluidFSEventClientAccessResetAdminPasswordFromConsole NOTIFICATION-TYPE
       OBJECTS { sysName }
       STATUS current
       DESCRIPTION
           "Administrator password was reset from the console.   Description:  Administrator password was reset from the console."
           --#TYPE         "Normal Event"
           --#SUMMARY      Administrator password was reset from the console.   Description:  Administrator password was reset from the console.
           --#ARGUMENTS    {}
           --#SEVERITY     INFORMATIONAL
           --#TIMEINDEX    99
           --#STATE        OK
       ::= { fluidFSEventsClientAccess 51 } 
    
    
    fluidFSEventClientAccessSMBMemThreshold1 NOTIFICATION-TYPE
       OBJECTS { sysName, fluidFSEventsParamsClientAccessNasControllerId }
       STATUS current
       DESCRIPTION
           "Due to SMB high resource usage disabling Large MTU.   Description:  Due to SMB high resource usage disabling Large MTU on NAS controller {{nasControllerId}}."
           --#TYPE         "Normal Event"
           --#SUMMARY      Due to SMB high resource usage disabling Large MTU.   Description:  Due to SMB high resource usage disabling Large MTU on NAS controller %s.
           --#ARGUMENTS    {1}
           --#SEVERITY     INFORMATIONAL
           --#TIMEINDEX    99
           --#STATE        OK
       ::= { fluidFSEventsClientAccess 54 } 
    
    
    fluidFSEventClientAccessSMBMemThreshold2 NOTIFICATION-TYPE
       OBJECTS { sysName, fluidFSEventsParamsClientAccessNasControllerId }
       STATUS current
       DESCRIPTION
           "Due to SMB high resource usage new connections not allowed.   Description:  Due to SMB high resource usage new connections are not allowed on NAS controller {{nasControllerId}}."
           --#TYPE         "Normal Event"
           --#SUMMARY      Due to SMB high resource usage new connections not allowed.   Description:  Due to SMB high resource usage new connections are not allowed on NAS controller %s.
           --#ARGUMENTS    {1}
           --#SEVERITY     INFORMATIONAL
           --#TIMEINDEX    99
           --#STATE        OK
       ::= { fluidFSEventsClientAccess 55 } 
    
    
    fluidFSEventClientAccessLockDBOutOfResources NOTIFICATION-TYPE
       OBJECTS { sysName, fluidFSEventsParamsClientAccessNodeId }
       STATUS current
       DESCRIPTION
           "File open or lock denied due to lack of internal resources.   Description:  NAS controller {{nodeId}} is low on resources and cannot serve SMB and NFSv4 file open and lock requests. Disconnect existing connections to free resources."
           --#TYPE         "Normal Event"
           --#SUMMARY      File open or lock denied due to lack of internal resources.   Description:  NAS controller %d is low on resources and cannot serve SMB and NFSv4 file open and lock requests. Disconnect existing connections to free resources.
           --#ARGUMENTS    {1}
           --#SEVERITY     INFORMATIONAL
           --#TIMEINDEX    99
           --#STATE        OK
       ::= { fluidFSEventsClientAccess 58 } 
    
    
    fluidFSEventClientAccessSessionDBOutOfResources NOTIFICATION-TYPE
       OBJECTS { sysName, fluidFSEventsParamsClientAccessNodeId }
       STATUS current
       DESCRIPTION
           "NFSv4 session was denied. Too many sessions currently in use   Description:  No resources available for new NFSv4 sessions as too many sessions are currently in use. NAS controller {{nodeId}}."
           --#TYPE         "Normal Event"
           --#SUMMARY      NFSv4 session was denied. Too many sessions currently in use   Description:  No resources available for new NFSv4 sessions as too many sessions are currently in use. NAS controller %d.
           --#ARGUMENTS    {1}
           --#SEVERITY     INFORMATIONAL
           --#TIMEINDEX    99
           --#STATE        OK
       ::= { fluidFSEventsClientAccess 59 } 
    
    
    fluidFSEventClientAccessUsersProxyNoService NOTIFICATION-TYPE
       OBJECTS { sysName, fluidFSEventsParamsClientAccessServerKind, fluidFSEventsParamsClientAccessService }
       STATUS current
       DESCRIPTION
           "NFS/SMB partial service   Description:  Access to {{serverKind}} directory service is limited or service is temporary unavailable   Action Items:  This scenario usually happens after directory changes (UNIX database re-configuration, Active Directory join, etc). The problem can occur due poor performance of newly configured directory; please wait some time until new directory will be fully initialized. In case of unexpected or persistent problem please check the operability of directory and network connectivity to directory service. Also problems with '{{service}}' internal service can cause this issue - please check for problematic services."
           --#TYPE         "Normal Event"
           --#SUMMARY      NFS/SMB partial service   Description:  Access to %s directory service is limited or service is temporary unavailable   Action Items:  This scenario usually happens after directory changes (UNIX database re-configuration, Active Directory join, etc). The problem can occur due poor performance of newly configured directory; please wait some time until new directory will be fully initialized. In case of unexpected or persistent problem please check the operability of directory and network connectivity to directory service. Also problems with '%s' internal service can cause this issue - please check for problematic services.
           --#ARGUMENTS    {1,2}
           --#SEVERITY     INFORMATIONAL
           --#TIMEINDEX    99
           --#STATE        OK
       ::= { fluidFSEventsClientAccess 70 } 
    
    
    fluidFSEventClientAccessSecChangeErrorBypassOn NOTIFICATION-TYPE
       OBJECTS { sysName }
       STATUS current
       DESCRIPTION
           "Security change errors bypassed   Description:  Errors due to chmod/chown/chgrp on volumes with windows security style now bypassed"
           --#TYPE         "Normal Event"
           --#SUMMARY      Security change errors bypassed   Description:  Errors due to chmod/chown/chgrp on volumes with windows security style now bypassed
           --#ARGUMENTS    {}
           --#SEVERITY     INFORMATIONAL
           --#TIMEINDEX    99
           --#STATE        OK
       ::= { fluidFSEventsClientAccess 71 } 
    
    
    fluidFSEventClientAccessSecChangeErrorBypassOff NOTIFICATION-TYPE
       OBJECTS { sysName }
       STATUS current
       DESCRIPTION
           "Security change errors returned   Description:  Errors due to chmod/chown/chgrp on volumes with windows security style now returned"
           --#TYPE         "Normal Event"
           --#SUMMARY      Security change errors returned   Description:  Errors due to chmod/chown/chgrp on volumes with windows security style now returned
           --#ARGUMENTS    {}
           --#SEVERITY     INFORMATIONAL
           --#TIMEINDEX    99
           --#STATE        OK
       ::= { fluidFSEventsClientAccess 72 } 
    
    
    fluidFSEventClientAccessFluidFsNotifyEventsDroppedDue2InternalIssues NOTIFICATION-TYPE
       OBJECTS { sysName, fluidFSEventsParamsClientAccessDroppedNotificationsCounter }
       STATUS current
       DESCRIPTION
           "File Access Notifications were dropped.   Description:  {{droppedNotificationsCounter}} File Access Notifications were dropped due to internal issues"
           --#TYPE         "Normal Event"
           --#SUMMARY      File Access Notifications were dropped.   Description:  %d File Access Notifications were dropped due to internal issues
           --#ARGUMENTS    {1}
           --#SEVERITY     INFORMATIONAL
           --#TIMEINDEX    99
           --#STATE        OK
       ::= { fluidFSEventsClientAccess 80 } 
    
    
    fluidFSEventClientAccessFluidFsNotifyEventsDroppedDue2ServerIssues NOTIFICATION-TYPE
       OBJECTS { sysName, fluidFSEventsParamsClientAccessDroppedNotificationsCounter }
       STATUS current
       DESCRIPTION
           "File Access Notifications were dropped.   Description:  {{droppedNotificationsCounter}} File Access Notifications were dropped due to auditing server issues"
           --#TYPE         "Normal Event"
           --#SUMMARY      File Access Notifications were dropped.   Description:  %d File Access Notifications were dropped due to auditing server issues
           --#ARGUMENTS    {1}
           --#SEVERITY     INFORMATIONAL
           --#TIMEINDEX    99
           --#STATE        OK
       ::= { fluidFSEventsClientAccess 81 } 
    
    
    fluidFSEventClientAccessFluidFsNotifyEncryptionFailure NOTIFICATION-TYPE
       OBJECTS { sysName }
       STATUS current
       DESCRIPTION
           "File Access Notification encryption failed   Description:  Failed initializing encrypted connection to the auditing server. encryption credentials configuration may be invalid"
           --#TYPE         "Normal Event"
           --#SUMMARY      File Access Notification encryption failed   Description:  Failed initializing encrypted connection to the auditing server. encryption credentials configuration may be invalid
           --#ARGUMENTS    {}
           --#SEVERITY     INFORMATIONAL
           --#TIMEINDEX    99
           --#STATE        OK
       ::= { fluidFSEventsClientAccess 82 } 
    
    
    fluidFSEventClientAccessMountFromInsecurePort NOTIFICATION-TYPE
       OBJECTS { sysName, fluidFSEventsParamsClientAccessClientIpAddr, fluidFSEventsParamsClientAccessNfsExport, fluidFSEventsParamsClientAccessNasContainerIdInteger, fluidFSEventsParamsClientAccessNfsClientPort }
       STATUS current
       DESCRIPTION
           "NFS mount failure. Wrong port was used for secure export {{nfsExport}}.   Description:  NFS mount failure: Client {{clientIpAddr}} attempted to mount the secure export {{nfsExport}} on NAS Volume {{nasContainerIdIntegerName}} but used port {{nfsClientPort}} instead of a well-known port (under 1024) on the client side.   Action Items:  Secure exports require that the client accessing them will perform the mount using a well-known port (under 1024). This is done as a security measure."
           --#TYPE         "Normal Event"
           --#SUMMARY      NFS mount failure. Wrong port was used for secure export %s.   Description:  NFS mount failure: Client %s attempted to mount the secure export %s on NAS Volume %s but used port %d instead of a well-known port (under 1024) on the client side.   Action Items:  Secure exports require that the client accessing them will perform the mount using a well-known port (under 1024). This is done as a security measure.
           --#ARGUMENTS    {1,2,3,4}
           --#SEVERITY     INFORMATIONAL
           --#TIMEINDEX    99
           --#STATE        OK
       ::= { fluidFSEventsClientAccess 89 } 
    
    
    fluidFSEventClientAccessMountExportDoesntExist NOTIFICATION-TYPE
       OBJECTS { sysName, fluidFSEventsParamsClientAccessTenantId, fluidFSEventsParamsClientAccessClientIpAddr, fluidFSEventsParamsClientAccessMountPath }
       STATUS current
       DESCRIPTION
           "NFS mount failure. The path {{mountPath}} is not exported by {{TenantName}}.   Description:  NFS mount failure: Client {{clientIpAddr}} attempted to mount the path ({{mountPath}}) from {{TenantName}} which is not exported to NFS clients.   Action Items:   This failure is commonly caused by spelling mistakes done on the client machine or when accessing the wrong server. List all available exports on the NAS and verify everything is as expected, all the needed exports exist and nothing has been changed unintentionally."
           --#TYPE         "Normal Event"
           --#SUMMARY      NFS mount failure. The path %s is not exported by %s.   Description:  NFS mount failure: Client %s attempted to mount the path (%s) from %s which is not exported to NFS clients.   Action Items:   This failure is commonly caused by spelling mistakes done on the client machine or when accessing the wrong server. List all available exports on the NAS and verify everything is as expected, all the needed exports exist and nothing has been changed unintentionally.
           --#ARGUMENTS    {1,2,3}
           --#SEVERITY     INFORMATIONAL
           --#TIMEINDEX    99
           --#STATE        OK
       ::= { fluidFSEventsClientAccess 90 } 
    
    
    fluidFSEventClientAccessMountPathDoesntExist NOTIFICATION-TYPE
       OBJECTS { sysName, fluidFSEventsParamsClientAccessClientIpAddr, fluidFSEventsParamsClientAccessMountPath, fluidFSEventsParamsClientAccessNasContainerIdInteger }
       STATUS current
       DESCRIPTION
           "NFS mount failure. Non existent mount path {{mountPath}}.   Description:  NFS mount failure: Client {{clientIpAddr}} tried to mount nonexistent mount path {{mountPath}} on NAS Volume {{nasContainerIdIntegerName}}."
           --#TYPE         "Normal Event"
           --#SUMMARY      NFS mount failure. Non existent mount path %s.   Description:  NFS mount failure: Client %s tried to mount nonexistent mount path %s on NAS Volume %s.
           --#ARGUMENTS    {1,2,3}
           --#SEVERITY     INFORMATIONAL
           --#TIMEINDEX    99
           --#STATE        OK
       ::= { fluidFSEventsClientAccess 91 } 
    
    
    fluidFSEventClientAccessMountFailurePermissionDenied NOTIFICATION-TYPE
       OBJECTS { sysName, fluidFSEventsParamsClientAccessClientIpAddr, fluidFSEventsParamsClientAccessMountPath, fluidFSEventsParamsClientAccessNasContainerIdInteger }
       STATUS current
       DESCRIPTION
           "NFS mount failure. Access denied during mount {{mountPath}}.   Description:  NFS mount failure: Access denied for the client {{clientIpAddr}} while mounting path {{mountPath}} on NAS Volume {{nasContainerIdIntegerName}}."
           --#TYPE         "Normal Event"
           --#SUMMARY      NFS mount failure. Access denied during mount %s.   Description:  NFS mount failure: Access denied for the client %s while mounting path %s on NAS Volume %s.
           --#ARGUMENTS    {1,2,3}
           --#SEVERITY     INFORMATIONAL
           --#TIMEINDEX    99
           --#STATE        OK
       ::= { fluidFSEventsClientAccess 92 } 
    
    
    fluidFSEventClientAccessMountFailedDueExportOptions NOTIFICATION-TYPE
       OBJECTS { sysName, fluidFSEventsParamsClientAccessClientIpAddr, fluidFSEventsParamsClientAccessNfsExport, fluidFSEventsParamsClientAccessNasContainerIdInteger, fluidFSEventsParamsClientAccessNfsExportOptions }
       STATUS current
       DESCRIPTION
           "NFS mount failure. Access attempt to limited export {{nfsExport}}   Description:  NFS mount failure: Client {{clientIpAddr}} is not allowed to access export {{nfsExport}} on NAS Volume {{nasContainerIdIntegerName}}, with defined export options: {{nfsExportOptions}}.   Action Items:   This error is caused by a client which accesses a limited export. The export was defined with clients limitations (network or netgroup or IP) that did not include the accessing client."
           --#TYPE         "Normal Event"
           --#SUMMARY      NFS mount failure. Access attempt to limited export %s   Description:  NFS mount failure: Client %s is not allowed to access export %s on NAS Volume %s, with defined export options: %s.   Action Items:   This error is caused by a client which accesses a limited export. The export was defined with clients limitations (network or netgroup or IP) that did not include the accessing client.
           --#ARGUMENTS    {1,2,3,4}
           --#SEVERITY     INFORMATIONAL
           --#TIMEINDEX    99
           --#STATE        OK
       ::= { fluidFSEventsClientAccess 93 } 
    
    
    fluidFSEventClientAccessMountFailedDueNetgroupFailure NOTIFICATION-TYPE
       OBJECTS { sysName, fluidFSEventsParamsClientAccessClientIpAddr, fluidFSEventsParamsClientAccessNfsExport, fluidFSEventsParamsClientAccessNasContainerIdInteger, fluidFSEventsParamsClientAccessNfsExportOptions }
       STATUS current
       DESCRIPTION
           "NFS mount failure. Netgroups could not be attained {{nfsExport}}.   Description:  NFS mount failure: Client {{clientIpAddr}} failed to mount export {{nfsExport}} on NAS Volume {{nasContainerIdIntegerName}} since the required netgroup information could not be attained. Export options: {{nfsExportOptions}}.   Action Items:  Check availability of NIS/LDAP server. This error is usually the outcome of a communication error between the NAS and the NIS/LDAP server. It could be caused by a network issue, directory server overload or a software malfunction in one of environment components."
           --#TYPE         "Normal Event"
           --#SUMMARY      NFS mount failure. Netgroups could not be attained %s.   Description:  NFS mount failure: Client %s failed to mount export %s on NAS Volume %s since the required netgroup information could not be attained. Export options: %s.   Action Items:  Check availability of NIS/LDAP server. This error is usually the outcome of a communication error between the NAS and the NIS/LDAP server. It could be caused by a network issue, directory server overload or a software malfunction in one of environment components.
           --#ARGUMENTS    {1,2,3,4}
           --#SEVERITY     INFORMATIONAL
           --#TIMEINDEX    99
           --#STATE        OK
       ::= { fluidFSEventsClientAccess 94 } 
    
    
    fluidFSEventClientAccessClientClockSkew NOTIFICATION-TYPE
       OBJECTS { sysName, fluidFSEventsParamsClientAccessTenantId, fluidFSEventsParamsClientAccessClientIpAddr, fluidFSEventsParamsClientAccessNasControllerId }
       STATUS current
       DESCRIPTION
           "Client authentication failed on {{TenantName}} due to client clock skew.   Description:  Kerberos authentication failed because of the client clock skew between client {{clientIpAddr}} and NAS controller {{nasControllerId}} of {{TenantName}}.   Action Items:  Fix client clock. Your client clock must be within 5 minutes range from the Kerberos server (i.e. AD) clock. Configure the used AD as an NTP server for this client to avoid clock skews errors."
           --#TYPE         "Normal Event"
           --#SUMMARY      Client authentication failed on %s due to client clock skew.   Description:  Kerberos authentication failed because of the client clock skew between client %s and NAS controller %s of %s.   Action Items:  Fix client clock. Your client clock must be within 5 minutes range from the Kerberos server (i.e. AD) clock. Configure the used AD as an NTP server for this client to avoid clock skews errors.
           --#ARGUMENTS    {1,2,3}
           --#SEVERITY     INFORMATIONAL
           --#TIMEINDEX    99
           --#STATE        OK
       ::= { fluidFSEventsClientAccess 95 } 
    
    
    fluidFSEventClientAccessSharePathNotFound NOTIFICATION-TYPE
       OBJECTS { sysName, fluidFSEventsParamsClientAccessClientIpAddr, fluidFSEventsParamsClientAccessCifsShare, fluidFSEventsParamsClientAccessNasContainerPath, fluidFSEventsParamsClientAccessNasContainerIdInteger }
       STATUS current
       DESCRIPTION
           "Client connect failure. Share {{cifsShare}} points to invalid directory.   Description:  SMB client connection failure: Client {{clientIpAddr}} accessed a nonexistent share {{cifsShare}} which refers to an inexistent directory {{nasContainerPath}} in NAS Volume {{nasContainerIdIntegerName}}.   Action Items:  List all available shares on the NAS and identify the problematic share. It should have an indication that it is not accessible."
           --#TYPE         "Normal Event"
           --#SUMMARY      Client connect failure. Share %s points to invalid directory.   Description:  SMB client connection failure: Client %s accessed a nonexistent share %s which refers to an inexistent directory %s in NAS Volume %s.   Action Items:  List all available shares on the NAS and identify the problematic share. It should have an indication that it is not accessible.
           --#ARGUMENTS    {1,2,3,4}
           --#SEVERITY     INFORMATIONAL
           --#TIMEINDEX    99
           --#STATE        OK
       ::= { fluidFSEventsClientAccess 96 } 
    
    
    fluidFSEventClientAccessIncorrectUserPassword NOTIFICATION-TYPE
       OBJECTS { sysName, fluidFSEventsParamsClientAccessTenantId, fluidFSEventsParamsClientAccessUserName, fluidFSEventsParamsClientAccessClientIpAddr, fluidFSEventsParamsClientAccessNasControllerId }
       STATUS current
       DESCRIPTION
           "SMB client login to {{TenantName}} failed. Wrong password for user {{userName}}.   Description:  SMB client login failure: Client {{clientIpAddr}} with user name '{{userName}}' supplied the wrong password. NAS Controller {{nasControllerId}} of {{TenantName}}."
           --#TYPE         "Normal Event"
           --#SUMMARY      SMB client login to %s failed. Wrong password for user %s.   Description:  SMB client login failure: Client %s with user name '%s' supplied the wrong password. NAS Controller %s of %s.
           --#ARGUMENTS    {1,2,3,4}
           --#SEVERITY     INFORMATIONAL
           --#TIMEINDEX    99
           --#STATE        OK
       ::= { fluidFSEventsClientAccess 97 } 
    
    
    fluidFSEventClientAccessLoginFailure NOTIFICATION-TYPE
       OBJECTS { sysName, fluidFSEventsParamsClientAccessTenantId, fluidFSEventsParamsClientAccessUserName, fluidFSEventsParamsClientAccessClientIpAddr, fluidFSEventsParamsClientAccessNasControllerId, fluidFSEventsParamsClientAccessInternalInfo }
       STATUS current
       DESCRIPTION
           "SMB client login to {{TenantName}} failed. Authorization failed for user {{userName}}.   Description:  Authorization for user '{{userName}}' failed, client {{clientIpAddr}}, NAS controller {{nasControllerId}} of {{TenantName}}.   Internal Information:   {{internalInfo}} "
           --#TYPE         "Normal Event"
           --#SUMMARY      SMB client login to %s failed. Authorization failed for user %s.   Description:  Authorization for user '%s' failed, client %s, NAS controller %s of %s.   Internal Information:   %s 
           --#ARGUMENTS    {1,2,3,4,5}
           --#SEVERITY     INFORMATIONAL
           --#TIMEINDEX    99
           --#STATE        OK
       ::= { fluidFSEventsClientAccess 98 } 
    
    
    fluidFSEventClientAccessShareDoesntExist NOTIFICATION-TYPE
       OBJECTS { sysName, fluidFSEventsParamsClientAccessTenantId, fluidFSEventsParamsClientAccessClientIpAddr, fluidFSEventsParamsClientAccessCifsShare }
       STATUS current
       DESCRIPTION
           "SMB client connection failure. Unavailable share {{cifsShare}} on {{TenantName}}.   Description:  SMB client connection failure: Client {{clientIpAddr}} attempted to connect to an unavailable share {{cifsShare}} of {{TenantName}}.   Action Items:  This failure is commonly caused by spelling mistakes done on the client machine or by a user trying to access the home share of a different user."
           --#TYPE         "Normal Event"
           --#SUMMARY      SMB client connection failure. Unavailable share %s on %s.   Description:  SMB client connection failure: Client %s attempted to connect to an unavailable share %s of %s.   Action Items:  This failure is commonly caused by spelling mistakes done on the client machine or by a user trying to access the home share of a different user.
           --#ARGUMENTS    {1,2,3}
           --#SEVERITY     INFORMATIONAL
           --#TIMEINDEX    99
           --#STATE        OK
       ::= { fluidFSEventsClientAccess 99 } 
    
    
    fluidFSEventClientAccessNfsAccessDenied NOTIFICATION-TYPE
       OBJECTS { sysName, fluidFSEventsParamsClientAccessNfsUser, fluidFSEventsParamsClientAccessDsid, fluidFSEventsParamsClientAccessNasContainerIdInteger, fluidFSEventsParamsClientAccessDesiredNfsAccessMask, fluidFSEventsParamsClientAccessGrantedNfsAccessMask, fluidFSEventsParamsClientAccessInternalInfo }
       STATUS current
       DESCRIPTION
           "NFS user {{nfsUserName}} access to a file denied. Insufficient permissions.   Description:  NFS access denied: user {{nfsUserName}} does not have sufficient permissions for the file {{dsidPath}} on NAS Volume {{nasContainerIdIntegerName}}. Desired/granted access mask: {{desiredNfsAccessMaskHrf}} / {{grantedNfsAccessMaskHrf}}.    Internal Information:   {{internalInfo}} "
           --#TYPE         "Normal Event"
           --#SUMMARY      NFS user %s access to a file denied. Insufficient permissions.   Description:  NFS access denied: user %s does not have sufficient permissions for the file %s on NAS Volume %s. Desired/granted access mask: %s / %s.    Internal Information:   %s 
           --#ARGUMENTS    {1,2,3,4,5,6}
           --#SEVERITY     INFORMATIONAL
           --#TIMEINDEX    99
           --#STATE        OK
       ::= { fluidFSEventsClientAccess 100 } 
    
    
    fluidFSEventClientAccessNfsModificationOfRoExport NOTIFICATION-TYPE
       OBJECTS { sysName, fluidFSEventsParamsClientAccessNfsUser, fluidFSEventsParamsClientAccessClientIpAddr, fluidFSEventsParamsClientAccessNfsExport, fluidFSEventsParamsClientAccessNasContainerIdInteger }
       STATUS current
       DESCRIPTION
           "NFS access denied. Attempt to modify a read-only export {{nfsExport}}.   Description:  NFS Access Denied: User {{nfsUserName}} accessing from {{clientIpAddr}} tried to perform modifications on a read-only export: {{nfsExport}}, NAS Volume {{nasContainerIdIntegerName}}.    Action Items:  Verify that the relevant export definition of read-only was done intentionally. Contact the user who is responsible for this access or for application access to understand the reason for using read-only export with write operations."
           --#TYPE         "Normal Event"
           --#SUMMARY      NFS access denied. Attempt to modify a read-only export %s.   Description:  NFS Access Denied: User %s accessing from %s tried to perform modifications on a read-only export: %s, NAS Volume %s.    Action Items:  Verify that the relevant export definition of read-only was done intentionally. Contact the user who is responsible for this access or for application access to understand the reason for using read-only export with write operations.
           --#ARGUMENTS    {1,2,3,4}
           --#SEVERITY     INFORMATIONAL
           --#TIMEINDEX    99
           --#STATE        OK
       ::= { fluidFSEventsClientAccess 101 } 
    
    
    fluidFSEventClientAccessNfsAccessFromInsecurePortToSecureExport NOTIFICATION-TYPE
       OBJECTS { sysName, fluidFSEventsParamsClientAccessNfsUser, fluidFSEventsParamsClientAccessClientIpAddr, fluidFSEventsParamsClientAccessNfsExport, fluidFSEventsParamsClientAccessNasContainerIdInteger, fluidFSEventsParamsClientAccessNfsClientPort }
       STATUS current
       DESCRIPTION
           "NFS access denied. Secured port must be used; export {{nfsExport}}.   Description:  NFS Access Denied: User {{nfsUserName}} tried to access from {{clientIpAddr}} to a secure export {{nfsExport}}, NAS Volume {{nasContainerIdIntegerName}} using a non secure port {{nfsClientPort}}.    Action Items:  Secure exports require that the client accessing them will use a well-known port (under 1024). This is done as a security measure. Identify the relevant export and the checkbox that marks it as secure/requires secure port.  If there is no need for a secure export (e.g. the network is not public) make the export insecure by unchecking the secure export option and try again.  If the export must remain secure, please refer to the NFS client documentation in order to change the currently used NFS client port to a well-known port (under 1024)."
           --#TYPE         "Normal Event"
           --#SUMMARY      NFS access denied. Secured port must be used; export %s.   Description:  NFS Access Denied: User %s tried to access from %s to a secure export %s, NAS Volume %s using a non secure port %d.    Action Items:  Secure exports require that the client accessing them will use a well-known port (under 1024). This is done as a security measure. Identify the relevant export and the checkbox that marks it as secure/requires secure port.  If there is no need for a secure export (e.g. the network is not public) make the export insecure by unchecking the secure export option and try again.  If the export must remain secure, please refer to the NFS client documentation in order to change the currently used NFS client port to a well-known port (under 1024).
           --#ARGUMENTS    {1,2,3,4,5}
           --#SEVERITY     INFORMATIONAL
           --#TIMEINDEX    99
           --#STATE        OK
       ::= { fluidFSEventsClientAccess 102 } 
    
    
    fluidFSEventClientAccessModificationOfRoVolume NOTIFICATION-TYPE
       OBJECTS { sysName, fluidFSEventsParamsClientAccessNfsUser, fluidFSEventsParamsClientAccessClientIpAddr, fluidFSEventsParamsClientAccessDsid, fluidFSEventsParamsClientAccessNfsOp, fluidFSEventsParamsClientAccessNasContainerIdInteger }
       STATUS current
       DESCRIPTION
           "Access denied. Attempt to modify a read-only NAS volume {{nasContainerIdIntegerName}}.   Description:  Access denied: User {{nfsUserName}} accessing from client {{clientIpAddr}} tried to modify the file {{dsidPath}} with operation '{{nfsOp}}' on a read-only NAS volume {{nasContainerIdIntegerName}}."
           --#TYPE         "Normal Event"
           --#SUMMARY      Access denied. Attempt to modify a read-only NAS volume %s.   Description:  Access denied: User %s accessing from client %s tried to modify the file %s with operation '%s' on a read-only NAS volume %s.
           --#ARGUMENTS    {1,2,3,4,5}
           --#SEVERITY     INFORMATIONAL
           --#TIMEINDEX    99
           --#STATE        OK
       ::= { fluidFSEventsClientAccess 103 } 
    
    
    fluidFSEventClientAccessModifyAccessToSnapshot NOTIFICATION-TYPE
       OBJECTS { sysName, fluidFSEventsParamsClientAccessNfsUser, fluidFSEventsParamsClientAccessClientIpAddr, fluidFSEventsParamsClientAccessDsid, fluidFSEventsParamsClientAccessNasContainerIdInteger }
       STATUS current
       DESCRIPTION
           "Access denied. Attempt to modify a snapshot; NAS volume {{nasContainerIdIntegerName}}.   Description:  Access denied: User {{nfsUserName}} accessing from client {{clientIpAddr}} tried to modify the file {{dsidPath}} on NAS volume {{nasContainerIdIntegerName}} that is located in a snapshot.   Action Items:  Snapshot is an exact representation of the NAS volume data at the time of the snapshot creation. For that reason, and by definition, snapshot data can't be modified.  Contact the user and instruct him to limit any modifications to the current work area in the NAS volume."
           --#TYPE         "Normal Event"
           --#SUMMARY      Access denied. Attempt to modify a snapshot; NAS volume %s.   Description:  Access denied: User %s accessing from client %s tried to modify the file %s on NAS volume %s that is located in a snapshot.   Action Items:  Snapshot is an exact representation of the NAS volume data at the time of the snapshot creation. For that reason, and by definition, snapshot data can't be modified.  Contact the user and instruct him to limit any modifications to the current work area in the NAS volume.
           --#ARGUMENTS    {1,2,3,4}
           --#SEVERITY     INFORMATIONAL
           --#TIMEINDEX    99
           --#STATE        OK
       ::= { fluidFSEventsClientAccess 104 } 
    
    
    fluidFSEventClientAccessNfsOpNotAllowedDueVolumeStyle NOTIFICATION-TYPE
       OBJECTS { sysName, fluidFSEventsParamsClientAccessNfsUser, fluidFSEventsParamsClientAccessClientIpAddr, fluidFSEventsParamsClientAccessNfsOp, fluidFSEventsParamsClientAccessVolumeStyle, fluidFSEventsParamsClientAccessNasContainerIdInteger, fluidFSEventsParamsClientAccessDsid }
       STATUS current
       DESCRIPTION
           "NFS access denied. Operation not permitted on {{volumeStyle}} volume {{nasContainerIdIntegerName}}.   Description:  NFS access denied: User {{nfsUserName}} accessing from client {{clientIpAddr}} tried to '{{nfsOp}}' on a {{volumeStyle}} NAS volume {{nasContainerIdIntegerName}}, file {{dsidPath}}. [[nl]] Choosing a volume security style dictates which protocol will be used to set permissions on files in this volume. This also sets certain limitations on operations which are not allowed for this security style: [[nl]]1.  Setting an ACL for a file in a NAS volume defined with UNIX  Security style. [[nl]]2.  Setting mode for a file in a NAS volume defined with NTFS Security style. [[nl]]3.  Changing the read-only flag for a file in a NAS volume defined with UNIX  Security style. [[nl]]4.  Setting SID/GSID ownership on UNIX Security style [[nl]]5.  Setting UID/GID ownership on NTFS Security style. [[nl]]A user might try to perform one of the above actions and get an 'Access denied' error without understanding why.   Action Items:  The NAS Volume security style should be chosen according to the main intended usage. If a user needs to perform a security related activity which is forbidden, consider splitting the data into two separate NAS Volumes based on the access pattern."
           --#TYPE         "Normal Event"
           --#SUMMARY      NFS access denied. Operation not permitted on %s volume %s.   Description:  NFS access denied: User %s accessing from client %s tried to '%s' on a %s NAS volume %s, file %s. [[nl]] Choosing a volume security style dictates which protocol will be used to set permissions on files in this volume. This also sets certain limitations on operations which are not allowed for this security style: [[nl]]1.  Setting an ACL for a file in a NAS volume defined with UNIX  Security style. [[nl]]2.  Setting mode for a file in a NAS volume defined with NTFS Security style. [[nl]]3.  Changing the read-only flag for a file in a NAS volume defined with UNIX  Security style. [[nl]]4.  Setting SID/GSID ownership on UNIX Security style [[nl]]5.  Setting UID/GID ownership on NTFS Security style. [[nl]]A user might try to perform one of the above actions and get an 'Access denied' error without understanding why.   Action Items:  The NAS Volume security style should be chosen according to the main intended usage. If a user needs to perform a security related activity which is forbidden, consider splitting the data into two separate NAS Volumes based on the access pattern.
           --#ARGUMENTS    {1,2,3,4,5,6}
           --#SEVERITY     INFORMATIONAL
           --#TIMEINDEX    99
           --#STATE        OK
       ::= { fluidFSEventsClientAccess 105 } 
    
    
    fluidFSEventClientAccessNotAnOwner NOTIFICATION-TYPE
       OBJECTS { sysName, fluidFSEventsParamsClientAccessNfsUser, fluidFSEventsParamsClientAccessClientIpAddr, fluidFSEventsParamsClientAccessNfsOp, fluidFSEventsParamsClientAccessDsid, fluidFSEventsParamsClientAccessNasContainerIdInteger, fluidFSEventsParamsClientAccessUserOwner, fluidFSEventsParamsClientAccessGroupOwner }
       STATUS current
       DESCRIPTION
           "NFS access denied. User {{nfsUserName}} not owner of file.   Description:  NFS Access Denied: User {{nfsUserName}} accessing from client {{clientIpAddr}} can't perform owner restricted operation {{nfsOp}} on file {{dsidPath}}, NAS Volume {{nasContainerIdIntegerName}}, file owner {{userOwnerName}} : {{groupOwnerName}}."
           --#TYPE         "Normal Event"
           --#SUMMARY      NFS access denied. User %s not owner of file.   Description:  NFS Access Denied: User %s accessing from client %s can't perform owner restricted operation %s on file %s, NAS Volume %s, file owner %s : %s.
           --#ARGUMENTS    {1,2,3,4,5,6,7}
           --#SEVERITY     INFORMATIONAL
           --#TIMEINDEX    99
           --#STATE        OK
       ::= { fluidFSEventsClientAccess 106 } 
    
    
    fluidFSEventClientAccessGiveUidOwnershipAwayDenied NOTIFICATION-TYPE
       OBJECTS { sysName, fluidFSEventsParamsClientAccessNfsUser, fluidFSEventsParamsClientAccessClientIpAddr, fluidFSEventsParamsClientAccessNfsOp, fluidFSEventsParamsClientAccessUserOwner, fluidFSEventsParamsClientAccessDsid, fluidFSEventsParamsClientAccessNasContainerIdInteger }
       STATUS current
       DESCRIPTION
           "NFS access denied. Root privileges needed to give ownership.   Description:  NFS Access Denied: User {{nfsUserName}} accessing from client {{clientIpAddr}} can't give ownership away by operation {{nfsOp}} on file {{dsidPath}} to {{userOwnerName}} because root privileges are required for that, NAS Volume {{nasContainerIdIntegerName}}."
           --#TYPE         "Normal Event"
           --#SUMMARY      NFS access denied. Root privileges needed to give ownership.   Description:  NFS Access Denied: User %s accessing from client %s can't give ownership away by operation %s on file %s to %s because root privileges are required for that, NAS Volume %s.
           --#ARGUMENTS    {1,2,3,4,5,6}
           --#SEVERITY     INFORMATIONAL
           --#TIMEINDEX    99
           --#STATE        OK
       ::= { fluidFSEventsClientAccess 107 } 
    
    
    fluidFSEventClientAccessGiveGidOwnershipAwayDenied NOTIFICATION-TYPE
       OBJECTS { sysName, fluidFSEventsParamsClientAccessNfsUser, fluidFSEventsParamsClientAccessClientIpAddr, fluidFSEventsParamsClientAccessNfsOp, fluidFSEventsParamsClientAccessGroupOwner, fluidFSEventsParamsClientAccessDsid, fluidFSEventsParamsClientAccessNasContainerIdInteger }
       STATUS current
       DESCRIPTION
           "NFS access denied. Root privileges needed to give ownership.   Description:  NFS Access Denied: User {{nfsUserName}} accessing from client {{clientIpAddr}} can't give ownership away by operation {{nfsOp}} on file {{dsidPath}} to {{groupOwnerName}} because root privileges are required for that, NAS Volume {{nasContainerIdIntegerName}}."
           --#TYPE         "Normal Event"
           --#SUMMARY      NFS access denied. Root privileges needed to give ownership.   Description:  NFS Access Denied: User %s accessing from client %s can't give ownership away by operation %s on file %s to %s because root privileges are required for that, NAS Volume %s.
           --#ARGUMENTS    {1,2,3,4,5,6}
           --#SEVERITY     INFORMATIONAL
           --#TIMEINDEX    99
           --#STATE        OK
       ::= { fluidFSEventsClientAccess 108 } 
    
    
    fluidFSEventClientAccessOwnerOfDifferentTypes NOTIFICATION-TYPE
       OBJECTS { sysName, fluidFSEventsParamsClientAccessClientIpAddr, fluidFSEventsParamsClientAccessNfsUser, fluidFSEventsParamsClientAccessDsid, fluidFSEventsParamsClientAccessNasContainerIdInteger, fluidFSEventsParamsClientAccessUserOwner, fluidFSEventsParamsClientAccessUserIdentityType, fluidFSEventsParamsClientAccessGroupOwner, fluidFSEventsParamsClientAccessGroupIdentityType }
       STATUS current
       DESCRIPTION
           "NFS access denied. File and group owner are inconsistent.   Description:  NFS Access Denied: both file owner and group owner must be from the same identity type (NTFS vs UNIX), attempt to set different identity types was detected.  Client {{clientIpAddr}} User: {{nfsUserName}}, file {{dsidPath}} on NAS Volume {{nasContainerIdIntegerName}}, setting ownership: {{userOwnerName}} ({{userIdentityType}}) : {{groupOwnerName}} ({{groupIdentityType}}).   Action Items:  It is impossible to change file owner id to UID if the original file ownership is SID/GSID. If the user wants to change the ownership of the file to UNIX ownership, he must set UID and GID at same time. For example:  user chown michael:group and not chown michael."
           --#TYPE         "Normal Event"
           --#SUMMARY      NFS access denied. File and group owner are inconsistent.   Description:  NFS Access Denied: both file owner and group owner must be from the same identity type (NTFS vs UNIX), attempt to set different identity types was detected.  Client %s User: %s, file %s on NAS Volume %s, setting ownership: %s (%s) : %s (%s).   Action Items:  It is impossible to change file owner id to UID if the original file ownership is SID/GSID. If the user wants to change the ownership of the file to UNIX ownership, he must set UID and GID at same time. For example:  user chown michael:group and not chown michael.
           --#ARGUMENTS    {1,2,3,4,5,6,7,8}
           --#SEVERITY     INFORMATIONAL
           --#TIMEINDEX    99
           --#STATE        OK
       ::= { fluidFSEventsClientAccess 109 } 
    
    
    fluidFSEventClientAccessCifsOpNotAllowedDueVolumeStyle NOTIFICATION-TYPE
       OBJECTS { sysName, fluidFSEventsParamsClientAccessNfsUser, fluidFSEventsParamsClientAccessNfsOp, fluidFSEventsParamsClientAccessVolumeStyle, fluidFSEventsParamsClientAccessNasContainerIdInteger, fluidFSEventsParamsClientAccessDsid }
       STATUS current
       DESCRIPTION
           "SMB access denied. Operation not permitted on {{volumeStyle}} volume.   Description:  Access Denied: User {{nfsUserName}} tried to '{{nfsOp}}' on a {{volumeStyle}} NAS Volume {{nasContainerIdIntegerName}}, file {{dsidPath}}. [[nl]]Choosing a volume security style dictates which protocol will be used to set permissions on files in this volume. This also sets certain limitations on operations which are not allowed for this security style: [[nl]]1.  Setting an ACL for a file in a NAS volume defined with UNIX  Security style. [[nl]]2.  Setting mode for a file in a NAS volume defined with NTFS Security style. [[nl]]3.  Changing the read-only flag for a file in a NAS volume defined with UNIX  Security style. [[nl]]4.  Setting SID/GSID ownership on UNIX Security style [[nl]]5.  Setting UID/GID ownership on NTFS Security style. [[nl]]A user might try to perform one of the above actions and get an 'Access denied' error without understanding why.   Action Items:  The NAS Volume security style should be chosen according to the main intended usage.  If a user needs to perform a security related activity which is forbidden, consider splitting the data into two separate NAS Volumes based on the access pattern."
           --#TYPE         "Normal Event"
           --#SUMMARY      SMB access denied. Operation not permitted on %s volume.   Description:  Access Denied: User %s tried to '%s' on a %s NAS Volume %s, file %s. [[nl]]Choosing a volume security style dictates which protocol will be used to set permissions on files in this volume. This also sets certain limitations on operations which are not allowed for this security style: [[nl]]1.  Setting an ACL for a file in a NAS volume defined with UNIX  Security style. [[nl]]2.  Setting mode for a file in a NAS volume defined with NTFS Security style. [[nl]]3.  Changing the read-only flag for a file in a NAS volume defined with UNIX  Security style. [[nl]]4.  Setting SID/GSID ownership on UNIX Security style [[nl]]5.  Setting UID/GID ownership on NTFS Security style. [[nl]]A user might try to perform one of the above actions and get an 'Access denied' error without understanding why.   Action Items:  The NAS Volume security style should be chosen according to the main intended usage.  If a user needs to perform a security related activity which is forbidden, consider splitting the data into two separate NAS Volumes based on the access pattern.
           --#ARGUMENTS    {1,2,3,4,5}
           --#SEVERITY     INFORMATIONAL
           --#TIMEINDEX    99
           --#STATE        OK
       ::= { fluidFSEventsClientAccess 110 } 
    
    
    fluidFSEventClientAccessConnectionFailurePermissionDenied NOTIFICATION-TYPE
       OBJECTS { sysName, fluidFSEventsParamsClientAccessUserName, fluidFSEventsParamsClientAccessCifsShare, fluidFSEventsParamsClientAccessClientIpAddr, fluidFSEventsParamsClientAccessNasControllerId, fluidFSEventsParamsClientAccessNasContainerIdInteger }
       STATUS current
       DESCRIPTION
           "Share {{cifsShare}} ACL's denied access to user {{userName}}.   Description:  Connection for user '{{userName}}' to share {{cifsShare}} denied due to share ACL permissions, client {{clientIpAddr}}, NAS Controller {{nasControllerId}}, NAS Volume {{nasContainerIdIntegerName}}."
           --#TYPE         "Normal Event"
           --#SUMMARY      Share %s ACL's denied access to user %s.   Description:  Connection for user '%s' to share %s denied due to share ACL permissions, client %s, NAS Controller %s, NAS Volume %s.
           --#ARGUMENTS    {1,2,3,4,5}
           --#SEVERITY     INFORMATIONAL
           --#TIMEINDEX    99
           --#STATE        OK
       ::= { fluidFSEventsClientAccess 111 } 
    
    
    fluidFSEventClientAccessGeneralAccessDenied NOTIFICATION-TYPE
       OBJECTS { sysName, fluidFSEventsParamsClientAccessCifsOp, fluidFSEventsParamsClientAccessDesiredCifsAccessMask, fluidFSEventsParamsClientAccessMissedCifsAccessBits, fluidFSEventsParamsClientAccessClientIpAddr, fluidFSEventsParamsClientAccessUser, fluidFSEventsParamsClientAccessDsid, fluidFSEventsParamsClientAccessNasContainerIdInteger, fluidFSEventsParamsClientAccessInternalInfo }
       STATUS current
       DESCRIPTION
           "Access denied.  Insufficient permissions, user {{userName}}.   Description:  Access denied on '{{cifsOp}}' operation.  Desired access mask: {{desiredCifsAccessMaskName}}, missing bits: {{missedCifsAccessBitsName}}, client: {{clientIpAddr}}, user: {{userName}}, file '{{dsidPath}}' on NAS Volume {{nasContainerIdIntegerName}}.   Internal Information:   {{internalInfo}} "
           --#TYPE         "Normal Event"
           --#SUMMARY      Access denied.  Insufficient permissions, user %s.   Description:  Access denied on '%s' operation.  Desired access mask: %s, missing bits: %s, client: %s, user: %s, file '%s' on NAS Volume %s.   Internal Information:   %s 
           --#ARGUMENTS    {1,2,3,4,5,6,7,8}
           --#SEVERITY     INFORMATIONAL
           --#TIMEINDEX    99
           --#STATE        OK
       ::= { fluidFSEventsClientAccess 112 } 
    
    
    fluidFSEventClientAccessNfs4WritePseudoFS NOTIFICATION-TYPE
       OBJECTS { sysName, fluidFSEventsParamsClientAccessClientIpAddr, fluidFSEventsParamsClientAccessUser, fluidFSEventsParamsClientAccessTenantId }
       STATUS current
       DESCRIPTION
           "Write Access to pseudo-fs of {{TenantName}}, user {{userName}}.   Description:  Write Access denied to user {{userName}}. Attempted modification of NFS4 Pseudo File System of {{TenantName}}). Client IP: {{clientIpAddr}}."
           --#TYPE         "Normal Event"
           --#SUMMARY      Write Access to pseudo-fs of %s, user %s.   Description:  Write Access denied to user %s. Attempted modification of NFS4 Pseudo File System of %s). Client IP: %s.
           --#ARGUMENTS    {1,2,3}
           --#SEVERITY     INFORMATIONAL
           --#TIMEINDEX    99
           --#STATE        OK
       ::= { fluidFSEventsClientAccess 113 } 
    
    
    fluidFSEventClientAccessAccessDeniedOpenModeConflict NOTIFICATION-TYPE
       OBJECTS { sysName, fluidFSEventsParamsClientAccessOperation, fluidFSEventsParamsClientAccessDesiredCifsAccessMask, fluidFSEventsParamsClientAccessOpenModeAccessBits, fluidFSEventsParamsClientAccessClientIpAddr, fluidFSEventsParamsClientAccessUser, fluidFSEventsParamsClientAccessDsid, fluidFSEventsParamsClientAccessNasContainerIdInteger }
       STATUS current
       DESCRIPTION
           "Access Denied. Open mode conflict; user {{userName}}.   Description:  Access Denied on '{{operation}}' operation due open mode conflict.  Desired access mask: {{desiredCifsAccessMaskName}},  open mode mask: {{openModeAccessBitsName}},  client: {{clientIpAddr}},  user: {{userName}},  file '{{dsidPath}}' on NAS Volume {{nasContainerIdIntegerName}}. "
           --#TYPE         "Normal Event"
           --#SUMMARY      Access Denied. Open mode conflict; user %s.   Description:  Access Denied on '%s' operation due open mode conflict.  Desired access mask: %s,  open mode mask: %s,  client: %s,  user: %s,  file '%s' on NAS Volume %s. 
           --#ARGUMENTS    {1,2,3,4,5,6,7}
           --#SEVERITY     INFORMATIONAL
           --#TIMEINDEX    99
           --#STATE        OK
       ::= { fluidFSEventsClientAccess 114 } 
    
    
    fluidFSEventClientAccessAccessDeniedShareModeConflict NOTIFICATION-TYPE
       OBJECTS { sysName, fluidFSEventsParamsClientAccessUser, fluidFSEventsParamsClientAccessClientIpAddr, fluidFSEventsParamsClientAccessDsid, fluidFSEventsParamsClientAccessNasContainerIdInteger }
       STATUS current
       DESCRIPTION
           "Access Denied. Conflict with share mode; NAS Volume {{nasContainerIdIntegerName}}.   Description:  Access Denied: User {{userName}} accessing from client {{clientIpAddr}} tried to open file {{dsidPath}} on NAS Volume {{nasContainerIdIntegerName}}, which is opened with conflicting share mode by another user."
           --#TYPE         "Normal Event"
           --#SUMMARY      Access Denied. Conflict with share mode; NAS Volume %s.   Description:  Access Denied: User %s accessing from client %s tried to open file %s on NAS Volume %s, which is opened with conflicting share mode by another user.
           --#ARGUMENTS    {1,2,3,4}
           --#SEVERITY     INFORMATIONAL
           --#TIMEINDEX    99
           --#STATE        OK
       ::= { fluidFSEventsClientAccess 115 } 
    
    
    fluidFSEventClientAccessDeleteOnCloseIsSet NOTIFICATION-TYPE
       OBJECTS { sysName, fluidFSEventsParamsClientAccessUser, fluidFSEventsParamsClientAccessClientIpAddr, fluidFSEventsParamsClientAccessDsid, fluidFSEventsParamsClientAccessNasContainerIdInteger }
       STATUS current
       DESCRIPTION
           "Access denied. File marked for deletion; File {{dsidPath}}.   Description:  Access denied: the file is marked for deletion.  Client: {{clientIpAddr}}, user: {{userName}}, file {{dsidPath}} on NAS Volume {{nasContainerIdIntegerName}}."
           --#TYPE         "Normal Event"
           --#SUMMARY      Access denied. File marked for deletion; File %s.   Description:  Access denied: the file is marked for deletion.  Client: %s, user: %s, file %s on NAS Volume %s.
           --#ARGUMENTS    {1,2,3,4}
           --#SEVERITY     INFORMATIONAL
           --#TIMEINDEX    99
           --#STATE        OK
       ::= { fluidFSEventsClientAccess 116 } 
    
    
    fluidFSEventClientAccessUserPasswordExpired NOTIFICATION-TYPE
       OBJECTS { sysName, fluidFSEventsParamsClientAccessTenantId, fluidFSEventsParamsClientAccessUserName, fluidFSEventsParamsClientAccessClientIpAddr, fluidFSEventsParamsClientAccessNasControllerId }
       STATUS current
       DESCRIPTION
           "SMB client login to {{TenantName}} failed. Password expired for user {{userName}}.   Description:  SMB client login failure: Password expired for client {{clientIpAddr}} user name '{{userName}}'. NAS Controller {{nasControllerId}} of {{TenantName}}."
           --#TYPE         "Normal Event"
           --#SUMMARY      SMB client login to %s failed. Password expired for user %s.   Description:  SMB client login failure: Password expired for client %s user name '%s'. NAS Controller %s of %s.
           --#ARGUMENTS    {1,2,3,4}
           --#SEVERITY     INFORMATIONAL
           --#TIMEINDEX    99
           --#STATE        OK
       ::= { fluidFSEventsClientAccess 117 } 
    
    
    fluidFSEventClientAccessNoSuchUser NOTIFICATION-TYPE
       OBJECTS { sysName, fluidFSEventsParamsClientAccessTenantId, fluidFSEventsParamsClientAccessUserName, fluidFSEventsParamsClientAccessClientIpAddr, fluidFSEventsParamsClientAccessNasControllerId }
       STATUS current
       DESCRIPTION
           "SMB client login to {{TenantName}} failed. The user {{userName}} could not be found.   Description:  SMB client login failure: The login username '{{userName}}' could not be found for client {{clientIpAddr}}. NAS Controller {{nasControllerId}} of {{TenantName}}."
           --#TYPE         "Normal Event"
           --#SUMMARY      SMB client login to %s failed. The user %s could not be found.   Description:  SMB client login failure: The login username '%s' could not be found for client %s. NAS Controller %s of %s.
           --#ARGUMENTS    {1,2,3,4}
           --#SEVERITY     INFORMATIONAL
           --#TIMEINDEX    99
           --#STATE        OK
       ::= { fluidFSEventsClientAccess 118 } 
    
    
    fluidFSEventClientAccessCifsAccessDeniedDueShareLevelPerms2 NOTIFICATION-TYPE
       OBJECTS { sysName, fluidFSEventsParamsClientAccessCifsOp, fluidFSEventsParamsClientAccessDesiredCifsAccessMask, fluidFSEventsParamsClientAccessClientIpAddr, fluidFSEventsParamsClientAccessUserName, fluidFSEventsParamsClientAccessCifsShare, fluidFSEventsParamsClientAccessNasContainerPath, fluidFSEventsParamsClientAccessNasContainerIdInteger }
       STATUS current
       DESCRIPTION
           "Share-level permissions denied access; share {{cifsShare}}.   Description:  SMB access denied on '{{cifsOp}}' operation: share-level permission applied for the share {{cifsShare}} prohibits such actions. Desired access mask: {{desiredCifsAccessMaskName}}, client: {{clientIpAddr}}, user: {{userName}}, file '{{nasContainerPath}}' on NAS Volume {{nasContainerIdIntegerName}}. "
           --#TYPE         "Normal Event"
           --#SUMMARY      Share-level permissions denied access; share %s.   Description:  SMB access denied on '%s' operation: share-level permission applied for the share %s prohibits such actions. Desired access mask: %s, client: %s, user: %s, file '%s' on NAS Volume %s. 
           --#ARGUMENTS    {1,2,3,4,5,6,7}
           --#SEVERITY     INFORMATIONAL
           --#TIMEINDEX    99
           --#STATE        OK
       ::= { fluidFSEventsClientAccess 119 } 
    
    
    fluidFSEventClientAccessCifsDotSnapshotsAccessDeniedDueToRestriction NOTIFICATION-TYPE
       OBJECTS { sysName, fluidFSEventsParamsClientAccessClientIpAddr, fluidFSEventsParamsClientAccessUserName, fluidFSEventsParamsClientAccessCifsShare, fluidFSEventsParamsClientAccessNasContainerPath, fluidFSEventsParamsClientAccessNasContainerIdInteger }
       STATUS current
       DESCRIPTION
           "Snapshot Access denied due to restriction   Description:  SMB snapshot access to share {{cifsShare}} was denied due to ".snapshots" restriction. client: {{clientIpAddr}}, user: {{userName}}, file '{{nasContainerPath}}' on NAS Volume {{nasContainerIdIntegerName}}. "
           --#TYPE         "Normal Event"
           --#SUMMARY      Snapshot Access denied due to restriction   Description:  SMB snapshot access to share %s was denied due to ".snapshots" restriction. client: %s, user: %s, file '%s' on NAS Volume %s. 
           --#ARGUMENTS    {1,2,3,4,5}
           --#SEVERITY     INFORMATIONAL
           --#TIMEINDEX    99
           --#STATE        OK
       ::= { fluidFSEventsClientAccess 120 } 
    
    
    fluidFSEventClientAccessNfsDotSnapshotsAccessDeniedDueToRestriction NOTIFICATION-TYPE
       OBJECTS { sysName, fluidFSEventsParamsClientAccessNfsUser, fluidFSEventsParamsClientAccessDsid, fluidFSEventsParamsClientAccessNasContainerIdInteger }
       STATUS current
       DESCRIPTION
           "Snapshot Access denied due to restriction   Description:  NFS snapshot access to file: {{nasContainerIdIntegerName}}/{{dsidPath}} for user {{nfsUserName}} was denied due to ".snapshots" restriction."
           --#TYPE         "Normal Event"
           --#SUMMARY      Snapshot Access denied due to restriction   Description:  NFS snapshot access to file: %s/%s for user %s was denied due to ".snapshots" restriction.
           --#ARGUMENTS    {1,2,3}
           --#SEVERITY     INFORMATIONAL
           --#TIMEINDEX    99
           --#STATE        OK
       ::= { fluidFSEventsClientAccess 121 } 
    
    
    fluidFSEventClientAccessCifsUserHasNoPrivileges2 NOTIFICATION-TYPE
       OBJECTS { sysName, fluidFSEventsParamsClientAccessCifsPrivileges, fluidFSEventsParamsClientAccessCifsOp, fluidFSEventsParamsClientAccessClientIpAddr, fluidFSEventsParamsClientAccessCifsUser2, fluidFSEventsParamsClientAccessNasContainerPath, fluidFSEventsParamsClientAccessNasContainerIdInteger }
       STATUS current
       DESCRIPTION
           "SMB access denied. User {{cifsUser2Name}} has insufficient privileges.   Description:  SMB access denied: accessing user does not have required privileges {{cifsPrivileges}} to perform '{{cifsOp}}', client: {{clientIpAddr}}, user: {{cifsUser2Name}}, file '{{nasContainerPath}}' on NAS Volume {{nasContainerIdIntegerName}}."
           --#TYPE         "Normal Event"
           --#SUMMARY      SMB access denied. User %s has insufficient privileges.   Description:  SMB access denied: accessing user does not have required privileges %s to perform '%s', client: %s, user: %s, file '%s' on NAS Volume %s.
           --#ARGUMENTS    {1,2,3,4,5,6}
           --#SEVERITY     INFORMATIONAL
           --#TIMEINDEX    99
           --#STATE        OK
       ::= { fluidFSEventsClientAccess 122 } 
    
    
    fluidFSEventClientAccessCifsUserHasNoPrivileges3 NOTIFICATION-TYPE
       OBJECTS { sysName, fluidFSEventsParamsClientAccessCifsPrivileges, fluidFSEventsParamsClientAccessCifsOp, fluidFSEventsParamsClientAccessClientIpAddr, fluidFSEventsParamsClientAccessCifsUser2, fluidFSEventsParamsClientAccessDsid, fluidFSEventsParamsClientAccessNasContainerIdInteger }
       STATUS current
       DESCRIPTION
           "SMB access denied. User {{cifsUser2Name}} has insufficient privileges   Description:  SMB access denied: accessing user does not have required privileges {{cifsPrivileges}} to perform '{{cifsOp}}', client: {{clientIpAddr}}, user: {{cifsUser2Name}}, file '{{dsidPath}}' on NAS Volume {{nasContainerIdIntegerName}}"
           --#TYPE         "Normal Event"
           --#SUMMARY      SMB access denied. User %s has insufficient privileges   Description:  SMB access denied: accessing user does not have required privileges %s to perform '%s', client: %s, user: %s, file '%s' on NAS Volume %s
           --#ARGUMENTS    {1,2,3,4,5,6}
           --#SEVERITY     INFORMATIONAL
           --#TIMEINDEX    99
           --#STATE        OK
       ::= { fluidFSEventsClientAccess 123 } 
    
    
    fluidFSEventClientAccessNestedNetgroupNotFound NOTIFICATION-TYPE
       OBJECTS { sysName, fluidFSEventsParamsClientAccessTenantId, fluidFSEventsParamsClientAccessNetgroupName, fluidFSEventsParamsClientAccessParentNetgroupName }
       STATUS current
       DESCRIPTION
           "Missing netgroup '{{netgroupName}}' could not be found by {{TenantName}}.   Description:  Nested netgroup '{{netgroupName}}' of parent netgroup '{{parentNetgroupName}}' was not found while resolving recursive definitions of export access list during NFS mount operation on {{TenantName}}. Missing netgroup was ignored.   Action Items:  Please check the content of the NIS/LDAP external repository and fix the definition of broken netgroup."
           --#TYPE         "Normal Event"
           --#SUMMARY      Missing netgroup '%s' could not be found by %s.   Description:  Nested netgroup '%s' of parent netgroup '%s' was not found while resolving recursive definitions of export access list during NFS mount operation on %s. Missing netgroup was ignored.   Action Items:  Please check the content of the NIS/LDAP external repository and fix the definition of broken netgroup.
           --#ARGUMENTS    {1,2,3}
           --#SEVERITY     INFORMATIONAL
           --#TIMEINDEX    99
           --#STATE        OK
       ::= { fluidFSEventsClientAccess 124 } 
    
    
    fluidFSEventClientAccessNetgroupRecursionIsTooDeep NOTIFICATION-TYPE
       OBJECTS { sysName, fluidFSEventsParamsClientAccessTenantId, fluidFSEventsParamsClientAccessNetgroupName, fluidFSEventsParamsClientAccessNetgroupThreshold }
       STATUS current
       DESCRIPTION
           "Netgroup '{{netgroupName}}' has too many levels of nesting on {{TenantName}}.   Description:  Circular netgroup definitions alert: netgroup has too many levels of nesting. Netgroup '{{netgroupName}}' exceeded the limit of {{netgroupThreshold}} levels of nesting on {{TenantName}}.   Action Items:  Consider reviewing your NIS/LDAP external repository for circular netgroup definitions."
           --#TYPE         "Normal Event"
           --#SUMMARY      Netgroup '%s' has too many levels of nesting on %s.   Description:  Circular netgroup definitions alert: netgroup has too many levels of nesting. Netgroup '%s' exceeded the limit of %d levels of nesting on %s.   Action Items:  Consider reviewing your NIS/LDAP external repository for circular netgroup definitions.
           --#ARGUMENTS    {1,2,3}
           --#SEVERITY     INFORMATIONAL
           --#TIMEINDEX    99
           --#STATE        OK
       ::= { fluidFSEventsClientAccess 125 } 
    
    
    fluidFSEventClientAccessSMBMemThreshold3 NOTIFICATION-TYPE
       OBJECTS { sysName, fluidFSEventsParamsClientAccessCifsUser2, fluidFSEventsParamsClientAccessNasContainerPath, fluidFSEventsParamsClientAccessNasContainerIdInteger, fluidFSEventsParamsClientAccessNasControllerId }
       STATUS current
       DESCRIPTION
           "Due to SMB high memory access denied on open file operation   Description:  SMB access denied on open file operation for user: {{cifsUser2Name}}, file '{{nasContainerPath}}' on NAS Volume {{nasContainerIdIntegerName}} due to SMB high memory consumption on NAS controller {{nasControllerId}}."
           --#TYPE         "Normal Event"
           --#SUMMARY      Due to SMB high memory access denied on open file operation   Description:  SMB access denied on open file operation for user: %s, file '%s' on NAS Volume %s due to SMB high memory consumption on NAS controller %s.
           --#ARGUMENTS    {1,2,3,4}
           --#SEVERITY     INFORMATIONAL
           --#TIMEINDEX    99
           --#STATE        OK
       ::= { fluidFSEventsClientAccess 126 } 
    
    
    fluidFSEventClientAccessSMBMemThreshold4 NOTIFICATION-TYPE
       OBJECTS { sysName, fluidFSEventsParamsClientAccessNasControllerId }
       STATUS current
       DESCRIPTION
           "Due to SMB high resource usage new sessions not allowed.   Description:  Due to SMB high resource usage new sessions are not allowed on NAS controller {{nasControllerId}}."
           --#TYPE         "Normal Event"
           --#SUMMARY      Due to SMB high resource usage new sessions not allowed.   Description:  Due to SMB high resource usage new sessions are not allowed on NAS controller %s.
           --#ARGUMENTS    {1}
           --#SEVERITY     INFORMATIONAL
           --#TIMEINDEX    99
           --#STATE        OK
       ::= { fluidFSEventsClientAccess 127 } 
    
    
    fluidFSEventClientAccessRpcSecGssAuthFailure NOTIFICATION-TYPE
       OBJECTS { sysName, fluidFSEventsParamsClientAccessTenantId, fluidFSEventsParamsClientAccessUserName, fluidFSEventsParamsClientAccessClientIpAddr, fluidFSEventsParamsClientAccessNasControllerId }
       STATUS current
       DESCRIPTION
           "NFS RPCSECGSS user authentication failure for user {{userName}} on {{TenantName}}.   Description:  NFS RPCSECGSS authentication for user '{{userName}}' failed, client {{clientIpAddr}}, NAS controller {{nasControllerId}} of {{TenantName}}."
           --#TYPE         "Normal Event"
           --#SUMMARY      NFS RPCSECGSS user authentication failure for user %s on %s.   Description:  NFS RPCSECGSS authentication for user '%s' failed, client %s, NAS controller %s of %s.
           --#ARGUMENTS    {1,2,3,4}
           --#SEVERITY     INFORMATIONAL
           --#TIMEINDEX    99
           --#STATE        OK
       ::= { fluidFSEventsClientAccess 128 } 
    
    
    fluidFSEventClientAccessSMBMaxOpenFilesThreshold NOTIFICATION-TYPE
       OBJECTS { sysName, fluidFSEventsParamsClientAccessNasControllerId, fluidFSEventsParamsClientAccessMaxOpenFilesPerNode }
       STATUS current
       DESCRIPTION
           "Due to SMB too many open files denied open file operation.   Description:   SMB access denied on open file operation due to SMB too many open files on NAS controller {{nasControllerId}}. Allowed number of open files per node is {{maxOpenFilesPerNode}}."
           --#TYPE         "Normal Event"
           --#SUMMARY      Due to SMB too many open files denied open file operation.   Description:   SMB access denied on open file operation due to SMB too many open files on NAS controller %s. Allowed number of open files per node is %d.
           --#ARGUMENTS    {1,2}
           --#SEVERITY     INFORMATIONAL
           --#TIMEINDEX    99
           --#STATE        OK
       ::= { fluidFSEventsClientAccess 129 } 
    
    
    fluidFSEventClientAccessExtensionIsDeniedOnShare NOTIFICATION-TYPE
       OBJECTS { sysName, fluidFSEventsParamsClientAccessNasContainerIdInteger, fluidFSEventsParamsClientAccessFileExtension, fluidFSEventsParamsClientAccessCifsShare, fluidFSEventsParamsClientAccessNasContainerPath, fluidFSEventsParamsClientAccessCifsUser2 }
       STATUS current
       DESCRIPTION
           "SMB access denied. Extension {{fileExtension}} is denied on share {{cifsShare}}.   Description:  SMB access denied: Extension based access is configured on share {{cifsShare}} on NAS volume {{nasContainerIdIntegerName}}, and extension {{fileExtension}} of file {{nasContainerPath}} is denied. User {{cifsUser2Name}} is not a member of the users groups to be excluded from filtering."
           --#TYPE         "Normal Event"
           --#SUMMARY      SMB access denied. Extension %s is denied on share %s.   Description:  SMB access denied: Extension based access is configured on share %s on NAS volume %s, and extension %s of file %s is denied. User %s is not a member of the users groups to be excluded from filtering.
           --#ARGUMENTS    {1,2,3,4,5}
           --#SEVERITY     INFORMATIONAL
           --#TIMEINDEX    99
           --#STATE        OK
       ::= { fluidFSEventsClientAccess 130 } 
    
    
    fluidFSEventClientAccessAutoHomeDirCreationError NOTIFICATION-TYPE
       OBJECTS { sysName, fluidFSEventsParamsClientAccessNasContainerIdInteger, fluidFSEventsParamsClientAccessCifsErrorCode, fluidFSEventsParamsClientAccessNasContainerPath, fluidFSEventsParamsClientAccessCifsUser2 }
       STATUS current
       DESCRIPTION
           "Error on creation home directory for user {{cifsUser2Name}}.   Description:  Auto home directory creation failed for user {{cifsUser2Name}} on NAS volume {{nasContainerIdIntegerName}} with path {{nasContainerPath}}. NT error code {{cifsErrorCode}}."
           --#TYPE         "Normal Event"
           --#SUMMARY      Error on creation home directory for user %s.   Description:  Auto home directory creation failed for user %s on NAS volume %s with path %s. NT error code %d.
           --#ARGUMENTS    {1,2,3,4}
           --#SEVERITY     INFORMATIONAL
           --#TIMEINDEX    99
           --#STATE        OK
       ::= { fluidFSEventsClientAccess 131 } 
    
    
    fluidFSEventClientAccessMountDeniedOnVip NOTIFICATION-TYPE
       OBJECTS { sysName, fluidFSEventsParamsClientAccessNasContainerIdInteger, fluidFSEventsParamsClientAccessClientIpAddr, fluidFSEventsParamsClientAccessMountPath, fluidFSEventsParamsClientAccessClusterVIP }
       STATUS current
       DESCRIPTION
           "NFS mount Denied. Path denied {{mountPath}} on subnet {{clusterVIP}}    Description:  NFS client {{clientIpAddr}} was trying to mount NFS export with path {{mountPath}} via cluster VIP {{clusterVIP}} but access from this subnet is not allowed by this NFS export. Access was denied. Client was accessing the export in blind mode that can be considered as security issue."
           --#TYPE         "Normal Event"
           --#SUMMARY      NFS mount Denied. Path denied %s on subnet %s    Description:  NFS client %s was trying to mount NFS export with path %s via cluster VIP %s but access from this subnet is not allowed by this NFS export. Access was denied. Client was accessing the export in blind mode that can be considered as security issue.
           --#ARGUMENTS    {1,2,3,4}
           --#SEVERITY     INFORMATIONAL
           --#TIMEINDEX    99
           --#STATE        OK
       ::= { fluidFSEventsClientAccess 132 } 
    
    
    fluidFSEventClientAccessCifsTreeConnectDeniedOnVip NOTIFICATION-TYPE
       OBJECTS { sysName, fluidFSEventsParamsClientAccessUserName, fluidFSEventsParamsClientAccessCifsShare, fluidFSEventsParamsClientAccessClientIpAddr, fluidFSEventsParamsClientAccessNasControllerId, fluidFSEventsParamsClientAccessNasContainerIdInteger }
       STATUS current
       DESCRIPTION
           "Access from disallowed subnet to share {{cifsShare}} was denied   Description:  Connection for user '{{userName}}' to share {{cifsShare}} denied because access from this subnet is not allowed by SMB share settings, client {{clientIpAddr}}, NAS Controller {{nasControllerId}}, NAS Volume {{nasContainerIdIntegerName}}."
           --#TYPE         "Normal Event"
           --#SUMMARY      Access from disallowed subnet to share %s was denied   Description:  Connection for user '%s' to share %s denied because access from this subnet is not allowed by SMB share settings, client %s, NAS Controller %s, NAS Volume %s.
           --#ARGUMENTS    {1,2,3,4,5}
           --#SEVERITY     INFORMATIONAL
           --#TIMEINDEX    99
           --#STATE        OK
       ::= { fluidFSEventsClientAccess 133 } 
    
    
    fluidFSEventClientAccessNoRootForOperation NOTIFICATION-TYPE
       OBJECTS { sysName, fluidFSEventsParamsClientAccessClientIpAddr, fluidFSEventsParamsClientAccessOperation, fluidFSEventsParamsClientAccessNasContainerIdInteger }
       STATUS current
       DESCRIPTION
           "NFS access denied. Root privileges on export needed for {{operation}}.   Description:  NFS Access Denied: Client {{clientIpAddr}} can't execute operation {{operation}} with volume {{nasContainerIdIntegerName}} because root privileges are required for the client in the relevant NFS export."
           --#TYPE         "Normal Event"
           --#SUMMARY      NFS access denied. Root privileges on export needed for %s.   Description:  NFS Access Denied: Client %s can't execute operation %s with volume %s because root privileges are required for the client in the relevant NFS export.
           --#ARGUMENTS    {1,2,3}
           --#SEVERITY     INFORMATIONAL
           --#TIMEINDEX    99
           --#STATE        OK
       ::= { fluidFSEventsClientAccess 134 } 
    
    
    fluidFSEventClientAccessFtpLoginFailed NOTIFICATION-TYPE
       OBJECTS { sysName, fluidFSEventsParamsClientAccessTenantId, fluidFSEventsParamsClientAccessClientIpAddr, fluidFSEventsParamsClientAccessUserName }
       STATUS current
       DESCRIPTION
           "FTP user log-in to {{TenantName}} failed   Description:  FTP access to {{TenantName}} from {{clientIpAddr}} is denied for user {{userName}}.   Action Items:  When the client attempts FTP connection but provides bad account details, this event is generated. Possible reasons: wrong password, bad username, disabled anonymous access, account is disabled, password is expired and needs to be changed. The user should verify account details."
           --#TYPE         "Normal Event"
           --#SUMMARY      FTP user log-in to %s failed   Description:  FTP access to %s from %s is denied for user %s.   Action Items:  When the client attempts FTP connection but provides bad account details, this event is generated. Possible reasons: wrong password, bad username, disabled anonymous access, account is disabled, password is expired and needs to be changed. The user should verify account details.
           --#ARGUMENTS    {1,2,3}
           --#SEVERITY     INFORMATIONAL
           --#TIMEINDEX    99
           --#STATE        OK
       ::= { fluidFSEventsClientAccess 135 } 
    
    
    fluidFSEventClientAccessFtpLoginAccountProblem NOTIFICATION-TYPE
       OBJECTS { sysName, fluidFSEventsParamsClientAccessTenantId, fluidFSEventsParamsClientAccessClientIpAddr, fluidFSEventsParamsClientAccessUserName }
       STATUS current
       DESCRIPTION
           "FTP user log-in to {{TenantName}} failed due to problematic account   Description:  FTP client {{clientIpAddr}} user {{userName}} log-in to {{TenantName}} failed due to problematic account   Action Items:  When the client makes FTP connection but provided account has problems, this event is generated. Possible reasons: account is locked, account is expired, logon with this account is disabled. System administrator might provide support to the user to fix the account problem."
           --#TYPE         "Normal Event"
           --#SUMMARY      FTP user log-in to %s failed due to problematic account   Description:  FTP client %s user %s log-in to %s failed due to problematic account   Action Items:  When the client makes FTP connection but provided account has problems, this event is generated. Possible reasons: account is locked, account is expired, logon with this account is disabled. System administrator might provide support to the user to fix the account problem.
           --#ARGUMENTS    {1,2,3}
           --#SEVERITY     INFORMATIONAL
           --#TIMEINDEX    99
           --#STATE        OK
       ::= { fluidFSEventsClientAccess 136 } 
    
    
    fluidFSEventClientAccessFtpLoginInternalProblem NOTIFICATION-TYPE
       OBJECTS { sysName, fluidFSEventsParamsClientAccessTenantId, fluidFSEventsParamsClientAccessClientIpAddr, fluidFSEventsParamsClientAccessUserName, fluidFSEventsParamsClientAccessInternalInfo }
       STATUS current
       DESCRIPTION
           "FTP user log-in to {{TenantName}} failed due to an internal problem   Description:  FTP client {{clientIpAddr}} user {{userName}} log-in to {{TenantName}} failed due to internal problem   Internal Information:  {{internalInfo}}"
           --#TYPE         "Normal Event"
           --#SUMMARY      FTP user log-in to %s failed due to an internal problem   Description:  FTP client %s user %s log-in to %s failed due to internal problem   Internal Information:  %s
           --#ARGUMENTS    {1,2,3,4}
           --#SEVERITY     MAJOR
           --#TIMEINDEX    99
           --#STATE        OK
       ::= { fluidFSEventsClientAccess 137 } 
    
    
    fluidFSEventClientAccessFtpLoginSucceeded NOTIFICATION-TYPE
       OBJECTS { sysName, fluidFSEventsParamsClientAccessTenantId, fluidFSEventsParamsClientAccessClientIpAddr, fluidFSEventsParamsClientAccessUserName }
       STATUS current
       DESCRIPTION
           "FTP user logged into {{TenantName}}   Description:  FTP client {{clientIpAddr}} user {{userName}} logged into {{TenantName}}   Action Items:  When the client makes FTP connection and successfully logs in, this event is generated"
           --#TYPE         "Normal Event"
           --#SUMMARY      FTP user logged into %s   Description:  FTP client %s user %s logged into %s   Action Items:  When the client makes FTP connection and successfully logs in, this event is generated
           --#ARGUMENTS    {1,2,3}
           --#SEVERITY     INFORMATIONAL
           --#TIMEINDEX    99
           --#STATE        OK
       ::= { fluidFSEventsClientAccess 138 } 
    
    
    fluidFSEventClientAccessFtpAnonymousLoggedIn NOTIFICATION-TYPE
       OBJECTS { sysName, fluidFSEventsParamsClientAccessTenantId, fluidFSEventsParamsClientAccessClientIpAddr, fluidFSEventsParamsClientAccessUserEmail }
       STATUS current
       DESCRIPTION
           "FTP Anonymous user logged into {{TenantName}}   Description:  FTP Anonymous user logged into {{TenantName}} with email {{userEmail}} from {{clientIpAddr}}.   Action Items:  We register an event for every anonymous user logins."
           --#TYPE         "Normal Event"
           --#SUMMARY      FTP Anonymous user logged into %s   Description:  FTP Anonymous user logged into %s with email %s from %s.   Action Items:  We register an event for every anonymous user logins.
           --#ARGUMENTS    {1,2,3}
           --#SEVERITY     INFORMATIONAL
           --#TIMEINDEX    99
           --#STATE        OK
       ::= { fluidFSEventsClientAccess 139 } 
    
    
    fluidFSEventClientAccessFtpTlsHandshakeVerMismatch NOTIFICATION-TYPE
       OBJECTS { sysName, fluidFSEventsParamsClientAccessTenantId, fluidFSEventsParamsClientAccessClientIpAddr, fluidFSEventsParamsClientAccessTlsVersion }
       STATUS current
       DESCRIPTION
           "FTP user log-in to {{TenantName}} failed due to wrong TLS version   Description:  FTP client {{clientIpAddr}} log-in to {{TenantName}} failed due to TLS protocol version mismatch   Action Items:  Please make sure FTP client software supports encryption method version TLS 1.{{tlsVersion}}"
           --#TYPE         "Normal Event"
           --#SUMMARY      FTP user log-in to %s failed due to wrong TLS version   Description:  FTP client %s log-in to %s failed due to TLS protocol version mismatch   Action Items:  Please make sure FTP client software supports encryption method version TLS 1.%d
           --#ARGUMENTS    {1,2,3}
           --#SEVERITY     INFORMATIONAL
           --#TIMEINDEX    99
           --#STATE        OK
       ::= { fluidFSEventsClientAccess 140 } 
    
    
    fluidFSEventClientAccessMaxFtpConnectionsReached NOTIFICATION-TYPE
       OBJECTS { sysName, fluidFSEventsParamsClientAccessTenantId, fluidFSEventsParamsClientAccessMaxConnections, fluidFSEventsParamsClientAccessNasControllerId }
       STATUS current
       DESCRIPTION
           "Reached Maximum FTP connections on NAS controller {{nasControllerId}} of {{TenantName}}. Maximum connection allowed per controller is {{maxConnections}}   Action Items:  This failure is common when there are too many FTP connections to the same fsd."
           --#TYPE         "Normal Event"
           --#SUMMARY      Reached Maximum FTP connections on NAS controller %s of %s. Maximum connection allowed per controller is %d   Action Items:  This failure is common when there are too many FTP connections to the same fsd.
           --#ARGUMENTS    {1,2,3}
           --#SEVERITY     INFORMATIONAL
           --#TIMEINDEX    99
           --#STATE        OK
       ::= { fluidFSEventsClientAccess 141 } 
    
    
    fluidFSEventClientAccessFtpMissingBaseLandingDir NOTIFICATION-TYPE
       OBJECTS { sysName, fluidFSEventsParamsClientAccessTenantId, fluidFSEventsParamsClientAccessClientIpAddr, fluidFSEventsParamsClientAccessUserName, fluidFSEventsParamsClientAccessNasContainerIdInteger, fluidFSEventsParamsClientAccessBaseLandingPath }
       STATUS current
       DESCRIPTION
           "FTP user log-in to {{TenantName}} failed due to missing landing path   Description:  FTP client {{clientIpAddr}} user {{userName}} log-in to {{TenantName}} failed due to missing landing directory '{{baseLandingPath}}' on volume {{nasContainerIdIntegerName}}}.   Action Items:  When the client makes FTP connection and successfully logs in but landing directory does not exist, this event is generated. Please create the landing directory."
           --#TYPE         "Normal Event"
           --#SUMMARY      FTP user log-in to %s failed due to missing landing path   Description:  FTP client %s user %s log-in to %s failed due to missing landing directory '%s' on volume %s}.   Action Items:  When the client makes FTP connection and successfully logs in but landing directory does not exist, this event is generated. Please create the landing directory.
           --#ARGUMENTS    {1,2,3,4,5}
           --#SEVERITY     INFORMATIONAL
           --#TIMEINDEX    99
           --#STATE        OK
       ::= { fluidFSEventsClientAccess 142 } 
    
    
    fluidFSEventClientAccessFtpMissingHomeLandingDir NOTIFICATION-TYPE
       OBJECTS { sysName, fluidFSEventsParamsClientAccessTenantId, fluidFSEventsParamsClientAccessClientIpAddr, fluidFSEventsParamsClientAccessUserName, fluidFSEventsParamsClientAccessNasContainerIdInteger, fluidFSEventsParamsClientAccessBaseLandingPath, fluidFSEventsParamsClientAccessSuffixLandingPath }
       STATUS current
       DESCRIPTION
           "FTP user log-in to {{TenantName}} failed due to missing home landing path   Description:  FTP client {{clientIpAddr}} user {{userName}} log-in to {{TenantName}} failed due to missing home directory '{{suffixLandingPath}}' within base landing directory '{{baseLandingPath}}' on volume {{nasContainerIdIntegerName}}   Action Items:  When the client makes FTP connection and successfully logs in but home landing directory does not exist, this event is generated. FTP does not create home folders automatically. Please create them manually."
           --#TYPE         "Normal Event"
           --#SUMMARY      FTP user log-in to %s failed due to missing home landing path   Description:  FTP client %s user %s log-in to %s failed due to missing home directory '%s' within base landing directory '%s' on volume %s   Action Items:  When the client makes FTP connection and successfully logs in but home landing directory does not exist, this event is generated. FTP does not create home folders automatically. Please create them manually.
           --#ARGUMENTS    {1,2,3,4,5,6}
           --#SEVERITY     INFORMATIONAL
           --#TIMEINDEX    99
           --#STATE        OK
       ::= { fluidFSEventsClientAccess 143 } 
    
    
    fluidFSEventClientAccessHdfsMaxConnectionsReached NOTIFICATION-TYPE
       OBJECTS { sysName }
       STATUS current
       DESCRIPTION
           "Reached maximum HDFS connections   Description:  Reached Maximum HDFS connections.   Action Items:  This failure is common when there are too many HDFS connections to the same fsd."
           --#TYPE         "Normal Event"
           --#SUMMARY      Reached maximum HDFS connections   Description:  Reached Maximum HDFS connections.   Action Items:  This failure is common when there are too many HDFS connections to the same fsd.
           --#ARGUMENTS    {}
           --#SEVERITY     INFORMATIONAL
           --#TIMEINDEX    99
           --#STATE        OK
       ::= { fluidFSEventsClientAccess 144 } 
    
    
    fluidFSEventClientAccessHdfsUserNotFound NOTIFICATION-TYPE
       OBJECTS { sysName, fluidFSEventsParamsClientAccessTenantId, fluidFSEventsParamsClientAccessClientIpAddr, fluidFSEventsParamsClientAccessUserName }
       STATUS current
       DESCRIPTION
           "HDFS user name was not found in any of the repositories of {{TenantName}}   Description:  HDFS access from {{clientIpAddr}} provided the user name {{userName}}, but a corresponding user was not found in any of the repositories of {{TenantName}}"
           --#TYPE         "Normal Event"
           --#SUMMARY      HDFS user name was not found in any of the repositories of %s   Description:  HDFS access from %s provided the user name %s, but a corresponding user was not found in any of the repositories of %s
           --#ARGUMENTS    {1,2,3}
           --#SEVERITY     INFORMATIONAL
           --#TIMEINDEX    99
           --#STATE        OK
       ::= { fluidFSEventsClientAccess 145 } 
    
    
    fluidFSEventClientAccessHdfsDotSnapshotsAccessDeniedDueToRestriction NOTIFICATION-TYPE
       OBJECTS { sysName, fluidFSEventsParamsClientAccessTenantId, fluidFSEventsParamsClientAccessClientIpAddr, fluidFSEventsParamsClientAccessUserName, fluidFSEventsParamsClientAccessNasContainerIdInteger, fluidFSEventsParamsClientAccessBaseLandingPath }
       STATUS current
       DESCRIPTION
           "Snapshot Access denied by {{TenantName}} due to restriction   Description:  Snapshot access to the HDFS landing directory of NAS Volume {{nasContainerIdIntegerName}} of {{TenantName}} was denied due to '.snapshots' restriction. client: {{clientIpAddr}}, user: {{userName}}, path: '{{baseLandingPath}}'. "
           --#TYPE         "Normal Event"
           --#SUMMARY      Snapshot Access denied by %s due to restriction   Description:  Snapshot access to the HDFS landing directory of NAS Volume %s of %s was denied due to '.snapshots' restriction. client: %s, user: %s, path: '%s'. 
           --#ARGUMENTS    {1,2,3,4,5}
           --#SEVERITY     INFORMATIONAL
           --#TIMEINDEX    99
           --#STATE        OK
       ::= { fluidFSEventsClientAccess 146 } 
    
    
    fluidFSEventClientAccessGpoExecutionTimeoutFailure NOTIFICATION-TYPE
       OBJECTS { sysName, fluidFSEventsParamsClientAccessTenantId, fluidFSEventsParamsClientAccessPolicyName, fluidFSEventsParamsClientAccessPolicyGuid }
       STATUS current
       DESCRIPTION
           "GPO Policy was not applied on {{TenantName}}. Took too much time.   Description:  Policy {{policyGuid}} {{policyName}} was not applied on {{TenantName}}. Took to much time."
           --#TYPE         "Normal Event"
           --#SUMMARY      GPO Policy was not applied on %s. Took too much time.   Description:  Policy %s %s was not applied on %s. Took to much time.
           --#ARGUMENTS    {1,2,3}
           --#SEVERITY     MAJOR
           --#TIMEINDEX    99
           --#STATE        OK
       ::= { fluidFSEventsClientAccess 147 } 
    
    
    fluidFSEventClientAccessGpoOtherFailure NOTIFICATION-TYPE
       OBJECTS { sysName, fluidFSEventsParamsClientAccessTenantId, fluidFSEventsParamsClientAccessPolicyName, fluidFSEventsParamsClientAccessPolicyGuid }
       STATUS current
       DESCRIPTION
           "GPO Policy was not applied on {{TenantName}} due to system error.   Description:  Policy {{policyGuid}} {{policyName}} was not applied on {{TenantName}} due to system error."
           --#TYPE         "Normal Event"
           --#SUMMARY      GPO Policy was not applied on %s due to system error.   Description:  Policy %s %s was not applied on %s due to system error.
           --#ARGUMENTS    {1,2,3}
           --#SEVERITY     MAJOR
           --#TIMEINDEX    99
           --#STATE        OK
       ::= { fluidFSEventsClientAccess 148 } 
    
    
    fluidFSEventClientAccessGpoSuccess NOTIFICATION-TYPE
       OBJECTS { sysName, fluidFSEventsParamsClientAccessTenantId, fluidFSEventsParamsClientAccessPolicyName, fluidFSEventsParamsClientAccessPolicyGuid }
       STATUS current
       DESCRIPTION
           "GPO Policy was applied successfully on {{TenantName}}.   Description:  Policy {{policyGuid}} {{policyName}} was applied successfully on {{TenantName}}."
           --#TYPE         "Normal Event"
           --#SUMMARY      GPO Policy was applied successfully on %s.   Description:  Policy %s %s was applied successfully on %s.
           --#ARGUMENTS    {1,2,3}
           --#SEVERITY     INFORMATIONAL
           --#TIMEINDEX    99
           --#STATE        OK
       ::= { fluidFSEventsClientAccess 149 } 
    
    
    fluidFSEventClientAccessGpoFileSecurityPolicyFailure NOTIFICATION-TYPE
       OBJECTS { sysName, fluidFSEventsParamsClientAccessTenantId, fluidFSEventsParamsClientAccessPolicyName, fluidFSEventsParamsClientAccessPolicyGuid, fluidFSEventsParamsClientAccessPolicyTargetPath }
       STATUS current
       DESCRIPTION
           "GPO Policy on target on {{TenantName}} was not applied due to system error   Description:  Policy {{policyGuid}} {{policyName}} on target {{policyTargetPath}} was not applied due to system error on {{TenantName}}."
           --#TYPE         "Normal Event"
           --#SUMMARY      GPO Policy on target on %s was not applied due to system error   Description:  Policy %s %s on target %s was not applied due to system error on %s.
           --#ARGUMENTS    {1,2,3,4}
           --#SEVERITY     MAJOR
           --#TIMEINDEX    99
           --#STATE        OK
       ::= { fluidFSEventsClientAccess 150 } 
    
    
    fluidFSEventClientAccessGpoFileSecurityPolicyDoNotReplaceFailure NOTIFICATION-TYPE
       OBJECTS { sysName, fluidFSEventsParamsClientAccessTenantId, fluidFSEventsParamsClientAccessPolicyName, fluidFSEventsParamsClientAccessPolicyGuid, fluidFSEventsParamsClientAccessPolicyTargetPath }
       STATUS current
       DESCRIPTION
           "GPO Do Not Replace was not applied on {{TenantName}} due to system error.   Description:  Do not replace logic was not applied in Policy {{policyGuid}} {{policyName}} on target {{policyTargetPath}} due to system error on {{TenantName}}."
           --#TYPE         "Normal Event"
           --#SUMMARY      GPO Do Not Replace was not applied on %s due to system error.   Description:  Do not replace logic was not applied in Policy %s %s on target %s due to system error on %s.
           --#ARGUMENTS    {1,2,3,4}
           --#SEVERITY     MAJOR
           --#TIMEINDEX    99
           --#STATE        OK
       ::= { fluidFSEventsClientAccess 151 } 
    
    
    fluidFSEventClientAccessGpoInfFileReadFailure NOTIFICATION-TYPE
       OBJECTS { sysName, fluidFSEventsParamsClientAccessTenantId, fluidFSEventsParamsClientAccessPolicyName, fluidFSEventsParamsClientAccessPolicyGuid, fluidFSEventsParamsClientAccessFilePath }
       STATUS current
       DESCRIPTION
           "GPO Policy .inf file read failure on {{TenantName}}.   Description:  {{TenantName}} failed to read the .inf file {{filePath}} of the Policy {{policyGuid}} {{policyName}}"
           --#TYPE         "Normal Event"
           --#SUMMARY      GPO Policy .inf file read failure on %s.   Description:  %s failed to read the .inf file %s of the Policy %s %s
           --#ARGUMENTS    {1,2,3,4}
           --#SEVERITY     MAJOR
           --#TIMEINDEX    99
           --#STATE        OK
       ::= { fluidFSEventsClientAccess 152 } 
    
    
    fluidFSEventClientAccessCapLdapQueryFailure NOTIFICATION-TYPE
       OBJECTS { sysName, fluidFSEventsParamsClientAccessTenantId, fluidFSEventsParamsClientAccessSearchedObjects }
       STATUS current
       DESCRIPTION
           "Central Access Policy LDAP query failure on {{TenantName}}.   Description:  LDAP query for Central Access Policy objects {{searchedObjects}} failed on {{TenantName}}."
           --#TYPE         "Normal Event"
           --#SUMMARY      Central Access Policy LDAP query failure on %s.   Description:  LDAP query for Central Access Policy objects %s failed on %s.
           --#ARGUMENTS    {1,2}
           --#SEVERITY     MAJOR
           --#TIMEINDEX    99
           --#STATE        OK
       ::= { fluidFSEventsClientAccess 153 } 
    
    
    fluidFSEventClientAccessCapCentralAccessRuleParsingFailure NOTIFICATION-TYPE
       OBJECTS { sysName, fluidFSEventsParamsClientAccessTenantId, fluidFSEventsParamsClientAccessRuleDN, fluidFSEventsParamsClientAccessPolicyDN }
       STATUS current
       DESCRIPTION
           "Central Access Policy rule parsing failure on {{TenantName}}.   Description:  Parsing of the Central Access Policy rule {{ruleDN}} of the policy {{policyDN}} failed on {{TenantName}}."
           --#TYPE         "Normal Event"
           --#SUMMARY      Central Access Policy rule parsing failure on %s.   Description:  Parsing of the Central Access Policy rule %s of the policy %s failed on %s.
           --#ARGUMENTS    {1,2,3}
           --#SEVERITY     MAJOR
           --#TIMEINDEX    99
           --#STATE        OK
       ::= { fluidFSEventsClientAccess 154 } 
    
    
    fluidFSEventClientAccessCapCentralAccessPolicyParsingFailure NOTIFICATION-TYPE
       OBJECTS { sysName, fluidFSEventsParamsClientAccessTenantId, fluidFSEventsParamsClientAccessPolicyDN }
       STATUS current
       DESCRIPTION
           "Central Access policy parsing failure on {{TenantName}}.   Description:  Parsing of the Central Access policy {{policyDN}} failed on {{TenantName}}."
           --#TYPE         "Normal Event"
           --#SUMMARY      Central Access policy parsing failure on %s.   Description:  Parsing of the Central Access policy %s failed on %s.
           --#ARGUMENTS    {1,2}
           --#SEVERITY     MAJOR
           --#TIMEINDEX    99
           --#STATE        OK
       ::= { fluidFSEventsClientAccess 155 } 
    
    
    fluidFSEventsParamsLicensing OBJECT IDENTIFIER ::= { fluidFSEventsParams 13 } 
    
    
    fluidFSEventsLicensing OBJECT IDENTIFIER ::= { fluidFSEvents 13 } 
    
    
    fluidFSEventsParamsLicensingFileName OBJECT-TYPE
       SYNTAX  DisplayString
       MAX-ACCESS  read-only
       STATUS  current
       DESCRIPTION
           "Name of the license xml file "
       ::= { fluidFSEventsParamsLicensing 1 }
    
    
    fluidFSEventsParamsLicensingInstalledFeatures OBJECT-TYPE
       SYNTAX  DisplayString
       MAX-ACCESS  read-only
       STATUS  current
       DESCRIPTION
           "List of the features which were installed, seperated by commas"
       ::= { fluidFSEventsParamsLicensing 2 }
    
    
    fluidFSEventsParamsLicensingNumOfDays OBJECT-TYPE
       SYNTAX  INTEGER
       MAX-ACCESS  read-only
       STATUS  current
       DESCRIPTION
           "Number of days till expiration of feature"
       ::= { fluidFSEventsParamsLicensing 3 }
    
    
    fluidFSEventsParamsLicensingFluidFsVersion OBJECT-TYPE
       SYNTAX  DisplayString
       MAX-ACCESS  read-only
       STATUS  current
       DESCRIPTION
           "FluidFS software version"
       ::= { fluidFSEventsParamsLicensing 4 }
    
    
    fluidFSEventLicensingEulaNotApprovedByUser NOTIFICATION-TYPE
       OBJECTS { sysName, fluidFSEventsParamsLicensingFluidFsVersion }
       STATUS current
       DESCRIPTION
           "End-user license agreement (EULA) was not accepted by user.   Description:  FluidFS version {{FluidFsVersion}} has a new end user license agreement. You must accept this agreement in order to use the system.   Action Items:  To accept the end user agreement go to User Interface System menu."
           --#TYPE         "Normal Event"
           --#SUMMARY      End-user license agreement (EULA) was not accepted by user.   Description:  FluidFS version %s has a new end user license agreement. You must accept this agreement in order to use the system.   Action Items:  To accept the end user agreement go to User Interface System menu.
           --#ARGUMENTS    {1}
           --#SEVERITY     MAJOR
           --#TIMEINDEX    99
           --#STATE        OK
       ::= { fluidFSEventsLicensing 14 } 
    
    
    fluidFSEventsParamsExaminer OBJECT IDENTIFIER ::= { fluidFSEventsParams 14 } 
    
    
    fluidFSEventsExaminer OBJECT IDENTIFIER ::= { fluidFSEvents 14 } 
    
    
    fluidFSEventsParamsExaminerCategory OBJECT-TYPE
       SYNTAX  DisplayString
       MAX-ACCESS  read-only
       STATUS  current
       DESCRIPTION
           "Corruption category"
       ::= { fluidFSEventsParamsExaminer 1 }
    
    
    fluidFSEventsParamsExaminerLevel OBJECT-TYPE
       SYNTAX  DisplayString
       MAX-ACCESS  read-only
       STATUS  current
       DESCRIPTION
           "Level of the error"
       ::= { fluidFSEventsParamsExaminer 2 }
    
    
    fluidFSEventExaminerSystemCorruption NOTIFICATION-TYPE
       OBJECTS { sysName, fluidFSEventsParamsExaminerCategory, fluidFSEventsParamsExaminerLevel }
       STATUS current
       DESCRIPTION
           "FluidFS Health Scan found an inconsistency in the system.   Description:  FluidFS Health Scan found an inconsistency in the system. Please contact Support.   Internal Information:  FluidFS Health Scan has found an error in {{category}} on level {{level}}"
           --#TYPE         "Normal Event"
           --#SUMMARY      FluidFS Health Scan found an inconsistency in the system.   Description:  FluidFS Health Scan found an inconsistency in the system. Please contact Support.   Internal Information:  FluidFS Health Scan has found an error in %s on level %s
           --#ARGUMENTS    {1,2}
           --#SEVERITY     MAJOR
           --#TIMEINDEX    99
           --#STATE        OK
       ::= { fluidFSEventsExaminer 1 } 
    
    
    fluidFSEventExaminerExaminingCycleFinished NOTIFICATION-TYPE
       OBJECTS { sysName }
       STATUS current
       DESCRIPTION
           "FluidFS Health Scan finished a scanning cycle.   Description:  FluidFS Health Scan finished a scanning cycle of the entire system"
           --#TYPE         "Normal Event"
           --#SUMMARY      FluidFS Health Scan finished a scanning cycle.   Description:  FluidFS Health Scan finished a scanning cycle of the entire system
           --#ARGUMENTS    {}
           --#SEVERITY     INFORMATIONAL
           --#TIMEINDEX    99
           --#STATE        OK
       ::= { fluidFSEventsExaminer 3 } 
    
    
    fluidFSEventsParamsComponent OBJECT IDENTIFIER ::= { fluidFSEventsParams 15 } 
    
    
    fluidFSEventsComponent OBJECT IDENTIFIER ::= { fluidFSEvents 15 } 
    
    
    fluidFSEventsParamsComponentUserName OBJECT-TYPE
       SYNTAX  DisplayString
       MAX-ACCESS  read-only
       STATUS  current
       DESCRIPTION
           "User name"
       ::= { fluidFSEventsParamsComponent 1 }
    
    
    fluidFSEventsParamsComponentObjectId OBJECT-TYPE
       SYNTAX  DisplayString
       MAX-ACCESS  read-only
       STATUS  current
       DESCRIPTION
           "objectId"
       ::= { fluidFSEventsParamsComponent 2 }
    
    
    fluidFSEventsParamsComponentTimezone OBJECT-TYPE
       SYNTAX  DisplayString
       MAX-ACCESS  read-only
       STATUS  current
       DESCRIPTION
           "timezone"
       ::= { fluidFSEventsParamsComponent 3 }
    
    
    fluidFSEventsParamsComponentName OBJECT-TYPE
       SYNTAX  DisplayString
       MAX-ACCESS  read-only
       STATUS  current
       DESCRIPTION
           "Name"
       ::= { fluidFSEventsParamsComponent 4 }
    
    
    fluidFSEventsParamsComponentRetcodeString OBJECT-TYPE
       SYNTAX  DisplayString
       MAX-ACCESS  read-only
       STATUS  current
       DESCRIPTION
           "RetCode string"
       ::= { fluidFSEventsParamsComponent 5 }
    
    
    fluidFSEventsParamsComponentRemoteVolume OBJECT-TYPE
       SYNTAX  DisplayString
       MAX-ACCESS  read-only
       STATUS  current
       DESCRIPTION
           "Remote Volume"
       ::= { fluidFSEventsParamsComponent 6 }
    
    
    fluidFSEventsParamsComponentSystemServiceState OBJECT-TYPE
       SYNTAX  DisplayString
       MAX-ACCESS  read-only
       STATUS  current
       DESCRIPTION
           "System Service Mode"
       ::= { fluidFSEventsParamsComponent 7 }
    
    
    fluidFSEventsParamsComponentAdministrator OBJECT-TYPE
       SYNTAX  DisplayString
       MAX-ACCESS  read-only
       STATUS  current
       DESCRIPTION
           "System administrator"
       ::= { fluidFSEventsParamsComponent 8 }
    
    
    fluidFSEventsParamsComponentFSID OBJECT-TYPE
       SYNTAX  DisplayString
       MAX-ACCESS  read-only
       STATUS  current
       DESCRIPTION
           "NAS volume id"
       ::= { fluidFSEventsParamsComponent 9 }
    
    
    fluidFSEventsParamsComponentSnapshotID OBJECT-TYPE
       SYNTAX  DisplayString
       MAX-ACCESS  read-only
       STATUS  current
       DESCRIPTION
           "Snapshot id"
       ::= { fluidFSEventsParamsComponent 10 }
    
    
    fluidFSEventsParamsComponentNdmpLock OBJECT-TYPE
       SYNTAX  DisplayString
       MAX-ACCESS  read-only
       STATUS  current
       DESCRIPTION
           "NdmpLock"
       ::= { fluidFSEventsParamsComponent 11 }
    
    
    fluidFSEventsParamsComponentExpiry OBJECT-TYPE
       SYNTAX  DisplayString
       MAX-ACCESS  read-only
       STATUS  current
       DESCRIPTION
           "Expiry"
       ::= { fluidFSEventsParamsComponent 12 }
    
    
    fluidFSEventsParamsComponentShareName OBJECT-TYPE
       SYNTAX  DisplayString
       MAX-ACCESS  read-only
       STATUS  current
       DESCRIPTION
           "Name of the SMB share"
       ::= { fluidFSEventsParamsComponent 13 }
    
    
    fluidFSEventsParamsComponentNFSExportPath OBJECT-TYPE
       SYNTAX  DisplayString
       MAX-ACCESS  read-only
       STATUS  current
       DESCRIPTION
           "Path that is exported by NFS filesystem"
       ::= { fluidFSEventsParamsComponent 14 }
    
    
    fluidFSEventsParamsComponentDomain OBJECT-TYPE
       SYNTAX  DisplayString
       MAX-ACCESS  read-only
       STATUS  current
       DESCRIPTION
           "Domain"
       ::= { fluidFSEventsParamsComponent 15 }
    
    
    fluidFSEventsParamsComponentUserInterfaceType OBJECT-TYPE
       SYNTAX  DisplayString
       MAX-ACCESS  read-only
       STATUS  current
       DESCRIPTION
           "User interface type"
       ::= { fluidFSEventsParamsComponent 16 }
    
    
    fluidFSEventsParamsComponentUserInterfaceClient OBJECT-TYPE
       SYNTAX  DisplayString
       MAX-ACCESS  read-only
       STATUS  current
       DESCRIPTION
           "User interface client"
       ::= { fluidFSEventsParamsComponent 17 }
    
    
    fluidFSEventsParamsComponentRemoteSystemName OBJECT-TYPE
       SYNTAX  DisplayString
       MAX-ACCESS  read-only
       STATUS  current
       DESCRIPTION
           "System (cluster) name"
       ::= { fluidFSEventsParamsComponent 18 }
    
    
    fluidFSEventsParamsComponentApplianceServiceTag OBJECT-TYPE
       SYNTAX  DisplayString
       MAX-ACCESS  read-only
       STATUS  current
       DESCRIPTION
           "NAS appliance service tag"
       ::= { fluidFSEventsParamsComponent 19 }
    
    
    fluidFSEventsParamsComponentServicePackFileName OBJECT-TYPE
       SYNTAX  DisplayString
       MAX-ACCESS  read-only
       STATUS  current
       DESCRIPTION
           "Service pack file name"
       ::= { fluidFSEventsParamsComponent 20 }
    
    
    fluidFSEventsParamsComponentNetworkId OBJECT-TYPE
       SYNTAX  DisplayString
       MAX-ACCESS  read-only
       STATUS  current
       DESCRIPTION
           "Network IP address"
       ::= { fluidFSEventsParamsComponent 21 }
    
    
    fluidFSEventsParamsComponentNetmask OBJECT-TYPE
       SYNTAX  DisplayString
       MAX-ACCESS  read-only
       STATUS  current
       DESCRIPTION
           "Network netmask"
       ::= { fluidFSEventsParamsComponent 22 }
    
    
    fluidFSEventsParamsComponentSubnetAccess OBJECT-TYPE
       SYNTAX  DisplayString
       MAX-ACCESS  read-only
       STATUS  current
       DESCRIPTION
           "Subnet Access type"
       ::= { fluidFSEventsParamsComponent 23 }
    
    
    fluidFSEventsParamsComponentRouteName OBJECT-TYPE
       SYNTAX  DisplayString
       MAX-ACCESS  read-only
       STATUS  current
       DESCRIPTION
           "Route Rules unique name"
       ::= { fluidFSEventsParamsComponent 24 }
    
    
    fluidFSEventsParamsComponentRouteGateway OBJECT-TYPE
       SYNTAX  DisplayString
       MAX-ACCESS  read-only
       STATUS  current
       DESCRIPTION
           "Route Rules Gateway IP"
       ::= { fluidFSEventsParamsComponent 25 }
    
    
    fluidFSEventsParamsComponentClientNetworkInterfaceMtu OBJECT-TYPE
       SYNTAX  DisplayString
       MAX-ACCESS  read-only
       STATUS  current
       DESCRIPTION
           "MTU"
       ::= { fluidFSEventsParamsComponent 26 }
    
    
    fluidFSEventsParamsComponentClientNetworkInterfaceBondMode OBJECT-TYPE
       SYNTAX  DisplayString
       MAX-ACCESS  read-only
       STATUS  current
       DESCRIPTION
           "Bonding mode"
       ::= { fluidFSEventsParamsComponent 27 }
    
    
    fluidFSEventsParamsComponentLocalAccountName OBJECT-TYPE
       SYNTAX  DisplayString
       MAX-ACCESS  read-only
       STATUS  current
       DESCRIPTION
           "Local user/group name"
       ::= { fluidFSEventsParamsComponent 28 }
    
    
    fluidFSEventsParamsComponentUserDatabaseType OBJECT-TYPE
       SYNTAX  DisplayString
       MAX-ACCESS  read-only
       STATUS  current
       DESCRIPTION
           "Type of external UNIX accounts repository: NIS, LDAP or None."
       ::= { fluidFSEventsParamsComponent 29 }
    
    
    fluidFSEventsParamsComponentWindowsUser OBJECT-TYPE
       SYNTAX  DisplayString
       MAX-ACCESS  read-only
       STATUS  current
       DESCRIPTION
           "User name from Windows repository"
       ::= { fluidFSEventsParamsComponent 30 }
    
    
    fluidFSEventsParamsComponentUnixUser OBJECT-TYPE
       SYNTAX  DisplayString
       MAX-ACCESS  read-only
       STATUS  current
       DESCRIPTION
           "User name from UNIX repository"
       ::= { fluidFSEventsParamsComponent 31 }
    
    
    fluidFSEventsParamsComponentBlink1 OBJECT-TYPE
       SYNTAX  DisplayString
       MAX-ACCESS  read-only
       STATUS  current
       DESCRIPTION
           "Blink first controller"
       ::= { fluidFSEventsParamsComponent 32 }
    
    
    fluidFSEventsParamsComponentBlink2 OBJECT-TYPE
       SYNTAX  DisplayString
       MAX-ACCESS  read-only
       STATUS  current
       DESCRIPTION
           "Blink second controller"
       ::= { fluidFSEventsParamsComponent 33 }
    
    
    fluidFSEventsParamsComponentControllerId OBJECT-TYPE
       SYNTAX  DisplayString
       MAX-ACCESS  read-only
       STATUS  current
       DESCRIPTION
           "The controller ID"
       ::= { fluidFSEventsParamsComponent 34 }
    
    
    fluidFSEventsParamsComponentClientIp OBJECT-TYPE
       SYNTAX  DisplayString
       MAX-ACCESS  read-only
       STATUS  current
       DESCRIPTION
           "Client Ip"
       ::= { fluidFSEventsParamsComponent 35 }
    
    
    fluidFSEventsParamsComponentAccessIp OBJECT-TYPE
       SYNTAX  DisplayString
       MAX-ACCESS  read-only
       STATUS  current
       DESCRIPTION
           "Access Ip"
       ::= { fluidFSEventsParamsComponent 36 }
    
    
    fluidFSEventsParamsComponentNodeId OBJECT-TYPE
       SYNTAX  DisplayString
       MAX-ACCESS  read-only
       STATUS  current
       DESCRIPTION
           "Node Id"
       ::= { fluidFSEventsParamsComponent 37 }
    
    
    fluidFSEventsParamsComponentNetworkInterface OBJECT-TYPE
       SYNTAX  DisplayString
       MAX-ACCESS  read-only
       STATUS  current
       DESCRIPTION
           "Network Interface"
       ::= { fluidFSEventsParamsComponent 38 }
    
    
    fluidFSEventsParamsComponentPinState OBJECT-TYPE
       SYNTAX  DisplayString
       MAX-ACCESS  read-only
       STATUS  current
       DESCRIPTION
           "Pin or Unpin client to specific controller"
       ::= { fluidFSEventsParamsComponent 39 }
    
    
    fluidFSEventsParamsComponentApplianceId OBJECT-TYPE
       SYNTAX  DisplayString
       MAX-ACCESS  read-only
       STATUS  current
       DESCRIPTION
           "Appliance Id"
       ::= { fluidFSEventsParamsComponent 40 }
    
    
    fluidFSEventsParamsComponentClusterName OBJECT-TYPE
       SYNTAX  DisplayString
       MAX-ACCESS  read-only
       STATUS  current
       DESCRIPTION
           "Cluster Name"
       ::= { fluidFSEventsParamsComponent 41 }
    
    
    fluidFSEventsParamsComponentLicensedFeature OBJECT-TYPE
       SYNTAX  DisplayString
       MAX-ACCESS  read-only
       STATUS  current
       DESCRIPTION
           "Licensed Feature"
       ::= { fluidFSEventsParamsComponent 42 }
    
    
    fluidFSEventsParamsComponentFabricName OBJECT-TYPE
       SYNTAX  DisplayString
       MAX-ACCESS  read-only
       STATUS  current
       DESCRIPTION
           "Fabric Name"
       ::= { fluidFSEventsParamsComponent 43 }
    
    
    fluidFSEventsParamsComponentSourceFilePath OBJECT-TYPE
       SYNTAX  DisplayString
       MAX-ACCESS  read-only
       STATUS  current
       DESCRIPTION
           "Source File Path"
       ::= { fluidFSEventsParamsComponent 44 }
    
    
    fluidFSEventsParamsComponentDestinationDir OBJECT-TYPE
       SYNTAX  DisplayString
       MAX-ACCESS  read-only
       STATUS  current
       DESCRIPTION
           "Destination Directory"
       ::= { fluidFSEventsParamsComponent 45 }
    
    
    fluidFSEventsParamsComponentDestinationFileName OBJECT-TYPE
       SYNTAX  DisplayString
       MAX-ACCESS  read-only
       STATUS  current
       DESCRIPTION
           "Destination File Name"
       ::= { fluidFSEventsParamsComponent 46 }
    
    
    fluidFSEventsParamsComponentDestinationParentDir OBJECT-TYPE
       SYNTAX  DisplayString
       MAX-ACCESS  read-only
       STATUS  current
       DESCRIPTION
           "Destination Parent Directory"
       ::= { fluidFSEventsParamsComponent 47 }
    
    
    fluidFSEventsParamsComponentNDMPSessionId OBJECT-TYPE
       SYNTAX  DisplayString
       MAX-ACCESS  read-only
       STATUS  current
       DESCRIPTION
           "NDMP Session ID"
       ::= { fluidFSEventsParamsComponent 48 }
    
    
    fluidFSEventsParamsComponentClientComputerName OBJECT-TYPE
       SYNTAX  DisplayString
       MAX-ACCESS  read-only
       STATUS  current
       DESCRIPTION
           "Client Computer Name"
       ::= { fluidFSEventsParamsComponent 49 }
    
    
    fluidFSEventsParamsComponentClientUserName OBJECT-TYPE
       SYNTAX  DisplayString
       MAX-ACCESS  read-only
       STATUS  current
       DESCRIPTION
           "Client User Name"
       ::= { fluidFSEventsParamsComponent 50 }
    
    
    fluidFSEventsParamsComponentPartnerIp OBJECT-TYPE
       SYNTAX  DisplayString
       MAX-ACCESS  read-only
       STATUS  current
       DESCRIPTION
           "Partner IP"
       ::= { fluidFSEventsParamsComponent 51 }
    
    
    fluidFSEventsParamsComponentVirtualVolumeFolderName OBJECT-TYPE
       SYNTAX  DisplayString
       MAX-ACCESS  read-only
       STATUS  current
       DESCRIPTION
           "Virtual Volume Folder Name"
       ::= { fluidFSEventsParamsComponent 52 }
    
    
    fluidFSEventsParamsComponentPrefix OBJECT-TYPE
       SYNTAX  DisplayString
       MAX-ACCESS  read-only
       STATUS  current
       DESCRIPTION
           "Network prefix"
       ::= { fluidFSEventsParamsComponent 53 }
    
    
    fluidFSEventsParamsComponentRunCifsFileAccessibilityDiagnosticShareName OBJECT-TYPE
       SYNTAX  DisplayString
       MAX-ACCESS  read-only
       STATUS  current
       DESCRIPTION
           "RunCifsFileAccessibilityDiagnosticShareName"
       ::= { fluidFSEventsParamsComponent 54 }
    
    
    fluidFSEventsParamsComponentRunCifsFileAccessibilityDiagnosticClientIP OBJECT-TYPE
       SYNTAX  DisplayString
       MAX-ACCESS  read-only
       STATUS  current
       DESCRIPTION
           "RunCifsFileAccessibilityDiagnosticClientIP"
       ::= { fluidFSEventsParamsComponent 55 }
    
    
    fluidFSEventsParamsComponentRunCifsFileAccessibilityDiagnosticPath OBJECT-TYPE
       SYNTAX  DisplayString
       MAX-ACCESS  read-only
       STATUS  current
       DESCRIPTION
           "RunCifsFileAccessibilityDiagnosticPath"
       ::= { fluidFSEventsParamsComponent 56 }
    
    
    fluidFSEventsParamsComponentRunClientConnectivityDiagnosticClientIP OBJECT-TYPE
       SYNTAX  DisplayString
       MAX-ACCESS  read-only
       STATUS  current
       DESCRIPTION
           "RunClientConnectivityDiagnosticClientIP"
       ::= { fluidFSEventsParamsComponent 57 }
    
    
    fluidFSEventsParamsComponentRunClientConnectivityDiagnosticProtocol OBJECT-TYPE
       SYNTAX  DisplayString
       MAX-ACCESS  read-only
       STATUS  current
       DESCRIPTION
           "RunClientConnectivityDiagnosticProtocol"
       ::= { fluidFSEventsParamsComponent 58 }
    
    
    fluidFSEventsParamsComponentRunNetworkDiagnosticClientIP OBJECT-TYPE
       SYNTAX  DisplayString
       MAX-ACCESS  read-only
       STATUS  current
       DESCRIPTION
           "RunNetworkDiagnosticClientIP"
       ::= { fluidFSEventsParamsComponent 59 }
    
    
    fluidFSEventsParamsComponentRunNfsFileAccessibilityDiagnosticExportPath OBJECT-TYPE
       SYNTAX  DisplayString
       MAX-ACCESS  read-only
       STATUS  current
       DESCRIPTION
           "RunNfsFileAccessibilityDiagnosticExportPath"
       ::= { fluidFSEventsParamsComponent 60 }
    
    
    fluidFSEventsParamsComponentRunNfsFileAccessibilityDiagnosticFSID OBJECT-TYPE
       SYNTAX  DisplayString
       MAX-ACCESS  read-only
       STATUS  current
       DESCRIPTION
           "RunNfsFileAccessibilityDiagnosticFSID"
       ::= { fluidFSEventsParamsComponent 61 }
    
    
    fluidFSEventsParamsComponentRunNfsFileAccessibilityDiagnosticClientIP OBJECT-TYPE
       SYNTAX  DisplayString
       MAX-ACCESS  read-only
       STATUS  current
       DESCRIPTION
           "RunNfsFileAccessibilityDiagnosticClientIP"
       ::= { fluidFSEventsParamsComponent 62 }
    
    
    fluidFSEventsParamsComponentRunNfsFileAccessibilityDiagnosticPath OBJECT-TYPE
       SYNTAX  DisplayString
       MAX-ACCESS  read-only
       STATUS  current
       DESCRIPTION
           "RunNfsFileAccessibilityDiagnosticPath"
       ::= { fluidFSEventsParamsComponent 63 }
    
    
    fluidFSEventsParamsComponentRunPerformanceDiagnosticFSID OBJECT-TYPE
       SYNTAX  DisplayString
       MAX-ACCESS  read-only
       STATUS  current
       DESCRIPTION
           "RunPerformanceDiagnosticFSID"
       ::= { fluidFSEventsParamsComponent 64 }
    
    
    fluidFSEventsParamsComponentFilePath OBJECT-TYPE
       SYNTAX  DisplayString
       MAX-ACCESS  read-only
       STATUS  current
       DESCRIPTION
           "File path"
       ::= { fluidFSEventsParamsComponent 65 }
    
    
    fluidFSEventsParamsComponentSourceFSID OBJECT-TYPE
       SYNTAX  DisplayString
       MAX-ACCESS  read-only
       STATUS  current
       DESCRIPTION
           "Source NAS volume id"
       ::= { fluidFSEventsParamsComponent 66 }
    
    
    fluidFSEventsParamsComponentDestinationFSID OBJECT-TYPE
       SYNTAX  DisplayString
       MAX-ACCESS  read-only
       STATUS  current
       DESCRIPTION
           "Destination NAS volume id"
       ::= { fluidFSEventsParamsComponent 67 }
    
    
    fluidFSEventsParamsComponentDestinationFilePath OBJECT-TYPE
       SYNTAX  DisplayString
       MAX-ACCESS  read-only
       STATUS  current
       DESCRIPTION
           ""
       ::= { fluidFSEventsParamsComponent 68 }
    
    
    fluidFSEventsParamsComponentClientProtocol OBJECT-TYPE
       SYNTAX  DisplayString
       MAX-ACCESS  read-only
       STATUS  current
       DESCRIPTION
           "NFS/SMB protocol"
       ::= { fluidFSEventsParamsComponent 69 }
    
    
    fluidFSEventsParamsComponentClientProtocolDetails OBJECT-TYPE
       SYNTAX  DisplayString
       MAX-ACCESS  read-only
       STATUS  current
       DESCRIPTION
           "Session or opened file details"
       ::= { fluidFSEventsParamsComponent 70 }
    
    
    fluidFSEventsParamsComponentSourceVMName OBJECT-TYPE
       SYNTAX  DisplayString
       MAX-ACCESS  read-only
       STATUS  current
       DESCRIPTION
           "Source VM Name"
       ::= { fluidFSEventsParamsComponent 71 }
    
    
    fluidFSEventsParamsComponentVmWareServerName OBJECT-TYPE
       SYNTAX  DisplayString
       MAX-ACCESS  read-only
       STATUS  current
       DESCRIPTION
           "VMWare Server Name"
       ::= { fluidFSEventsParamsComponent 72 }
    
    
    fluidFSEventsParamsComponentNumberOfClones OBJECT-TYPE
       SYNTAX  DisplayString
       MAX-ACCESS  read-only
       STATUS  current
       DESCRIPTION
           "Number Of Clones"
       ::= { fluidFSEventsParamsComponent 73 }
    
    
    fluidFSEventsParamsComponentServicePackVersion OBJECT-TYPE
       SYNTAX  DisplayString
       MAX-ACCESS  read-only
       STATUS  current
       DESCRIPTION
           "Version of a service pack"
       ::= { fluidFSEventsParamsComponent 74 }
    
    
    fluidFSEventsParamsComponentDestinationNetworkID OBJECT-TYPE
       SYNTAX  DisplayString
       MAX-ACCESS  read-only
       STATUS  current
       DESCRIPTION
           "Route Rules route ip address"
       ::= { fluidFSEventsParamsComponent 75 }
    
    
    fluidFSEventsParamsComponentDestinationPrefix OBJECT-TYPE
       SYNTAX  DisplayString
       MAX-ACCESS  read-only
       STATUS  current
       DESCRIPTION
           "Route Rules route ip prefix"
       ::= { fluidFSEventsParamsComponent 76 }
    
    
    fluidFSEventsParamsComponentFolderPath OBJECT-TYPE
       SYNTAX  DisplayString
       MAX-ACCESS  read-only
       STATUS  current
       DESCRIPTION
           "Folder path"
       ::= { fluidFSEventsParamsComponent 77 }
    
    
    fluidFSEventsParamsComponentDSID OBJECT-TYPE
       SYNTAX  DisplayString
       MAX-ACCESS  read-only
       STATUS  current
       DESCRIPTION
           ""
       ::= { fluidFSEventsParamsComponent 78 }
    
    
    fluidFSEventsParamsComponentTapeDeviceName OBJECT-TYPE
       SYNTAX  DisplayString
       MAX-ACCESS  read-only
       STATUS  current
       DESCRIPTION
           "Configured name of tape device"
       ::= { fluidFSEventsParamsComponent 79 }
    
    
    fluidFSEventsParamsComponentEventsSpace OBJECT-TYPE
       SYNTAX  DisplayString
       MAX-ACCESS  read-only
       STATUS  current
       DESCRIPTION
           ""
       ::= { fluidFSEventsParamsComponent 80 }
    
    
    fluidFSEventsParamsComponentGpoTimeout OBJECT-TYPE
       SYNTAX  DisplayString
       MAX-ACCESS  read-only
       STATUS  current
       DESCRIPTION
           ""
       ::= { fluidFSEventsParamsComponent 81 }
    
    
    fluidFSEventsParamsComponentTenantId OBJECT-TYPE
       SYNTAX  DisplayString
       MAX-ACCESS  read-only
       STATUS  current
       DESCRIPTION
           "Tenant unique identifier"
       ::= { fluidFSEventsParamsComponent 82 }
    
    
    fluidFSEventsParamsComponentFSID OBJECT-TYPE
       SYNTAX  INTEGER
       MAX-ACCESS  read-only
       STATUS  current
       DESCRIPTION
           "NAS volume id"
       ::= { fluidFSEventsParamsComponent 83 }
    
    
    fluidFSEventsParamsComponentUID OBJECT-TYPE
       SYNTAX  DisplayString
       MAX-ACCESS  read-only
       STATUS  current
       DESCRIPTION
           ""
       ::= { fluidFSEventsParamsComponent 84 }
    
    
    fluidFSEventsParamsComponentRemoteClusterId OBJECT-TYPE
       SYNTAX  DisplayString
       MAX-ACCESS  read-only
       STATUS  current
       DESCRIPTION
           ""
       ::= { fluidFSEventsParamsComponent 85 }
    
    
    fluidFSEventsParamsComponentRemoteFSID OBJECT-TYPE
       SYNTAX  INTEGER
       MAX-ACCESS  read-only
       STATUS  current
       DESCRIPTION
           ""
       ::= { fluidFSEventsParamsComponent 86 }
    
    
    fluidFSEventsParamsComponentStorageId OBJECT-TYPE
       SYNTAX  DisplayString
       MAX-ACCESS  read-only
       STATUS  current
       DESCRIPTION
           ""
       ::= { fluidFSEventsParamsComponent 87 }
    
    
    fluidFSEventsParamsComponentSourceFSID OBJECT-TYPE
       SYNTAX  INTEGER
       MAX-ACCESS  read-only
       STATUS  current
       DESCRIPTION
           "Source NAS volume id"
       ::= { fluidFSEventsParamsComponent 88 }
    
    
    fluidFSEventsParamsComponentDestinationFSID OBJECT-TYPE
       SYNTAX  INTEGER
       MAX-ACCESS  read-only
       STATUS  current
       DESCRIPTION
           "Destination NAS volume id"
       ::= { fluidFSEventsParamsComponent 89 }
    
    
    fluidFSEventsParamsComponentState OBJECT-TYPE
       SYNTAX  DisplayString
       MAX-ACCESS  read-only
       STATUS  current
       DESCRIPTION
           ""
       ::= { fluidFSEventsParamsComponent 90 }
    
    
    fluidFSEventsParamsComponentFSIDName OBJECT-TYPE
       SYNTAX  DisplayString
       MAX-ACCESS  read-only
       STATUS  current
       DESCRIPTION
           ""
       ::= { fluidFSEventsParamsComponent 91 }
    
    
    fluidFSEventsParamsComponentTenantName OBJECT-TYPE
       SYNTAX  DisplayString
       MAX-ACCESS  read-only
       STATUS  current
       DESCRIPTION
           ""
       ::= { fluidFSEventsParamsComponent 92 }
    
    
    fluidFSEventsParamsComponentAdminName OBJECT-TYPE
       SYNTAX  DisplayString
       MAX-ACCESS  read-only
       STATUS  current
       DESCRIPTION
           ""
       ::= { fluidFSEventsParamsComponent 93 }
    
    
    fluidFSEventsParamsComponentRemoteClusterName OBJECT-TYPE
       SYNTAX  DisplayString
       MAX-ACCESS  read-only
       STATUS  current
       DESCRIPTION
           "Name of the partner system"
       ::= { fluidFSEventsParamsComponent 94 }
    
    
    fluidFSEventsParamsComponentRemoteVolumeName OBJECT-TYPE
       SYNTAX  DisplayString
       MAX-ACCESS  read-only
       STATUS  current
       DESCRIPTION
           "Name of the remote NAS volume"
       ::= { fluidFSEventsParamsComponent 95 }
    
    
    fluidFSEventsParamsComponentWindowsUserName OBJECT-TYPE
       SYNTAX  DisplayString
       MAX-ACCESS  read-only
       STATUS  current
       DESCRIPTION
           ""
       ::= { fluidFSEventsParamsComponent 96 }
    
    
    fluidFSEventsParamsComponentUnixUserName OBJECT-TYPE
       SYNTAX  DisplayString
       MAX-ACCESS  read-only
       STATUS  current
       DESCRIPTION
           ""
       ::= { fluidFSEventsParamsComponent 97 }
    
    
    fluidFSEventsParamsComponentSourceFSIDName OBJECT-TYPE
       SYNTAX  DisplayString
       MAX-ACCESS  read-only
       STATUS  current
       DESCRIPTION
           ""
       ::= { fluidFSEventsParamsComponent 98 }
    
    
    fluidFSEventsParamsComponentDestinationFSIDName OBJECT-TYPE
       SYNTAX  DisplayString
       MAX-ACCESS  read-only
       STATUS  current
       DESCRIPTION
           ""
       ::= { fluidFSEventsParamsComponent 99 }
    
    
    fluidFSEventsParamsComponentDSIDPath OBJECT-TYPE
       SYNTAX  DisplayString
       MAX-ACCESS  read-only
       STATUS  current
       DESCRIPTION
           ""
       ::= { fluidFSEventsParamsComponent 100 }
    
    
    fluidFSEventComponentExampleCreateSuccess NOTIFICATION-TYPE
       OBJECTS { sysName, fluidFSEventsParamsComponentUserName, fluidFSEventsParamsComponentName, fluidFSEventsParamsComponentRetcodeString }
       STATUS current
       DESCRIPTION
           "Example {{Name}} was created by {{userName}}.  Result: {{retcodeString}}."
           --#TYPE         "Normal Event"
           --#SUMMARY      Example %s was created by %s.  Result: %s.
           --#ARGUMENTS    {1,2,3}
           --#SEVERITY     INFORMATIONAL
           --#TIMEINDEX    99
           --#STATE        OK
       ::= { fluidFSEventsComponent 3 } 
    
    
    fluidFSEventComponentExampleCreateFailed NOTIFICATION-TYPE
       OBJECTS { sysName, fluidFSEventsParamsComponentUserName, fluidFSEventsParamsComponentName, fluidFSEventsParamsComponentRetcodeString }
       STATUS current
       DESCRIPTION
           "Failed to create Example {{Name}} by {{userName}}. {{retcodeString}}."
           --#TYPE         "Normal Event"
           --#SUMMARY      Failed to create Example %s by %s. %s.
           --#ARGUMENTS    {1,2,3}
           --#SEVERITY     MAJOR
           --#TIMEINDEX    99
           --#STATE        OK
       ::= { fluidFSEventsComponent 4 } 
    
    
    fluidFSEventComponentExampleCreateWarning NOTIFICATION-TYPE
       OBJECTS { sysName, fluidFSEventsParamsComponentUserName, fluidFSEventsParamsComponentName, fluidFSEventsParamsComponentRetcodeString }
       STATUS current
       DESCRIPTION
           "Example {{Name}} was created by {{userName}}, but with a warning: {{retcodeString}}."
           --#TYPE         "Normal Event"
           --#SUMMARY      Example %s was created by %s, but with a warning: %s.
           --#ARGUMENTS    {1,2,3}
           --#SEVERITY     MAJOR
           --#TIMEINDEX    99
           --#STATE        OK
       ::= { fluidFSEventsComponent 5 } 
    
    
    fluidFSEventComponentExampleModifySuccess NOTIFICATION-TYPE
       OBJECTS { sysName, fluidFSEventsParamsComponentUserName, fluidFSEventsParamsComponentName, fluidFSEventsParamsComponentRetcodeString }
       STATUS current
       DESCRIPTION
           "Example {{Name}} was modified by {{userName}}. Result: {{retcodeString}}."
           --#TYPE         "Normal Event"
           --#SUMMARY      Example %s was modified by %s. Result: %s.
           --#ARGUMENTS    {1,2,3}
           --#SEVERITY     INFORMATIONAL
           --#TIMEINDEX    99
           --#STATE        OK
       ::= { fluidFSEventsComponent 6 } 
    
    
    fluidFSEventComponentExampleModifyFailed NOTIFICATION-TYPE
       OBJECTS { sysName, fluidFSEventsParamsComponentUserName, fluidFSEventsParamsComponentName, fluidFSEventsParamsComponentRetcodeString }
       STATUS current
       DESCRIPTION
           "Failed to modify Example {{Name}} by {{userName}}. {{retcodeString}}."
           --#TYPE         "Normal Event"
           --#SUMMARY      Failed to modify Example %s by %s. %s.
           --#ARGUMENTS    {1,2,3}
           --#SEVERITY     MAJOR
           --#TIMEINDEX    99
           --#STATE        OK
       ::= { fluidFSEventsComponent 7 } 
    
    
    fluidFSEventComponentExampleModifyWarning NOTIFICATION-TYPE
       OBJECTS { sysName, fluidFSEventsParamsComponentUserName, fluidFSEventsParamsComponentName, fluidFSEventsParamsComponentRetcodeString }
       STATUS current
       DESCRIPTION
           "Example {{Name}} was modified by {{userName}}, but with a warning: {{retcodeString}}."
           --#TYPE         "Normal Event"
           --#SUMMARY      Example %s was modified by %s, but with a warning: %s.
           --#ARGUMENTS    {1,2,3}
           --#SEVERITY     MAJOR
           --#TIMEINDEX    99
           --#STATE        OK
       ::= { fluidFSEventsComponent 8 } 
    
    
    fluidFSEventComponentExampleDeleteSuccess NOTIFICATION-TYPE
       OBJECTS { sysName, fluidFSEventsParamsComponentUserName, fluidFSEventsParamsComponentName, fluidFSEventsParamsComponentRetcodeString }
       STATUS current
       DESCRIPTION
           "Example {{Name}} was deleted by {{userName}}. Result: {{retcodeString}}."
           --#TYPE         "Normal Event"
           --#SUMMARY      Example %s was deleted by %s. Result: %s.
           --#ARGUMENTS    {1,2,3}
           --#SEVERITY     INFORMATIONAL
           --#TIMEINDEX    99
           --#STATE        OK
       ::= { fluidFSEventsComponent 9 } 
    
    
    fluidFSEventComponentExampleDeleteFailed NOTIFICATION-TYPE
       OBJECTS { sysName, fluidFSEventsParamsComponentUserName, fluidFSEventsParamsComponentName, fluidFSEventsParamsComponentRetcodeString }
       STATUS current
       DESCRIPTION
           "Failed to delete {{Name}} by {{userName}}. {{retcodeString}}."
           --#TYPE         "Normal Event"
           --#SUMMARY      Failed to delete %s by %s. %s.
           --#ARGUMENTS    {1,2,3}
           --#SEVERITY     MAJOR
           --#TIMEINDEX    99
           --#STATE        OK
       ::= { fluidFSEventsComponent 10 } 
    
    
    fluidFSEventComponentExampleDeleteWarning NOTIFICATION-TYPE
       OBJECTS { sysName, fluidFSEventsParamsComponentUserName, fluidFSEventsParamsComponentName, fluidFSEventsParamsComponentRetcodeString }
       STATUS current
       DESCRIPTION
           "Example {{Name}} was deleted by {{userName}}, but with a warning: {{retcodeString}}."
           --#TYPE         "Normal Event"
           --#SUMMARY      Example %s was deleted by %s, but with a warning: %s.
           --#ARGUMENTS    {1,2,3}
           --#SEVERITY     MAJOR
           --#TIMEINDEX    99
           --#STATE        OK
       ::= { fluidFSEventsComponent 11 } 
    
    
    fluidFSEventComponentTimeModifySuccess NOTIFICATION-TYPE
       OBJECTS { sysName, fluidFSEventsParamsComponentUserName }
       STATUS current
       DESCRIPTION
           "Time configuration was modified by {{userName}}"
           --#TYPE         "Normal Event"
           --#SUMMARY      Time configuration was modified by %s
           --#ARGUMENTS    {1}
           --#SEVERITY     INFORMATIONAL
           --#TIMEINDEX    99
           --#STATE        OK
       ::= { fluidFSEventsComponent 12 } 
    
    
    fluidFSEventComponentTimeModifyFailed NOTIFICATION-TYPE
       OBJECTS { sysName, fluidFSEventsParamsComponentUserName, fluidFSEventsParamsComponentRetcodeString }
       STATUS current
       DESCRIPTION
           "Failed to modify time configuration by {{userName}}. {{retcodeString}}."
           --#TYPE         "Normal Event"
           --#SUMMARY      Failed to modify time configuration by %s. %s.
           --#ARGUMENTS    {1,2}
           --#SEVERITY     MAJOR
           --#TIMEINDEX    99
           --#STATE        OK
       ::= { fluidFSEventsComponent 13 } 
    
    
    fluidFSEventComponentRouteRulesCreateSuccess NOTIFICATION-TYPE
       OBJECTS { sysName, fluidFSEventsParamsComponentUserName, fluidFSEventsParamsComponentDestinationNetworkID, fluidFSEventsParamsComponentDestinationPrefix, fluidFSEventsParamsComponentRouteGateway }
       STATUS current
       DESCRIPTION
           "Route to {{destinationNetworkID}}/{{destinationPrefix}} with gateway IP {{routeGateway}}  was successfully created by {{userName}}."
           --#TYPE         "Normal Event"
           --#SUMMARY      Route to %s/%s with gateway IP %s  was successfully created by %s.
           --#ARGUMENTS    {1,2,3,4}
           --#SEVERITY     INFORMATIONAL
           --#TIMEINDEX    99
           --#STATE        OK
       ::= { fluidFSEventsComponent 14 } 
    
    
    fluidFSEventComponentSnmpModifySuccess NOTIFICATION-TYPE
       OBJECTS { sysName, fluidFSEventsParamsComponentUserName }
       STATUS current
       DESCRIPTION
           "SNMP configuration was modified by {{userName}}. "
           --#TYPE         "Normal Event"
           --#SUMMARY      SNMP configuration was modified by %s. 
           --#ARGUMENTS    {1}
           --#SEVERITY     INFORMATIONAL
           --#TIMEINDEX    99
           --#STATE        OK
       ::= { fluidFSEventsComponent 15 } 
    
    
    fluidFSEventComponentSnmpModifyFailed NOTIFICATION-TYPE
       OBJECTS { sysName, fluidFSEventsParamsComponentUserName, fluidFSEventsParamsComponentRetcodeString }
       STATUS current
       DESCRIPTION
           "Failed to modify SNMP by {{userName}}. {{retcodeString}}."
           --#TYPE         "Normal Event"
           --#SUMMARY      Failed to modify SNMP by %s. %s.
           --#ARGUMENTS    {1,2}
           --#SEVERITY     MAJOR
           --#TIMEINDEX    99
           --#STATE        OK
       ::= { fluidFSEventsComponent 16 } 
    
    
    fluidFSEventComponentRouteRulesModifySuccess NOTIFICATION-TYPE
       OBJECTS { sysName, fluidFSEventsParamsComponentUserName, fluidFSEventsParamsComponentDestinationNetworkID, fluidFSEventsParamsComponentDestinationPrefix, fluidFSEventsParamsComponentRouteGateway }
       STATUS current
       DESCRIPTION
           "Route to {{destinationNetworkID}}/{{destinationPrefix}} with gateway IP {{routeGateway}}  was successfully modified by {{userName}}."
           --#TYPE         "Normal Event"
           --#SUMMARY      Route to %s/%s with gateway IP %s  was successfully modified by %s.
           --#ARGUMENTS    {1,2,3,4}
           --#SEVERITY     INFORMATIONAL
           --#TIMEINDEX    99
           --#STATE        OK
       ::= { fluidFSEventsComponent 30 } 
    
    
    fluidFSEventComponentMailConfModifySuccess NOTIFICATION-TYPE
       OBJECTS { sysName, fluidFSEventsParamsComponentUserName }
       STATUS current
       DESCRIPTION
           "Mail configuration was modified by {{userName}}. "
           --#TYPE         "Normal Event"
           --#SUMMARY      Mail configuration was modified by %s. 
           --#ARGUMENTS    {1}
           --#SEVERITY     INFORMATIONAL
           --#TIMEINDEX    99
           --#STATE        OK
       ::= { fluidFSEventsComponent 31 } 
    
    
    fluidFSEventComponentSystemServiceModeChangedSuccess NOTIFICATION-TYPE
       OBJECTS { sysName, fluidFSEventsParamsComponentSystemServiceState }
       STATUS current
       DESCRIPTION
           "The System Service Mode is changed to {{systemServiceState}}.   Description:  The System Service Mode is changed to {{systemServiceState}}. "
           --#TYPE         "Normal Event"
           --#SUMMARY      The System Service Mode is changed to %s.   Description:  The System Service Mode is changed to %s. 
           --#ARGUMENTS    {1}
           --#SEVERITY     INFORMATIONAL
           --#TIMEINDEX    99
           --#STATE        OK
       ::= { fluidFSEventsComponent 32 } 
    
    
    fluidFSEventComponentSystemServiceModeChangedFailed NOTIFICATION-TYPE
       OBJECTS { sysName, fluidFSEventsParamsComponentSystemServiceState, fluidFSEventsParamsComponentRetcodeString }
       STATUS current
       DESCRIPTION
           "Failed to change System Service Mode.   Description:  The System Service Mode failed to be changed to {{systemServiceState}}: {{retcodeString}}. "
           --#TYPE         "Normal Event"
           --#SUMMARY      Failed to change System Service Mode.   Description:  The System Service Mode failed to be changed to %s: %s. 
           --#ARGUMENTS    {1,2}
           --#SEVERITY     INFORMATIONAL
           --#TIMEINDEX    99
           --#STATE        OK
       ::= { fluidFSEventsComponent 35 } 
    
    
    fluidFSEventComponentNasAppliancesCreateSuccess NOTIFICATION-TYPE
       OBJECTS { sysName, fluidFSEventsParamsComponentUserName, fluidFSEventsParamsComponentApplianceId, fluidFSEventsParamsComponentApplianceServiceTag }
       STATUS current
       DESCRIPTION
           "NAS Appliance {{applianceId}} ({{applianceServiceTag}}) was successfully created by user {{userName}}."
           --#TYPE         "Normal Event"
           --#SUMMARY      NAS Appliance %s (%s) was successfully created by user %s.
           --#ARGUMENTS    {1,2,3}
           --#SEVERITY     INFORMATIONAL
           --#TIMEINDEX    99
           --#STATE        OK
       ::= { fluidFSEventsComponent 36 } 
    
    
    fluidFSEventComponentNasAppliancesCreateFailed NOTIFICATION-TYPE
       OBJECTS { sysName, fluidFSEventsParamsComponentUserName, fluidFSEventsParamsComponentApplianceId, fluidFSEventsParamsComponentApplianceServiceTag, fluidFSEventsParamsComponentRetcodeString }
       STATUS current
       DESCRIPTION
           "NAS Appliance {{applianceId}} ({{applianceServiceTag}}) could not be created by user {{userName}}. {{retcodeString}}."
           --#TYPE         "Normal Event"
           --#SUMMARY      NAS Appliance %s (%s) could not be created by user %s. %s.
           --#ARGUMENTS    {1,2,3,4}
           --#SEVERITY     MAJOR
           --#TIMEINDEX    99
           --#STATE        OK
       ::= { fluidFSEventsComponent 37 } 
    
    
    fluidFSEventComponentNasAppliancesModifySuccess NOTIFICATION-TYPE
       OBJECTS { sysName, fluidFSEventsParamsComponentUserName, fluidFSEventsParamsComponentApplianceId, fluidFSEventsParamsComponentApplianceServiceTag }
       STATUS current
       DESCRIPTION
           "NAS Appliance {{applianceId}} ({{applianceServiceTag}}) was successfully modified by user {{userName}}."
           --#TYPE         "Normal Event"
           --#SUMMARY      NAS Appliance %s (%s) was successfully modified by user %s.
           --#ARGUMENTS    {1,2,3}
           --#SEVERITY     INFORMATIONAL
           --#TIMEINDEX    99
           --#STATE        OK
       ::= { fluidFSEventsComponent 38 } 
    
    
    fluidFSEventComponentNasAppliancesModifyFailed NOTIFICATION-TYPE
       OBJECTS { sysName, fluidFSEventsParamsComponentUserName, fluidFSEventsParamsComponentApplianceId, fluidFSEventsParamsComponentApplianceServiceTag, fluidFSEventsParamsComponentRetcodeString }
       STATUS current
       DESCRIPTION
           "NAS Appliance {{applianceId}} ({{applianceServiceTag}}) could not be modified by user {{userName}}. {{retcodeString}}."
           --#TYPE         "Normal Event"
           --#SUMMARY      NAS Appliance %s (%s) could not be modified by user %s. %s.
           --#ARGUMENTS    {1,2,3,4}
           --#SEVERITY     MAJOR
           --#TIMEINDEX    99
           --#STATE        OK
       ::= { fluidFSEventsComponent 39 } 
    
    
    fluidFSEventComponentNasAppliancesDeleteSuccess NOTIFICATION-TYPE
       OBJECTS { sysName, fluidFSEventsParamsComponentUserName, fluidFSEventsParamsComponentApplianceId, fluidFSEventsParamsComponentApplianceServiceTag }
       STATUS current
       DESCRIPTION
           "NAS Appliance {{applianceId}} ({{applianceServiceTag}}) was successfully deleted by user {{userName}}."
           --#TYPE         "Normal Event"
           --#SUMMARY      NAS Appliance %s (%s) was successfully deleted by user %s.
           --#ARGUMENTS    {1,2,3}
           --#SEVERITY     INFORMATIONAL
           --#TIMEINDEX    99
           --#STATE        OK
       ::= { fluidFSEventsComponent 40 } 
    
    
    fluidFSEventComponentNasAppliancesDeleteFailed NOTIFICATION-TYPE
       OBJECTS { sysName, fluidFSEventsParamsComponentUserName, fluidFSEventsParamsComponentApplianceId, fluidFSEventsParamsComponentApplianceServiceTag, fluidFSEventsParamsComponentRetcodeString }
       STATUS current
       DESCRIPTION
           "NAS Appliance {{applianceId}} ({{applianceServiceTag}}) could not be deleted by user {{userName}}. {{retcodeString}}."
           --#TYPE         "Normal Event"
           --#SUMMARY      NAS Appliance %s (%s) could not be deleted by user %s. %s.
           --#ARGUMENTS    {1,2,3,4}
           --#SEVERITY     MAJOR
           --#TIMEINDEX    99
           --#STATE        OK
       ::= { fluidFSEventsComponent 41 } 
    
    
    fluidFSEventComponentRestoreClusterCompletedSuccessfully NOTIFICATION-TYPE
       OBJECTS { sysName, fluidFSEventsParamsComponentUserName }
       STATUS current
       DESCRIPTION
           "The configuration of the cluster was restored successfully by user {{userName}}."
           --#TYPE         "Normal Event"
           --#SUMMARY      The configuration of the cluster was restored successfully by user %s.
           --#ARGUMENTS    {1}
           --#SEVERITY     INFORMATIONAL
           --#TIMEINDEX    99
           --#STATE        OK
       ::= { fluidFSEventsComponent 42 } 
    
    
    fluidFSEventComponentRestoreClusterFinishedWithErrors NOTIFICATION-TYPE
       OBJECTS { sysName, fluidFSEventsParamsComponentUserName, fluidFSEventsParamsComponentRetcodeString }
       STATUS current
       DESCRIPTION
           "Restore of cluster configuration finished with errors.   Description:  The configuration of the cluster was restored by user {{userName}} with errors: {{retcodeString}}."
           --#TYPE         "Normal Event"
           --#SUMMARY      Restore of cluster configuration finished with errors.   Description:  The configuration of the cluster was restored by user %s with errors: %s.
           --#ARGUMENTS    {1,2}
           --#SEVERITY     MAJOR
           --#TIMEINDEX    99
           --#STATE        OK
       ::= { fluidFSEventsComponent 43 } 
    
    
    fluidFSEventComponentRestoreSystemCompletedSuccessfully NOTIFICATION-TYPE
       OBJECTS { sysName, fluidFSEventsParamsComponentUserName }
       STATUS current
       DESCRIPTION
           "The configuration of the system was restored successfully by user {{userName}}."
           --#TYPE         "Normal Event"
           --#SUMMARY      The configuration of the system was restored successfully by user %s.
           --#ARGUMENTS    {1}
           --#SEVERITY     INFORMATIONAL
           --#TIMEINDEX    99
           --#STATE        OK
       ::= { fluidFSEventsComponent 44 } 
    
    
    fluidFSEventComponentRestoreSystemFinishedWithErrors NOTIFICATION-TYPE
       OBJECTS { sysName, fluidFSEventsParamsComponentUserName, fluidFSEventsParamsComponentRetcodeString }
       STATUS current
       DESCRIPTION
           "Restore of system configuration finished with errors.   Description:  The configuration of the system was restored by user {{userName}} with errors: {{retcodeString}}."
           --#TYPE         "Normal Event"
           --#SUMMARY      Restore of system configuration finished with errors.   Description:  The configuration of the system was restored by user %s with errors: %s.
           --#ARGUMENTS    {1,2}
           --#SEVERITY     MAJOR
           --#TIMEINDEX    99
           --#STATE        OK
       ::= { fluidFSEventsComponent 45 } 
    
    
    fluidFSEventComponentRestoreSystemFromFilesCompletedSuccessfully NOTIFICATION-TYPE
       OBJECTS { sysName, fluidFSEventsParamsComponentUserName }
       STATUS current
       DESCRIPTION
           "The configuration of the system was restored from files successfully by user {{userName}}."
           --#TYPE         "Normal Event"
           --#SUMMARY      The configuration of the system was restored from files successfully by user %s.
           --#ARGUMENTS    {1}
           --#SEVERITY     INFORMATIONAL
           --#TIMEINDEX    99
           --#STATE        OK
       ::= { fluidFSEventsComponent 48 } 
    
    
    fluidFSEventComponentRestoreSystemFromFilesFinishedWithErrors NOTIFICATION-TYPE
       OBJECTS { sysName, fluidFSEventsParamsComponentUserName, fluidFSEventsParamsComponentRetcodeString }
       STATUS current
       DESCRIPTION
           "Restore of system configuration finished with errors.   Description:  The configuration of the system was restored from files by user {{userName}} with errors: {{retcodeString}}"
           --#TYPE         "Normal Event"
           --#SUMMARY      Restore of system configuration finished with errors.   Description:  The configuration of the system was restored from files by user %s with errors: %s
           --#ARGUMENTS    {1,2}
           --#SEVERITY     MAJOR
           --#TIMEINDEX    99
           --#STATE        OK
       ::= { fluidFSEventsComponent 49 } 
    
    
    fluidFSEventComponentStorageSubsystemCreateSuccess NOTIFICATION-TYPE
       OBJECTS { sysName, fluidFSEventsParamsComponentUserName }
       STATUS current
       DESCRIPTION
           "NAS pool was successfully created by {{userName}}."
           --#TYPE         "Normal Event"
           --#SUMMARY      NAS pool was successfully created by %s.
           --#ARGUMENTS    {1}
           --#SEVERITY     INFORMATIONAL
           --#TIMEINDEX    99
           --#STATE        OK
       ::= { fluidFSEventsComponent 62 } 
    
    
    fluidFSEventComponentStorageSubsystemCreateFailed NOTIFICATION-TYPE
       OBJECTS { sysName, fluidFSEventsParamsComponentUserName, fluidFSEventsParamsComponentRetcodeString }
       STATUS current
       DESCRIPTION
           "NAS pool could not be created by {{userName}}. {{retcodeString}}."
           --#TYPE         "Normal Event"
           --#SUMMARY      NAS pool could not be created by %s. %s.
           --#ARGUMENTS    {1,2}
           --#SEVERITY     MAJOR
           --#TIMEINDEX    99
           --#STATE        OK
       ::= { fluidFSEventsComponent 63 } 
    
    
    fluidFSEventComponentStorageSubsystemModifySuccess NOTIFICATION-TYPE
       OBJECTS { sysName, fluidFSEventsParamsComponentUserName }
       STATUS current
       DESCRIPTION
           "NAS pool was successfully expanded by {{userName}}."
           --#TYPE         "Normal Event"
           --#SUMMARY      NAS pool was successfully expanded by %s.
           --#ARGUMENTS    {1}
           --#SEVERITY     INFORMATIONAL
           --#TIMEINDEX    99
           --#STATE        OK
       ::= { fluidFSEventsComponent 64 } 
    
    
    fluidFSEventComponentStorageSubsystemModifyFailed NOTIFICATION-TYPE
       OBJECTS { sysName, fluidFSEventsParamsComponentUserName, fluidFSEventsParamsComponentRetcodeString }
       STATUS current
       DESCRIPTION
           "NAS pool could not be expanded by {{userName}}. {{retcodeString}}."
           --#TYPE         "Normal Event"
           --#SUMMARY      NAS pool could not be expanded by %s. %s.
           --#ARGUMENTS    {1,2}
           --#SEVERITY     MAJOR
           --#TIMEINDEX    99
           --#STATE        OK
       ::= { fluidFSEventsComponent 65 } 
    
    
    fluidFSEventComponentAuthenticateAdministratorFailure NOTIFICATION-TYPE
       OBJECTS { sysName, fluidFSEventsParamsComponentDomain, fluidFSEventsParamsComponentName, fluidFSEventsParamsComponentUserInterfaceType, fluidFSEventsParamsComponentUserInterfaceClient }
       STATUS current
       DESCRIPTION
           "User {{Domain}}\{{Name}} failed login to FluidFS {{UserInterfaceType}} from {{UserInterfaceClient}} client."
           --#TYPE         "Normal Event"
           --#SUMMARY      User %s\%s failed login to FluidFS %s from %s client.
           --#ARGUMENTS    {1,2,3,4}
           --#SEVERITY     INFORMATIONAL
           --#TIMEINDEX    99
           --#STATE        OK
       ::= { fluidFSEventsComponent 72 } 
    
    
    fluidFSEventComponentServicePackRunSuccessEvent NOTIFICATION-TYPE
       OBJECTS { sysName, fluidFSEventsParamsComponentUserName, fluidFSEventsParamsComponentServicePackFileName }
       STATUS current
       DESCRIPTION
           "{{userName}} successfully upgraded with service pack file {{servicePackFileName}}."
           --#TYPE         "Normal Event"
           --#SUMMARY      %s successfully upgraded with service pack file %s.
           --#ARGUMENTS    {1,2}
           --#SEVERITY     INFORMATIONAL
           --#TIMEINDEX    99
           --#STATE        OK
       ::= { fluidFSEventsComponent 73 } 
    
    
    fluidFSEventComponentServicePackRunFailedEvent NOTIFICATION-TYPE
       OBJECTS { sysName, fluidFSEventsParamsComponentUserName, fluidFSEventsParamsComponentServicePackFileName, fluidFSEventsParamsComponentRetcodeString }
       STATUS current
       DESCRIPTION
           "{{userName}} failed upgrade with service pack file {{servicePackFileName}}. {{retcodeString}}."
           --#TYPE         "Normal Event"
           --#SUMMARY      %s failed upgrade with service pack file %s. %s.
           --#ARGUMENTS    {1,2,3}
           --#SEVERITY     MAJOR
           --#TIMEINDEX    99
           --#STATE        OK
       ::= { fluidFSEventsComponent 74 } 
    
    
    fluidFSEventComponentEulaApproveSuccessEvent NOTIFICATION-TYPE
       OBJECTS { sysName, fluidFSEventsParamsComponentUserName }
       STATUS current
       DESCRIPTION
           "{{userName}} approved the EULA."
           --#TYPE         "Normal Event"
           --#SUMMARY      %s approved the EULA.
           --#ARGUMENTS    {1}
           --#SEVERITY     INFORMATIONAL
           --#TIMEINDEX    99
           --#STATE        OK
       ::= { fluidFSEventsComponent 75 } 
    
    
    fluidFSEventComponentAuthenticateAdministratorSuccess NOTIFICATION-TYPE
       OBJECTS { sysName, fluidFSEventsParamsComponentDomain, fluidFSEventsParamsComponentName, fluidFSEventsParamsComponentUserInterfaceType, fluidFSEventsParamsComponentUserInterfaceClient }
       STATUS current
       DESCRIPTION
           "User {{Domain}}\{{Name}} logged in to FluidFS {{UserInterfaceType}} from {{UserInterfaceClient}} client."
           --#TYPE         "Normal Event"
           --#SUMMARY      User %s\%s logged in to FluidFS %s from %s client.
           --#ARGUMENTS    {1,2,3,4}
           --#SEVERITY     INFORMATIONAL
           --#TIMEINDEX    99
           --#STATE        OK
       ::= { fluidFSEventsComponent 76 } 
    
    
    fluidFSEventComponentSetCurrentTimeActionEvent NOTIFICATION-TYPE
       OBJECTS { sysName, fluidFSEventsParamsComponentUserName }
       STATUS current
       DESCRIPTION
           "{{userName}} changed the current time."
           --#TYPE         "Normal Event"
           --#SUMMARY      %s changed the current time.
           --#ARGUMENTS    {1}
           --#SEVERITY     INFORMATIONAL
           --#TIMEINDEX    99
           --#STATE        OK
       ::= { fluidFSEventsComponent 77 } 
    
    
    fluidFSEventComponentDataReductionConfigurationModifySuccess NOTIFICATION-TYPE
       OBJECTS { sysName, fluidFSEventsParamsComponentUserName }
       STATUS current
       DESCRIPTION
           "The user {{userName}} updated the configuration of Data Reduction schedule policy."
           --#TYPE         "Normal Event"
           --#SUMMARY      The user %s updated the configuration of Data Reduction schedule policy.
           --#ARGUMENTS    {1}
           --#SEVERITY     INFORMATIONAL
           --#TIMEINDEX    99
           --#STATE        OK
       ::= { fluidFSEventsComponent 79 } 
    
    
    fluidFSEventComponentClientNetworkInterfaceModifySuccess NOTIFICATION-TYPE
       OBJECTS { sysName, fluidFSEventsParamsComponentUserName, fluidFSEventsParamsComponentClientNetworkInterfaceMtu, fluidFSEventsParamsComponentClientNetworkInterfaceBondMode }
       STATUS current
       DESCRIPTION
           "Client network interface was successfully modified to MTU {{clientNetworkInterfaceMtu}} and bonding mode {{clientNetworkInterfaceBondMode}} by {{userName}}."
           --#TYPE         "Normal Event"
           --#SUMMARY      Client network interface was successfully modified to MTU %s and bonding mode %s by %s.
           --#ARGUMENTS    {1,2,3}
           --#SEVERITY     INFORMATIONAL
           --#TIMEINDEX    99
           --#STATE        OK
       ::= { fluidFSEventsComponent 93 } 
    
    
    fluidFSEventComponentEqlFabricCreateSuccess NOTIFICATION-TYPE
       OBJECTS { sysName, fluidFSEventsParamsComponentUserName }
       STATUS current
       DESCRIPTION
           "EQL fabric created by {{userName}}."
           --#TYPE         "Normal Event"
           --#SUMMARY      EQL fabric created by %s.
           --#ARGUMENTS    {1}
           --#SEVERITY     INFORMATIONAL
           --#TIMEINDEX    99
           --#STATE        OK
       ::= { fluidFSEventsComponent 94 } 
    
    
    fluidFSEventComponentEqlFabricCreateWarning NOTIFICATION-TYPE
       OBJECTS { sysName, fluidFSEventsParamsComponentUserName, fluidFSEventsParamsComponentRetcodeString }
       STATUS current
       DESCRIPTION
           "EQL fabric created by {{userName}}. {{retcodeString}}"
           --#TYPE         "Normal Event"
           --#SUMMARY      EQL fabric created by %s. %s
           --#ARGUMENTS    {1,2}
           --#SEVERITY     INFORMATIONAL
           --#TIMEINDEX    99
           --#STATE        OK
       ::= { fluidFSEventsComponent 95 } 
    
    
    fluidFSEventComponentEqlFabricModifySuccess NOTIFICATION-TYPE
       OBJECTS { sysName, fluidFSEventsParamsComponentUserName }
       STATUS current
       DESCRIPTION
           "EQL fabric modified by {{userName}}."
           --#TYPE         "Normal Event"
           --#SUMMARY      EQL fabric modified by %s.
           --#ARGUMENTS    {1}
           --#SEVERITY     INFORMATIONAL
           --#TIMEINDEX    99
           --#STATE        OK
       ::= { fluidFSEventsComponent 96 } 
    
    
    fluidFSEventComponentEqlFabricModifyWarning NOTIFICATION-TYPE
       OBJECTS { sysName, fluidFSEventsParamsComponentUserName, fluidFSEventsParamsComponentRetcodeString }
       STATUS current
       DESCRIPTION
           "EQL fabric modified by {{userName}}. {{retcodeString}}"
           --#TYPE         "Normal Event"
           --#SUMMARY      EQL fabric modified by %s. %s
           --#ARGUMENTS    {1,2}
           --#SEVERITY     INFORMATIONAL
           --#TIMEINDEX    99
           --#STATE        OK
       ::= { fluidFSEventsComponent 97 } 
    
    
    fluidFSEventComponentEqlFabricDeleteSuccess NOTIFICATION-TYPE
       OBJECTS { sysName, fluidFSEventsParamsComponentUserName }
       STATUS current
       DESCRIPTION
           "EQL fabric deleted by {{userName}}."
           --#TYPE         "Normal Event"
           --#SUMMARY      EQL fabric deleted by %s.
           --#ARGUMENTS    {1}
           --#SEVERITY     INFORMATIONAL
           --#TIMEINDEX    99
           --#STATE        OK
       ::= { fluidFSEventsComponent 98 } 
    
    
    fluidFSEventComponentEqlFabricRoutesCreateSuccess NOTIFICATION-TYPE
       OBJECTS { sysName, fluidFSEventsParamsComponentUserName, fluidFSEventsParamsComponentNetworkId }
       STATUS current
       DESCRIPTION
           "EQL fabric route {{networkId}} created by {{userName}}."
           --#TYPE         "Normal Event"
           --#SUMMARY      EQL fabric route %s created by %s.
           --#ARGUMENTS    {1,2}
           --#SEVERITY     INFORMATIONAL
           --#TIMEINDEX    99
           --#STATE        OK
       ::= { fluidFSEventsComponent 99 } 
    
    
    fluidFSEventComponentEqlFabricRoutesModifySuccess NOTIFICATION-TYPE
       OBJECTS { sysName, fluidFSEventsParamsComponentUserName, fluidFSEventsParamsComponentNetworkId }
       STATUS current
       DESCRIPTION
           "EQL fabric route {{networkId}} modified by {{userName}}."
           --#TYPE         "Normal Event"
           --#SUMMARY      EQL fabric route %s modified by %s.
           --#ARGUMENTS    {1,2}
           --#SEVERITY     INFORMATIONAL
           --#TIMEINDEX    99
           --#STATE        OK
       ::= { fluidFSEventsComponent 100 } 
    
    
    fluidFSEventComponentEqlFabricRoutesDeleteSuccess NOTIFICATION-TYPE
       OBJECTS { sysName, fluidFSEventsParamsComponentUserName, fluidFSEventsParamsComponentNetworkId }
       STATUS current
       DESCRIPTION
           "EQL fabric route {{networkId}} deleted by {{userName}}."
           --#TYPE         "Normal Event"
           --#SUMMARY      EQL fabric route %s deleted by %s.
           --#ARGUMENTS    {1,2}
           --#SEVERITY     INFORMATIONAL
           --#TIMEINDEX    99
           --#STATE        OK
       ::= { fluidFSEventsComponent 101 } 
    
    
    fluidFSEventComponentFabricIscsiV4CreateSuccess NOTIFICATION-TYPE
       OBJECTS { sysName, fluidFSEventsParamsComponentUserName, fluidFSEventsParamsComponentName }
       STATUS current
       DESCRIPTION
           "iSCSI IPv4 fabric {{Name}} created by {{userName}}."
           --#TYPE         "Normal Event"
           --#SUMMARY      iSCSI IPv4 fabric %s created by %s.
           --#ARGUMENTS    {1,2}
           --#SEVERITY     INFORMATIONAL
           --#TIMEINDEX    99
           --#STATE        OK
       ::= { fluidFSEventsComponent 102 } 
    
    
    fluidFSEventComponentFabricIscsiV4CreateWarning NOTIFICATION-TYPE
       OBJECTS { sysName, fluidFSEventsParamsComponentUserName, fluidFSEventsParamsComponentName, fluidFSEventsParamsComponentRetcodeString }
       STATUS current
       DESCRIPTION
           "iSCSI IPv4 fabric {{Name}} created by {{userName}}. {{retcodeString}}"
           --#TYPE         "Normal Event"
           --#SUMMARY      iSCSI IPv4 fabric %s created by %s. %s
           --#ARGUMENTS    {1,2,3}
           --#SEVERITY     INFORMATIONAL
           --#TIMEINDEX    99
           --#STATE        OK
       ::= { fluidFSEventsComponent 103 } 
    
    
    fluidFSEventComponentFabricIscsiV4ModifySuccess NOTIFICATION-TYPE
       OBJECTS { sysName, fluidFSEventsParamsComponentUserName, fluidFSEventsParamsComponentName }
       STATUS current
       DESCRIPTION
           "iSCSI IPv4 fabric {{Name}} modified by {{userName}}."
           --#TYPE         "Normal Event"
           --#SUMMARY      iSCSI IPv4 fabric %s modified by %s.
           --#ARGUMENTS    {1,2}
           --#SEVERITY     INFORMATIONAL
           --#TIMEINDEX    99
           --#STATE        OK
       ::= { fluidFSEventsComponent 104 } 
    
    
    fluidFSEventComponentFabricIscsiV4ModifyWarning NOTIFICATION-TYPE
       OBJECTS { sysName, fluidFSEventsParamsComponentUserName, fluidFSEventsParamsComponentName, fluidFSEventsParamsComponentRetcodeString }
       STATUS current
       DESCRIPTION
           "iSCSI IPv4 fabric {{Name}} modified by {{userName}}. {{retcodeString}}"
           --#TYPE         "Normal Event"
           --#SUMMARY      iSCSI IPv4 fabric %s modified by %s. %s
           --#ARGUMENTS    {1,2,3}
           --#SEVERITY     INFORMATIONAL
           --#TIMEINDEX    99
           --#STATE        OK
       ::= { fluidFSEventsComponent 105 } 
    
    
    fluidFSEventComponentFabricIscsiV4DeleteSuccess NOTIFICATION-TYPE
       OBJECTS { sysName, fluidFSEventsParamsComponentUserName, fluidFSEventsParamsComponentName }
       STATUS current
       DESCRIPTION
           "iSCSI IPv4 fabric {{Name}} deleted by {{userName}}."
           --#TYPE         "Normal Event"
           --#SUMMARY      iSCSI IPv4 fabric %s deleted by %s.
           --#ARGUMENTS    {1,2}
           --#SEVERITY     INFORMATIONAL
           --#TIMEINDEX    99
           --#STATE        OK
       ::= { fluidFSEventsComponent 106 } 
    
    
    fluidFSEventComponentStorageEqlGroupModifySuccess NOTIFICATION-TYPE
       OBJECTS { sysName, fluidFSEventsParamsComponentUserName }
       STATUS current
       DESCRIPTION
           "EQL storage group modified by {{userName}}."
           --#TYPE         "Normal Event"
           --#SUMMARY      EQL storage group modified by %s.
           --#ARGUMENTS    {1}
           --#SEVERITY     INFORMATIONAL
           --#TIMEINDEX    99
           --#STATE        OK
       ::= { fluidFSEventsComponent 107 } 
    
    
    fluidFSEventComponentStorageIscsiPortalsModifySuccess NOTIFICATION-TYPE
       OBJECTS { sysName, fluidFSEventsParamsComponentUserName }
       STATUS current
       DESCRIPTION
           "iSCSI storage portals modified by {{userName}}."
           --#TYPE         "Normal Event"
           --#SUMMARY      iSCSI storage portals modified by %s.
           --#ARGUMENTS    {1}
           --#SEVERITY     INFORMATIONAL
           --#TIMEINDEX    99
           --#STATE        OK
       ::= { fluidFSEventsComponent 108 } 
    
    
    fluidFSEventComponentStorageIscsiPortalsModifyFailure NOTIFICATION-TYPE
       OBJECTS { sysName, fluidFSEventsParamsComponentUserName, fluidFSEventsParamsComponentRetcodeString }
       STATUS current
       DESCRIPTION
           "Failure to modify iSCSI storage portals by {{userName}}. {{retcodeString}}"
           --#TYPE         "Normal Event"
           --#SUMMARY      Failure to modify iSCSI storage portals by %s. %s
           --#ARGUMENTS    {1,2}
           --#SEVERITY     MAJOR
           --#TIMEINDEX    99
           --#STATE        OK
       ::= { fluidFSEventsComponent 109 } 
    
    
    fluidFSEventComponentNasApplianceBlinkSuccess NOTIFICATION-TYPE
       OBJECTS { sysName, fluidFSEventsParamsComponentUserName, fluidFSEventsParamsComponentApplianceId, fluidFSEventsParamsComponentBlink1, fluidFSEventsParamsComponentBlink2 }
       STATUS current
       DESCRIPTION
           "User {{userName}} set the appliance ID {{applianceId}} blink state for the 1st controller to {{blink1}} and the 2nd controller to {{blink2}}."
           --#TYPE         "Normal Event"
           --#SUMMARY      User %s set the appliance ID %s blink state for the 1st controller to %s and the 2nd controller to %s.
           --#ARGUMENTS    {1,2,3,4}
           --#SEVERITY     INFORMATIONAL
           --#TIMEINDEX    99
           --#STATE        OK
       ::= { fluidFSEventsComponent 122 } 
    
    
    fluidFSEventComponentRebootNasControllerSuccess NOTIFICATION-TYPE
       OBJECTS { sysName, fluidFSEventsParamsComponentUserName, fluidFSEventsParamsComponentControllerId }
       STATUS current
       DESCRIPTION
           "User {{userName}} rebooted NAS controller {{controllerId}}."
           --#TYPE         "Normal Event"
           --#SUMMARY      User %s rebooted NAS controller %s.
           --#ARGUMENTS    {1,2}
           --#SEVERITY     INFORMATIONAL
           --#TIMEINDEX    99
           --#STATE        OK
       ::= { fluidFSEventsComponent 123 } 
    
    
    fluidFSEventComponentMoveClientActionSuccess NOTIFICATION-TYPE
       OBJECTS { sysName, fluidFSEventsParamsComponentClientIp, fluidFSEventsParamsComponentAccessIp, fluidFSEventsParamsComponentNodeId, fluidFSEventsParamsComponentUserName }
       STATUS current
       DESCRIPTION
           "Client or router with {{ClientIp}} IP, which referred to {{AccessIp}} IP, was moved to controller{{NodeId}} by {{userName}}."
           --#TYPE         "Normal Event"
           --#SUMMARY      Client or router with %s IP, which referred to %s IP, was moved to controller%s by %s.
           --#ARGUMENTS    {1,2,3,4}
           --#SEVERITY     INFORMATIONAL
           --#TIMEINDEX    99
           --#STATE        OK
       ::= { fluidFSEventsComponent 124 } 
    
    
    fluidFSEventComponentPinClientActionSuccess NOTIFICATION-TYPE
       OBJECTS { sysName, fluidFSEventsParamsComponentClientIp, fluidFSEventsParamsComponentAccessIp, fluidFSEventsParamsComponentPinState, fluidFSEventsParamsComponentUserName }
       STATUS current
       DESCRIPTION
           "Client or router with {{ClientIp}} IP, which referred to {{AccessIp}} IP was restricted to the required controller (pin state is {{PinState}}) by {{userName}}."
           --#TYPE         "Normal Event"
           --#SUMMARY      Client or router with %s IP, which referred to %s IP was restricted to the required controller (pin state is %s) by %s.
           --#ARGUMENTS    {1,2,3,4}
           --#SEVERITY     INFORMATIONAL
           --#TIMEINDEX    99
           --#STATE        OK
       ::= { fluidFSEventsComponent 125 } 
    
    
    fluidFSEventComponentClientLoadBalancingMassFailbackSuccess NOTIFICATION-TYPE
       OBJECTS { sysName, fluidFSEventsParamsComponentUserName }
       STATUS current
       DESCRIPTION
           "{{userName}} had performed failback of all the clients to their preferred controller."
           --#TYPE         "Normal Event"
           --#SUMMARY      %s had performed failback of all the clients to their preferred controller.
           --#ARGUMENTS    {1}
           --#SEVERITY     INFORMATIONAL
           --#TIMEINDEX    99
           --#STATE        OK
       ::= { fluidFSEventsComponent 126 } 
    
    
    fluidFSEventComponentClientLoadBalancingMassRebalancingSuccess NOTIFICATION-TYPE
       OBJECTS { sysName, fluidFSEventsParamsComponentUserName }
       STATUS current
       DESCRIPTION
           "{{userName}} had performed a rebalance of all the clients between the controllers."
           --#TYPE         "Normal Event"
           --#SUMMARY      %s had performed a rebalance of all the clients between the controllers.
           --#ARGUMENTS    {1}
           --#SEVERITY     INFORMATIONAL
           --#TIMEINDEX    99
           --#STATE        OK
       ::= { fluidFSEventsComponent 127 } 
    
    
    fluidFSEventComponentNDMPConfigurationModifySuccess NOTIFICATION-TYPE
       OBJECTS { sysName, fluidFSEventsParamsComponentUserName }
       STATUS current
       DESCRIPTION
           "NDMP configuration was modified by {{userName}}."
           --#TYPE         "Normal Event"
           --#SUMMARY      NDMP configuration was modified by %s.
           --#ARGUMENTS    {1}
           --#SEVERITY     INFORMATIONAL
           --#TIMEINDEX    99
           --#STATE        OK
       ::= { fluidFSEventsComponent 128 } 
    
    
    fluidFSEventComponentAntiVirusHostsModifySuccess NOTIFICATION-TYPE
       OBJECTS { sysName, fluidFSEventsParamsComponentUserName }
       STATUS current
       DESCRIPTION
           "The user {{userName}} updated the antivirus hosts."
           --#TYPE         "Normal Event"
           --#SUMMARY      The user %s updated the antivirus hosts.
           --#ARGUMENTS    {1}
           --#SEVERITY     INFORMATIONAL
           --#TIMEINDEX    99
           --#STATE        OK
       ::= { fluidFSEventsComponent 134 } 
    
    
    fluidFSEventComponentClusterIdModifySuccess NOTIFICATION-TYPE
       OBJECTS { sysName, fluidFSEventsParamsComponentUserName }
       STATUS current
       DESCRIPTION
           "The user {{userName}} updated the cluster identifier."
           --#TYPE         "Normal Event"
           --#SUMMARY      The user %s updated the cluster identifier.
           --#ARGUMENTS    {1}
           --#SEVERITY     INFORMATIONAL
           --#TIMEINDEX    99
           --#STATE        OK
       ::= { fluidFSEventsComponent 136 } 
    
    
    fluidFSEventComponentClusterNameModifySuccess NOTIFICATION-TYPE
       OBJECTS { sysName, fluidFSEventsParamsComponentUserName, fluidFSEventsParamsComponentClusterName }
       STATUS current
       DESCRIPTION
           "The user {{userName}} renamed the cluster to {{ClusterName}}."
           --#TYPE         "Normal Event"
           --#SUMMARY      The user %s renamed the cluster to %s.
           --#ARGUMENTS    {1,2}
           --#SEVERITY     INFORMATIONAL
           --#TIMEINDEX    99
           --#STATE        OK
       ::= { fluidFSEventsComponent 137 } 
    
    
    fluidFSEventComponentBackupConfigurationObjectsToFileSuccess NOTIFICATION-TYPE
       OBJECTS { sysName, fluidFSEventsParamsComponentUserName }
       STATUS current
       DESCRIPTION
           "The user {{userName}} backed up the cluster configuration to file."
           --#TYPE         "Normal Event"
           --#SUMMARY      The user %s backed up the cluster configuration to file.
           --#ARGUMENTS    {1}
           --#SEVERITY     INFORMATIONAL
           --#TIMEINDEX    99
           --#STATE        OK
       ::= { fluidFSEventsComponent 138 } 
    
    
    fluidFSEventComponentDestroyClusterSuccess NOTIFICATION-TYPE
       OBJECTS { sysName, fluidFSEventsParamsComponentUserName }
       STATUS current
       DESCRIPTION
           "The user {{userName}} destroyed the cluster."
           --#TYPE         "Normal Event"
           --#SUMMARY      The user %s destroyed the cluster.
           --#ARGUMENTS    {1}
           --#SEVERITY     INFORMATIONAL
           --#TIMEINDEX    99
           --#STATE        OK
       ::= { fluidFSEventsComponent 140 } 
    
    
    fluidFSEventComponentEMRecipientsModifySuccess NOTIFICATION-TYPE
       OBJECTS { sysName, fluidFSEventsParamsComponentUserName }
       STATUS current
       DESCRIPTION
           "The user {{userName}} updated the Enterprise Manager recipients."
           --#TYPE         "Normal Event"
           --#SUMMARY      The user %s updated the Enterprise Manager recipients.
           --#ARGUMENTS    {1}
           --#SEVERITY     INFORMATIONAL
           --#TIMEINDEX    99
           --#STATE        OK
       ::= { fluidFSEventsComponent 141 } 
    
    
    fluidFSEventComponentFabricFcCreateSuccess NOTIFICATION-TYPE
       OBJECTS { sysName, fluidFSEventsParamsComponentUserName, fluidFSEventsParamsComponentFabricName }
       STATUS current
       DESCRIPTION
           "The user {{userName}} created {{FabricName}} Fibre Channel fabric."
           --#TYPE         "Normal Event"
           --#SUMMARY      The user %s created %s Fibre Channel fabric.
           --#ARGUMENTS    {1,2}
           --#SEVERITY     INFORMATIONAL
           --#TIMEINDEX    99
           --#STATE        OK
       ::= { fluidFSEventsComponent 142 } 
    
    
    fluidFSEventComponentFabricFcModifySuccess NOTIFICATION-TYPE
       OBJECTS { sysName, fluidFSEventsParamsComponentUserName, fluidFSEventsParamsComponentFabricName }
       STATUS current
       DESCRIPTION
           "The user {{userName}} updated {{FabricName}} Fibre Channel fabric."
           --#TYPE         "Normal Event"
           --#SUMMARY      The user %s updated %s Fibre Channel fabric.
           --#ARGUMENTS    {1,2}
           --#SEVERITY     INFORMATIONAL
           --#TIMEINDEX    99
           --#STATE        OK
       ::= { fluidFSEventsComponent 143 } 
    
    
    fluidFSEventComponentFabricFcDeleteSuccess NOTIFICATION-TYPE
       OBJECTS { sysName, fluidFSEventsParamsComponentUserName, fluidFSEventsParamsComponentFabricName }
       STATUS current
       DESCRIPTION
           "The user {{userName}} deleted {{FabricName}} Fibre Channel fabric."
           --#TYPE         "Normal Event"
           --#SUMMARY      The user %s deleted %s Fibre Channel fabric.
           --#ARGUMENTS    {1,2}
           --#SEVERITY     INFORMATIONAL
           --#TIMEINDEX    99
           --#STATE        OK
       ::= { fluidFSEventsComponent 144 } 
    
    
    fluidFSEventComponentFTPConfigurationModifySuccess NOTIFICATION-TYPE
       OBJECTS { sysName, fluidFSEventsParamsComponentUserName }
       STATUS current
       DESCRIPTION
           "The user {{userName}} updated the FTP configuration."
           --#TYPE         "Normal Event"
           --#SUMMARY      The user %s updated the FTP configuration.
           --#ARGUMENTS    {1}
           --#SEVERITY     INFORMATIONAL
           --#TIMEINDEX    99
           --#STATE        OK
       ::= { fluidFSEventsComponent 147 } 
    
    
    fluidFSEventComponentHealthScanConfigurationModifySuccess NOTIFICATION-TYPE
       OBJECTS { sysName, fluidFSEventsParamsComponentUserName }
       STATUS current
       DESCRIPTION
           "The user {{userName}} updated the file system health scan configuration."
           --#TYPE         "Normal Event"
           --#SUMMARY      The user %s updated the file system health scan configuration.
           --#ARGUMENTS    {1}
           --#SEVERITY     INFORMATIONAL
           --#TIMEINDEX    99
           --#STATE        OK
       ::= { fluidFSEventsComponent 148 } 
    
    
    fluidFSEventComponentLanguageModifySuccess NOTIFICATION-TYPE
       OBJECTS { sysName, fluidFSEventsParamsComponentUserName }
       STATUS current
       DESCRIPTION
           "The user {{userName}} updated the language of the cluster."
           --#TYPE         "Normal Event"
           --#SUMMARY      The user %s updated the language of the cluster.
           --#ARGUMENTS    {1}
           --#SEVERITY     INFORMATIONAL
           --#TIMEINDEX    99
           --#STATE        OK
       ::= { fluidFSEventsComponent 150 } 
    
    
    fluidFSEventComponentLogoffActiveNdmpSessionSuccess NOTIFICATION-TYPE
       OBJECTS { sysName, fluidFSEventsParamsComponentUserName, fluidFSEventsParamsComponentNDMPSessionId, fluidFSEventsParamsComponentControllerId }
       STATUS current
       DESCRIPTION
           "The user {{userName}} killed {{NDMPSessionId}} NDMP session on NAS controller{{controllerId}}."
           --#TYPE         "Normal Event"
           --#SUMMARY      The user %s killed %s NDMP session on NAS controller%s.
           --#ARGUMENTS    {1,2,3}
           --#SEVERITY     INFORMATIONAL
           --#TIMEINDEX    99
           --#STATE        OK
       ::= { fluidFSEventsComponent 152 } 
    
    
    fluidFSEventComponentNasPoolConfigurationModifySuccess NOTIFICATION-TYPE
       OBJECTS { sysName, fluidFSEventsParamsComponentUserName }
       STATUS current
       DESCRIPTION
           "The user {{userName}} updated the NAS pool thresholds."
           --#TYPE         "Normal Event"
           --#SUMMARY      The user %s updated the NAS pool thresholds.
           --#ARGUMENTS    {1}
           --#SEVERITY     INFORMATIONAL
           --#TIMEINDEX    99
           --#STATE        OK
       ::= { fluidFSEventsComponent 154 } 
    
    
    fluidFSEventComponentSupportAccessModifySuccess NOTIFICATION-TYPE
       OBJECTS { sysName, fluidFSEventsParamsComponentUserName }
       STATUS current
       DESCRIPTION
           "The user {{userName}} updated the support access settings."
           --#TYPE         "Normal Event"
           --#SUMMARY      The user %s updated the support access settings.
           --#ARGUMENTS    {1}
           --#SEVERITY     INFORMATIONAL
           --#TIMEINDEX    99
           --#STATE        OK
       ::= { fluidFSEventsComponent 155 } 
    
    
    fluidFSEventComponentSystemConfigurationStateModifySuccess NOTIFICATION-TYPE
       OBJECTS { sysName, fluidFSEventsParamsComponentUserName }
       STATUS current
       DESCRIPTION
           "The user {{userName}} updated the system configuration state."
           --#TYPE         "Normal Event"
           --#SUMMARY      The user %s updated the system configuration state.
           --#ARGUMENTS    {1}
           --#SEVERITY     INFORMATIONAL
           --#TIMEINDEX    99
           --#STATE        OK
       ::= { fluidFSEventsComponent 156 } 
    
    
    fluidFSEventComponentTriggerFabricDiscoverySuccess NOTIFICATION-TYPE
       OBJECTS { sysName, fluidFSEventsParamsComponentUserName }
       STATUS current
       DESCRIPTION
           "The user {{userName}} triggered LUNs discovery."
           --#TYPE         "Normal Event"
           --#SUMMARY      The user %s triggered LUNs discovery.
           --#ARGUMENTS    {1}
           --#SEVERITY     INFORMATIONAL
           --#TIMEINDEX    99
           --#STATE        OK
       ::= { fluidFSEventsComponent 158 } 
    
    
    fluidFSEventComponentTrustedSystemCreateSuccess NOTIFICATION-TYPE
       OBJECTS { sysName, fluidFSEventsParamsComponentUserName, fluidFSEventsParamsComponentPartnerIp }
       STATUS current
       DESCRIPTION
           "The user {{userName}} created partnership with {{PartnerIp}}."
           --#TYPE         "Normal Event"
           --#SUMMARY      The user %s created partnership with %s.
           --#ARGUMENTS    {1,2}
           --#SEVERITY     INFORMATIONAL
           --#TIMEINDEX    99
           --#STATE        OK
       ::= { fluidFSEventsComponent 159 } 
    
    
    fluidFSEventComponentTrustedSystemModifySuccess NOTIFICATION-TYPE
       OBJECTS { sysName, fluidFSEventsParamsComponentUserName, fluidFSEventsParamsComponentPartnerIp }
       STATUS current
       DESCRIPTION
           "The user {{userName}} updated partnership with {{PartnerIp}}."
           --#TYPE         "Normal Event"
           --#SUMMARY      The user %s updated partnership with %s.
           --#ARGUMENTS    {1,2}
           --#SEVERITY     INFORMATIONAL
           --#TIMEINDEX    99
           --#STATE        OK
       ::= { fluidFSEventsComponent 160 } 
    
    
    fluidFSEventComponentTrustedSystemDeleteSuccess NOTIFICATION-TYPE
       OBJECTS { sysName, fluidFSEventsParamsComponentUserName, fluidFSEventsParamsComponentPartnerIp }
       STATUS current
       DESCRIPTION
           "The user {{userName}} deleted partnership with {{PartnerIp}}."
           --#TYPE         "Normal Event"
           --#SUMMARY      The user %s deleted partnership with %s.
           --#ARGUMENTS    {1,2}
           --#SEVERITY     INFORMATIONAL
           --#TIMEINDEX    99
           --#STATE        OK
       ::= { fluidFSEventsComponent 161 } 
    
    
    fluidFSEventComponentUIConfigurationModifySuccess NOTIFICATION-TYPE
       OBJECTS { sysName, fluidFSEventsParamsComponentUserName }
       STATUS current
       DESCRIPTION
           "The user {{userName}} updated the UI settings."
           --#TYPE         "Normal Event"
           --#SUMMARY      The user %s updated the UI settings.
           --#ARGUMENTS    {1}
           --#SEVERITY     INFORMATIONAL
           --#TIMEINDEX    99
           --#STATE        OK
       ::= { fluidFSEventsComponent 162 } 
    
    
    fluidFSEventComponentRunFileSystemDiagnosticSuccess NOTIFICATION-TYPE
       OBJECTS { sysName, fluidFSEventsParamsComponentUserName }
       STATUS current
       DESCRIPTION
           "The user {{userName}} ran core file system diagnostic.   Description:  The user {{userName}} ran core file system diagnostic."
           --#TYPE         "Normal Event"
           --#SUMMARY      The user %s ran core file system diagnostic.   Description:  The user %s ran core file system diagnostic.
           --#ARGUMENTS    {1}
           --#SEVERITY     INFORMATIONAL
           --#TIMEINDEX    99
           --#STATE        OK
       ::= { fluidFSEventsComponent 170 } 
    
    
    fluidFSEventComponentRunGeneralSystemDiagnosticSuccess NOTIFICATION-TYPE
       OBJECTS { sysName, fluidFSEventsParamsComponentUserName }
       STATUS current
       DESCRIPTION
           "The user {{userName}} ran general system diagnostic.   Description:  The user {{userName}} ran general system diagnostic."
           --#TYPE         "Normal Event"
           --#SUMMARY      The user %s ran general system diagnostic.   Description:  The user %s ran general system diagnostic.
           --#ARGUMENTS    {1}
           --#SEVERITY     INFORMATIONAL
           --#TIMEINDEX    99
           --#STATE        OK
       ::= { fluidFSEventsComponent 171 } 
    
    
    fluidFSEventComponentRunNetworkDiagnosticSuccess NOTIFICATION-TYPE
       OBJECTS { sysName, fluidFSEventsParamsComponentUserName, fluidFSEventsParamsComponentRunNetworkDiagnosticClientIP }
       STATUS current
       DESCRIPTION
           "The user {{userName}} ran networking diagnostic.   Description:  The user {{userName}} ran networking diagnostic.[[nl]]Diagnostic arguments:[[nl]]ClientIP - {{RunNetworkDiagnosticClientIP}}."
           --#TYPE         "Normal Event"
           --#SUMMARY      The user %s ran networking diagnostic.   Description:  The user %s ran networking diagnostic.[[nl]]Diagnostic arguments:[[nl]]ClientIP - %s.
           --#ARGUMENTS    {1,2}
           --#SEVERITY     INFORMATIONAL
           --#TIMEINDEX    99
           --#STATE        OK
       ::= { fluidFSEventsComponent 172 } 
    
    
    fluidFSEventComponentRunPerformanceDiagnosticSuccess NOTIFICATION-TYPE
       OBJECTS { sysName, fluidFSEventsParamsComponentUserName, fluidFSEventsParamsComponentRunPerformanceDiagnosticFSID }
       STATUS current
       DESCRIPTION
           "The user {{userName}} ran performance diagnostic.   Description:  The user {{userName}} ran performance diagnostic.[[nl]]Diagnostic arguments:[[nl]]FSID - {{RunPerformanceDiagnosticFSID}}."
           --#TYPE         "Normal Event"
           --#SUMMARY      The user %s ran performance diagnostic.   Description:  The user %s ran performance diagnostic.[[nl]]Diagnostic arguments:[[nl]]FSID - %s.
           --#ARGUMENTS    {1,2}
           --#SEVERITY     INFORMATIONAL
           --#TIMEINDEX    99
           --#STATE        OK
       ::= { fluidFSEventsComponent 174 } 
    
    
    fluidFSEventComponentRunFileSystemDiagnosticActionFailure NOTIFICATION-TYPE
       OBJECTS { sysName, fluidFSEventsParamsComponentUserName, fluidFSEventsParamsComponentRetcodeString }
       STATUS current
       DESCRIPTION
           "File System diagnostic failed.   Description:  File System diagnostic, which was run by user {{userName}} failed.[[nl]]{{retcodeString}}"
           --#TYPE         "Normal Event"
           --#SUMMARY      File System diagnostic failed.   Description:  File System diagnostic, which was run by user %s failed.[[nl]]%s
           --#ARGUMENTS    {1,2}
           --#SEVERITY     MAJOR
           --#TIMEINDEX    99
           --#STATE        OK
       ::= { fluidFSEventsComponent 178 } 
    
    
    fluidFSEventComponentRunGeneralSystemDiagnosticActionFailure NOTIFICATION-TYPE
       OBJECTS { sysName, fluidFSEventsParamsComponentUserName, fluidFSEventsParamsComponentRetcodeString }
       STATUS current
       DESCRIPTION
           "General System diagnostic failed.   Description:  General System diagnostic, which was run by user {{userName}} failed.[[nl]]{{retcodeString}}"
           --#TYPE         "Normal Event"
           --#SUMMARY      General System diagnostic failed.   Description:  General System diagnostic, which was run by user %s failed.[[nl]]%s
           --#ARGUMENTS    {1,2}
           --#SEVERITY     MAJOR
           --#TIMEINDEX    99
           --#STATE        OK
       ::= { fluidFSEventsComponent 179 } 
    
    
    fluidFSEventComponentRunNetworkDiagnosticActionFailure NOTIFICATION-TYPE
       OBJECTS { sysName, fluidFSEventsParamsComponentUserName, fluidFSEventsParamsComponentRunNetworkDiagnosticClientIP, fluidFSEventsParamsComponentRetcodeString }
       STATUS current
       DESCRIPTION
           "Network diagnostic failed.   Description:  Network diagnostic, which was run by user {{userName}} failed.[[nl]]Diagnostic arguments:[[nl]]ClientIP - {{RunNetworkDiagnosticClientIP}}[[nl]]{{retcodeString}}"
           --#TYPE         "Normal Event"
           --#SUMMARY      Network diagnostic failed.   Description:  Network diagnostic, which was run by user %s failed.[[nl]]Diagnostic arguments:[[nl]]ClientIP - %s[[nl]]%s
           --#ARGUMENTS    {1,2,3}
           --#SEVERITY     MAJOR
           --#TIMEINDEX    99
           --#STATE        OK
       ::= { fluidFSEventsComponent 180 } 
    
    
    fluidFSEventComponentRunPerformanceDiagnosticActionFailure NOTIFICATION-TYPE
       OBJECTS { sysName, fluidFSEventsParamsComponentUserName, fluidFSEventsParamsComponentRunPerformanceDiagnosticFSID, fluidFSEventsParamsComponentRetcodeString }
       STATUS current
       DESCRIPTION
           "Performance diagnostic failed.   Description:  Performance diagnostic, which was run by user {{userName}} failed.[[nl]]Diagnostic arguments:[[nl]]FSID - {{RunPerformanceDiagnosticFSID}}[[nl]]{{retcodeString}}"
           --#TYPE         "Normal Event"
           --#SUMMARY      Performance diagnostic failed.   Description:  Performance diagnostic, which was run by user %s failed.[[nl]]Diagnostic arguments:[[nl]]FSID - %s[[nl]]%s
           --#ARGUMENTS    {1,2,3}
           --#SEVERITY     MAJOR
           --#TIMEINDEX    99
           --#STATE        OK
       ::= { fluidFSEventsComponent 182 } 
    
    
    fluidFSEventComponentFileSystemCoreDiagnosticsFailed NOTIFICATION-TYPE
       OBJECTS { sysName, fluidFSEventsParamsComponentRetcodeString }
       STATUS current
       DESCRIPTION
           "Failed to generate diagnostics package for 'FileSystemCoreDiagnostics'. {{retcodeString}}"
           --#TYPE         "Normal Event"
           --#SUMMARY      Failed to generate diagnostics package for 'FileSystemCoreDiagnostics'. %s
           --#ARGUMENTS    {1}
           --#SEVERITY     MAJOR
           --#TIMEINDEX    99
           --#STATE        OK
       ::= { fluidFSEventsComponent 189 } 
    
    
    fluidFSEventComponentFileSystemCoreDiagnosticsFailesOk NOTIFICATION-TYPE
       OBJECTS { sysName }
       STATUS current
       DESCRIPTION
           "Package generation for 'FileSystemCoreDiagnostics' completed successfully."
           --#TYPE         "Normal Event"
           --#SUMMARY      Package generation for 'FileSystemCoreDiagnostics' completed successfully.
           --#ARGUMENTS    {}
           --#SEVERITY     INFORMATIONAL
           --#TIMEINDEX    99
           --#STATE        OK
       ::= { fluidFSEventsComponent 190 } 
    
    
    fluidFSEventComponentGeneralSystemDiagnosticsFailed NOTIFICATION-TYPE
       OBJECTS { sysName, fluidFSEventsParamsComponentRetcodeString }
       STATUS current
       DESCRIPTION
           "Failed to generate diagnostics package for 'GeneralSystemDiagnostics'. {{retcodeString}}"
           --#TYPE         "Normal Event"
           --#SUMMARY      Failed to generate diagnostics package for 'GeneralSystemDiagnostics'. %s
           --#ARGUMENTS    {1}
           --#SEVERITY     MAJOR
           --#TIMEINDEX    99
           --#STATE        OK
       ::= { fluidFSEventsComponent 191 } 
    
    
    fluidFSEventComponentGeneralSystemDiagnosticsOk NOTIFICATION-TYPE
       OBJECTS { sysName }
       STATUS current
       DESCRIPTION
           "Package generation for 'GeneralSystemDiagnostics' completed successfully."
           --#TYPE         "Normal Event"
           --#SUMMARY      Package generation for 'GeneralSystemDiagnostics' completed successfully.
           --#ARGUMENTS    {}
           --#SEVERITY     INFORMATIONAL
           --#TIMEINDEX    99
           --#STATE        OK
       ::= { fluidFSEventsComponent 192 } 
    
    
    fluidFSEventComponentNetworkDiagnosticsFailed NOTIFICATION-TYPE
       OBJECTS { sysName, fluidFSEventsParamsComponentRetcodeString }
       STATUS current
       DESCRIPTION
           "Failed to generate diagnostics package for 'NetworkDiagnostics'. {{retcodeString}}"
           --#TYPE         "Normal Event"
           --#SUMMARY      Failed to generate diagnostics package for 'NetworkDiagnostics'. %s
           --#ARGUMENTS    {1}
           --#SEVERITY     MAJOR
           --#TIMEINDEX    99
           --#STATE        OK
       ::= { fluidFSEventsComponent 193 } 
    
    
    fluidFSEventComponentNetworkDiagnosticsOk NOTIFICATION-TYPE
       OBJECTS { sysName }
       STATUS current
       DESCRIPTION
           "Package generation for 'NetworkDiagnostics' completed successfully."
           --#TYPE         "Normal Event"
           --#SUMMARY      Package generation for 'NetworkDiagnostics' completed successfully.
           --#ARGUMENTS    {}
           --#SEVERITY     INFORMATIONAL
           --#TIMEINDEX    99
           --#STATE        OK
       ::= { fluidFSEventsComponent 194 } 
    
    
    fluidFSEventComponentPerformanceDiagnosticsFailed NOTIFICATION-TYPE
       OBJECTS { sysName, fluidFSEventsParamsComponentRetcodeString }
       STATUS current
       DESCRIPTION
           "Failed to generate diagnostics package for 'PerformanceDiagnostics'. {{retcodeString}}"
           --#TYPE         "Normal Event"
           --#SUMMARY      Failed to generate diagnostics package for 'PerformanceDiagnostics'. %s
           --#ARGUMENTS    {1}
           --#SEVERITY     MAJOR
           --#TIMEINDEX    99
           --#STATE        OK
       ::= { fluidFSEventsComponent 197 } 
    
    
    fluidFSEventComponentPerformanceDiagnosticsOk NOTIFICATION-TYPE
       OBJECTS { sysName }
       STATUS current
       DESCRIPTION
           "Package generation for 'PerformanceDiagnostics' completed successfully."
           --#TYPE         "Normal Event"
           --#SUMMARY      Package generation for 'PerformanceDiagnostics' completed successfully.
           --#ARGUMENTS    {}
           --#SEVERITY     INFORMATIONAL
           --#TIMEINDEX    99
           --#STATE        OK
       ::= { fluidFSEventsComponent 198 } 
    
    
    fluidFSEventComponentExampleCreateStart NOTIFICATION-TYPE
       OBJECTS { sysName, fluidFSEventsParamsComponentUserName, fluidFSEventsParamsComponentName }
       STATUS current
       DESCRIPTION
           "Example {{Name}} create started by {{userName}}."
           --#TYPE         "Normal Event"
           --#SUMMARY      Example %s create started by %s.
           --#ARGUMENTS    {1,2}
           --#SEVERITY     MAJOR
           --#TIMEINDEX    99
           --#STATE        OK
       ::= { fluidFSEventsComponent 201 } 
    
    
    fluidFSEventComponentPostUpgradeActionsEvent NOTIFICATION-TYPE
       OBJECTS { sysName, fluidFSEventsParamsComponentServicePackVersion }
       STATUS current
       DESCRIPTION
           "System was successfully upgraded to version {{servicePackVersion}}"
           --#TYPE         "Normal Event"
           --#SUMMARY      System was successfully upgraded to version %s
           --#ARGUMENTS    {1}
           --#SEVERITY     INFORMATIONAL
           --#TIMEINDEX    99
           --#STATE        OK
       ::= { fluidFSEventsComponent 203 } 
    
    
    fluidFSEventComponentRouteRulesDeleteSuccess NOTIFICATION-TYPE
       OBJECTS { sysName, fluidFSEventsParamsComponentUserName, fluidFSEventsParamsComponentDestinationNetworkID, fluidFSEventsParamsComponentDestinationPrefix, fluidFSEventsParamsComponentRouteGateway }
       STATUS current
       DESCRIPTION
           "Route to {{destinationNetworkID}}/{{destinationPrefix}} with gateway IP {{routeGateway}}  was successfully deleted by {{userName}}."
           --#TYPE         "Normal Event"
           --#SUMMARY      Route to %s/%s with gateway IP %s  was successfully deleted by %s.
           --#ARGUMENTS    {1,2,3,4}
           --#SEVERITY     INFORMATIONAL
           --#TIMEINDEX    99
           --#STATE        OK
       ::= { fluidFSEventsComponent 204 } 
    
    
    fluidFSEventComponentSecureConsoleAccessModifySuccess NOTIFICATION-TYPE
       OBJECTS { sysName, fluidFSEventsParamsComponentUserName }
       STATUS current
       DESCRIPTION
           "The user {{userName}} had modified the Secure Console Access settings   Description:  The user {{userName}} had modified the Secure Console Access settings"
           --#TYPE         "Normal Event"
           --#SUMMARY      The user %s had modified the Secure Console Access settings   Description:  The user %s had modified the Secure Console Access settings
           --#ARGUMENTS    {1}
           --#SEVERITY     INFORMATIONAL
           --#TIMEINDEX    99
           --#STATE        OK
       ::= { fluidFSEventsComponent 205 } 
    
    
    fluidFSEventComponentSecureConsoleAccessModifyFailure NOTIFICATION-TYPE
       OBJECTS { sysName, fluidFSEventsParamsComponentUserName, fluidFSEventsParamsComponentRetcodeString }
       STATUS current
       DESCRIPTION
           "{{userName}} failed to modify the Secure Console Access settings   Description:  The user {{userName}} had failed to modify the Secure Console Access settings due to the following error: {{retcodeString}}"
           --#TYPE         "Normal Event"
           --#SUMMARY      %s failed to modify the Secure Console Access settings   Description:  The user %s had failed to modify the Secure Console Access settings due to the following error: %s
           --#ARGUMENTS    {1,2}
           --#SEVERITY     MAJOR
           --#TIMEINDEX    99
           --#STATE        OK
       ::= { fluidFSEventsComponent 206 } 
    
    
    fluidFSEventComponentSecureConsoleAccessModifyWarning NOTIFICATION-TYPE
       OBJECTS { sysName, fluidFSEventsParamsComponentUserName, fluidFSEventsParamsComponentRetcodeString }
       STATUS current
       DESCRIPTION
           "{{userName}} failed to modify the Secure Console Access settings   Description:  The user {{userName}} had failed to modify the Secure Console Access settings due to the following error: {{retcodeString}}"
           --#TYPE         "Normal Event"
           --#SUMMARY      %s failed to modify the Secure Console Access settings   Description:  The user %s had failed to modify the Secure Console Access settings due to the following error: %s
           --#ARGUMENTS    {1,2}
           --#SEVERITY     INFORMATIONAL
           --#TIMEINDEX    99
           --#STATE        OK
       ::= { fluidFSEventsComponent 207 } 
    
    
    fluidFSEventComponentExampleBackgroundCreateSuccess NOTIFICATION-TYPE
       OBJECTS { sysName, fluidFSEventsParamsComponentName }
       STATUS current
       DESCRIPTION
           "ExampleBackground {{Name}} was created ."
           --#TYPE         "Normal Event"
           --#SUMMARY      ExampleBackground %s was created .
           --#ARGUMENTS    {1}
           --#SEVERITY     INFORMATIONAL
           --#TIMEINDEX    99
           --#STATE        OK
       ::= { fluidFSEventsComponent 209 } 
    
    
    fluidFSEventComponentFilesystemCreatedStartingDomainMigration NOTIFICATION-TYPE
       OBJECTS { sysName }
       STATUS current
       DESCRIPTION
           "The NAS appliance is now part of the file-system. Starting resource optimization using domain migration."
           --#TYPE         "Normal Event"
           --#SUMMARY      The NAS appliance is now part of the file-system. Starting resource optimization using domain migration.
           --#ARGUMENTS    {}
           --#SEVERITY     INFORMATIONAL
           --#TIMEINDEX    99
           --#STATE        OK
       ::= { fluidFSEventsComponent 211 } 
    
    
    fluidFSEventComponentStartingJoinNASAppliance NOTIFICATION-TYPE
       OBJECTS { sysName }
       STATUS current
       DESCRIPTION
           "The system is starting to join the NAS appliance to the file-system."
           --#TYPE         "Normal Event"
           --#SUMMARY      The system is starting to join the NAS appliance to the file-system.
           --#ARGUMENTS    {}
           --#SEVERITY     INFORMATIONAL
           --#TIMEINDEX    99
           --#STATE        OK
       ::= { fluidFSEventsComponent 212 } 
    
    
    fluidFSEventComponentFilesystemCreatedNoDomainMigrationRequired NOTIFICATION-TYPE
       OBJECTS { sysName }
       STATUS current
       DESCRIPTION
           "The NAS appliance is now part of the file-system."
           --#TYPE         "Normal Event"
           --#SUMMARY      The NAS appliance is now part of the file-system.
           --#ARGUMENTS    {}
           --#SEVERITY     INFORMATIONAL
           --#TIMEINDEX    99
           --#STATE        OK
       ::= { fluidFSEventsComponent 213 } 
    
    
    fluidFSEventComponentEventsStoreFilterModifySuccess NOTIFICATION-TYPE
       OBJECTS { sysName, fluidFSEventsParamsComponentUserName }
       STATUS current
       DESCRIPTION
           "Events filter configuration was modified by {{userName}}   Description:  Events filter configuration was modified by {{userName}}"
           --#TYPE         "Normal Event"
           --#SUMMARY      Events filter configuration was modified by %s   Description:  Events filter configuration was modified by %s
           --#ARGUMENTS    {1}
           --#SEVERITY     INFORMATIONAL
           --#TIMEINDEX    99
           --#STATE        OK
       ::= { fluidFSEventsComponent 214 } 
    
    
    fluidFSEventComponentEventsStoreFilterModifyFailure NOTIFICATION-TYPE
       OBJECTS { sysName, fluidFSEventsParamsComponentUserName, fluidFSEventsParamsComponentRetcodeString }
       STATUS current
       DESCRIPTION
           "{{userName}} had failed to modify the Events filter configuration   Description:  {{userName}} had failed to modify the Events filter configuration. {{retcodeString}}"
           --#TYPE         "Normal Event"
           --#SUMMARY      %s had failed to modify the Events filter configuration   Description:  %s had failed to modify the Events filter configuration. %s
           --#ARGUMENTS    {1,2}
           --#SEVERITY     MAJOR
           --#TIMEINDEX    99
           --#STATE        OK
       ::= { fluidFSEventsComponent 215 } 
    
    
    fluidFSEventComponentPhoneHomeModifySuccess NOTIFICATION-TYPE
       OBJECTS { sysName, fluidFSEventsParamsComponentUserName }
       STATUS current
       DESCRIPTION
           "{{userName}} updated phone home settings   Description:  {{userName}} updated phone home settings"
           --#TYPE         "Normal Event"
           --#SUMMARY      %s updated phone home settings   Description:  %s updated phone home settings
           --#ARGUMENTS    {1}
           --#SEVERITY     MAJOR
           --#TIMEINDEX    99
           --#STATE        OK
       ::= { fluidFSEventsComponent 216 } 
    
    
    fluidFSEventComponentBMCNetworkConfigurationModifySuccess NOTIFICATION-TYPE
       OBJECTS { sysName, fluidFSEventsParamsComponentUserName }
       STATUS current
       DESCRIPTION
           "The user {{userName}} updated the BMC network configuration."
           --#TYPE         "Normal Event"
           --#SUMMARY      The user %s updated the BMC network configuration.
           --#ARGUMENTS    {1}
           --#SEVERITY     INFORMATIONAL
           --#TIMEINDEX    99
           --#STATE        OK
       ::= { fluidFSEventsComponent 219 } 
    
    
    fluidFSEventComponentFSStorageConfigurationModifySuccess NOTIFICATION-TYPE
       OBJECTS { sysName, fluidFSEventsParamsComponentUserName }
       STATUS current
       DESCRIPTION
           "The user {{userName}} updated the file system storage configuration."
           --#TYPE         "Normal Event"
           --#SUMMARY      The user %s updated the file system storage configuration.
           --#ARGUMENTS    {1}
           --#SEVERITY     INFORMATIONAL
           --#TIMEINDEX    99
           --#STATE        OK
       ::= { fluidFSEventsComponent 220 } 
    
    
    fluidFSEventComponentUpgradeStandbyNodeSuccessEvent NOTIFICATION-TYPE
       OBJECTS { sysName, fluidFSEventsParamsComponentUserName, fluidFSEventsParamsComponentServicePackFileName }
       STATUS current
       DESCRIPTION
           "{{userName}} successfully flashed standby node with service pack file {{servicePackFileName}}."
           --#TYPE         "Normal Event"
           --#SUMMARY      %s successfully flashed standby node with service pack file %s.
           --#ARGUMENTS    {1,2}
           --#SEVERITY     INFORMATIONAL
           --#TIMEINDEX    99
           --#STATE        OK
       ::= { fluidFSEventsComponent 223 } 
    
    
    fluidFSEventComponentUpgradeStandbyNodeFailedEvent NOTIFICATION-TYPE
       OBJECTS { sysName, fluidFSEventsParamsComponentUserName, fluidFSEventsParamsComponentServicePackFileName, fluidFSEventsParamsComponentRetcodeString }
       STATUS current
       DESCRIPTION
           "{{userName}} failed to flash standby node with service pack file {{servicePackFileName}}. {{retcodeString}}."
           --#TYPE         "Normal Event"
           --#SUMMARY      %s failed to flash standby node with service pack file %s. %s.
           --#ARGUMENTS    {1,2,3}
           --#SEVERITY     MAJOR
           --#TIMEINDEX    99
           --#STATE        OK
       ::= { fluidFSEventsComponent 224 } 
    
    
    fluidFSEventComponentPostUpgradeActionsWarningEvent NOTIFICATION-TYPE
       OBJECTS { sysName, fluidFSEventsParamsComponentRetcodeString }
       STATUS current
       DESCRIPTION
           "Upgraded with warnings: {{retcodeString}}"
           --#TYPE         "Normal Event"
           --#SUMMARY      Upgraded with warnings: %s
           --#ARGUMENTS    {1}
           --#SEVERITY     INFORMATIONAL
           --#TIMEINDEX    99
           --#STATE        OK
       ::= { fluidFSEventsComponent 225 } 
    
    
    fluidFSEventComponentServicePackValidateSuccessEvent NOTIFICATION-TYPE
       OBJECTS { sysName, fluidFSEventsParamsComponentUserName, fluidFSEventsParamsComponentServicePackFileName }
       STATUS current
       DESCRIPTION
           "{{userName}} successfully validated service pack file {{servicePackFileName}}."
           --#TYPE         "Normal Event"
           --#SUMMARY      %s successfully validated service pack file %s.
           --#ARGUMENTS    {1,2}
           --#SEVERITY     INFORMATIONAL
           --#TIMEINDEX    99
           --#STATE        OK
       ::= { fluidFSEventsComponent 226 } 
    
    
    fluidFSEventComponentServicePackValidateFailedEvent NOTIFICATION-TYPE
       OBJECTS { sysName, fluidFSEventsParamsComponentUserName, fluidFSEventsParamsComponentServicePackFileName, fluidFSEventsParamsComponentRetcodeString }
       STATUS current
       DESCRIPTION
           "{{userName}}: Failed validation of service pack file {{servicePackFileName}}. {{retcodeString}}."
           --#TYPE         "Normal Event"
           --#SUMMARY      %s: Failed validation of service pack file %s. %s.
           --#ARGUMENTS    {1,2,3}
           --#SEVERITY     MAJOR
           --#TIMEINDEX    99
           --#STATE        OK
       ::= { fluidFSEventsComponent 227 } 
    
    
    fluidFSEventComponentCloneVMSuccess NOTIFICATION-TYPE
       OBJECTS { sysName, fluidFSEventsParamsComponentUserName, fluidFSEventsParamsComponentSourceVMName, fluidFSEventsParamsComponentVmWareServerName, fluidFSEventsParamsComponentNumberOfClones }
       STATUS current
       DESCRIPTION
           "The user {{userName}} successfully created {{numberOfClones}} cloned virtual machines from {{sourceVMName}}. on server {{vmWareServerName}}"
           --#TYPE         "Normal Event"
           --#SUMMARY      The user %s successfully created %s cloned virtual machines from %s. on server %s
           --#ARGUMENTS    {1,2,3,4}
           --#SEVERITY     INFORMATIONAL
           --#TIMEINDEX    99
           --#STATE        OK
       ::= { fluidFSEventsComponent 228 } 
    
    
    fluidFSEventComponentCreateVMWareServerSuccess NOTIFICATION-TYPE
       OBJECTS { sysName, fluidFSEventsParamsComponentUserName, fluidFSEventsParamsComponentVmWareServerName }
       STATUS current
       DESCRIPTION
           "The user {{userName}} created VMWare server {{vmWareServerName}}."
           --#TYPE         "Normal Event"
           --#SUMMARY      The user %s created VMWare server %s.
           --#ARGUMENTS    {1,2}
           --#SEVERITY     INFORMATIONAL
           --#TIMEINDEX    99
           --#STATE        OK
       ::= { fluidFSEventsComponent 229 } 
    
    
    fluidFSEventComponentModifyVMWareServerSuccess NOTIFICATION-TYPE
       OBJECTS { sysName, fluidFSEventsParamsComponentUserName, fluidFSEventsParamsComponentVmWareServerName }
       STATUS current
       DESCRIPTION
           "The user {{userName}} modified VMWare server {{vmWareServerName}}."
           --#TYPE         "Normal Event"
           --#SUMMARY      The user %s modified VMWare server %s.
           --#ARGUMENTS    {1,2}
           --#SEVERITY     INFORMATIONAL
           --#TIMEINDEX    99
           --#STATE        OK
       ::= { fluidFSEventsComponent 230 } 
    
    
    fluidFSEventComponentEnableMetadataRedundancyForNewVolumes NOTIFICATION-TYPE
       OBJECTS { sysName, fluidFSEventsParamsComponentUserName }
       STATUS current
       DESCRIPTION
           "Metadata redundancy for new NAS volumes was enabled by {{userName}}."
           --#TYPE         "Normal Event"
           --#SUMMARY      Metadata redundancy for new NAS volumes was enabled by %s.
           --#ARGUMENTS    {1}
           --#SEVERITY     INFORMATIONAL
           --#TIMEINDEX    99
           --#STATE        OK
       ::= { fluidFSEventsComponent 231 } 
    
    
    fluidFSEventComponentDisableMetadataRedundancyForNewVolumes NOTIFICATION-TYPE
       OBJECTS { sysName, fluidFSEventsParamsComponentUserName }
       STATUS current
       DESCRIPTION
           "Metadata redundancy for new NAS volumes was disabled by {{userName}}. Be aware that newly created NAS Volumes will be less resistant to failure"
           --#TYPE         "Normal Event"
           --#SUMMARY      Metadata redundancy for new NAS volumes was disabled by %s. Be aware that newly created NAS Volumes will be less resistant to failure
           --#ARGUMENTS    {1}
           --#SEVERITY     MAJOR
           --#TIMEINDEX    99
           --#STATE        OK
       ::= { fluidFSEventsComponent 232 } 
    
    
    fluidFSEventComponentModifyVMWareSettingsSuccess NOTIFICATION-TYPE
       OBJECTS { sysName, fluidFSEventsParamsComponentUserName }
       STATUS current
       DESCRIPTION
           "The user {{userName}} modified VMWare settings"
           --#TYPE         "Normal Event"
           --#SUMMARY      The user %s modified VMWare settings
           --#ARGUMENTS    {1}
           --#SEVERITY     INFORMATIONAL
           --#TIMEINDEX    99
           --#STATE        OK
       ::= { fluidFSEventsComponent 234 } 
    
    
    fluidFSEventComponentRunNdmpDiagnosticSuccess NOTIFICATION-TYPE
       OBJECTS { sysName, fluidFSEventsParamsComponentUserName }
       STATUS current
       DESCRIPTION
           "The user {{userName}} ran NDMP diagnostic.   Description:  The user {{userName}} ran NDMP diagnostic."
           --#TYPE         "Normal Event"
           --#SUMMARY      The user %s ran NDMP diagnostic.   Description:  The user %s ran NDMP diagnostic.
           --#ARGUMENTS    {1}
           --#SEVERITY     INFORMATIONAL
           --#TIMEINDEX    99
           --#STATE        OK
       ::= { fluidFSEventsComponent 236 } 
    
    
    fluidFSEventComponentRunNdmpDiagnosticActionFailure NOTIFICATION-TYPE
       OBJECTS { sysName, fluidFSEventsParamsComponentUserName, fluidFSEventsParamsComponentRetcodeString }
       STATUS current
       DESCRIPTION
           "Ndmp diagnostic failed.   Description:  Ndmp diagnostic, which was run by user {{userName}} failed.[[nl]]{{retcodeString}}"
           --#TYPE         "Normal Event"
           --#SUMMARY      Ndmp diagnostic failed.   Description:  Ndmp diagnostic, which was run by user %s failed.[[nl]]%s
           --#ARGUMENTS    {1,2}
           --#SEVERITY     MAJOR
           --#TIMEINDEX    99
           --#STATE        OK
       ::= { fluidFSEventsComponent 237 } 
    
    
    fluidFSEventComponentNdmpDiagnosticsFailed NOTIFICATION-TYPE
       OBJECTS { sysName, fluidFSEventsParamsComponentRetcodeString }
       STATUS current
       DESCRIPTION
           "Failed to generate diagnostics package for 'NdmpDiagnostics'. {{retcodeString}}"
           --#TYPE         "Normal Event"
           --#SUMMARY      Failed to generate diagnostics package for 'NdmpDiagnostics'. %s
           --#ARGUMENTS    {1}
           --#SEVERITY     MAJOR
           --#TIMEINDEX    99
           --#STATE        OK
       ::= { fluidFSEventsComponent 238 } 
    
    
    fluidFSEventComponentNdmpDiagnosticsOk NOTIFICATION-TYPE
       OBJECTS { sysName }
       STATUS current
       DESCRIPTION
           "Package generation for 'NdmpDiagnostics' completed successfully."
           --#TYPE         "Normal Event"
           --#SUMMARY      Package generation for 'NdmpDiagnostics' completed successfully.
           --#ARGUMENTS    {}
           --#SEVERITY     INFORMATIONAL
           --#TIMEINDEX    99
           --#STATE        OK
       ::= { fluidFSEventsComponent 239 } 
    
    
    fluidFSEventComponentRediscoverLunsSuccess NOTIFICATION-TYPE
       OBJECTS { sysName }
       STATUS current
       DESCRIPTION
           "The system sucessfully triggered iSCSI targets discovery."
           --#TYPE         "Normal Event"
           --#SUMMARY      The system sucessfully triggered iSCSI targets discovery.
           --#ARGUMENTS    {}
           --#SEVERITY     INFORMATIONAL
           --#TIMEINDEX    99
           --#STATE        OK
       ::= { fluidFSEventsComponent 241 } 
    
    
    fluidFSEventComponentFileAccessNotificationConfigModifySuccess NOTIFICATION-TYPE
       OBJECTS { sysName }
       STATUS current
       DESCRIPTION
           "File Access Notification settings updated   Description:  File Access Notification settings updated"
           --#TYPE         "Normal Event"
           --#SUMMARY      File Access Notification settings updated   Description:  File Access Notification settings updated
           --#ARGUMENTS    {}
           --#SEVERITY     INFORMATIONAL
           --#TIMEINDEX    99
           --#STATE        OK
       ::= { fluidFSEventsComponent 247 } 
    
    
    fluidFSEventComponentFileAccessNotificationPolicyModifySuccess NOTIFICATION-TYPE
       OBJECTS { sysName }
       STATUS current
       DESCRIPTION
           "File Access Notification Policy changed   Description:  File Access Notification Policy changed"
           --#TYPE         "Normal Event"
           --#SUMMARY      File Access Notification Policy changed   Description:  File Access Notification Policy changed
           --#ARGUMENTS    {}
           --#SEVERITY     INFORMATIONAL
           --#TIMEINDEX    99
           --#STATE        OK
       ::= { fluidFSEventsComponent 248 } 
    
    
    fluidFSEventComponentFileAccessNotificationSubscriberModifySuccess NOTIFICATION-TYPE
       OBJECTS { sysName }
       STATUS current
       DESCRIPTION
           "File Access Notifications Subscribers changed   Description:  File Access Notifications Subscribers changed"
           --#TYPE         "Normal Event"
           --#SUMMARY      File Access Notifications Subscribers changed   Description:  File Access Notifications Subscribers changed
           --#ARGUMENTS    {}
           --#SEVERITY     INFORMATIONAL
           --#TIMEINDEX    99
           --#STATE        OK
       ::= { fluidFSEventsComponent 249 } 
    
    
    fluidFSEventComponentTapeDeviceConfigurationCreateSuccess NOTIFICATION-TYPE
       OBJECTS { sysName, fluidFSEventsParamsComponentUserName, fluidFSEventsParamsComponentTapeDeviceName }
       STATUS current
       DESCRIPTION
           "The user {{userName}} created a new tape device with name {{tapeDeviceName}}."
           --#TYPE         "Normal Event"
           --#SUMMARY      The user %s created a new tape device with name %s.
           --#ARGUMENTS    {1,2}
           --#SEVERITY     INFORMATIONAL
           --#TIMEINDEX    99
           --#STATE        OK
       ::= { fluidFSEventsComponent 250 } 
    
    
    fluidFSEventComponentTapeDeviceConfigurationModifySuccess NOTIFICATION-TYPE
       OBJECTS { sysName, fluidFSEventsParamsComponentUserName, fluidFSEventsParamsComponentTapeDeviceName }
       STATUS current
       DESCRIPTION
           "The user {{userName}} modified a tape device name to {{tapeDeviceName}}."
           --#TYPE         "Normal Event"
           --#SUMMARY      The user %s modified a tape device name to %s.
           --#ARGUMENTS    {1,2}
           --#SEVERITY     INFORMATIONAL
           --#TIMEINDEX    99
           --#STATE        OK
       ::= { fluidFSEventsComponent 251 } 
    
    
    fluidFSEventComponentTapeDeviceConfigurationDeleteSuccess NOTIFICATION-TYPE
       OBJECTS { sysName, fluidFSEventsParamsComponentUserName, fluidFSEventsParamsComponentTapeDeviceName }
       STATUS current
       DESCRIPTION
           "The user {{userName}} deleted a tape device with name {{tapeDeviceName}}."
           --#TYPE         "Normal Event"
           --#SUMMARY      The user %s deleted a tape device with name %s.
           --#ARGUMENTS    {1,2}
           --#SEVERITY     INFORMATIONAL
           --#TIMEINDEX    99
           --#STATE        OK
       ::= { fluidFSEventsComponent 252 } 
    
    
    fluidFSEventComponentInternalStorageReservationSetSuccess NOTIFICATION-TYPE
       OBJECTS { sysName, fluidFSEventsParamsComponentUserName, fluidFSEventsParamsComponentEventsSpace }
       STATUS current
       DESCRIPTION
           "The user {{userName}} set the internal storage reservation   Description:  The user {{userName}} set the internal storage reservation. Current configuration: events - {{eventsSpace}} MB"
           --#TYPE         "Normal Event"
           --#SUMMARY      The user %s set the internal storage reservation   Description:  The user %s set the internal storage reservation. Current configuration: events - %s MB
           --#ARGUMENTS    {1,2}
           --#SEVERITY     INFORMATIONAL
           --#TIMEINDEX    99
           --#STATE        OK
       ::= { fluidFSEventsComponent 253 } 
    
    
    fluidFSEventComponentBwLimiterCreateSuccess NOTIFICATION-TYPE
       OBJECTS { sysName, fluidFSEventsParamsComponentUserName, fluidFSEventsParamsComponentName }
       STATUS current
       DESCRIPTION
           "The user {{userName}} created Bw Limiter {{Name}}."
           --#TYPE         "Normal Event"
           --#SUMMARY      The user %s created Bw Limiter %s.
           --#ARGUMENTS    {1,2}
           --#SEVERITY     INFORMATIONAL
           --#TIMEINDEX    99
           --#STATE        OK
       ::= { fluidFSEventsComponent 254 } 
    
    
    fluidFSEventComponentBwLimiterModifySuccess NOTIFICATION-TYPE
       OBJECTS { sysName, fluidFSEventsParamsComponentUserName, fluidFSEventsParamsComponentName }
       STATUS current
       DESCRIPTION
           "The user {{userName}} updated the configuration of BW Limiter {{Name}}."
           --#TYPE         "Normal Event"
           --#SUMMARY      The user %s updated the configuration of BW Limiter %s.
           --#ARGUMENTS    {1,2}
           --#SEVERITY     INFORMATIONAL
           --#TIMEINDEX    99
           --#STATE        OK
       ::= { fluidFSEventsComponent 255 } 
    
    
    fluidFSEventComponentBwLimiterDeleteSuccess NOTIFICATION-TYPE
       OBJECTS { sysName, fluidFSEventsParamsComponentUserName, fluidFSEventsParamsComponentName }
       STATUS current
       DESCRIPTION
           "The user {{userName}} deleted BW Limiter {{Name}}."
           --#TYPE         "Normal Event"
           --#SUMMARY      The user %s deleted BW Limiter %s.
           --#ARGUMENTS    {1,2}
           --#SEVERITY     INFORMATIONAL
           --#TIMEINDEX    99
           --#STATE        OK
       ::= { fluidFSEventsComponent 256 } 
    
    
    fluidFSEventComponentStorageDevicesRescanSuccessEvent NOTIFICATION-TYPE
       OBJECTS { sysName, fluidFSEventsParamsComponentUserName }
       STATUS current
       DESCRIPTION
           "The user {{userName}} performed rescan storage devices."
           --#TYPE         "Normal Event"
           --#SUMMARY      The user %s performed rescan storage devices.
           --#ARGUMENTS    {1}
           --#SEVERITY     INFORMATIONAL
           --#TIMEINDEX    99
           --#STATE        OK
       ::= { fluidFSEventsComponent 258 } 
    
    
    fluidFSEventComponentVAppCloningSuccess NOTIFICATION-TYPE
       OBJECTS { sysName, fluidFSEventsParamsComponentUserName }
       STATUS current
       DESCRIPTION
           "The user {{userName}} has successfully cloned VMware Virtual Appliance"
           --#TYPE         "Normal Event"
           --#SUMMARY      The user %s has successfully cloned VMware Virtual Appliance
           --#ARGUMENTS    {1}
           --#SEVERITY     INFORMATIONAL
           --#TIMEINDEX    99
           --#STATE        OK
       ::= { fluidFSEventsComponent 264 } 
    
    
    fluidFSEventComponentTenantCreateSuccess NOTIFICATION-TYPE
       OBJECTS { sysName, fluidFSEventsParamsComponentTenantId, fluidFSEventsParamsComponentUserName, fluidFSEventsParamsComponentName }
       STATUS current
       DESCRIPTION
           "The user {{userName}} created Tenant {{Name}}."
           --#TYPE         "Normal Event"
           --#SUMMARY      The user %s created Tenant %s.
           --#ARGUMENTS    {1,2,3}
           --#SEVERITY     INFORMATIONAL
           --#TIMEINDEX    99
           --#STATE        OK
       ::= { fluidFSEventsComponent 265 } 
    
    
    fluidFSEventComponentTenantModifySuccess NOTIFICATION-TYPE
       OBJECTS { sysName, fluidFSEventsParamsComponentTenantId, fluidFSEventsParamsComponentUserName, fluidFSEventsParamsComponentName }
       STATUS current
       DESCRIPTION
           "The user {{userName}} updated the configuration of {{Name}}."
           --#TYPE         "Normal Event"
           --#SUMMARY      The user %s updated the configuration of %s.
           --#ARGUMENTS    {1,2,3}
           --#SEVERITY     INFORMATIONAL
           --#TIMEINDEX    99
           --#STATE        OK
       ::= { fluidFSEventsComponent 266 } 
    
    
    fluidFSEventComponentTenantDeleteSuccess NOTIFICATION-TYPE
       OBJECTS { sysName, fluidFSEventsParamsComponentTenantId, fluidFSEventsParamsComponentUserName, fluidFSEventsParamsComponentName }
       STATUS current
       DESCRIPTION
           "The user {{userName}} deleted Tenant {{Name}}."
           --#TYPE         "Normal Event"
           --#SUMMARY      The user %s deleted Tenant %s.
           --#ARGUMENTS    {1,2,3}
           --#SEVERITY     INFORMATIONAL
           --#TIMEINDEX    99
           --#STATE        OK
       ::= { fluidFSEventsComponent 267 } 
    
    
    fluidFSEventComponentVirtualVolumeCreateSuccess NOTIFICATION-TYPE
       OBJECTS { sysName, fluidFSEventsParamsComponentUserName, fluidFSEventsParamsComponentName, fluidFSEventsParamsComponentTenantId }
       STATUS current
       DESCRIPTION
           "The user {{userName}} created NAS volume {{Name}}."
           --#TYPE         "Normal Event"
           --#SUMMARY      The user %s created NAS volume %s.
           --#ARGUMENTS    {1,2,3}
           --#SEVERITY     INFORMATIONAL
           --#TIMEINDEX    99
           --#STATE        OK
       ::= { fluidFSEventsComponent 268 } 
    
    
    fluidFSEventComponentVirtualVolumeModifySuccess NOTIFICATION-TYPE
       OBJECTS { sysName, fluidFSEventsParamsComponentUserName, fluidFSEventsParamsComponentName, fluidFSEventsParamsComponentTenantId }
       STATUS current
       DESCRIPTION
           "The user {{userName}} updated the configuration of NAS volume {{Name}}."
           --#TYPE         "Normal Event"
           --#SUMMARY      The user %s updated the configuration of NAS volume %s.
           --#ARGUMENTS    {1,2,3}
           --#SEVERITY     INFORMATIONAL
           --#TIMEINDEX    99
           --#STATE        OK
       ::= { fluidFSEventsComponent 269 } 
    
    
    fluidFSEventComponentVirtualVolumeDeleteSuccess NOTIFICATION-TYPE
       OBJECTS { sysName, fluidFSEventsParamsComponentUserName, fluidFSEventsParamsComponentName, fluidFSEventsParamsComponentTenantId }
       STATUS current
       DESCRIPTION
           "The user {{userName}} deleted NAS volume {{Name}}."
           --#TYPE         "Normal Event"
           --#SUMMARY      The user %s deleted NAS volume %s.
           --#ARGUMENTS    {1,2,3}
           --#SEVERITY     INFORMATIONAL
           --#TIMEINDEX    99
           --#STATE        OK
       ::= { fluidFSEventsComponent 270 } 
    
    
    fluidFSEventComponentSnapshotsRestoreSuccess NOTIFICATION-TYPE
       OBJECTS { sysName, fluidFSEventsParamsComponentUserName, fluidFSEventsParamsComponentFSID, fluidFSEventsParamsComponentSnapshotID, fluidFSEventsParamsComponentName }
       STATUS current
       DESCRIPTION
           "The user {{userName}} restored snapshot {{SnapshotID}} - {{Name}} on NAS volume {{FSIDName}}."
           --#TYPE         "Normal Event"
           --#SUMMARY      The user %s restored snapshot %s - %s on NAS volume %s.
           --#ARGUMENTS    {1,2,3,4}
           --#SEVERITY     INFORMATIONAL
           --#TIMEINDEX    99
           --#STATE        OK
       ::= { fluidFSEventsComponent 271 } 
    
    
    fluidFSEventComponentSnapshotModifySuccess NOTIFICATION-TYPE
       OBJECTS { sysName, fluidFSEventsParamsComponentUserName, fluidFSEventsParamsComponentFSID, fluidFSEventsParamsComponentSnapshotID, fluidFSEventsParamsComponentName, fluidFSEventsParamsComponentExpiry }
       STATUS current
       DESCRIPTION
           "The user {{userName}} modified snapshot {{SnapshotID}} on NAS volume {{FSIDName}} to name {{Name}} and expiry {{Expiry}}."
           --#TYPE         "Normal Event"
           --#SUMMARY      The user %s modified snapshot %s on NAS volume %s to name %s and expiry %s.
           --#ARGUMENTS    {1,2,3,4,5}
           --#SEVERITY     INFORMATIONAL
           --#TIMEINDEX    99
           --#STATE        OK
       ::= { fluidFSEventsComponent 272 } 
    
    
    fluidFSEventComponentSnapshotModifyFailure NOTIFICATION-TYPE
       OBJECTS { sysName, fluidFSEventsParamsComponentUserName, fluidFSEventsParamsComponentFSID, fluidFSEventsParamsComponentSnapshotID, fluidFSEventsParamsComponentName }
       STATUS current
       DESCRIPTION
           "The user {{userName}} failed to rename snapshot {{SnapshotID}} on NAS volume {{FSIDName}} to name {{Name}}."
           --#TYPE         "Normal Event"
           --#SUMMARY      The user %s failed to rename snapshot %s on NAS volume %s to name %s.
           --#ARGUMENTS    {1,2,3,4}
           --#SEVERITY     MAJOR
           --#TIMEINDEX    99
           --#STATE        OK
       ::= { fluidFSEventsComponent 273 } 
    
    
    fluidFSEventComponentSnapshotDeleteSuccess NOTIFICATION-TYPE
       OBJECTS { sysName, fluidFSEventsParamsComponentUserName, fluidFSEventsParamsComponentFSID, fluidFSEventsParamsComponentSnapshotID, fluidFSEventsParamsComponentName }
       STATUS current
       DESCRIPTION
           "The user {{userName}} deleted snapshot {{SnapshotID}} - {{Name}} on NAS volume {{FSIDName}}."
           --#TYPE         "Normal Event"
           --#SUMMARY      The user %s deleted snapshot %s - %s on NAS volume %s.
           --#ARGUMENTS    {1,2,3,4}
           --#SEVERITY     INFORMATIONAL
           --#TIMEINDEX    99
           --#STATE        OK
       ::= { fluidFSEventsComponent 274 } 
    
    
    fluidFSEventComponentSnapshotDeleteFailure NOTIFICATION-TYPE
       OBJECTS { sysName, fluidFSEventsParamsComponentUserName, fluidFSEventsParamsComponentFSID, fluidFSEventsParamsComponentSnapshotID }
       STATUS current
       DESCRIPTION
           "The user {{userName}} failed to delete snapshot {{SnapshotID}} on NAS volume {{FSIDName}}."
           --#TYPE         "Normal Event"
           --#SUMMARY      The user %s failed to delete snapshot %s on NAS volume %s.
           --#ARGUMENTS    {1,2,3}
           --#SEVERITY     MAJOR
           --#TIMEINDEX    99
           --#STATE        OK
       ::= { fluidFSEventsComponent 275 } 
    
    
    fluidFSEventComponentSnapshotCreateSuccess NOTIFICATION-TYPE
       OBJECTS { sysName, fluidFSEventsParamsComponentUserName, fluidFSEventsParamsComponentFSID, fluidFSEventsParamsComponentName, fluidFSEventsParamsComponentSnapshotID }
       STATUS current
       DESCRIPTION
           "The user {{userName}} created snapshot {{SnapshotID}} - {{Name}} on NAS volume {{FSIDName}}."
           --#TYPE         "Normal Event"
           --#SUMMARY      The user %s created snapshot %s - %s on NAS volume %s.
           --#ARGUMENTS    {1,2,3,4}
           --#SEVERITY     INFORMATIONAL
           --#TIMEINDEX    99
           --#STATE        OK
       ::= { fluidFSEventsComponent 276 } 
    
    
    fluidFSEventComponentSnapshotCreateFailure NOTIFICATION-TYPE
       OBJECTS { sysName, fluidFSEventsParamsComponentUserName, fluidFSEventsParamsComponentFSID, fluidFSEventsParamsComponentName, fluidFSEventsParamsComponentSnapshotID }
       STATUS current
       DESCRIPTION
           "The user {{userName}} failed to create snapshot {{SnapshotID}} - {{Name}} on NAS volume {{FSIDName}}."
           --#TYPE         "Normal Event"
           --#SUMMARY      The user %s failed to create snapshot %s - %s on NAS volume %s.
           --#ARGUMENTS    {1,2,3,4}
           --#SEVERITY     MAJOR
           --#TIMEINDEX    99
           --#STATE        OK
       ::= { fluidFSEventsComponent 277 } 
    
    
    fluidFSEventComponentSnapshotMakeManualSuccess NOTIFICATION-TYPE
       OBJECTS { sysName, fluidFSEventsParamsComponentUserName, fluidFSEventsParamsComponentFSID, fluidFSEventsParamsComponentSnapshotID, fluidFSEventsParamsComponentNdmpLock }
       STATUS current
       DESCRIPTION
           "The user {{userName}} set NDMP lock on snapshot {{SnapshotID}} on NAS volume {{FSIDName}} to {{NdmpLock}}."
           --#TYPE         "Normal Event"
           --#SUMMARY      The user %s set NDMP lock on snapshot %s on NAS volume %s to %s.
           --#ARGUMENTS    {1,2,3,4}
           --#SEVERITY     INFORMATIONAL
           --#TIMEINDEX    99
           --#STATE        OK
       ::= { fluidFSEventsComponent 278 } 
    
    
    fluidFSEventComponentDnsModifySuccess NOTIFICATION-TYPE
       OBJECTS { sysName, fluidFSEventsParamsComponentUserName, fluidFSEventsParamsComponentTenantId }
       STATUS current
       DESCRIPTION
           "DNS configuration of {{TenantName}} was modified by {{userName}}."
           --#TYPE         "Normal Event"
           --#SUMMARY      DNS configuration of %s was modified by %s.
           --#ARGUMENTS    {1,2}
           --#SEVERITY     INFORMATIONAL
           --#TIMEINDEX    99
           --#STATE        OK
       ::= { fluidFSEventsComponent 279 } 
    
    
    fluidFSEventComponentDnsModifyWarning NOTIFICATION-TYPE
       OBJECTS { sysName, fluidFSEventsParamsComponentUserName, fluidFSEventsParamsComponentRetcodeString, fluidFSEventsParamsComponentTenantId }
       STATUS current
       DESCRIPTION
           "DNS configuration of {{TenantName}} was modified by {{userName}}. {{retcodeString}}"
           --#TYPE         "Normal Event"
           --#SUMMARY      DNS configuration of %s was modified by %s. %s
           --#ARGUMENTS    {1,2,3}
           --#SEVERITY     INFORMATIONAL
           --#TIMEINDEX    99
           --#STATE        OK
       ::= { fluidFSEventsComponent 280 } 
    
    
    fluidFSEventComponentSnapshotsRestoreSuccessName NOTIFICATION-TYPE
       OBJECTS { sysName, fluidFSEventsParamsComponentFSID, fluidFSEventsParamsComponentName, fluidFSEventsParamsComponentSnapshotID }
       STATUS current
       DESCRIPTION
           "Snapshot {{SnapshotID}} - {{Name}} was restored on NAS volume {{FSIDName}}."
           --#TYPE         "Normal Event"
           --#SUMMARY      Snapshot %s - %s was restored on NAS volume %s.
           --#ARGUMENTS    {1,2,3}
           --#SEVERITY     INFORMATIONAL
           --#TIMEINDEX    99
           --#STATE        OK
       ::= { fluidFSEventsComponent 281 } 
    
    
    fluidFSEventComponentSnapshotsRestoreFailureName NOTIFICATION-TYPE
       OBJECTS { sysName, fluidFSEventsParamsComponentFSID, fluidFSEventsParamsComponentName, fluidFSEventsParamsComponentSnapshotID }
       STATUS current
       DESCRIPTION
           "Snapshot {{SnapshotID}} - {{Name}} failed to be restored on NAS volume {{FSIDName}}."
           --#TYPE         "Normal Event"
           --#SUMMARY      Snapshot %s - %s failed to be restored on NAS volume %s.
           --#ARGUMENTS    {1,2,3}
           --#SEVERITY     MAJOR
           --#TIMEINDEX    99
           --#STATE        OK
       ::= { fluidFSEventsComponent 282 } 
    
    
    fluidFSEventComponentRestoreVirtualVolumeCompletedSuccessfully NOTIFICATION-TYPE
       OBJECTS { sysName, fluidFSEventsParamsComponentUserName, fluidFSEventsParamsComponentFSID }
       STATUS current
       DESCRIPTION
           "The configuration of the NAS volume {{FSIDName}} was restored successfully by user {{userName}}."
           --#TYPE         "Normal Event"
           --#SUMMARY      The configuration of the NAS volume %s was restored successfully by user %s.
           --#ARGUMENTS    {1,2}
           --#SEVERITY     INFORMATIONAL
           --#TIMEINDEX    99
           --#STATE        OK
       ::= { fluidFSEventsComponent 283 } 
    
    
    fluidFSEventComponentRestoreVirtualVolumeFinishedWithErrors NOTIFICATION-TYPE
       OBJECTS { sysName, fluidFSEventsParamsComponentUserName, fluidFSEventsParamsComponentFSID, fluidFSEventsParamsComponentRetcodeString }
       STATUS current
       DESCRIPTION
           "Restore NAS container configuration {{FSIDName}} finished with errors.   Description:  The configuration of the NAS container {{FSIDName}} was restored by user {{userName}} with errors: {{retcodeString}}"
           --#TYPE         "Normal Event"
           --#SUMMARY      Restore NAS container configuration %s finished with errors.   Description:  The configuration of the NAS container %s was restored by user %s with errors: %s
           --#ARGUMENTS    {1,2,3}
           --#SEVERITY     MAJOR
           --#TIMEINDEX    99
           --#STATE        OK
       ::= { fluidFSEventsComponent 284 } 
    
    
    fluidFSEventComponentRestoreVirtualVolumeFromFilesCompletedSuccessfully NOTIFICATION-TYPE
       OBJECTS { sysName, fluidFSEventsParamsComponentUserName, fluidFSEventsParamsComponentFSID }
       STATUS current
       DESCRIPTION
           "The configuration of the NAS volume {{FSIDName}} was restored from files successfully by user {{userName}}."
           --#TYPE         "Normal Event"
           --#SUMMARY      The configuration of the NAS volume %s was restored from files successfully by user %s.
           --#ARGUMENTS    {1,2}
           --#SEVERITY     INFORMATIONAL
           --#TIMEINDEX    99
           --#STATE        OK
       ::= { fluidFSEventsComponent 285 } 
    
    
    fluidFSEventComponentRestoreVirtualVolumeFromFilesFinishedWithErrors NOTIFICATION-TYPE
       OBJECTS { sysName, fluidFSEventsParamsComponentUserName, fluidFSEventsParamsComponentFSID, fluidFSEventsParamsComponentRetcodeString }
       STATUS current
       DESCRIPTION
           "Restore NAS volume {{FSIDName}} configuration finished with errors.   Description:  The configuration of the NAS volume {{FSIDName}} was restored from files by user {{userName}} with errors: {{retcodeString}}."
           --#TYPE         "Normal Event"
           --#SUMMARY      Restore NAS volume %s configuration finished with errors.   Description:  The configuration of the NAS volume %s was restored from files by user %s with errors: %s.
           --#ARGUMENTS    {1,2,3}
           --#SEVERITY     MAJOR
           --#TIMEINDEX    99
           --#STATE        OK
       ::= { fluidFSEventsComponent 286 } 
    
    
    fluidFSEventComponentAdministratorCreateSuccess NOTIFICATION-TYPE
       OBJECTS { sysName, fluidFSEventsParamsComponentUserName, fluidFSEventsParamsComponentUID, fluidFSEventsParamsComponentTenantId }
       STATUS current
       DESCRIPTION
           "The user {{userName}} created new administrator {{AdminName}}."
           --#TYPE         "Normal Event"
           --#SUMMARY      The user %s created new administrator %s.
           --#ARGUMENTS    {1,2,3}
           --#SEVERITY     INFORMATIONAL
           --#TIMEINDEX    99
           --#STATE        OK
       ::= { fluidFSEventsComponent 287 } 
    
    
    fluidFSEventComponentAdministratorModifySuccess NOTIFICATION-TYPE
       OBJECTS { sysName, fluidFSEventsParamsComponentUserName, fluidFSEventsParamsComponentUID, fluidFSEventsParamsComponentTenantId }
       STATUS current
       DESCRIPTION
           "The user {{userName}} modified the configuration of administrator {{AdminName}}."
           --#TYPE         "Normal Event"
           --#SUMMARY      The user %s modified the configuration of administrator %s.
           --#ARGUMENTS    {1,2,3}
           --#SEVERITY     INFORMATIONAL
           --#TIMEINDEX    99
           --#STATE        OK
       ::= { fluidFSEventsComponent 288 } 
    
    
    fluidFSEventComponentAdministratorDeleteSuccess NOTIFICATION-TYPE
       OBJECTS { sysName, fluidFSEventsParamsComponentUserName, fluidFSEventsParamsComponentUID, fluidFSEventsParamsComponentTenantId }
       STATUS current
       DESCRIPTION
           "The user {{userName}} deleted administrator {{AdminName}}."
           --#TYPE         "Normal Event"
           --#SUMMARY      The user %s deleted administrator %s.
           --#ARGUMENTS    {1,2,3}
           --#SEVERITY     INFORMATIONAL
           --#TIMEINDEX    99
           --#STATE        OK
       ::= { fluidFSEventsComponent 289 } 
    
    
    fluidFSEventComponentCifsShareCreateSuccess NOTIFICATION-TYPE
       OBJECTS { sysName, fluidFSEventsParamsComponentUserName, fluidFSEventsParamsComponentShareName, fluidFSEventsParamsComponentFSID }
       STATUS current
       DESCRIPTION
           "The user {{userName}} created the {{shareName}} SMB share on {{FSIDName}} NAS volume."
           --#TYPE         "Normal Event"
           --#SUMMARY      The user %s created the %s SMB share on %s NAS volume.
           --#ARGUMENTS    {1,2,3}
           --#SEVERITY     INFORMATIONAL
           --#TIMEINDEX    99
           --#STATE        OK
       ::= { fluidFSEventsComponent 290 } 
    
    
    fluidFSEventComponentCifsShareModifySuccess NOTIFICATION-TYPE
       OBJECTS { sysName, fluidFSEventsParamsComponentUserName, fluidFSEventsParamsComponentShareName, fluidFSEventsParamsComponentFSID }
       STATUS current
       DESCRIPTION
           "The user {{userName}} updated the configuration of {{shareName}} SMB share on {{FSIDName}} NAS volume."
           --#TYPE         "Normal Event"
           --#SUMMARY      The user %s updated the configuration of %s SMB share on %s NAS volume.
           --#ARGUMENTS    {1,2,3}
           --#SEVERITY     INFORMATIONAL
           --#TIMEINDEX    99
           --#STATE        OK
       ::= { fluidFSEventsComponent 291 } 
    
    
    fluidFSEventComponentCifsShareDeleteSuccess NOTIFICATION-TYPE
       OBJECTS { sysName, fluidFSEventsParamsComponentUserName, fluidFSEventsParamsComponentShareName, fluidFSEventsParamsComponentFSID }
       STATUS current
       DESCRIPTION
           "The user {{userName}} deleted the {{shareName}} SMB share on {{FSIDName}} NAS volume."
           --#TYPE         "Normal Event"
           --#SUMMARY      The user %s deleted the %s SMB share on %s NAS volume.
           --#ARGUMENTS    {1,2,3}
           --#SEVERITY     INFORMATIONAL
           --#TIMEINDEX    99
           --#STATE        OK
       ::= { fluidFSEventsComponent 292 } 
    
    
    fluidFSEventComponentCifsHomeShareModifySuccess NOTIFICATION-TYPE
       OBJECTS { sysName, fluidFSEventsParamsComponentUserName, fluidFSEventsParamsComponentFSID, fluidFSEventsParamsComponentTenantId }
       STATUS current
       DESCRIPTION
           "The user {{userName}} updated the configuration of home SMB share on {{FSIDName}} NAS volume of {{TenantName}}."
           --#TYPE         "Normal Event"
           --#SUMMARY      The user %s updated the configuration of home SMB share on %s NAS volume of %s.
           --#ARGUMENTS    {1,2,3}
           --#SEVERITY     INFORMATIONAL
           --#TIMEINDEX    99
           --#STATE        OK
       ::= { fluidFSEventsComponent 293 } 
    
    
    fluidFSEventComponentNfsExportCreateSuccess NOTIFICATION-TYPE
       OBJECTS { sysName, fluidFSEventsParamsComponentUserName, fluidFSEventsParamsComponentNFSExportPath, fluidFSEventsParamsComponentFSID }
       STATUS current
       DESCRIPTION
           "The user {{userName}} created the {{NFSExportPath}} NFS export on {{FSIDName}} NAS volume."
           --#TYPE         "Normal Event"
           --#SUMMARY      The user %s created the %s NFS export on %s NAS volume.
           --#ARGUMENTS    {1,2,3}
           --#SEVERITY     INFORMATIONAL
           --#TIMEINDEX    99
           --#STATE        OK
       ::= { fluidFSEventsComponent 294 } 
    
    
    fluidFSEventComponentNfsExportModifySuccess NOTIFICATION-TYPE
       OBJECTS { sysName, fluidFSEventsParamsComponentUserName, fluidFSEventsParamsComponentNFSExportPath, fluidFSEventsParamsComponentFSID }
       STATUS current
       DESCRIPTION
           "The user {{userName}} updated the configuration of {{NFSExportPath}} NFS export on {{FSIDName}} NAS volume."
           --#TYPE         "Normal Event"
           --#SUMMARY      The user %s updated the configuration of %s NFS export on %s NAS volume.
           --#ARGUMENTS    {1,2,3}
           --#SEVERITY     INFORMATIONAL
           --#TIMEINDEX    99
           --#STATE        OK
       ::= { fluidFSEventsComponent 295 } 
    
    
    fluidFSEventComponentNfsExportDeleteSuccess NOTIFICATION-TYPE
       OBJECTS { sysName, fluidFSEventsParamsComponentUserName, fluidFSEventsParamsComponentNFSExportPath, fluidFSEventsParamsComponentFSID }
       STATUS current
       DESCRIPTION
           "The user {{userName}} deleted {{NFSExportPath}} NFS export on {{FSIDName}} NAS volume."
           --#TYPE         "Normal Event"
           --#SUMMARY      The user %s deleted %s NFS export on %s NAS volume.
           --#ARGUMENTS    {1,2,3}
           --#SEVERITY     INFORMATIONAL
           --#TIMEINDEX    99
           --#STATE        OK
       ::= { fluidFSEventsComponent 296 } 
    
    
    fluidFSEventComponentSnapshotScheduleCreateSuccess NOTIFICATION-TYPE
       OBJECTS { sysName, fluidFSEventsParamsComponentUserName, fluidFSEventsParamsComponentName, fluidFSEventsParamsComponentFSID }
       STATUS current
       DESCRIPTION
           "The user {{userName}} created the {{Name}} snapshot schedule on {{FSIDName}} NAS volume."
           --#TYPE         "Normal Event"
           --#SUMMARY      The user %s created the %s snapshot schedule on %s NAS volume.
           --#ARGUMENTS    {1,2,3}
           --#SEVERITY     INFORMATIONAL
           --#TIMEINDEX    99
           --#STATE        OK
       ::= { fluidFSEventsComponent 297 } 
    
    
    fluidFSEventComponentSnapshotScheduleModifySuccess NOTIFICATION-TYPE
       OBJECTS { sysName, fluidFSEventsParamsComponentUserName, fluidFSEventsParamsComponentName, fluidFSEventsParamsComponentFSID }
       STATUS current
       DESCRIPTION
           "The user {{userName}} updated the configuration of {{Name}} snapshot schedule on {{FSIDName}} NAS volume."
           --#TYPE         "Normal Event"
           --#SUMMARY      The user %s updated the configuration of %s snapshot schedule on %s NAS volume.
           --#ARGUMENTS    {1,2,3}
           --#SEVERITY     INFORMATIONAL
           --#TIMEINDEX    99
           --#STATE        OK
       ::= { fluidFSEventsComponent 298 } 
    
    
    fluidFSEventComponentSnapshotScheduleDeleteSuccess NOTIFICATION-TYPE
       OBJECTS { sysName, fluidFSEventsParamsComponentUserName, fluidFSEventsParamsComponentName, fluidFSEventsParamsComponentFSID }
       STATUS current
       DESCRIPTION
           "The user {{userName}} deleted the {{Name}} snapshot schedule on {{FSIDName}} NAS volume."
           --#TYPE         "Normal Event"
           --#SUMMARY      The user %s deleted the %s snapshot schedule on %s NAS volume.
           --#ARGUMENTS    {1,2,3}
           --#SEVERITY     INFORMATIONAL
           --#TIMEINDEX    99
           --#STATE        OK
       ::= { fluidFSEventsComponent 299 } 
    
    
    fluidFSEventComponentReplicationScheduleCreateSuccess NOTIFICATION-TYPE
       OBJECTS { sysName, fluidFSEventsParamsComponentUserName, fluidFSEventsParamsComponentName, fluidFSEventsParamsComponentFSID, fluidFSEventsParamsComponentRemoteClusterId, fluidFSEventsParamsComponentRemoteFSID }
       STATUS current
       DESCRIPTION
           "The user {{userName}} created the {{Name}} schedule for replication between {{FSIDName}} and {{remoteVolumeName}}@{{remoteClusterName}} NAS volumes."
           --#TYPE         "Normal Event"
           --#SUMMARY      The user %s created the %s schedule for replication between %s and %s@%s NAS volumes.
           --#ARGUMENTS    {1,2,3,4,5}
           --#SEVERITY     INFORMATIONAL
           --#TIMEINDEX    99
           --#STATE        OK
       ::= { fluidFSEventsComponent 300 } 
    
    
    fluidFSEventComponentReplicationScheduleModifySuccess NOTIFICATION-TYPE
       OBJECTS { sysName, fluidFSEventsParamsComponentUserName, fluidFSEventsParamsComponentName, fluidFSEventsParamsComponentFSID, fluidFSEventsParamsComponentRemoteClusterId, fluidFSEventsParamsComponentRemoteFSID }
       STATUS current
       DESCRIPTION
           "The user {{userName}} updated the configuration of {{Name}} schedule for replication between {{FSIDName}} and {{remoteVolumeName}}@{{remoteClusterName}} NAS volumes."
           --#TYPE         "Normal Event"
           --#SUMMARY      The user %s updated the configuration of %s schedule for replication between %s and %s@%s NAS volumes.
           --#ARGUMENTS    {1,2,3,4,5}
           --#SEVERITY     INFORMATIONAL
           --#TIMEINDEX    99
           --#STATE        OK
       ::= { fluidFSEventsComponent 301 } 
    
    
    fluidFSEventComponentReplicationScheduleDeleteSuccess NOTIFICATION-TYPE
       OBJECTS { sysName, fluidFSEventsParamsComponentUserName, fluidFSEventsParamsComponentName, fluidFSEventsParamsComponentFSID, fluidFSEventsParamsComponentRemoteClusterId, fluidFSEventsParamsComponentRemoteFSID }
       STATUS current
       DESCRIPTION
           "The user {{userName}} deleted the {{Name}} schedule for replication between {{FSIDName}} and {{remoteVolumeName}}@{{remoteClusterName}} NAS volumes."
           --#TYPE         "Normal Event"
           --#SUMMARY      The user %s deleted the %s schedule for replication between %s and %s@%s NAS volumes.
           --#ARGUMENTS    {1,2,3,4,5}
           --#SEVERITY     INFORMATIONAL
           --#TIMEINDEX    99
           --#STATE        OK
       ::= { fluidFSEventsComponent 302 } 
    
    
    fluidFSEventComponentSnapshotDeleteSuccessNoName NOTIFICATION-TYPE
       OBJECTS { sysName, fluidFSEventsParamsComponentUserName, fluidFSEventsParamsComponentFSID, fluidFSEventsParamsComponentSnapshotID }
       STATUS current
       DESCRIPTION
           "The user {{userName}} deleted snapshot {{SnapshotID}} on NAS volume {{FSIDName}}."
           --#TYPE         "Normal Event"
           --#SUMMARY      The user %s deleted snapshot %s on NAS volume %s.
           --#ARGUMENTS    {1,2,3}
           --#SEVERITY     INFORMATIONAL
           --#TIMEINDEX    99
           --#STATE        OK
       ::= { fluidFSEventsComponent 303 } 
    
    
    fluidFSEventComponentReplicationActionAttachSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has connected {{FSIDName}} volume to {{remoteVolume}} volume of {{remoteSystemName}} system.   Description:  The user {{userName}} has connected NAS volume to {{remoteVolume}} NAS volume of {{remoteSystemName}} system."
           --#TYPE         "Normal Event"
           --#SUMMARY      The user %s has connected %s volume to %s volume of %s system.   Description:  The user %s has connected NAS volume to %s NAS volume of %s system.
           --#ARGUMENTS    {1,2,3,4}
           --#SEVERITY     INFORMATIONAL
           --#TIMEINDEX    99
           --#STATE        OK
       ::= { fluidFSEventsComponent 304 } 
    
    
    fluidFSEventComponentReplicationActionDetachSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has disconnected {{FSIDName}} and {{remoteVolume}}@{{remoteSystemName}} volumes.   Description:  The user {{userName}} has disconnected the replication between {{FSIDName}} NAS volume and {{remoteVolume}} NAS volume of {{remoteSystemName}} system."
           --#TYPE         "Normal Event"
           --#SUMMARY      The user %s has disconnected %s and %s@%s volumes.   Description:  The user %s has disconnected the replication between %s NAS volume and %s NAS volume of %s system.
           --#ARGUMENTS    {1,2,3,4}
           --#SEVERITY     INFORMATIONAL
           --#TIMEINDEX    99
           --#STATE        OK
       ::= { fluidFSEventsComponent 305 } 
    
    
    fluidFSEventComponentReplicationActionPauseSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has disabled replication between {{FSIDName}} and {{remoteVolume}}@{{remoteSystemName}} volumes.   Description:  The user {{userName}} has disabled the replication between {{FSIDName}} NAS volume and {{remoteVolume}} NAS volume of {{remoteSystemName}} system."
           --#TYPE         "Normal Event"
           --#SUMMARY      The user %s has disabled replication between %s and %s@%s volumes.   Description:  The user %s has disabled the replication between %s NAS volume and %s NAS volume of %s system.
           --#ARGUMENTS    {1,2,3,4}
           --#SEVERITY     INFORMATIONAL
           --#TIMEINDEX    99
           --#STATE        OK
       ::= { fluidFSEventsComponent 306 } 
    
    
    fluidFSEventComponentReplicationActionResumeSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has enabled replication between {{FSIDName}} and {{remoteVolume}}@{{remoteSystemName}} volumes.   Description:  The user {{userName}} has enabled the replication between {{FSIDName}} NAS volume and {{remoteVolume}} NAS volume of {{remoteSystemName}} system."
           --#TYPE         "Normal Event"
           --#SUMMARY      The user %s has enabled replication between %s and %s@%s volumes.   Description:  The user %s has enabled the replication between %s NAS volume and %s NAS volume of %s system.
           --#ARGUMENTS    {1,2,3,4}
           --#SEVERITY     INFORMATIONAL
           --#TIMEINDEX    99
           --#STATE        OK
       ::= { fluidFSEventsComponent 307 } 
    
    
    fluidFSEventComponentReplicationActionPromoteSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has promoted replication between {{FSIDName}} and {{remoteVolume}}@{{remoteSystemName}} volumes.   Description:  The user {{userName}} has promoted replication between {{FSIDName}} NAS volume and {{remoteVolume}} NAS volume of {{remoteSystemName}} system."
           --#TYPE         "Normal Event"
           --#SUMMARY      The user %s has promoted replication between %s and %s@%s volumes.   Description:  The user %s has promoted replication between %s NAS volume and %s NAS volume of %s system.
           --#ARGUMENTS    {1,2,3,4}
           --#SEVERITY     INFORMATIONAL
           --#TIMEINDEX    99
           --#STATE        OK
       ::= { fluidFSEventsComponent 308 } 
    
    
    fluidFSEventComponentReplicationActionDemoteSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has demoted replication between {{FSIDName}} and {{remoteVolume}}@{{remoteSystemName}} volumes.   Description:  The user {{userName}} has demoted replication between {{FSIDName}} NAS volume and {{remoteVolume}} NAS volume of {{remoteSystemName}} system."
           --#TYPE         "Normal Event"
           --#SUMMARY      The user %s has demoted replication between %s and %s@%s volumes.   Description:  The user %s has demoted replication between %s NAS volume and %s NAS volume of %s system.
           --#ARGUMENTS    {1,2,3,4}
           --#SEVERITY     INFORMATIONAL
           --#TIMEINDEX    99
           --#STATE        OK
       ::= { fluidFSEventsComponent 309 } 
    
    
    fluidFSEventComponentReplicationActionStartSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has started replication between {{FSIDName}} and {{remoteVolume}}@{{remoteSystemName}} volumes.   Description:  The user {{userName}} has started replication from {{FSIDName}} NAS volume to {{remoteVolume}} NAS volume of {{remoteSystemName}} system."
           --#TYPE         "Normal Event"
           --#SUMMARY      The user %s has started replication between %s and %s@%s volumes.   Description:  The user %s has started replication from %s NAS volume to %s NAS volume of %s system.
           --#ARGUMENTS    {1,2,3,4}
           --#SEVERITY     INFORMATIONAL
           --#TIMEINDEX    99
           --#STATE        OK
       ::= { fluidFSEventsComponent 310 } 
    
    
    fluidFSEventComponentCreateBlockStorageSuccess NOTIFICATION-TYPE
       OBJECTS { sysName, fluidFSEventsParamsComponentStorageId }
       STATUS current
       DESCRIPTION
           "BlockStorage {{storageId}} was successfully created."
           --#TYPE         "Normal Event"
           --#SUMMARY      BlockStorage %s was successfully created.
           --#ARGUMENTS    {1}
           --#SEVERITY     INFORMATIONAL
           --#TIMEINDEX    99
           --#STATE        OK
       ::= { fluidFSEventsComponent 311 } 
    
    
    fluidFSEventComponentModifyBlockStorageSuccess NOTIFICATION-TYPE
       OBJECTS { sysName, fluidFSEventsParamsComponentStorageId }
       STATUS current
       DESCRIPTION
           "Client subnet {{storageId}} was successfully modified."
           --#TYPE         "Normal Event"
           --#SUMMARY      Client subnet %s was successfully modified.
           --#ARGUMENTS    {1}
           --#SEVERITY     INFORMATIONAL
           --#TIMEINDEX    99
           --#STATE        OK
       ::= { fluidFSEventsComponent 312 } 
    
    
    fluidFSEventComponentDeleteBlockStorageSuccess NOTIFICATION-TYPE
       OBJECTS { sysName, fluidFSEventsParamsComponentStorageId }
       STATUS current
       DESCRIPTION
           "Client subnet {{storageId}} was successfully deleted."
           --#TYPE         "Normal Event"
           --#SUMMARY      Client subnet %s was successfully deleted.
           --#ARGUMENTS    {1}
           --#SEVERITY     INFORMATIONAL
           --#TIMEINDEX    99
           --#STATE        OK
       ::= { fluidFSEventsComponent 313 } 
    
    
    fluidFSEventComponentSubnetsCreateSuccess NOTIFICATION-TYPE
       OBJECTS { sysName, fluidFSEventsParamsComponentUserName, fluidFSEventsParamsComponentNetworkId, fluidFSEventsParamsComponentPrefix }
       STATUS current
       DESCRIPTION
           "Client subnet {{networkId}}/{{prefix}} was successfully created by {{userName}}."
           --#TYPE         "Normal Event"
           --#SUMMARY      Client subnet %s/%s was successfully created by %s.
           --#ARGUMENTS    {1,2,3}
           --#SEVERITY     INFORMATIONAL
           --#TIMEINDEX    99
           --#STATE        OK
       ::= { fluidFSEventsComponent 314 } 
    
    
    fluidFSEventComponentSubnetsModifySuccess NOTIFICATION-TYPE
       OBJECTS { sysName, fluidFSEventsParamsComponentUserName, fluidFSEventsParamsComponentNetworkId, fluidFSEventsParamsComponentPrefix }
       STATUS current
       DESCRIPTION
           "Client subnet {{networkId}}/{{prefix}} was successfully modified by {{userName}}."
           --#TYPE         "Normal Event"
           --#SUMMARY      Client subnet %s/%s was successfully modified by %s.
           --#ARGUMENTS    {1,2,3}
           --#SEVERITY     INFORMATIONAL
           --#TIMEINDEX    99
           --#STATE        OK
       ::= { fluidFSEventsComponent 315 } 
    
    
    fluidFSEventComponentSubnetsDeleteSuccess NOTIFICATION-TYPE
       OBJECTS { sysName, fluidFSEventsParamsComponentUserName, fluidFSEventsParamsComponentNetworkId, fluidFSEventsParamsComponentPrefix }
       STATUS current
       DESCRIPTION
           "Client subnet {{networkId}}/{{prefix}} was successfully deleted by {{userName}}."
           --#TYPE         "Normal Event"
           --#SUMMARY      Client subnet %s/%s was successfully deleted by %s.
           --#ARGUMENTS    {1,2,3}
           --#SEVERITY     INFORMATIONAL
           --#TIMEINDEX    99
           --#STATE        OK
       ::= { fluidFSEventsComponent 316 } 
    
    
    fluidFSEventComponentActiveDirectoryJoinSuccess NOTIFICATION-TYPE
       OBJECTS { sysName, fluidFSEventsParamsComponentUserName, fluidFSEventsParamsComponentDomain, fluidFSEventsParamsComponentTenantId }
       STATUS current
       DESCRIPTION
           "The user {{userName}} has successfully joined {{TenantName}} to Active Directory domain '{{Domain}}'."
           --#TYPE         "Normal Event"
           --#SUMMARY      The user %s has successfully joined %s to Active Directory domain '%s'.
           --#ARGUMENTS    {1,2,3}
           --#SEVERITY     INFORMATIONAL
           --#TIMEINDEX    99
           --#STATE        OK
       ::= { fluidFSEventsComponent 317 } 
    
    
    fluidFSEventComponentActiveDirectoryJoinWarning NOTIFICATION-TYPE
       OBJECTS { sysName, fluidFSEventsParamsComponentUserName, fluidFSEventsParamsComponentDomain, fluidFSEventsParamsComponentRetcodeString, fluidFSEventsParamsComponentTenantId }
       STATUS current
       DESCRIPTION
           "The user {{userName}} has joined {{TenantName}} to Active Directory domain '{{Domain}}', but with a warning: {{retcodeString}}"
           --#TYPE         "Normal Event"
           --#SUMMARY      The user %s has joined %s to Active Directory domain '%s', but with a warning: %s
           --#ARGUMENTS    {1,2,3,4}
           --#SEVERITY     INFORMATIONAL
           --#TIMEINDEX    99
           --#STATE        OK
       ::= { fluidFSEventsComponent 318 } 
    
    
    fluidFSEventComponentActiveDirectoryLeaveSuccess NOTIFICATION-TYPE
       OBJECTS { sysName, fluidFSEventsParamsComponentUserName, fluidFSEventsParamsComponentTenantId }
       STATUS current
       DESCRIPTION
           "The user {{userName}} has successfully left {{TenantName}} from Active Directory domain."
           --#TYPE         "Normal Event"
           --#SUMMARY      The user %s has successfully left %s from Active Directory domain.
           --#ARGUMENTS    {1,2}
           --#SEVERITY     INFORMATIONAL
           --#TIMEINDEX    99
           --#STATE        OK
       ::= { fluidFSEventsComponent 319 } 
    
    
    fluidFSEventComponentLocalUsersCreateSuccess NOTIFICATION-TYPE
       OBJECTS { sysName, fluidFSEventsParamsComponentUserName, fluidFSEventsParamsComponentLocalAccountName, fluidFSEventsParamsComponentTenantId }
       STATUS current
       DESCRIPTION
           "The user {{userName}} has successfully added new Local User '{{localAccountName}}' to {{TenantName}} cluster repository."
           --#TYPE         "Normal Event"
           --#SUMMARY      The user %s has successfully added new Local User '%s' to %s cluster repository.
           --#ARGUMENTS    {1,2,3}
           --#SEVERITY     INFORMATIONAL
           --#TIMEINDEX    99
           --#STATE        OK
       ::= { fluidFSEventsComponent 320 } 
    
    
    fluidFSEventComponentLocalUsersDeleteSuccess NOTIFICATION-TYPE
       OBJECTS { sysName, fluidFSEventsParamsComponentUserName, fluidFSEventsParamsComponentLocalAccountName, fluidFSEventsParamsComponentTenantId }
       STATUS current
       DESCRIPTION
           "The user {{userName}} has successfully deleted Local User '{{localAccountName}}' from {{TenantName}} cluster repository."
           --#TYPE         "Normal Event"
           --#SUMMARY      The user %s has successfully deleted Local User '%s' from %s cluster repository.
           --#ARGUMENTS    {1,2,3}
           --#SEVERITY     INFORMATIONAL
           --#TIMEINDEX    99
           --#STATE        OK
       ::= { fluidFSEventsComponent 321 } 
    
    
    fluidFSEventComponentLocalUsersModifySuccess NOTIFICATION-TYPE
       OBJECTS { sysName, fluidFSEventsParamsComponentUserName, fluidFSEventsParamsComponentLocalAccountName, fluidFSEventsParamsComponentTenantId }
       STATUS current
       DESCRIPTION
           "The user {{userName}} has successfully modified Local User '{{localAccountName}}' in {{TenantName}} cluster repository."
           --#TYPE         "Normal Event"
           --#SUMMARY      The user %s has successfully modified Local User '%s' in %s cluster repository.
           --#ARGUMENTS    {1,2,3}
           --#SEVERITY     INFORMATIONAL
           --#TIMEINDEX    99
           --#STATE        OK
       ::= { fluidFSEventsComponent 322 } 
    
    
    fluidFSEventComponentLocalGroupsCreateSuccess NOTIFICATION-TYPE
       OBJECTS { sysName, fluidFSEventsParamsComponentUserName, fluidFSEventsParamsComponentLocalAccountName, fluidFSEventsParamsComponentTenantId }
       STATUS current
       DESCRIPTION
           "The user {{userName}} has successfully added new Local Group '{{localAccountName}}' to {{TenantName}} cluster repository."
           --#TYPE         "Normal Event"
           --#SUMMARY      The user %s has successfully added new Local Group '%s' to %s cluster repository.
           --#ARGUMENTS    {1,2,3}
           --#SEVERITY     INFORMATIONAL
           --#TIMEINDEX    99
           --#STATE        OK
       ::= { fluidFSEventsComponent 323 } 
    
    
    fluidFSEventComponentLocalGroupsDeleteSuccess NOTIFICATION-TYPE
       OBJECTS { sysName, fluidFSEventsParamsComponentUserName, fluidFSEventsParamsComponentLocalAccountName, fluidFSEventsParamsComponentTenantId }
       STATUS current
       DESCRIPTION
           "The user {{userName}} has successfully deleted Local Group '{{localAccountName}}' from {{TenantName}} cluster repository."
           --#TYPE         "Normal Event"
           --#SUMMARY      The user %s has successfully deleted Local Group '%s' from %s cluster repository.
           --#ARGUMENTS    {1,2,3}
           --#SEVERITY     INFORMATIONAL
           --#TIMEINDEX    99
           --#STATE        OK
       ::= { fluidFSEventsComponent 324 } 
    
    
    fluidFSEventComponentLocalGroupsModifySuccess NOTIFICATION-TYPE
       OBJECTS { sysName, fluidFSEventsParamsComponentUserName, fluidFSEventsParamsComponentLocalAccountName, fluidFSEventsParamsComponentTenantId }
       STATUS current
       DESCRIPTION
           "The user {{userName}} has successfully modified Local Group '{{localAccountName}}' in {{TenantName}} cluster repository."
           --#TYPE         "Normal Event"
           --#SUMMARY      The user %s has successfully modified Local Group '%s' in %s cluster repository.
           --#ARGUMENTS    {1,2,3}
           --#SEVERITY     INFORMATIONAL
           --#TIMEINDEX    99
           --#STATE        OK
       ::= { fluidFSEventsComponent 325 } 
    
    
    fluidFSEventComponentUserDatabaseModifySuccess NOTIFICATION-TYPE
       OBJECTS { sysName, fluidFSEventsParamsComponentUserName, fluidFSEventsParamsComponentUserDatabaseType, fluidFSEventsParamsComponentTenantId }
       STATUS current
       DESCRIPTION
           "The user {{userName}} has successfully re-configured UNIX external repository of {{TenantName}} to use '{{userDatabaseType}}' accounts database."
           --#TYPE         "Normal Event"
           --#SUMMARY      The user %s has successfully re-configured UNIX external repository of %s to use '%s' accounts database.
           --#ARGUMENTS    {1,2,3}
           --#SEVERITY     INFORMATIONAL
           --#TIMEINDEX    99
           --#STATE        OK
       ::= { fluidFSEventsComponent 326 } 
    
    
    fluidFSEventComponentMappingPolicyModifySuccess NOTIFICATION-TYPE
       OBJECTS { sysName, fluidFSEventsParamsComponentUserName, fluidFSEventsParamsComponentTenantId }
       STATUS current
       DESCRIPTION
           "The user {{userName}} has successfully re-configured users mapping policy of {{TenantName}}."
           --#TYPE         "Normal Event"
           --#SUMMARY      The user %s has successfully re-configured users mapping policy of %s.
           --#ARGUMENTS    {1,2}
           --#SEVERITY     INFORMATIONAL
           --#TIMEINDEX    99
           --#STATE        OK
       ::= { fluidFSEventsComponent 327 } 
    
    
    fluidFSEventComponentManualMappingsCreateSuccess NOTIFICATION-TYPE
       OBJECTS { sysName, fluidFSEventsParamsComponentUserName, fluidFSEventsParamsComponentWindowsUser, fluidFSEventsParamsComponentUnixUser, fluidFSEventsParamsComponentTenantId }
       STATUS current
       DESCRIPTION
           "The user {{userName}} has successfully added new manual mapping rule between Windows user '{{windowsUserName}}' and UNIX user '{{unixUserName}}' on {{TenantName}}."
           --#TYPE         "Normal Event"
           --#SUMMARY      The user %s has successfully added new manual mapping rule between Windows user '%s' and UNIX user '%s' on %s.
           --#ARGUMENTS    {1,2,3,4}
           --#SEVERITY     INFORMATIONAL
           --#TIMEINDEX    99
           --#STATE        OK
       ::= { fluidFSEventsComponent 328 } 
    
    
    fluidFSEventComponentManualMappingsDeleteSuccess NOTIFICATION-TYPE
       OBJECTS { sysName, fluidFSEventsParamsComponentUserName, fluidFSEventsParamsComponentWindowsUser, fluidFSEventsParamsComponentUnixUser, fluidFSEventsParamsComponentTenantId }
       STATUS current
       DESCRIPTION
           "The user {{userName}} has successfully deleted manual mapping rule between Windows user '{{windowsUserName}}' and UNIX user '{{unixUserName}}' on {{TenantName}}."
           --#TYPE         "Normal Event"
           --#SUMMARY      The user %s has successfully deleted manual mapping rule between Windows user '%s' and UNIX user '%s' on %s.
           --#ARGUMENTS    {1,2,3,4}
           --#SEVERITY     INFORMATIONAL
           --#TIMEINDEX    99
           --#STATE        OK
       ::= { fluidFSEventsComponent 329 } 
    
    
    fluidFSEventComponentManualMappingsModifySuccess NOTIFICATION-TYPE
       OBJECTS { sysName, fluidFSEventsParamsComponentUserName, fluidFSEventsParamsComponentWindowsUser, fluidFSEventsParamsComponentUnixUser, fluidFSEventsParamsComponentTenantId }
       STATUS current
       DESCRIPTION
           "The user {{userName}} has successfully modified manual mapping rule between Windows user '{{windowsUserName}}' and UNIX user '{{unixUserName}}' on {{TenantName}}."
           --#TYPE         "Normal Event"
           --#SUMMARY      The user %s has successfully modified manual mapping rule between Windows user '%s' and UNIX user '%s' on %s.
           --#ARGUMENTS    {1,2,3,4}
           --#SEVERITY     INFORMATIONAL
           --#TIMEINDEX    99
           --#STATE        OK
       ::= { fluidFSEventsComponent 330 } 
    
    
    fluidFSEventComponentQuotaRuleCreateSuccess NOTIFICATION-TYPE
       OBJECTS { sysName, fluidFSEventsParamsComponentUserName, fluidFSEventsParamsComponentFSID }
       STATUS current
       DESCRIPTION
           "The user {{userName}} created quota rule on volume {{FSIDName}}."
           --#TYPE         "Normal Event"
           --#SUMMARY      The user %s created quota rule on volume %s.
           --#ARGUMENTS    {1,2}
           --#SEVERITY     INFORMATIONAL
           --#TIMEINDEX    99
           --#STATE        OK
       ::= { fluidFSEventsComponent 331 } 
    
    
    fluidFSEventComponentQuotaRuleModifySuccess NOTIFICATION-TYPE
       OBJECTS { sysName, fluidFSEventsParamsComponentUserName, fluidFSEventsParamsComponentFSID }
       STATUS current
       DESCRIPTION
           "The user {{userName}} modified quota rule on volume {{FSIDName}}."
           --#TYPE         "Normal Event"
           --#SUMMARY      The user %s modified quota rule on volume %s.
           --#ARGUMENTS    {1,2}
           --#SEVERITY     INFORMATIONAL
           --#TIMEINDEX    99
           --#STATE        OK
       ::= { fluidFSEventsComponent 332 } 
    
    
    fluidFSEventComponentQuotaRuleDeleteSuccess NOTIFICATION-TYPE
       OBJECTS { sysName, fluidFSEventsParamsComponentUserName, fluidFSEventsParamsComponentFSID }
       STATUS current
       DESCRIPTION
           "The user {{userName}} deleted quota rule on volume {{FSIDName}}."
           --#TYPE         "Normal Event"
           --#SUMMARY      The user %s deleted quota rule on volume %s.
           --#ARGUMENTS    {1,2}
           --#SEVERITY     INFORMATIONAL
           --#TIMEINDEX    99
           --#STATE        OK
       ::= { fluidFSEventsComponent 333 } 
    
    
    fluidFSEventComponentCifsProtocolModifySuccess NOTIFICATION-TYPE
       OBJECTS { sysName, fluidFSEventsParamsComponentUserName, fluidFSEventsParamsComponentTenantId }
       STATUS current
       DESCRIPTION
           "The user {{userName}} updated the general local users settings of {{TenantName}}."
           --#TYPE         "Normal Event"
           --#SUMMARY      The user %s updated the general local users settings of %s.
           --#ARGUMENTS    {1,2}
           --#SEVERITY     INFORMATIONAL
           --#TIMEINDEX    99
           --#STATE        OK
       ::= { fluidFSEventsComponent 334 } 
    
    
    fluidFSEventComponentFileCloningSuccess NOTIFICATION-TYPE
       OBJECTS { sysName, fluidFSEventsParamsComponentUserName, fluidFSEventsParamsComponentFSID, fluidFSEventsParamsComponentSourceFilePath, fluidFSEventsParamsComponentDestinationDir, fluidFSEventsParamsComponentDestinationFileName }
       STATUS current
       DESCRIPTION
           "The user {{userName}} cloned ({{FSIDName}}){{SourceFilePath}} to ({{FSIDName}}){{DestinationDir}}/{{DestinationFileName}}."
           --#TYPE         "Normal Event"
           --#SUMMARY      The user %s cloned (%s)%s to (%s)%s/%s.
           --#ARGUMENTS    {1,2,3,4,5}
           --#SEVERITY     INFORMATIONAL
           --#TIMEINDEX    99
           --#STATE        OK
       ::= { fluidFSEventsComponent 335 } 
    
    
    fluidFSEventComponentFolderCreateSuccess NOTIFICATION-TYPE
       OBJECTS { sysName, fluidFSEventsParamsComponentUserName, fluidFSEventsParamsComponentFSID, fluidFSEventsParamsComponentDestinationParentDir, fluidFSEventsParamsComponentDestinationDir }
       STATUS current
       DESCRIPTION
           "The user {{userName}} created {{DestinationParentDir}}/{{DestinationDir}} directory on NAS volume {{FSIDName}}."
           --#TYPE         "Normal Event"
           --#SUMMARY      The user %s created %s/%s directory on NAS volume %s.
           --#ARGUMENTS    {1,2,3,4}
           --#SEVERITY     INFORMATIONAL
           --#TIMEINDEX    99
           --#STATE        OK
       ::= { fluidFSEventsComponent 336 } 
    
    
    fluidFSEventComponentNfsProtocolModifySuccess NOTIFICATION-TYPE
       OBJECTS { sysName, fluidFSEventsParamsComponentUserName, fluidFSEventsParamsComponentTenantId }
       STATUS current
       DESCRIPTION
           "The user {{userName}} updated the general NFS settings of {{TenantName}}."
           --#TYPE         "Normal Event"
           --#SUMMARY      The user %s updated the general NFS settings of %s.
           --#ARGUMENTS    {1,2}
           --#SEVERITY     INFORMATIONAL
           --#TIMEINDEX    99
           --#STATE        OK
       ::= { fluidFSEventsComponent 337 } 
    
    
    fluidFSEventComponentVirtualVolumeFolderCreateSuccess NOTIFICATION-TYPE
       OBJECTS { sysName, fluidFSEventsParamsComponentUserName, fluidFSEventsParamsComponentVirtualVolumeFolderName, fluidFSEventsParamsComponentTenantId }
       STATUS current
       DESCRIPTION
           "The user {{userName}} created {{VirtualVolumeFolderName}} NAS volumes folder on {{TenantName}}."
           --#TYPE         "Normal Event"
           --#SUMMARY      The user %s created %s NAS volumes folder on %s.
           --#ARGUMENTS    {1,2,3}
           --#SEVERITY     INFORMATIONAL
           --#TIMEINDEX    99
           --#STATE        OK
       ::= { fluidFSEventsComponent 338 } 
    
    
    fluidFSEventComponentVirtualVolumeFolderModifySuccess NOTIFICATION-TYPE
       OBJECTS { sysName, fluidFSEventsParamsComponentUserName, fluidFSEventsParamsComponentVirtualVolumeFolderName, fluidFSEventsParamsComponentTenantId }
       STATUS current
       DESCRIPTION
           "The user {{userName}} updated {{VirtualVolumeFolderName}} NAS volumes folder on {{TenantName}}."
           --#TYPE         "Normal Event"
           --#SUMMARY      The user %s updated %s NAS volumes folder on %s.
           --#ARGUMENTS    {1,2,3}
           --#SEVERITY     INFORMATIONAL
           --#TIMEINDEX    99
           --#STATE        OK
       ::= { fluidFSEventsComponent 339 } 
    
    
    fluidFSEventComponentVirtualVolumeFolderDeleteSuccess NOTIFICATION-TYPE
       OBJECTS { sysName, fluidFSEventsParamsComponentUserName, fluidFSEventsParamsComponentVirtualVolumeFolderName, fluidFSEventsParamsComponentTenantId }
       STATUS current
       DESCRIPTION
           "The user {{userName}} deleted {{VirtualVolumeFolderName}} NAS volumes folder on {{TenantName}}."
           --#TYPE         "Normal Event"
           --#SUMMARY      The user %s deleted %s NAS volumes folder on %s.
           --#ARGUMENTS    {1,2,3}
           --#SEVERITY     INFORMATIONAL
           --#TIMEINDEX    99
           --#STATE        OK
       ::= { fluidFSEventsComponent 340 } 
    
    
    fluidFSEventComponentRunHdfsDiagnosticSuccess NOTIFICATION-TYPE
       OBJECTS { sysName, fluidFSEventsParamsComponentUserName }
       STATUS current
       DESCRIPTION
           "The user {{userName}} ran HDFS diagnostic.   Description:  The user {{userName}} ran HDFS diagnostic."
           --#TYPE         "Normal Event"
           --#SUMMARY      The user %s ran HDFS diagnostic.   Description:  The user %s ran HDFS diagnostic.
           --#ARGUMENTS    {1}
           --#SEVERITY     INFORMATIONAL
           --#TIMEINDEX    99
           --#STATE        OK
       ::= { fluidFSEventsComponent 341 } 
    
    
    fluidFSEventComponentRunHdfsDiagnosticActionFailure NOTIFICATION-TYPE
       OBJECTS { sysName, fluidFSEventsParamsComponentUserName, fluidFSEventsParamsComponentRetcodeString }
       STATUS current
       DESCRIPTION
           "Hdfs diagnostic failed.   Description:  Hdfs diagnostic, which was run by user {{userName}} failed.[[nl]]{{retcodeString}}"
           --#TYPE         "Normal Event"
           --#SUMMARY      Hdfs diagnostic failed.   Description:  Hdfs diagnostic, which was run by user %s failed.[[nl]]%s
           --#ARGUMENTS    {1,2}
           --#SEVERITY     MAJOR
           --#TIMEINDEX    99
           --#STATE        OK
       ::= { fluidFSEventsComponent 342 } 
    
    
    fluidFSEventComponentReplicationModifyRetPolicy NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has modified the replication snapshot retention.   Description:  The user {{userName}} has modified the replication snapshot retention policy for replication between {{FSIDName}} and {{remoteVolume}}@{{remoteSystemName}} volumes."
           --#TYPE         "Normal Event"
           --#SUMMARY      The user %s has modified the replication snapshot retention.   Description:  The user %s has modified the replication snapshot retention policy for replication between %s and %s@%s volumes.
           --#ARGUMENTS    {1,2,3,4}
           --#SEVERITY     INFORMATIONAL
           --#TIMEINDEX    99
           --#STATE        OK
       ::= { fluidFSEventsComponent 343 } 
    
    
    fluidFSEventComponentHdfsDiagnosticsFailed NOTIFICATION-TYPE
       OBJECTS { sysName, fluidFSEventsParamsComponentRetcodeString }
       STATUS current
       DESCRIPTION
           "Failed to generate diagnostics package for 'HdfsDiagnostics'. {{retcodeString}}"
           --#TYPE         "Normal Event"
           --#SUMMARY      Failed to generate diagnostics package for 'HdfsDiagnostics'. %s
           --#ARGUMENTS    {1}
           --#SEVERITY     MAJOR
           --#TIMEINDEX    99
           --#STATE        OK
       ::= { fluidFSEventsComponent 344 } 
    
    
    fluidFSEventComponentHdfsDiagnosticsOk NOTIFICATION-TYPE
       OBJECTS { sysName }
       STATUS current
       DESCRIPTION
           "Package generation for 'HdfsDiagnostics' completed successfully."
           --#TYPE         "Normal Event"
           --#SUMMARY      Package generation for 'HdfsDiagnostics' completed successfully.
           --#ARGUMENTS    {}
           --#SEVERITY     INFORMATIONAL
           --#TIMEINDEX    99
           --#STATE        OK
       ::= { fluidFSEventsComponent 345 } 
    
    
    fluidFSEventComponentActiveDirectoryPreferredDcSuccess NOTIFICATION-TYPE
       OBJECTS { sysName, fluidFSEventsParamsComponentUserName, fluidFSEventsParamsComponentTenantId }
       STATUS current
       DESCRIPTION
           "The user {{userName}} has successfully configured preferred domain controllers of {{TenantName}}."
           --#TYPE         "Normal Event"
           --#SUMMARY      The user %s has successfully configured preferred domain controllers of %s.
           --#ARGUMENTS    {1,2}
           --#SEVERITY     INFORMATIONAL
           --#TIMEINDEX    99
           --#STATE        OK
       ::= { fluidFSEventsComponent 346 } 
    
    
    fluidFSEventComponentFileCopySuccess NOTIFICATION-TYPE
       OBJECTS { sysName, fluidFSEventsParamsComponentUserName, fluidFSEventsParamsComponentSourceFilePath, fluidFSEventsParamsComponentSourceFSID, fluidFSEventsParamsComponentDestinationFSID, fluidFSEventsParamsComponentDestinationFilePath }
       STATUS current
       DESCRIPTION
           "The user {{userName}} copied {{SourceFSIDName}}\{{SourceFilePath}} to {{DestinationFSIDName}}\{{DestinationFilePath}}."
           --#TYPE         "Normal Event"
           --#SUMMARY      The user %s copied %s\%s to %s\%s.
           --#ARGUMENTS    {1,2,3,4,5}
           --#SEVERITY     INFORMATIONAL
           --#TIMEINDEX    99
           --#STATE        OK
       ::= { fluidFSEventsComponent 347 } 
    
    
    fluidFSEventComponentFileCopyFailure NOTIFICATION-TYPE
       OBJECTS { sysName, fluidFSEventsParamsComponentUserName, fluidFSEventsParamsComponentSourceFilePath, fluidFSEventsParamsComponentSourceFSID, fluidFSEventsParamsComponentDestinationFSID, fluidFSEventsParamsComponentDestinationFilePath }
       STATUS current
       DESCRIPTION
           "The user {{userName}} failed to copy {{SourceFSIDName}}\{{SourceFilePath}} to {{DestinationFSIDName}}\{{DestinationFilePath}}."
           --#TYPE         "Normal Event"
           --#SUMMARY      The user %s failed to copy %s\%s to %s\%s.
           --#ARGUMENTS    {1,2,3,4,5}
           --#SEVERITY     INFORMATIONAL
           --#TIMEINDEX    99
           --#STATE        OK
       ::= { fluidFSEventsComponent 348 } 
    
    
    fluidFSEventComponentLogoffActiveProtocolSessionGeneralSuccess NOTIFICATION-TYPE
       OBJECTS { sysName, fluidFSEventsParamsComponentTenantId, fluidFSEventsParamsComponentAdministrator, fluidFSEventsParamsComponentClientProtocol, fluidFSEventsParamsComponentClientProtocolDetails }
       STATUS current
       DESCRIPTION
           "NAS Administrator '{{administrator}}' closed {{ClientProtocol}} connection(s) on {{TenantName}}. Filter details: {{ClientProtocolDetails}}"
           --#TYPE         "Normal Event"
           --#SUMMARY      NAS Administrator '%s' closed %s connection(s) on %s. Filter details: %s
           --#ARGUMENTS    {1,2,3,4}
           --#SEVERITY     INFORMATIONAL
           --#TIMEINDEX    99
           --#STATE        OK
       ::= { fluidFSEventsComponent 349 } 
    
    
    fluidFSEventComponentCloseOpenFileGeneralSuccess NOTIFICATION-TYPE
       OBJECTS { sysName, fluidFSEventsParamsComponentTenantId, fluidFSEventsParamsComponentAdministrator, fluidFSEventsParamsComponentClientProtocolDetails }
       STATUS current
       DESCRIPTION
           "NAS Administrator '{{administrator}}' closed file(s) on {{TenantName}}. Filter details: {{ClientProtocolDetails}}"
           --#TYPE         "Normal Event"
           --#SUMMARY      NAS Administrator '%s' closed file(s) on %s. Filter details: %s
           --#ARGUMENTS    {1,2,3}
           --#SEVERITY     INFORMATIONAL
           --#TIMEINDEX    99
           --#STATE        OK
       ::= { fluidFSEventsComponent 350 } 
    
    
    fluidFSEventComponentFlashClusterSuccessEvent NOTIFICATION-TYPE
       OBJECTS { sysName, fluidFSEventsParamsComponentUserName, fluidFSEventsParamsComponentServicePackFileName }
       STATUS current
       DESCRIPTION
           "{{userName}} successfully flashed cluster with service pack file {{servicePackFileName}}."
           --#TYPE         "Normal Event"
           --#SUMMARY      %s successfully flashed cluster with service pack file %s.
           --#ARGUMENTS    {1,2}
           --#SEVERITY     INFORMATIONAL
           --#TIMEINDEX    99
           --#STATE        OK
       ::= { fluidFSEventsComponent 351 } 
    
    
    fluidFSEventComponentFlashClusterFailedEvent NOTIFICATION-TYPE
       OBJECTS { sysName, fluidFSEventsParamsComponentUserName, fluidFSEventsParamsComponentServicePackFileName, fluidFSEventsParamsComponentRetcodeString }
       STATUS current
       DESCRIPTION
           "{{userName}} failed to flash cluster with service pack file {{servicePackFileName}}. {{retcodeString}}."
           --#TYPE         "Normal Event"
           --#SUMMARY      %s failed to flash cluster with service pack file %s. %s.
           --#ARGUMENTS    {1,2,3}
           --#SEVERITY     MAJOR
           --#TIMEINDEX    99
           --#STATE        OK
       ::= { fluidFSEventsComponent 352 } 
    
    
    fluidFSEventComponentSmbShareSecurityDescriptorModifySuccess NOTIFICATION-TYPE
       OBJECTS { sysName, fluidFSEventsParamsComponentUserName, fluidFSEventsParamsComponentShareName, fluidFSEventsParamsComponentFSID }
       STATUS current
       DESCRIPTION
           "The user {{userName}} modified ACL on the root folder of SMB share {{shareName}} on NAS volume {{FSIDName}}."
           --#TYPE         "Normal Event"
           --#SUMMARY      The user %s modified ACL on the root folder of SMB share %s on NAS volume %s.
           --#ARGUMENTS    {1,2,3}
           --#SEVERITY     INFORMATIONAL
           --#TIMEINDEX    99
           --#STATE        OK
       ::= { fluidFSEventsComponent 353 } 
    
    
    fluidFSEventComponentRedirectionFolderAddSuccess NOTIFICATION-TYPE
       OBJECTS { sysName, fluidFSEventsParamsComponentUserName, fluidFSEventsParamsComponentFSID, fluidFSEventsParamsComponentFolderPath }
       STATUS current
       DESCRIPTION
           "The user {{userName}} added redirection on the folder {{FolderPath}} on NAS volume {{FSIDName}}."
           --#TYPE         "Normal Event"
           --#SUMMARY      The user %s added redirection on the folder %s on NAS volume %s.
           --#ARGUMENTS    {1,2,3}
           --#SEVERITY     INFORMATIONAL
           --#TIMEINDEX    99
           --#STATE        OK
       ::= { fluidFSEventsComponent 354 } 
    
    
    fluidFSEventComponentRedirectionFolderModifySuccess NOTIFICATION-TYPE
       OBJECTS { sysName, fluidFSEventsParamsComponentUserName, fluidFSEventsParamsComponentFSID, fluidFSEventsParamsComponentDSID }
       STATUS current
       DESCRIPTION
           "The user {{userName}} modified redirection on the folder {{DSIDPath}} on NAS volume {{FSIDName}}."
           --#TYPE         "Normal Event"
           --#SUMMARY      The user %s modified redirection on the folder %s on NAS volume %s.
           --#ARGUMENTS    {1,2,3}
           --#SEVERITY     INFORMATIONAL
           --#TIMEINDEX    99
           --#STATE        OK
       ::= { fluidFSEventsComponent 355 } 
    
    
    fluidFSEventComponentRedirectionFolderDeleteSuccess NOTIFICATION-TYPE
       OBJECTS { sysName, fluidFSEventsParamsComponentUserName, fluidFSEventsParamsComponentFSID, fluidFSEventsParamsComponentDSID }
       STATUS current
       DESCRIPTION
           "The user {{userName}} deleted redirection on the folder {{DSIDPath}} on NAS volume {{FSIDName}}."
           --#TYPE         "Normal Event"
           --#SUMMARY      The user %s deleted redirection on the folder %s on NAS volume %s.
           --#ARGUMENTS    {1,2,3}
           --#SEVERITY     INFORMATIONAL
           --#TIMEINDEX    99
           --#STATE        OK
       ::= { fluidFSEventsComponent 356 } 
    
    
    fluidFSEventComponentFtpProtocolModifySuccess NOTIFICATION-TYPE
       OBJECTS { sysName, fluidFSEventsParamsComponentUserName, fluidFSEventsParamsComponentTenantId }
       STATUS current
       DESCRIPTION
           "The user {{userName}} updated the FTP configuration of {{TenantName}}."
           --#TYPE         "Normal Event"
           --#SUMMARY      The user %s updated the FTP configuration of %s.
           --#ARGUMENTS    {1,2}
           --#SEVERITY     INFORMATIONAL
           --#TIMEINDEX    99
           --#STATE        OK
       ::= { fluidFSEventsComponent 357 } 
    
    
    fluidFSEventComponentReplicationActionModifyBwLimiterSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has modified the BW limiter for replication between {{FSIDName}} and {{remoteVolume}}@{{remoteSystemName}} NAS volumes."
           --#TYPE         "Normal Event"
           --#SUMMARY      The user %s has modified the BW limiter for replication between %s and %s@%s NAS volumes.
           --#ARGUMENTS    {1,2,3,4}
           --#SEVERITY     INFORMATIONAL
           --#TIMEINDEX    99
           --#STATE        OK
       ::= { fluidFSEventsComponent 358 } 
    
    
    fluidFSEventComponentGpoModifySuccess NOTIFICATION-TYPE
       OBJECTS { sysName, fluidFSEventsParamsComponentUserName, fluidFSEventsParamsComponentTenantId }
       STATUS current
       DESCRIPTION
           "GPO configuration of {{TenantName}} was modified successfully   Description:  The user {{userName}} has successfully modified the GPO configuration of {{TenantName}}."
           --#TYPE         "Normal Event"
           --#SUMMARY      GPO configuration of %s was modified successfully   Description:  The user %s has successfully modified the GPO configuration of %s.
           --#ARGUMENTS    {1,2}
           --#SEVERITY     INFORMATIONAL
           --#TIMEINDEX    99
           --#STATE        OK
       ::= { fluidFSEventsComponent 359 } 
    
    
    fluidFSEventComponentGpoTriggerSuccess NOTIFICATION-TYPE
       OBJECTS { sysName, fluidFSEventsParamsComponentUserName, fluidFSEventsParamsComponentTenantId }
       STATUS current
       DESCRIPTION
           "Group policy polling was triggered successfully on {{TenantName}}   Description:  The user {{userName}} has triggered group policy polling successfully on {{TenantName}}."
           --#TYPE         "Normal Event"
           --#SUMMARY      Group policy polling was triggered successfully on %s   Description:  The user %s has triggered group policy polling successfully on %s.
           --#ARGUMENTS    {1,2}
           --#SEVERITY     INFORMATIONAL
           --#TIMEINDEX    99
           --#STATE        OK
       ::= { fluidFSEventsComponent 360 } 
    
    
    fluidFSEventComponentTenantPublicIPsModifySuccess NOTIFICATION-TYPE
       OBJECTS { sysName, fluidFSEventsParamsComponentUserName, fluidFSEventsParamsComponentTenantId }
       STATUS current
       DESCRIPTION
           "The user {{userName}} updated the configuration of {{TenantName}} client network Public IPs."
           --#TYPE         "Normal Event"
           --#SUMMARY      The user %s updated the configuration of %s client network Public IPs.
           --#ARGUMENTS    {1,2}
           --#SEVERITY     INFORMATIONAL
           --#TIMEINDEX    99
           --#STATE        OK
       ::= { fluidFSEventsComponent 361 } 
    
    
    fluidFSEventComponentReplicationActionModifyCompressionAndDedupSuccess NOTIFICATION-TYPE
       OBJECTS { sysName, fluidFSEventsParamsComponentUserName, fluidFSEventsParamsComponentFSID, fluidFSEventsParamsComponentRemoteVolume, fluidFSEventsParamsComponentRemoteSystemName }
       STATUS current
       DESCRIPTION
           "The user {{userName}} has modifyed the compression and deduplication mode for replication between {{FSIDName}} and {{remoteVolume}}@{{remoteSystemName}} NAS volumes."
           --#TYPE         "Normal Event"
           --#SUMMARY      The user %s has modifyed the compression and deduplication mode for replication between %s and %s@%s NAS volumes.
           --#ARGUMENTS    {1,2,3,4}
           --#SEVERITY     INFORMATIONAL
           --#TIMEINDEX    99
           --#STATE        OK
       ::= { fluidFSEventsComponent 362 } 
    
    
    fluidFSEventComponentExampleActionSyncSuccess NOTIFICATION-TYPE
       OBJECTS { sysName }
       STATUS current
       DESCRIPTION
           "Example action with sync succeeded."
           --#TYPE         "Normal Event"
           --#SUMMARY      Example action with sync succeeded.
           --#ARGUMENTS    {}
           --#SEVERITY     INFORMATIONAL
           --#TIMEINDEX    99
           --#STATE        OK
       ::= { fluidFSEventsComponent 363 } 
    
    
    fluidFSEventComponentExampleActionSyncFailed NOTIFICATION-TYPE
       OBJECTS { sysName, fluidFSEventsParamsComponentRetcodeString }
       STATUS current
       DESCRIPTION
           "Failed to perform example action with sync. Error: {{retcodeString}}."
           --#TYPE         "Normal Event"
           --#SUMMARY      Failed to perform example action with sync. Error: %s.
           --#ARGUMENTS    {1}
           --#SEVERITY     MAJOR
           --#TIMEINDEX    99
           --#STATE        OK
       ::= { fluidFSEventsComponent 364 } 
    
    
    fluidFSEventComponentAdminSubnetModifySuccess NOTIFICATION-TYPE
       OBJECTS { sysName, fluidFSEventsParamsComponentUserName, fluidFSEventsParamsComponentNetworkId, fluidFSEventsParamsComponentPrefix, fluidFSEventsParamsComponentState }
       STATUS current
       DESCRIPTION
           "Management subnet {{networkId}}/{{prefix}} was successfully modified by {{userName}}. State is {{state}}"
           --#TYPE         "Normal Event"
           --#SUMMARY      Management subnet %s/%s was successfully modified by %s. State is %s
           --#ARGUMENTS    {1,2,3,4}
           --#SEVERITY     INFORMATIONAL
           --#TIMEINDEX    99
           --#STATE        OK
       ::= { fluidFSEventsComponent 365 } 
    
    
    fluidFSEventComponentTriggerPhoneHomeSuccess NOTIFICATION-TYPE
       OBJECTS { sysName, fluidFSEventsParamsComponentUserName }
       STATUS current
       DESCRIPTION
           "The user {{userName}} triggered phone home."
           --#TYPE         "Normal Event"
           --#SUMMARY      The user %s triggered phone home.
           --#ARGUMENTS    {1}
           --#SEVERITY     INFORMATIONAL
           --#TIMEINDEX    99
           --#STATE        OK
       ::= { fluidFSEventsComponent 366 } 
    
    
    fluidFSEventComponentInterfaceRolesModifySuccess NOTIFICATION-TYPE
       OBJECTS { sysName, fluidFSEventsParamsComponentUserName, fluidFSEventsParamsComponentApplianceId }
       STATUS current
       DESCRIPTION
           "Interface Roles for NAS Appliance {{applianceId}} were successfully modified by user {{userName}}."
           --#TYPE         "Normal Event"
           --#SUMMARY      Interface Roles for NAS Appliance %s were successfully modified by user %s.
           --#ARGUMENTS    {1,2}
           --#SEVERITY     INFORMATIONAL
           --#TIMEINDEX    99
           --#STATE        OK
       ::= { fluidFSEventsComponent 367 } 
    
    
    fluidFSEventComponentSmbDiagnosticOk NOTIFICATION-TYPE
       OBJECTS { sysName }
       STATUS current
       DESCRIPTION
           "Package generation for 'SMB Diagnostics' completed successfully."
           --#TYPE         "Normal Event"
           --#SUMMARY      Package generation for 'SMB Diagnostics' completed successfully.
           --#ARGUMENTS    {}
           --#SEVERITY     INFORMATIONAL
           --#TIMEINDEX    99
           --#STATE        OK
       ::= { fluidFSEventsComponent 368 } 
    
    
    fluidFSEventComponentSmbDiagnosticFailed NOTIFICATION-TYPE
       OBJECTS { sysName, fluidFSEventsParamsComponentRetcodeString }
       STATUS current
       DESCRIPTION
           "Failed to generate diagnostics package for 'SMB Diagnostics'. {{retcodeString}}"
           --#TYPE         "Normal Event"
           --#SUMMARY      Failed to generate diagnostics package for 'SMB Diagnostics'. %s
           --#ARGUMENTS    {1}
           --#SEVERITY     MAJOR
           --#TIMEINDEX    99
           --#STATE        OK
       ::= { fluidFSEventsComponent 369 } 
    
    
    fluidFSEventComponentNfsDiagnosticOk NOTIFICATION-TYPE
       OBJECTS { sysName }
       STATUS current
       DESCRIPTION
           "Package generation for 'NFS Diagnostics' completed successfully."
           --#TYPE         "Normal Event"
           --#SUMMARY      Package generation for 'NFS Diagnostics' completed successfully.
           --#ARGUMENTS    {}
           --#SEVERITY     INFORMATIONAL
           --#TIMEINDEX    99
           --#STATE        OK
       ::= { fluidFSEventsComponent 370 } 
    
    
    fluidFSEventComponentNfsDiagnosticFailed NOTIFICATION-TYPE
       OBJECTS { sysName, fluidFSEventsParamsComponentRetcodeString }
       STATUS current
       DESCRIPTION
           "Failed to generate diagnostics package for 'NFS Diagnostics'. {{retcodeString}}"
           --#TYPE         "Normal Event"
           --#SUMMARY      Failed to generate diagnostics package for 'NFS Diagnostics'. %s
           --#ARGUMENTS    {1}
           --#SEVERITY     MAJOR
           --#TIMEINDEX    99
           --#STATE        OK
       ::= { fluidFSEventsComponent 371 } 
    
    
    fluidFSEventComponentFtpDiagnosticOk NOTIFICATION-TYPE
       OBJECTS { sysName }
       STATUS current
       DESCRIPTION
           "Package generation for 'FTP Diagnostics' completed successfully."
           --#TYPE         "Normal Event"
           --#SUMMARY      Package generation for 'FTP Diagnostics' completed successfully.
           --#ARGUMENTS    {}
           --#SEVERITY     INFORMATIONAL
           --#TIMEINDEX    99
           --#STATE        OK
       ::= { fluidFSEventsComponent 372 } 
    
    
    fluidFSEventComponentFtpDiagnosticFailed NOTIFICATION-TYPE
       OBJECTS { sysName, fluidFSEventsParamsComponentRetcodeString }
       STATUS current
       DESCRIPTION
           "Failed to generate diagnostics package for 'FTP Diagnostics'. {{retcodeString}}"
           --#TYPE         "Normal Event"
           --#SUMMARY      Failed to generate diagnostics package for 'FTP Diagnostics'. %s
           --#ARGUMENTS    {1}
           --#SEVERITY     MAJOR
           --#TIMEINDEX    99
           --#STATE        OK
       ::= { fluidFSEventsComponent 373 } 
    
    
    fluidFSEventComponentActiveDirectorySetKrbCompoundAuthSuccess NOTIFICATION-TYPE
       OBJECTS { sysName, fluidFSEventsParamsComponentUserName, fluidFSEventsParamsComponentTenantId }
       STATUS current
       DESCRIPTION
           "The user {{userName}} has successfully configured Kerberos Compound Authentication support for the cluster {{TenantName}}."
           --#TYPE         "Normal Event"
           --#SUMMARY      The user %s has successfully configured Kerberos Compound Authentication support for the cluster %s.
           --#ARGUMENTS    {1,2}
           --#SEVERITY     INFORMATIONAL
           --#TIMEINDEX    99
           --#STATE        OK
       ::= { fluidFSEventsComponent 374 } 
    
    
    fluidFSEventComponentHdfsProtocolModifySuccess NOTIFICATION-TYPE
       OBJECTS { sysName, fluidFSEventsParamsComponentUserName, fluidFSEventsParamsComponentTenantId }
       STATUS current
       DESCRIPTION
           "The user {{userName}} updated the HDFS configuration of {{TenantName}}."
           --#TYPE         "Normal Event"
           --#SUMMARY      The user %s updated the HDFS configuration of %s.
           --#ARGUMENTS    {1,2}
           --#SEVERITY     INFORMATIONAL
           --#TIMEINDEX    99
           --#STATE        OK
       ::= { fluidFSEventsComponent 375 } 
    
    
    fluidFSEventsParamsSupportShell OBJECT IDENTIFIER ::= { fluidFSEventsParams 16 } 
    
    
    fluidFSEventsSupportShell OBJECT IDENTIFIER ::= { fluidFSEvents 16 } 
    
    
    fluidFSEventsParamsSupportShellNode OBJECT-TYPE
       SYNTAX  DisplayString
       MAX-ACCESS  read-only
       STATUS  current
       DESCRIPTION
           "Node name"
       ::= { fluidFSEventsParamsSupportShell 1 }
    
    
    fluidFSEventsParamsSupportShellCommand OBJECT-TYPE
       SYNTAX  DisplayString
       MAX-ACCESS  read-only
       STATUS  current
       DESCRIPTION
           "Command executed in support shell"
       ::= { fluidFSEventsParamsSupportShell 2 }
    
    
    fluidFSEventsParamsSupportShellUserName OBJECT-TYPE
       SYNTAX  DisplayString
       MAX-ACCESS  read-only
       STATUS  current
       DESCRIPTION
           ""
       ::= { fluidFSEventsParamsSupportShell 3 }
    
    
    fluidFSEventSupportShellSecureConsoleAccessDisabledReservation NOTIFICATION-TYPE
       OBJECTS { sysName, fluidFSEventsParamsSupportShellNode }
       STATUS current
       DESCRIPTION
           "Secure Console Access on NAS Controller {{node}} cannot be enabled   Description:  Secure Console Access session on NAS Controller {{node}} had been disconnected from the server side or the system is disabled on the reservation web server"
           --#TYPE         "Normal Event"
           --#SUMMARY      Secure Console Access on NAS Controller %s cannot be enabled   Description:  Secure Console Access session on NAS Controller %s had been disconnected from the server side or the system is disabled on the reservation web server
           --#ARGUMENTS    {1}
           --#SEVERITY     INFORMATIONAL
           --#TIMEINDEX    99
           --#STATE        OK
       ::= { fluidFSEventsSupportShell 4 } 
    
    
    fluidFSEventSupportShellSecureConsoleAccessSshTunnelFailure NOTIFICATION-TYPE
       OBJECTS { sysName, fluidFSEventsParamsSupportShellNode }
       STATUS current
       DESCRIPTION
           "Secure Console Access failure on NAS Controller {{node}}   Description:  Secure Console Access session on NAS Controller {{node}} had been disconnected due to SSH tunnel failure"
           --#TYPE         "Normal Event"
           --#SUMMARY      Secure Console Access failure on NAS Controller %s   Description:  Secure Console Access session on NAS Controller %s had been disconnected due to SSH tunnel failure
           --#ARGUMENTS    {1}
           --#SEVERITY     MAJOR
           --#TIMEINDEX    99
           --#STATE        OK
       ::= { fluidFSEventsSupportShell 5 } 
    
    
    fluidFSEventSupportShellSecureConsoleAccessSessionStartFailed NOTIFICATION-TYPE
       OBJECTS { sysName, fluidFSEventsParamsSupportShellNode }
       STATUS current
       DESCRIPTION
           "Failed to establish the Secure Console Access session   Description:  Failed to establish the Secure Console Access session on NAS Controller {{node}} due to error response from the reservation web server"
           --#TYPE         "Normal Event"
           --#SUMMARY      Failed to establish the Secure Console Access session   Description:  Failed to establish the Secure Console Access session on NAS Controller %s due to error response from the reservation web server
           --#ARGUMENTS    {1}
           --#SEVERITY     MAJOR
           --#TIMEINDEX    99
           --#STATE        OK
       ::= { fluidFSEventsSupportShell 6 } 
    
    
    fluidFSEventSupportShellSecureConsoleAccessSessionExpired NOTIFICATION-TYPE
       OBJECTS { sysName, fluidFSEventsParamsSupportShellNode }
       STATUS current
       DESCRIPTION
           "Secure Console Access session on NAS Controller {{node}} had expired   Description:  Secure Console Access session on NAS Controller {{node}} had been disconnected due to TTL expiry"
           --#TYPE         "Normal Event"
           --#SUMMARY      Secure Console Access session on NAS Controller %s had expired   Description:  Secure Console Access session on NAS Controller %s had been disconnected due to TTL expiry
           --#ARGUMENTS    {1}
           --#SEVERITY     MAJOR
           --#TIMEINDEX    99
           --#STATE        OK
       ::= { fluidFSEventsSupportShell 7 } 
    
    
    fluidFSEventSupportShellSupportShellLogin NOTIFICATION-TYPE
       OBJECTS { sysName, fluidFSEventsParamsSupportShellUserName, fluidFSEventsParamsSupportShellNode }
       STATUS current
       DESCRIPTION
           "User logged-in into Support Shell   Description:  User {{userName}} logged-in into support shell in NAS Controller {{node}}"
           --#TYPE         "Normal Event"
           --#SUMMARY      User logged-in into Support Shell   Description:  User %s logged-in into support shell in NAS Controller %s
           --#ARGUMENTS    {1,2}
           --#SEVERITY     INFORMATIONAL
           --#TIMEINDEX    99
           --#STATE        OK
       ::= { fluidFSEventsSupportShell 8 } 
    
    
    fluidFSEventSupportShellSupportShellLogout NOTIFICATION-TYPE
       OBJECTS { sysName, fluidFSEventsParamsSupportShellUserName, fluidFSEventsParamsSupportShellNode }
       STATUS current
       DESCRIPTION
           "User logged-out from Support Shell   Description:  User {{userName}} logged-out from support shell in NAS Controller {{node}}"
           --#TYPE         "Normal Event"
           --#SUMMARY      User logged-out from Support Shell   Description:  User %s logged-out from support shell in NAS Controller %s
           --#ARGUMENTS    {1,2}
           --#SEVERITY     INFORMATIONAL
           --#TIMEINDEX    99
           --#STATE        OK
       ::= { fluidFSEventsSupportShell 9 } 
    
    
    fluidFSEventSupportShellSupportShellCommandInvokation NOTIFICATION-TYPE
       OBJECTS { sysName, fluidFSEventsParamsSupportShellUserName, fluidFSEventsParamsSupportShellCommand }
       STATUS current
       DESCRIPTION
           "User executed command in Support Shell   Description:  User {{userName}} executed command {{command}}"
           --#TYPE         "Normal Event"
           --#SUMMARY      User executed command in Support Shell   Description:  User %s executed command %s
           --#ARGUMENTS    {1,2}
           --#SEVERITY     INFORMATIONAL
           --#TIMEINDEX    99
           --#STATE        OK
       ::= { fluidFSEventsSupportShell 10 } 
    
    
    fluidFSEventsParamsAuditing OBJECT IDENTIFIER ::= { fluidFSEventsParams 17 } 
    
    
    fluidFSEventsAuditing OBJECT IDENTIFIER ::= { fluidFSEvents 17 } 
    
    
    fluidFSEventsParamsAuditingU OBJECT-TYPE
       SYNTAX  DisplayString
       MAX-ACCESS  read-only
       STATUS  current
       DESCRIPTION
           "User ID as seen from Samba - TUID. Will be translated to username by 'tuid2name' translator automatically"
       ::= { fluidFSEventsParamsAuditing 1 }
    
    
    fluidFSEventsParamsAuditingD OBJECT-TYPE
       SYNTAX  DisplayString
       MAX-ACCESS  read-only
       STATUS  current
       DESCRIPTION
           "DSID (internal filesystem ID) of file or directory. Use dsid2name utility to translate dsid to path."
       ::= { fluidFSEventsParamsAuditing 2 }
    
    
    fluidFSEventsParamsAuditingN OBJECT-TYPE
       SYNTAX  INTEGER
       MAX-ACCESS  read-only
       STATUS  current
       DESCRIPTION
           "NAS Volume ID (volume ID, i.e. FSID uint32 value). Will be translated to volume name by translator"
       ::= { fluidFSEventsParamsAuditing 3 }
    
    
    fluidFSEventsParamsAuditingDesiredCifsAccessMask OBJECT-TYPE
       SYNTAX  INTEGER
       MAX-ACCESS  read-only
       STATUS  current
       DESCRIPTION
           "Desired access mask"
       ::= { fluidFSEventsParamsAuditing 4 }
    
    
    fluidFSEventsParamsAuditingName OBJECT-TYPE
       SYNTAX  DisplayString
       MAX-ACCESS  read-only
       STATUS  current
       DESCRIPTION
           "Name"
       ::= { fluidFSEventsParamsAuditing 5 }
    
    
    fluidFSEventsParamsAuditingUName OBJECT-TYPE
       SYNTAX  DisplayString
       MAX-ACCESS  read-only
       STATUS  current
       DESCRIPTION
           ""
       ::= { fluidFSEventsParamsAuditing 6 }
    
    
    fluidFSEventsParamsAuditingNName OBJECT-TYPE
       SYNTAX  DisplayString
       MAX-ACCESS  read-only
       STATUS  current
       DESCRIPTION
           ""
       ::= { fluidFSEventsParamsAuditing 7 }
    
    
    fluidFSEventsParamsAuditingDPath OBJECT-TYPE
       SYNTAX  DisplayString
       MAX-ACCESS  read-only
       STATUS  current
       DESCRIPTION
           ""
       ::= { fluidFSEventsParamsAuditing 8 }
    
    
    fluidFSEventsParamsAuditingDesiredCifsAccessMaskName OBJECT-TYPE
       SYNTAX  DisplayString
       MAX-ACCESS  read-only
       STATUS  current
       DESCRIPTION
           ""
       ::= { fluidFSEventsParamsAuditing 9 }
    
    
    fluidFSEventAuditingSuccessfulAuditWrite NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Write by {{uName}} on {{nName}}/{{dPath}}   Description:  The User {{uName}} performed a successful write operation on file {{nName}}/{{dPath}}. The Desired access mask: {{desiredCifsAccessMaskName}}"
           --#TYPE         "Normal Event"
           --#SUMMARY      Successful Write by %s on %s/%s   Description:  The User %s performed a successful write operation on file %s/%s. The Desired access mask: %s
           --#ARGUMENTS    {1,2,3,4}
           --#SEVERITY     INFORMATIONAL
           --#TIMEINDEX    99
           --#STATE        OK
       ::= { fluidFSEventsAuditing 23 } 
    
    
    fluidFSEventAuditingSuccessfulAuditRead NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Read by {{uName}} on {{nName}}/{{dPath}}   Description:  The User {{uName}} performed a successful read operation on file {{nName}}/{{dPath}}. The Desired access mask: {{desiredCifsAccessMaskName}}"
           --#TYPE         "Normal Event"
           --#SUMMARY      Successful Read by %s on %s/%s   Description:  The User %s performed a successful read operation on file %s/%s. The Desired access mask: %s
           --#ARGUMENTS    {1,2,3,4}
           --#SEVERITY     INFORMATIONAL
           --#TIMEINDEX    99
           --#STATE        OK
       ::= { fluidFSEventsAuditing 24 } 
    
    
    fluidFSEventAuditingSuccessfulAuditDelete NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Delete by {{uName}} on {{nName}}/{{dPath}}   Description:  The User {{uName}} performed a successful delete operation on file {{nName}}/{{dPath}}. The Desired access mask: {{desiredCifsAccessMaskName}}"
           --#TYPE         "Normal Event"
           --#SUMMARY      Successful Delete by %s on %s/%s   Description:  The User %s performed a successful delete operation on file %s/%s. The Desired access mask: %s
           --#ARGUMENTS    {1,2,3,4}
           --#SEVERITY     INFORMATIONAL
           --#TIMEINDEX    99
           --#STATE        OK
       ::= { fluidFSEventsAuditing 25 } 
    
    
    fluidFSEventAuditingSuccessfulAuditReadAttr NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Read Attributes by {{uName}} on {{nName}}/{{dPath}}   Description:  The User {{uName}} performed a successful read attributes operation on file {{nName}}/{{dPath}}. The Desired access mask: {{desiredCifsAccessMaskName}}"
           --#TYPE         "Normal Event"
           --#SUMMARY      Successful Read Attributes by %s on %s/%s   Description:  The User %s performed a successful read attributes operation on file %s/%s. The Desired access mask: %s
           --#ARGUMENTS    {1,2,3,4}
           --#SEVERITY     INFORMATIONAL
           --#TIMEINDEX    99
           --#STATE        OK
       ::= { fluidFSEventsAuditing 26 } 
    
    
    fluidFSEventAuditingSuccessfulAuditWriteAttr NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Write Attributes by {{uName}} on {{nName}}/{{dPath}}   Description:  The User {{uName}} performed a successful write attributes operation on file {{nName}}/{{dPath}}. The Desired access mask: {{desiredCifsAccessMaskName}}"
           --#TYPE         "Normal Event"
           --#SUMMARY      Successful Write Attributes by %s on %s/%s   Description:  The User %s performed a successful write attributes operation on file %s/%s. The Desired access mask: %s
           --#ARGUMENTS    {1,2,3,4}
           --#SEVERITY     INFORMATIONAL
           --#TIMEINDEX    99
           --#STATE        OK
       ::= { fluidFSEventsAuditing 27 } 
    
    
    fluidFSEventAuditingSuccessfulAuditWriteOwner NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Change Owner by {{uName}} on {{nName}}/{{dPath}}   Description:  The User {{uName}} performed a successful change owner operation on file {{nName}}/{{dPath}}. The Desired access mask: {{desiredCifsAccessMaskName}}"
           --#TYPE         "Normal Event"
           --#SUMMARY      Successful Change Owner by %s on %s/%s   Description:  The User %s performed a successful change owner operation on file %s/%s. The Desired access mask: %s
           --#ARGUMENTS    {1,2,3,4}
           --#SEVERITY     INFORMATIONAL
           --#TIMEINDEX    99
           --#STATE        OK
       ::= { fluidFSEventsAuditing 28 } 
    
    
    fluidFSEventAuditingSuccessfulAuditWriteDACL NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Change permissions by {{uName}} on {{nName}}/{{dPath}}   Description:  The User {{uName}} performed a successful write to DACL operation on file {{nName}}/{{dPath}}. The Desired access mask: {{desiredCifsAccessMaskName}}"
           --#TYPE         "Normal Event"
           --#SUMMARY      Successful Change permissions by %s on %s/%s   Description:  The User %s performed a successful write to DACL operation on file %s/%s. The Desired access mask: %s
           --#ARGUMENTS    {1,2,3,4}
           --#SEVERITY     INFORMATIONAL
           --#TIMEINDEX    99
           --#STATE        OK
       ::= { fluidFSEventsAuditing 29 } 
    
    
    fluidFSEventAuditingSuccessfulAuditAccessSACL NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful System Security Access by {{uName}} on {{nName}}/{{dPath}}   Description:  The User {{uName}} performed a successful access to SACL operation on file {{nName}}/{{dPath}}. The Desired access mask: {{desiredCifsAccessMaskName}}"
           --#TYPE         "Normal Event"
           --#SUMMARY      Successful System Security Access by %s on %s/%s   Description:  The User %s performed a successful access to SACL operation on file %s/%s. The Desired access mask: %s
           --#ARGUMENTS    {1,2,3,4}
           --#SEVERITY     INFORMATIONAL
           --#TIMEINDEX    99
           --#STATE        OK
       ::= { fluidFSEventsAuditing 30 } 
    
    
    fluidFSEventAuditingSuccessfulAuditReadCtl NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Successful Read Security Descriptor by {{uName}} on {{nName}}/{{dPath}}   Description:  The User {{uName}} performed a successful read security descriptor operation on file {{nName}}/{{dPath}}. The Desired access mask: {{desiredCifsAccessMaskName}}"
           --#TYPE         "Normal Event"
           --#SUMMARY      Successful Read Security Descriptor by %s on %s/%s   Description:  The User %s performed a successful read security descriptor operation on file %s/%s. The Desired access mask: %s
           --#ARGUMENTS    {1,2,3,4}
           --#SEVERITY     INFORMATIONAL
           --#TIMEINDEX    99
           --#STATE        OK
       ::= { fluidFSEventsAuditing 31 } 
    
    
    fluidFSEventAuditingFailedAuditWrite NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Write by {{uName}} on {{nName}}/{{dPath}}   Description:  The User {{uName}} performed a failed write operation on file {{nName}}/{{dPath}}. The Desired access mask: {{desiredCifsAccessMaskName}}"
           --#TYPE         "Normal Event"
           --#SUMMARY      Failed Write by %s on %s/%s   Description:  The User %s performed a failed write operation on file %s/%s. The Desired access mask: %s
           --#ARGUMENTS    {1,2,3,4}
           --#SEVERITY     INFORMATIONAL
           --#TIMEINDEX    99
           --#STATE        OK
       ::= { fluidFSEventsAuditing 32 } 
    
    
    fluidFSEventAuditingFailedAuditRead NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Read by {{uName}} on {{nName}}/{{dPath}}   Description:  The User {{uName}} performed a failed read operation on file {{nName}}/{{dPath}}. The Desired access mask: {{desiredCifsAccessMaskName}}"
           --#TYPE         "Normal Event"
           --#SUMMARY      Failed Read by %s on %s/%s   Description:  The User %s performed a failed read operation on file %s/%s. The Desired access mask: %s
           --#ARGUMENTS    {1,2,3,4}
           --#SEVERITY     INFORMATIONAL
           --#TIMEINDEX    99
           --#STATE        OK
       ::= { fluidFSEventsAuditing 33 } 
    
    
    fluidFSEventAuditingFailedAuditDelete NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Delete by {{uName}} on {{nName}}/{{dPath}}   Description:  The User {{uName}} performed a failed delete operation on file {{nName}}/{{dPath}}. The Desired access mask: {{desiredCifsAccessMaskName}}"
           --#TYPE         "Normal Event"
           --#SUMMARY      Failed Delete by %s on %s/%s   Description:  The User %s performed a failed delete operation on file %s/%s. The Desired access mask: %s
           --#ARGUMENTS    {1,2,3,4}
           --#SEVERITY     INFORMATIONAL
           --#TIMEINDEX    99
           --#STATE        OK
       ::= { fluidFSEventsAuditing 34 } 
    
    
    fluidFSEventAuditingFailedAuditReadAttr NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Read Attributes by {{uName}} on {{nName}}/{{dPath}}   Description:  The User {{uName}} performed a failed read attributes operation on file {{nName}}/{{dPath}}. The Desired access mask: {{desiredCifsAccessMaskName}}"
           --#TYPE         "Normal Event"
           --#SUMMARY      Failed Read Attributes by %s on %s/%s   Description:  The User %s performed a failed read attributes operation on file %s/%s. The Desired access mask: %s
           --#ARGUMENTS    {1,2,3,4}
           --#SEVERITY     INFORMATIONAL
           --#TIMEINDEX    99
           --#STATE        OK
       ::= { fluidFSEventsAuditing 35 } 
    
    
    fluidFSEventAuditingFailedAuditWriteAttr NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Write Attributes by {{uName}} on {{nName}}/{{dPath}}   Description:  The User {{uName}} performed a failed write attributes operation on file {{nName}}/{{dPath}}. The Desired access mask: {{desiredCifsAccessMaskName}}"
           --#TYPE         "Normal Event"
           --#SUMMARY      Failed Write Attributes by %s on %s/%s   Description:  The User %s performed a failed write attributes operation on file %s/%s. The Desired access mask: %s
           --#ARGUMENTS    {1,2,3,4}
           --#SEVERITY     INFORMATIONAL
           --#TIMEINDEX    99
           --#STATE        OK
       ::= { fluidFSEventsAuditing 36 } 
    
    
    fluidFSEventAuditingFailedAuditWriteOwner NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Change Owner by {{uName}} on {{nName}}/{{dPath}}   Description:  The User {{uName}} performed a failed change owner operation on file {{nName}}/{{dPath}}. The Desired access mask: {{desiredCifsAccessMaskName}}"
           --#TYPE         "Normal Event"
           --#SUMMARY      Failed Change Owner by %s on %s/%s   Description:  The User %s performed a failed change owner operation on file %s/%s. The Desired access mask: %s
           --#ARGUMENTS    {1,2,3,4}
           --#SEVERITY     INFORMATIONAL
           --#TIMEINDEX    99
           --#STATE        OK
       ::= { fluidFSEventsAuditing 37 } 
    
    
    fluidFSEventAuditingFailedAuditWriteDACL NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Change permissions by {{uName}} on {{nName}}/{{dPath}}   Description:  The User {{uName}} performed a failed write to DACL operation on file {{nName}}/{{dPath}}. The Desired access mask: {{desiredCifsAccessMaskName}}"
           --#TYPE         "Normal Event"
           --#SUMMARY      Failed Change permissions by %s on %s/%s   Description:  The User %s performed a failed write to DACL operation on file %s/%s. The Desired access mask: %s
           --#ARGUMENTS    {1,2,3,4}
           --#SEVERITY     INFORMATIONAL
           --#TIMEINDEX    99
           --#STATE        OK
       ::= { fluidFSEventsAuditing 38 } 
    
    
    fluidFSEventAuditingFailedAuditAccessSACL NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Access to SACL by {{uName}} on {{nName}}/{{dPath}}   Description:  The User {{uName}} performed a failed access to SACL operation on file {{nName}}/{{dPath}}. The Desired access mask: {{desiredCifsAccessMaskName}}"
           --#TYPE         "Normal Event"
           --#SUMMARY      Failed Access to SACL by %s on %s/%s   Description:  The User %s performed a failed access to SACL operation on file %s/%s. The Desired access mask: %s
           --#ARGUMENTS    {1,2,3,4}
           --#SEVERITY     INFORMATIONAL
           --#TIMEINDEX    99
           --#STATE        OK
       ::= { fluidFSEventsAuditing 39 } 
    
    
    fluidFSEventAuditingFailedAuditReadCtl NOTIFICATION-TYPE
       OBJECTS { sysName, fluidFSEventsParamsAuditingU, fluidFSEventsParamsAuditingN, fluidFSEventsParamsAuditingD, fluidFSEventsParamsAuditingDesiredCifsAccessMask }
       STATUS current
       DESCRIPTION
           "Failed Read Security Descriptor by {{uName}} on {{nName}}/{{dPath}}   Description:  The User {{uName}} performed a failed read security descriptor operation on file {{nName}}/{{dPath}}. The Desired access mask: {{desiredCifsAccessMaskName}}"
           --#TYPE         "Normal Event"
           --#SUMMARY      Failed Read Security Descriptor by %s on %s/%s   Description:  The User %s performed a failed read security descriptor operation on file %s/%s. The Desired access mask: %s
           --#ARGUMENTS    {1,2,3,4}
           --#SEVERITY     INFORMATIONAL
           --#TIMEINDEX    99
           --#STATE        OK
       ::= { fluidFSEventsAuditing 40 } 
    
    
    fluidFSEventAuditingFailedAuditDeleteName NOTIFICATION-TYPE
       OBJECTS { sysName, fluidFSEventsParamsAuditingU, fluidFSEventsParamsAuditingN, fluidFSEventsParamsAuditingName, fluidFSEventsParamsAuditingDesiredCifsAccessMask }
       STATUS current
       DESCRIPTION
           "Failed Delete by {{uName}} on {{nName}}/{{name}}   Description:  The User {{uName}} performed a failed delete operation on file {{nName}}/{{name}}. The Desired access mask: {{desiredCifsAccessMaskName}}"
           --#TYPE         "Normal Event"
           --#SUMMARY      Failed Delete by %s on %s/%s   Description:  The User %s performed a failed delete operation on file %s/%s. The Desired access mask: %s
           --#ARGUMENTS    {1,2,3,4}
           --#SEVERITY     INFORMATIONAL
           --#TIMEINDEX    99
           --#STATE        OK
       ::= { fluidFSEventsAuditing 41 } 
    
    
    fluidFSEventAuditingSuccessfulAuditDeleteName NOTIFICATION-TYPE
       OBJECTS { sysName, fluidFSEventsParamsAuditingU, fluidFSEventsParamsAuditingN, fluidFSEventsParamsAuditingName, fluidFSEventsParamsAuditingDesiredCifsAccessMask }
       STATUS current
       DESCRIPTION
           "Successful Delete by {{uName}} on {{nName}}/{{name}}   Description:  The User {{uName}} performed a successful delete operation on file {{nName}}/{{name}}. The Desired access mask: {{desiredCifsAccessMaskName}}"
           --#TYPE         "Normal Event"
           --#SUMMARY      Successful Delete by %s on %s/%s   Description:  The User %s performed a successful delete operation on file %s/%s. The Desired access mask: %s
           --#ARGUMENTS    {1,2,3,4}
           --#SEVERITY     INFORMATIONAL
           --#TIMEINDEX    99
           --#STATE        OK
       ::= { fluidFSEventsAuditing 42 } 
    
    
    fluidFSEventsParamsUpgrade OBJECT IDENTIFIER ::= { fluidFSEventsParams 18 } 
    
    
    fluidFSEventsUpgrade OBJECT IDENTIFIER ::= { fluidFSEvents 18 } 
    
    
    fluidFSEventsParamsUpgradeServicePackName OBJECT-TYPE
       SYNTAX  DisplayString
       MAX-ACCESS  read-only
       STATUS  current
       DESCRIPTION
           "File name of the Service Pack"
       ::= { fluidFSEventsParamsUpgrade 1 }
    
    
    fluidFSEventUpgradeFailedToReadFileInformation NOTIFICATION-TYPE
       OBJECTS { sysName, fluidFSEventsParamsUpgradeServicePackName }
       STATUS current
       DESCRIPTION
           "Fail to read information of file {{servicePackName}} while checking for new service pack. File was removed"
           --#TYPE         "Normal Event"
           --#SUMMARY      Fail to read information of file %s while checking for new service pack. File was removed
           --#ARGUMENTS    {1}
           --#SEVERITY     INFORMATIONAL
           --#TIMEINDEX    99
           --#STATE        OK
       ::= { fluidFSEventsUpgrade 1 } 
    
    
    fluidFSEventUpgradeFailedToGetFileSize NOTIFICATION-TYPE
       OBJECTS { sysName, fluidFSEventsParamsUpgradeServicePackName }
       STATUS current
       DESCRIPTION
           "Fail to get size of file {{servicePackName}} while checking for new service pack. File was removed"
           --#TYPE         "Normal Event"
           --#SUMMARY      Fail to get size of file %s while checking for new service pack. File was removed
           --#ARGUMENTS    {1}
           --#SEVERITY     INFORMATIONAL
           --#TIMEINDEX    99
           --#STATE        OK
       ::= { fluidFSEventsUpgrade 2 } 
    
    
    fluidFSEventUpgradeInvalidFileFormatOrChecksum NOTIFICATION-TYPE
       OBJECTS { sysName, fluidFSEventsParamsUpgradeServicePackName }
       STATUS current
       DESCRIPTION
           "File {{servicePackName}} is not a valid package for upgrade. File was removed"
           --#TYPE         "Normal Event"
           --#SUMMARY      File %s is not a valid package for upgrade. File was removed
           --#ARGUMENTS    {1}
           --#SEVERITY     MAJOR
           --#TIMEINDEX    99
           --#STATE        OK
       ::= { fluidFSEventsUpgrade 3 } 
    
    
    fluidFSEventUpgradeServicePackIsOlderThanCurrentVersion NOTIFICATION-TYPE
       OBJECTS { sysName, fluidFSEventsParamsUpgradeServicePackName }
       STATUS current
       DESCRIPTION
           "The service pack {{servicePackName}} was removed because its version is older than current one"
           --#TYPE         "Normal Event"
           --#SUMMARY      The service pack %s was removed because its version is older than current one
           --#ARGUMENTS    {1}
           --#SEVERITY     INFORMATIONAL
           --#TIMEINDEX    99
           --#STATE        OK
       ::= { fluidFSEventsUpgrade 4 } 
    
    
    fluidFSEventUpgradeServicePackHasOldVersion NOTIFICATION-TYPE
       OBJECTS { sysName, fluidFSEventsParamsUpgradeServicePackName }
       STATUS current
       DESCRIPTION
           "The service pack {{servicePackName}} was removed because its version is older than available versions on the current node"
           --#TYPE         "Normal Event"
           --#SUMMARY      The service pack %s was removed because its version is older than available versions on the current node
           --#ARGUMENTS    {1}
           --#SEVERITY     INFORMATIONAL
           --#TIMEINDEX    99
           --#STATE        OK
       ::= { fluidFSEventsUpgrade 5 } 
    
    
    fluidFSEventUpgradeServicePackAlreadyExists NOTIFICATION-TYPE
       OBJECTS { sysName, fluidFSEventsParamsUpgradeServicePackName }
       STATUS current
       DESCRIPTION
           "The service pack {{servicePackName}} was removed because file with the same version already exists"
           --#TYPE         "Normal Event"
           --#SUMMARY      The service pack %s was removed because file with the same version already exists
           --#ARGUMENTS    {1}
           --#SEVERITY     INFORMATIONAL
           --#TIMEINDEX    99
           --#STATE        OK
       ::= { fluidFSEventsUpgrade 6 } 
    
    
    fluidFSEventUpgradeMonitoringDataCorruption NOTIFICATION-TYPE
       OBJECTS { sysName }
       STATUS current
       DESCRIPTION
           "Failed to recover the monitored data after upgrade because of corruption"
           --#TYPE         "Normal Event"
           --#SUMMARY      Failed to recover the monitored data after upgrade because of corruption
           --#ARGUMENTS    {}
           --#SEVERITY     INFORMATIONAL
           --#TIMEINDEX    99
           --#STATE        OK
       ::= { fluidFSEventsUpgrade 7 } 
    
    
    fluidFSEventUpgradeServicePackDownloaded NOTIFICATION-TYPE
       OBJECTS { sysName, fluidFSEventsParamsUpgradeServicePackName }
       STATUS current
       DESCRIPTION
           "New service pack {{servicePackName}} downloaded"
           --#TYPE         "Normal Event"
           --#SUMMARY      New service pack %s downloaded
           --#ARGUMENTS    {1}
           --#SEVERITY     INFORMATIONAL
           --#TIMEINDEX    99
           --#STATE        OK
       ::= { fluidFSEventsUpgrade 8 } 
    


    
END
