-- CET Group
-- General MIB for Energy Site Monitoring 
-- 
-- { iso org(3) dod(6) internet(1) private(4) enterprises(1) cet(12551) } 
-- ============================================================================================== 
SITE-MONITORING-MIB DEFINITIONS ::= BEGIN 

IMPORTS
    enterprises, MODULE-IDENTITY, OBJECT-TYPE, NOTIFICATION-TYPE, Unsigned32, Integer32
        FROM SNMPv2-SMI
    DisplayString, RowStatus
        FROM SNMPv2-TC
    MODULE-COMPLIANCE, OBJECT-GROUP, NOTIFICATION-GROUP
        FROM SNMPv2-CONF;


   siteMonitoring   MODULE-IDENTITY 
   LAST-UPDATED "202103101600Z" 
    ORGANIZATION "CE+T Group" 
   CONTACT-INFO " CE+T Group 
        Postal:     Rue du Charbonnage 12 
                    B-4020 Wandre 
                    Belgium 
        e-mail      customer.support@cet-power.com" 

   DESCRIPTION "CE+T Group SNMP corporate naming convention
   Organises the SNMP OIDs according to the 
   design centers that generate the different MIBs"
   REVISION "202103101600Z" 
    DESCRIPTION "This revision is the first release of the MIB" 

::= { cet 20 } 
cet          OBJECT IDENTIFIER ::= { enterprises 12551 } 

siteV1   OBJECT IDENTIFIER ::= {siteMonitoring 1}
siteV1GlobalStatus      OBJECT-TYPE 
              SYNTAX  DisplayString (SIZE (0..255)) 
              MAX-ACCESS  read-only 
              STATUS  current 
              DESCRIPTION "A textual string (alarms, normal or unknown) containing the status of the Site" 
              ::={siteV1 1 } 

siteV1GlobalAlarmSeverityType  OBJECT-TYPE 
              SYNTAX DisplayString
              MAX-ACCESS  read-only 
              STATUS  current 
              DESCRIPTION "The alarm severity type (critical, major, minor, warning, none, disabled) of the Site" 
              ::= { siteV1 2 }

siteV1GlobalAlarmSeverityLevel  OBJECT-TYPE 
              SYNTAX Integer32
              MAX-ACCESS  read-only 
              STATUS  current 
              DESCRIPTION "The alarm severity level (0-9) of the Site" 
              ::= { siteV1 3 }

siteV1GlobalAlarmSeverityTypeInt  OBJECT-TYPE 
              SYNTAX Integer32
              MAX-ACCESS  read-only 
              STATUS  current 
              DESCRIPTION "The alarm severity type as integer (critical=4, major=3, minor=2, warning=1, none=0) of the Site" 
              ::= { siteV1 4 }

siteV1Description     OBJECT IDENTIFIER ::= { siteV1 10 }
siteV1DescriptionNumber      OBJECT-TYPE
              SYNTAX          Integer32
              MAX-ACCESS      read-only
              STATUS          current
              DESCRIPTION    "The number of entries in the Site Description table"
              ::= { siteV1Description 1 }
siteV1DescriptionTable      OBJECT-TYPE
              SYNTAX          SEQUENCE OF SiteV1DescriptionEntry
              MAX-ACCESS      not-accessible
              STATUS          current
              DESCRIPTION    "The Description table of the Site" 
              ::= { siteV1Description 2 }
siteV1DescriptionEntry      OBJECT-TYPE
              SYNTAX          SiteV1DescriptionEntry
              MAX-ACCESS      not-accessible
              STATUS          current
              DESCRIPTION    "A Description entry"
              INDEX {siteV1DescriptionIndex}
              ::= { siteV1DescriptionTable 1 }
SiteV1DescriptionEntry ::= 
              SEQUENCE{ 
              siteV1DescriptionIndex    Unsigned32,  
              siteV1DescriptionName     DisplayString,
              siteV1DescriptionValue    DisplayString, 
              siteV1DescriptionEntryStatus RowStatus 
              }
siteV1DescriptionIndex      OBJECT-TYPE
              SYNTAX          Unsigned32
              MAX-ACCESS      not-accessible
              STATUS          current
              DESCRIPTION    "Description Index"
              ::= { siteV1DescriptionEntry 1 }
siteV1DescriptionName      OBJECT-TYPE
              SYNTAX          DisplayString
              MAX-ACCESS      read-only
              STATUS          current
              DESCRIPTION    "Description Name"
              ::= { siteV1DescriptionEntry 2 }
siteV1DescriptionValue      OBJECT-TYPE
              SYNTAX          DisplayString
              MAX-ACCESS      read-create
              STATUS          current
              DESCRIPTION    "Description Value"
              ::= { siteV1DescriptionEntry 3 }
siteV1DescriptionEntryStatus      OBJECT-TYPE
              SYNTAX          RowStatus
              MAX-ACCESS      read-create
              STATUS          current
              DESCRIPTION    "The status of this table entry"
              ::= { siteV1DescriptionEntry 4 }
siteV1DescriptionList         OBJECT IDENTIFIER ::= { siteV1Description 3 }
siteV1DescDescriptionSiteInformationSiteNumber     OBJECT-TYPE
              SYNTAX          DisplayString
              MAX-ACCESS      read-write
              STATUS          current
              DESCRIPTION    "The identification number of the site"
              ::= { siteV1DescriptionList 1}
siteV1DescDescriptionSiteInformationSiteName     OBJECT-TYPE
              SYNTAX          DisplayString
              MAX-ACCESS      read-write
              STATUS          current
              DESCRIPTION    "The name of the site"
              ::= { siteV1DescriptionList 2}
siteV1DescDescriptionSiteInformationShortDescription     OBJECT-TYPE
              SYNTAX          DisplayString
              MAX-ACCESS      read-write
              STATUS          current
              DESCRIPTION    "A short description of the site"
              ::= { siteV1DescriptionList 3}
siteV1DescDescriptionSiteInformationInfo     OBJECT-TYPE
              SYNTAX          DisplayString
              MAX-ACCESS      read-write
              STATUS          current
              DESCRIPTION    "Some more information about the site"
              ::= { siteV1DescriptionList 4}
siteV1DescDescriptionCustomDescriptionDescription     OBJECT-TYPE
              SYNTAX          DisplayString
              MAX-ACCESS      read-write
              STATUS          current
              DESCRIPTION    "A free text zone to write a system description"
              ::= { siteV1DescriptionList 5}
siteV1DescDescriptionCustomDescriptionReference     OBJECT-TYPE
              SYNTAX          DisplayString
              MAX-ACCESS      read-write
              STATUS          current
              DESCRIPTION    "A free text zone to write the customer reference of the system"
              ::= { siteV1DescriptionList 6}
siteV1DescDescriptionContactContactName     OBJECT-TYPE
              SYNTAX          DisplayString
              MAX-ACCESS      read-write
              STATUS          current
              DESCRIPTION    "Contact Name"
              ::= { siteV1DescriptionList 7}
siteV1DescDescriptionContactPhoneNumber     OBJECT-TYPE
              SYNTAX          DisplayString
              MAX-ACCESS      read-write
              STATUS          current
              DESCRIPTION    "Phone Number"
              ::= { siteV1DescriptionList 8}
siteV1DescDescriptionAddressLocation     OBJECT-TYPE
              SYNTAX          DisplayString
              MAX-ACCESS      read-write
              STATUS          current
              DESCRIPTION    "Location"
              ::= { siteV1DescriptionList 10}
siteV1DescDescriptionAddressStreet     OBJECT-TYPE
              SYNTAX          DisplayString
              MAX-ACCESS      read-write
              STATUS          current
              DESCRIPTION    "Street part of the site address"
              ::= { siteV1DescriptionList 11}
siteV1DescDescriptionAddressCity     OBJECT-TYPE
              SYNTAX          DisplayString
              MAX-ACCESS      read-write
              STATUS          current
              DESCRIPTION    "City part of the site address"
              ::= { siteV1DescriptionList 12}
siteV1DescDescriptionAddressProvince     OBJECT-TYPE
              SYNTAX          DisplayString
              MAX-ACCESS      read-write
              STATUS          current
              DESCRIPTION    "Province part of the site address"
              ::= { siteV1DescriptionList 13}
siteV1DescDescriptionAddressPostalCode     OBJECT-TYPE
              SYNTAX          DisplayString
              MAX-ACCESS      read-write
              STATUS          current
              DESCRIPTION    "Postal Code part of the site address"
              ::= { siteV1DescriptionList 14}
siteV1DescDescriptionAddressRegion     OBJECT-TYPE
              SYNTAX          DisplayString
              MAX-ACCESS      read-write
              STATUS          current
              DESCRIPTION    "Region part of the site address"
              ::= { siteV1DescriptionList 15}
siteV1DescDescriptionAddressCountry     OBJECT-TYPE
              SYNTAX          DisplayString
              MAX-ACCESS      read-write
              STATUS          current
              DESCRIPTION    "Country part of the site address"
              ::= { siteV1DescriptionList 16}
siteV1DescDescriptionClusteringGroup1     OBJECT-TYPE
              SYNTAX          DisplayString
              MAX-ACCESS      read-write
              STATUS          current
              DESCRIPTION    "Group Level 1 (For Armada Clustering)"
              ::= { siteV1DescriptionList 21}
siteV1DescDescriptionClusteringGroup2     OBJECT-TYPE
              SYNTAX          DisplayString
              MAX-ACCESS      read-write
              STATUS          current
              DESCRIPTION    "Group Level 2 (For Armada Clustering)"
              ::= { siteV1DescriptionList 22}
siteV1DescDescriptionClusteringGroup3     OBJECT-TYPE
              SYNTAX          DisplayString
              MAX-ACCESS      read-write
              STATUS          current
              DESCRIPTION    "Group Level 3 (For Armada Clustering)"
              ::= { siteV1DescriptionList 23}
siteV1DescDescriptionClusteringGroup4     OBJECT-TYPE
              SYNTAX          DisplayString
              MAX-ACCESS      read-write
              STATUS          current
              DESCRIPTION    "Group Level 4 (For Armada Clustering)"
              ::= { siteV1DescriptionList 24}
siteV1DescDescriptionClusteringGroup5     OBJECT-TYPE
              SYNTAX          DisplayString
              MAX-ACCESS      read-write
              STATUS          current
              DESCRIPTION    "Group Level 5 (For Armada Clustering)"
              ::= { siteV1DescriptionList 25}
siteV1DescDescriptionGPSPositionLatitude     OBJECT-TYPE
              SYNTAX          DisplayString
              MAX-ACCESS      read-write
              STATUS          current
              DESCRIPTION    "The latitude of the site"
              ::= { siteV1DescriptionList 31}
siteV1DescDescriptionGPSPositionLongitude     OBJECT-TYPE
              SYNTAX          DisplayString
              MAX-ACCESS      read-write
              STATUS          current
              DESCRIPTION    "The longitude of the site"
              ::= { siteV1DescriptionList 32}
siteV1DescDescriptionGPSPositionAltitude     OBJECT-TYPE
              SYNTAX          DisplayString
              MAX-ACCESS      read-write
              STATUS          current
              DESCRIPTION    "The altitude of the site"
              ::= { siteV1DescriptionList 33}
siteV1DescControllerSoftwareRunningCompasInformationalVersion     OBJECT-TYPE
              SYNTAX          DisplayString
              MAX-ACCESS      read-only
              STATUS          current
              DESCRIPTION    "The software revision of Compas (read only)"
              ::= { siteV1DescriptionList 90}
siteV1DescControllerSoftwareRunningCompasVersion     OBJECT-TYPE
              SYNTAX          DisplayString
              MAX-ACCESS      read-only
              STATUS          current
              DESCRIPTION    "The software revision of Compas (read only)"
              ::= { siteV1DescriptionList 91}
siteV1DescControllerSoftwarePlatformVersion     OBJECT-TYPE
              SYNTAX          DisplayString
              MAX-ACCESS      read-only
              STATUS          current
              DESCRIPTION    "The platform version including operating system"
              ::= { siteV1DescriptionList 92}
siteV1DescControllerHardwareCPU     OBJECT-TYPE
              SYNTAX          DisplayString
              MAX-ACCESS      read-only
              STATUS          current
              DESCRIPTION    "Information about the CPU"
              ::= { siteV1DescriptionList 93}
siteV1DescControllerHardwarePlatform     OBJECT-TYPE
              SYNTAX          DisplayString
              MAX-ACCESS      read-only
              STATUS          current
              DESCRIPTION    "Information about the hardware system containing Compas"
              ::= { siteV1DescriptionList 94}
siteV1DescControllerHardwarePartNumber     OBJECT-TYPE
              SYNTAX          DisplayString
              MAX-ACCESS      read-only
              STATUS          current
              DESCRIPTION    "NA"
              ::= { siteV1DescriptionList 95}
siteV1DescControllerHardwareSerialNumber     OBJECT-TYPE
              SYNTAX          DisplayString
              MAX-ACCESS      read-only
              STATUS          current
              DESCRIPTION    "NA"
              ::= { siteV1DescriptionList 96}
siteV1DescControllerSoftwareFactoryCompasVersion     OBJECT-TYPE
              SYNTAX          DisplayString
              MAX-ACCESS      read-only
              STATUS          current
              DESCRIPTION    "Information about the revision of Compas in Factory folder"
              ::= { siteV1DescriptionList 105}
siteV1DescControllerSoftwareUserCompasVersion     OBJECT-TYPE
              SYNTAX          DisplayString
              MAX-ACCESS      read-only
              STATUS          current
              DESCRIPTION    "Information about the revision of Compas in user folder"
              ::= { siteV1DescriptionList 106}
siteV1Alarm          OBJECT IDENTIFIER ::= { siteV1 11 }
siteV1AlarmNumber      OBJECT-TYPE
              SYNTAX          Integer32
              MAX-ACCESS      read-only
              STATUS          current
              DESCRIPTION    "The number of entries in the Site Alarm table"
              ::= { siteV1Alarm 1 }
siteV1AlarmTable      OBJECT-TYPE
              SYNTAX          SEQUENCE OF SiteV1AlarmEntry
              MAX-ACCESS      not-accessible
              STATUS          current
              DESCRIPTION    "The table of Alarm entries"
              ::= { siteV1Alarm 2 }
siteV1AlarmEntry      OBJECT-TYPE
              SYNTAX          SiteV1AlarmEntry
              MAX-ACCESS      not-accessible
              STATUS          current
              DESCRIPTION    "An alarm entry"
              INDEX {siteV1AlarmIndex}
              ::= { siteV1AlarmTable 1 }
SiteV1AlarmEntry ::= 
             SEQUENCE{ 
             siteV1AlarmIndex         Unsigned32,  
             siteV1AlarmName          DisplayString,
             siteV1AlarmActive        DisplayString, 
             siteV1AlarmSeverityType  DisplayString, 
             siteV1AlarmSeverityLevel DisplayString, 
             siteV1AlarmStartTime      DisplayString, 
             siteV1AlarmStopTime       DisplayString, 
              siteV1AlarmEntryStatus  RowStatus 
             }
siteV1AlarmIndex      OBJECT-TYPE
              SYNTAX          Unsigned32
              MAX-ACCESS      not-accessible
              STATUS          current
              DESCRIPTION    "Alarm Index"
              ::= { siteV1AlarmEntry 1 }
siteV1AlarmName      OBJECT-TYPE
              SYNTAX          DisplayString
              MAX-ACCESS      read-only
              STATUS          current
              DESCRIPTION    "Alarm Name"
              ::= { siteV1AlarmEntry 2 }
siteV1AlarmActive   OBJECT-TYPE
              SYNTAX          DisplayString
              MAX-ACCESS      read-only
              STATUS          current
              DESCRIPTION    "Is the Alarm active ? 'true' for active, 'false' for not-active"
              ::= { siteV1AlarmEntry 3 }
siteV1AlarmSeverityType      OBJECT-TYPE
              SYNTAX          DisplayString
              MAX-ACCESS      read-write
              STATUS          current
              DESCRIPTION    "The alarm severity type (major, minor, warning, none, disabled) of this alarm entry" 
              ::= { siteV1AlarmEntry 4 }
siteV1AlarmSeverityLevel      OBJECT-TYPE
              SYNTAX          DisplayString
              MAX-ACCESS      read-write
              STATUS          current
              DESCRIPTION    "The alarm severity level (0-9) of this alarm entry" 
              ::= { siteV1AlarmEntry 5 }
siteV1AlarmStartTime      OBJECT-TYPE
              SYNTAX          DisplayString
              MAX-ACCESS      read-only
              STATUS          current
              DESCRIPTION    "The last start time of this alarm entry (null if never active)"
              ::= { siteV1AlarmEntry 6 }
siteV1AlarmStopTime      OBJECT-TYPE
              SYNTAX          DisplayString
              MAX-ACCESS      read-only
              STATUS          current
              DESCRIPTION    "The last stop time of this alarm entry (null if alarm active)"
              ::= { siteV1AlarmEntry 7 }
siteV1AlarmEntryStatus      OBJECT-TYPE
              SYNTAX          RowStatus
              MAX-ACCESS      read-create
              STATUS          current
              DESCRIPTION    "The status of this table entry - not used, only for MIB compliance "
              ::= { siteV1AlarmEntry 8 }
siteV1AlarmSummary      OBJECT-TYPE
              SYNTAX BITS{
                  inventoryCANBusFail (0),          -- Alarm : Inventory CAN Bus Failure
                  inventoryCANBusAddressingError (1),          -- Alarm : Inventory CAN Bus Addressing Error
                  inventoryCANBusMissingDevices (2),          -- Alarm : Inventory CAN Bus Missing Devices
                  inventoryCANBusRunningCANOpenLSSDeviceDetection (3),          -- Alarm : Inventory CAN Bus Running CANOpen LSS Device Detection
                  inventoryCANBusRunningCANFirmwareUpgrade (4),          -- Alarm : Inventory CAN Bus Running CAN Firmware Upgrade
                  controllerRebootControllerRebootRequired (10),          -- Alarm : Controller Reboot Controller Reboot Required
                  controllerSaveLastConfChangesUnsaved (14),          -- Alarm : Controller Save Last Configuration Changes Unsaved
                  xMLHeartbeatFail (20),          -- Alarm : XML Heartbeat Failure
                  controllerLicenseFail (50),          -- Alarm : Controller License Failure
                  controllerPowerAuxiliaryPowerFail (99),          -- Alarm : Controller Power Auxiliary Power Failure
                  digInputD1DiginputIVSDI1active (500),          -- Alarm : Digital Input D1 Digital input IVS-DI1 active
                  digInputD2DiginputIVSDI2active (505)          -- Alarm : Digital Input D2 Digital input IVS-DI2 active
              }
              MAX-ACCESS      read-only
              STATUS          current
              DESCRIPTION    "Summary bit vector with all the alarms state of the Site. A '1' means alarm active, '0' means not active. Unimplemented alarms are always '0'." 
              ::= { siteV1Alarm 3 }
siteV1Event          OBJECT IDENTIFIER ::= { siteV1 12 }
siteV1EventNumber      OBJECT-TYPE
              SYNTAX          Integer32
              MAX-ACCESS      read-only
              STATUS          current
              DESCRIPTION    "The number of entries in the Event Table related to the Site" 
              ::= { siteV1Event 1 }
siteV1EventTable      OBJECT-TYPE
              SYNTAX          SEQUENCE OF SiteV1EventEntry
              MAX-ACCESS      not-accessible
              STATUS          current
              DESCRIPTION    "The Event table related to the Site" 
              ::= { siteV1Event 2 }
siteV1EventEntry      OBJECT-TYPE
              SYNTAX          SiteV1EventEntry
              MAX-ACCESS      not-accessible
              STATUS          current
              DESCRIPTION    "."
              INDEX {siteV1EventIndex}
              ::= { siteV1EventTable 1 }
SiteV1EventEntry ::= 
             SEQUENCE{ 
             siteV1EventIndex           Unsigned32,  
             siteV1EventId              Unsigned32,  
             siteV1EventName            DisplayString,
             siteV1EventDateTime        DisplayString, 
             siteV1EventSeverityType    DisplayString, 
             siteV1EventSeverityLevel   DisplayString,
              siteV1EventEntryStatus    RowStatus 
             }
siteV1EventIndex      OBJECT-TYPE
              SYNTAX          Unsigned32
              MAX-ACCESS      not-accessible
              STATUS          current
              DESCRIPTION    "Event Index"
              ::= { siteV1EventEntry 1 }
siteV1EventId      OBJECT-TYPE
              SYNTAX          Unsigned32
              MAX-ACCESS      read-only
              STATUS          current
              DESCRIPTION    "Event Index"
              ::= { siteV1EventEntry 2 }
siteV1EventName      OBJECT-TYPE
              SYNTAX          DisplayString
              MAX-ACCESS      read-only
              STATUS          current
              DESCRIPTION    "Event Name"
              ::= { siteV1EventEntry 3 }
siteV1EventDateTime      OBJECT-TYPE
              SYNTAX          DisplayString
              MAX-ACCESS      read-only
              STATUS          current
              DESCRIPTION    "The date and time of the event"
              ::= { siteV1EventEntry 4 }
siteV1EventSeverityType      OBJECT-TYPE
              SYNTAX          DisplayString
              MAX-ACCESS      read-only
              STATUS          current
              DESCRIPTION    "The event severity type ('major', 'minor', 'warning' or 'none')"
              ::= { siteV1EventEntry 5 }
siteV1EventSeverityLevel      OBJECT-TYPE
              SYNTAX          DisplayString
              MAX-ACCESS      read-only
              STATUS          current
              DESCRIPTION    "The event severity level (0-9)"
              ::= { siteV1EventEntry 6 }
siteV1EventEntryStatus      OBJECT-TYPE
              SYNTAX          RowStatus
              MAX-ACCESS      read-create
              STATUS          current
              DESCRIPTION    "The status of this table entry"
              ::= { siteV1EventEntry 7 }
siteV1Data            OBJECT IDENTIFIER ::= { siteV1 13 }
siteV1DataNumber      OBJECT-TYPE
              SYNTAX          Integer32
              MAX-ACCESS      read-only
              STATUS          current
              DESCRIPTION    "The number of entries in the Data Table related to the Site" 
              ::= { siteV1Data 1 }
siteV1DataTable      OBJECT-TYPE
              SYNTAX          SEQUENCE OF SiteV1DataEntry
              MAX-ACCESS      not-accessible
              STATUS          current
              DESCRIPTION    "The table of Data entries"
              ::= { siteV1Data 2 }
siteV1DataEntry      OBJECT-TYPE
              SYNTAX          SiteV1DataEntry
              MAX-ACCESS      not-accessible
              STATUS          current
              DESCRIPTION    "A data entry"
              INDEX {siteV1DataIndex}
              ::= { siteV1DataTable 1 }
SiteV1DataEntry ::= 
             SEQUENCE{ 
             siteV1DataIndex       Unsigned32,  
             siteV1DataName        DisplayString,
             siteV1DataValue       DisplayString, 
              siteV1DataEntryStatus  RowStatus 
             }
siteV1DataIndex      OBJECT-TYPE
              SYNTAX          Unsigned32
              MAX-ACCESS      not-accessible
              STATUS          current
              DESCRIPTION    "The data index"
              ::= { siteV1DataEntry 1 }

siteV1DataName      OBJECT-TYPE
              SYNTAX          DisplayString
              MAX-ACCESS      read-only
              STATUS          current
              DESCRIPTION    "The data name"
              ::= { siteV1DataEntry 2 }
siteV1DataValue     OBJECT-TYPE
              SYNTAX          DisplayString
              MAX-ACCESS      read-only
              STATUS          current
              DESCRIPTION    "The data value"
              ::= { siteV1DataEntry 3 }
siteV1DataEntryStatus      OBJECT-TYPE
              SYNTAX          RowStatus
              MAX-ACCESS      read-create
              STATUS          current
              DESCRIPTION    "The status of this table entry - not used, only present for compliance"
              ::= { siteV1DataEntry 4 }
siteV1DataList         OBJECT IDENTIFIER ::= { siteV1Data 3 }
siteV1DataNetworkIPv4Address     OBJECT-TYPE
              SYNTAX          Integer32
              MAX-ACCESS      read-only
              STATUS          current
              DESCRIPTION    "This is the actual IP address of the Compas platform. If the Ethernet cable is not correctly connected, the address will be 0.0.0.0."
              ::= { siteV1DataList 1}
siteV1DataNetworkIPv4Mask     OBJECT-TYPE
              SYNTAX          Integer32
              MAX-ACCESS      read-only
              STATUS          current
              DESCRIPTION    "This is the actual Network Mask of the Compas platform."
              ::= { siteV1DataList 2}
siteV1DataNetworkMACAddress     OBJECT-TYPE
              SYNTAX          Integer32
              MAX-ACCESS      read-only
              STATUS          current
              DESCRIPTION    "This is the MAC address of IP interface."
              ::= { siteV1DataList 3}
siteV1DataNetworkIPv6SiteLocalAddress     OBJECT-TYPE
              SYNTAX          Integer32
              MAX-ACCESS      read-only
              STATUS          current
              DESCRIPTION    "NA"
              ::= { siteV1DataList 5}
siteV1DataNetworkIPv6LinkLocalAddress     OBJECT-TYPE
              SYNTAX          Integer32
              MAX-ACCESS      read-only
              STATUS          current
              DESCRIPTION    "NA"
              ::= { siteV1DataList 6}
siteV1DataControllerLicenseLicensedOptions     OBJECT-TYPE
              SYNTAX          DisplayString
              MAX-ACCESS      read-only
              STATUS          current
              DESCRIPTION    "This is the options of the actual licenses."
              ::= { siteV1DataList 11}
siteV1DataNetworkMegabytesReceived     OBJECT-TYPE
              SYNTAX          Integer32
              MAX-ACCESS      read-only
              STATUS          current
              DESCRIPTION    "NA"
              ::= { siteV1DataList 15}
siteV1DataNetworkMegabytesSent     OBJECT-TYPE
              SYNTAX          Integer32
              MAX-ACCESS      read-only
              STATUS          current
              DESCRIPTION    "NA"
              ::= { siteV1DataList 16}
siteV1DataTimeLocalDateAndTime     OBJECT-TYPE
              SYNTAX          DisplayString
              MAX-ACCESS      read-only
              STATUS          current
              DESCRIPTION    "This is the local time of the monitoring."
              ::= { siteV1DataList 21}
siteV1DataTimeUTCDateAndTime     OBJECT-TYPE
              SYNTAX          DisplayString
              MAX-ACCESS      read-only
              STATUS          current
              DESCRIPTION    "This is the UTC time of the monitoring."
              ::= { siteV1DataList 22}
siteV1DataControllerOperatingSystemInfoMonitoringMemoryUsed     OBJECT-TYPE
              SYNTAX          Integer32
              MAX-ACCESS      read-only
              STATUS          current
              DESCRIPTION    "This is actual amount of RAM memory used by the application."
              ::= { siteV1DataList 31}
siteV1DataControllerOperatingSystemInfoCPUPercentageUsage     OBJECT-TYPE
              SYNTAX          Integer32
              MAX-ACCESS      read-only
              STATUS          current
              DESCRIPTION    "This is actual percentage of CPU used"
              ::= { siteV1DataList 32}
siteV1DataControllerOperatingSystemInfoFreeFlashMemorySpace     OBJECT-TYPE
              SYNTAX          Integer32
              MAX-ACCESS      read-only
              STATUS          current
              DESCRIPTION    "This is free flash memory available on the Compas card, in Megabytes"
              ::= { siteV1DataList 33}
siteV1DataDataRecordsTotalFifoSizeOfSecondRecords     OBJECT-TYPE
              SYNTAX          Integer32
              MAX-ACCESS      read-only
              STATUS          current
              DESCRIPTION    "NA"
              ::= { siteV1DataList 41}
siteV1DataDataRecordsTotalFifoSizeOfMinuteRecords     OBJECT-TYPE
              SYNTAX          Integer32
              MAX-ACCESS      read-only
              STATUS          current
              DESCRIPTION    "NA"
              ::= { siteV1DataList 42}
siteV1DataDataRecordsTotalFifoSizeOfHourRecords     OBJECT-TYPE
              SYNTAX          Integer32
              MAX-ACCESS      read-only
              STATUS          current
              DESCRIPTION    "NA"
              ::= { siteV1DataList 43}
siteV1DataDataRecordsTotalFifoSizeOfDayRecords     OBJECT-TYPE
              SYNTAX          Integer32
              MAX-ACCESS      read-only
              STATUS          current
              DESCRIPTION    "NA"
              ::= { siteV1DataList 44}
siteV1DataAlarmsNumberOfActiveMajor     OBJECT-TYPE
              SYNTAX          Integer32
              MAX-ACCESS      read-only
              STATUS          current
              DESCRIPTION    "NA"
              ::= { siteV1DataList 47}
siteV1DataAlarmsNumberOfActiveMinor     OBJECT-TYPE
              SYNTAX          Integer32
              MAX-ACCESS      read-only
              STATUS          current
              DESCRIPTION    "NA"
              ::= { siteV1DataList 48}
siteV1DataAlarmsNumberOfActiveWarning     OBJECT-TYPE
              SYNTAX          Integer32
              MAX-ACCESS      read-only
              STATUS          current
              DESCRIPTION    "NA"
              ::= { siteV1DataList 49}
siteV1DataInventoryCANBusCANOpenBusNodeIDs     OBJECT-TYPE
              SYNTAX          Integer32
              MAX-ACCESS      read-only
              STATUS          current
              DESCRIPTION    "The coma separated list of the node ids present on the CAN bus."
              ::= { siteV1DataList 51}
siteV1DataSNMPAgentCounterAuthenticationFail     OBJECT-TYPE
              SYNTAX          Integer32
              MAX-ACCESS      read-only
              STATUS          current
              DESCRIPTION    "Count the number of get request since startup. It can overflow"
              ::= { siteV1DataList 61}
siteV1DataSNMPAgentCounterReadRequest     OBJECT-TYPE
              SYNTAX          Integer32
              MAX-ACCESS      read-only
              STATUS          current
              DESCRIPTION    "Count the number of get request since startup. It can overflow"
              ::= { siteV1DataList 62}
siteV1DataSNMPAgentCounterWriteRequest     OBJECT-TYPE
              SYNTAX          Integer32
              MAX-ACCESS      read-only
              STATUS          current
              DESCRIPTION    "Count the number of get request since startup. It can overflow"
              ::= { siteV1DataList 63}
siteV1DataModbusCounterReadRequest     OBJECT-TYPE
              SYNTAX          Integer32
              MAX-ACCESS      read-only
              STATUS          current
              DESCRIPTION    "Count the number of request since startup. It can overflow"
              ::= { siteV1DataList 155}
siteV1DataModbusCounterWriteRequest     OBJECT-TYPE
              SYNTAX          Integer32
              MAX-ACCESS      read-only
              STATUS          current
              DESCRIPTION    "Count the number of request since startup. It can overflow"
              ::= { siteV1DataList 156}
siteV1DataBuzzerState     OBJECT-TYPE
              SYNTAX          Integer32
              MAX-ACCESS      read-only
              STATUS          current
              DESCRIPTION    "The live state of the buzzer"
              ::= { siteV1DataList 270}
siteV1DataNetworkFirewallListeningTcpPorts     OBJECT-TYPE
              SYNTAX          DisplayString
              MAX-ACCESS      read-only
              STATUS          current
              DESCRIPTION    "NA"
              ::= { siteV1DataList 340}
siteV1DataNetworkFirewallListeningUdpPorts     OBJECT-TYPE
              SYNTAX          DisplayString
              MAX-ACCESS      read-only
              STATUS          current
              DESCRIPTION    "NA"
              ::= { siteV1DataList 341}
siteV1DataNetworkWifiEnabled     OBJECT-TYPE
              SYNTAX          Integer32
              MAX-ACCESS      read-only
              STATUS          current
              DESCRIPTION    "NA"
              ::= { siteV1DataList 390}
siteV1DataNetworkWifiRemainingMinutes     OBJECT-TYPE
              SYNTAX          Integer32
              MAX-ACCESS      read-only
              STATUS          current
              DESCRIPTION    "NA"
              ::= { siteV1DataList 391}
siteV1DataRelK1State     OBJECT-TYPE
              SYNTAX          Integer32
              MAX-ACCESS      read-only
              STATUS          current
              DESCRIPTION    "Actual state of the Relay"
              ::= { siteV1DataList 401}
siteV1DataRelK2State     OBJECT-TYPE
              SYNTAX          Integer32
              MAX-ACCESS      read-only
              STATUS          current
              DESCRIPTION    "Actual state of the Relay"
              ::= { siteV1DataList 406}
siteV1DataDigInputD1State     OBJECT-TYPE
              SYNTAX          Integer32
              MAX-ACCESS      read-only
              STATUS          current
              DESCRIPTION    "The state of the digital input"
              ::= { siteV1DataList 501}
siteV1DataDigInputD1Counter     OBJECT-TYPE
              SYNTAX          Integer32
              MAX-ACCESS      read-only
              STATUS          current
              DESCRIPTION    "The counter of state change"
              ::= { siteV1DataList 502}
siteV1DataDigInputD2State     OBJECT-TYPE
              SYNTAX          Integer32
              MAX-ACCESS      read-only
              STATUS          current
              DESCRIPTION    "The state of the digital input"
              ::= { siteV1DataList 506}
siteV1DataDigInputD2Counter     OBJECT-TYPE
              SYNTAX          Integer32
              MAX-ACCESS      read-only
              STATUS          current
              DESCRIPTION    "The counter of state change"
              ::= { siteV1DataList 507}
siteV1Config          OBJECT IDENTIFIER ::= { siteV1 15 }
siteV1ConfigNumber      OBJECT-TYPE
              SYNTAX          Integer32
              MAX-ACCESS      read-only
              STATUS          current
              DESCRIPTION    "The number of entries in the Config table related to the Site" 
              ::= { siteV1Config 1 }
siteV1ConfigTable      OBJECT-TYPE
              SYNTAX          SEQUENCE OF SiteV1ConfigEntry
              MAX-ACCESS      not-accessible
              STATUS          current
              DESCRIPTION    "The table of Config entries related to the Site" 
              ::= { siteV1Config 2 }
siteV1ConfigEntry      OBJECT-TYPE
              SYNTAX          SiteV1ConfigEntry
              MAX-ACCESS      not-accessible
              STATUS          current
              DESCRIPTION    "A Config entry"
              INDEX {siteV1ConfigIndex}
              ::= { siteV1ConfigTable 1 }
SiteV1ConfigEntry ::= 
             SEQUENCE{ 
             siteV1ConfigIndex       Unsigned32,  
             siteV1ConfigName        DisplayString,
             siteV1ConfigValue       DisplayString, 
              siteV1ConfigEntryStatus  RowStatus 
             }
siteV1ConfigIndex      OBJECT-TYPE
              SYNTAX          Unsigned32
              MAX-ACCESS      not-accessible
              STATUS          current
              DESCRIPTION    "The Config entry Index"
              ::= { siteV1ConfigEntry 1 }
siteV1ConfigName      OBJECT-TYPE
              SYNTAX          DisplayString
              MAX-ACCESS      read-only
              STATUS          current
              DESCRIPTION    "The Config entry name"
              ::= { siteV1ConfigEntry 2 }
siteV1ConfigValue     OBJECT-TYPE
              SYNTAX          DisplayString
              MAX-ACCESS      read-write
              STATUS          current
              DESCRIPTION    "The Config entry value"
              ::= { siteV1ConfigEntry 3 }
siteV1ConfigEntryStatus      OBJECT-TYPE
              SYNTAX          RowStatus
              MAX-ACCESS      read-create
              STATUS          current
              DESCRIPTION    "The status of this table entry - not used, only for compliance"
              ::= { siteV1ConfigEntry 4 }
siteV1ConfigList         OBJECT IDENTIFIER ::= { siteV1Config 3 }
siteV1CfgNetworkDHCPEnabled     OBJECT-TYPE
              SYNTAX          DisplayString
              MAX-ACCESS      read-write
              STATUS          current
              DESCRIPTION    "The monitoring will try to get an IP with the DHCP protocol if this parameter is set to True. By default, this parameter is set to False."
              ::= { siteV1ConfigList 1}
siteV1CfgNetworkIPAddressIfStatic     OBJECT-TYPE
              SYNTAX          DisplayString
              MAX-ACCESS      read-write
              STATUS          current
              DESCRIPTION    "The static IP address of the monitoring. This configuration parameter is not used if the DHCP is enabled. The default IP is 192.168.45.2."
              ::= { siteV1ConfigList 2}
siteV1CfgNetworkSubnetMaskIfStatic     OBJECT-TYPE
              SYNTAX          DisplayString
              MAX-ACCESS      read-write
              STATUS          current
              DESCRIPTION    "The static Subnet Mask of the monitoring. This configuration parameter is not used if the DHCP is enabled. The default mask is 255.255.255.0."
              ::= { siteV1ConfigList 3}
siteV1CfgNetworkDefaultGatewayIfStatic     OBJECT-TYPE
              SYNTAX          DisplayString
              MAX-ACCESS      read-write
              STATUS          current
              DESCRIPTION    "The static Default Gateway of the monitoring. This configuration parameter is not used if DHCP is enabled. This is only useful if the monitoring have to use a gateway, this is generally not necessary. The default gateway is 192.168.45.1."
              ::= { siteV1ConfigList 4}
siteV1CfgNetworkDNSIfStatic     OBJECT-TYPE
              SYNTAX          DisplayString
              MAX-ACCESS      read-write
              STATUS          current
              DESCRIPTION    "The static DNS of the monitoring. This configuration parameter is used to resolve URI and server name. This is not necessary if you are only IP address as target server. The default DNS server is 192.168.45.1."
              ::= { siteV1ConfigList 5}
siteV1CfgNetworkDNS2IfStatic     OBJECT-TYPE
              SYNTAX          DisplayString
              MAX-ACCESS      read-write
              STATUS          current
              DESCRIPTION    "The secondary static DNS of the monitoring. This configuration parameter is used to resolve URI and server name."
              ::= { siteV1ConfigList 6}
siteV1CfgTimeNTPTimeServer     OBJECT-TYPE
              SYNTAX          DisplayString
              MAX-ACCESS      read-write
              STATUS          current
              DESCRIPTION    "The address or hostname of the server acting as SNTP timer server. If this server is invalid, the time of the monitoring cannot be updated automatically. You can enter several comma-separated time servers (e.g. 'time.google.com,0.pool.ntp.org')."
              ::= { siteV1ConfigList 11}
siteV1CfgTimeTimeZoneName     OBJECT-TYPE
              SYNTAX          DisplayString
              MAX-ACCESS      read-write
              STATUS          current
              DESCRIPTION    "The Time Zone of the site"
              ::= { siteV1ConfigList 14}
siteV1CfgWebServerAuthenticationEnabled     OBJECT-TYPE
              SYNTAX          DisplayString
              MAX-ACCESS      read-write
              STATUS          current
              DESCRIPTION    "This is a True/False parameter used to activate or deactivate the access control to the web server."
              ::= { siteV1ConfigList 22}
siteV1CfgWebServerHttpPort     OBJECT-TYPE
              SYNTAX          DisplayString
              MAX-ACCESS      read-write
              STATUS          current
              DESCRIPTION    "This is an unsigned integer parameter used to configure the port at which the web server is accessible. By default, the port is 80. If you change this port, you must be sure that the traffic is allowed by your switches and routers on this port."
              ::= { siteV1ConfigList 23}
siteV1CfgWebServerAuthenticationMethod     OBJECT-TYPE
              SYNTAX          DisplayString
              MAX-ACCESS      read-write
              STATUS          current
              DESCRIPTION    "The web access security can be managed with 3 authentication methods: Basic Access, Digest Access or Basic with Radius."
              ::= { siteV1ConfigList 24}
siteV1CfgWebServerSessionTimeout     OBJECT-TYPE
              SYNTAX          DisplayString
              MAX-ACCESS      read-write
              STATUS          current
              DESCRIPTION    "The Timeout in minutes for token (Only used by Token Authentication)"
              ::= { siteV1ConfigList 25}
siteV1CfgWebServerHttpsPort     OBJECT-TYPE
              SYNTAX          DisplayString
              MAX-ACCESS      read-write
              STATUS          current
              DESCRIPTION    "This is a port number to activate or deactivate the https web server - 0 or 443 by default"
              ::= { siteV1ConfigList 26}
siteV1CfgWebServerRedirectHttptoHttps     OBJECT-TYPE
              SYNTAX          DisplayString
              MAX-ACCESS      read-write
              STATUS          current
              DESCRIPTION    "Redirect the Http request to Https"
              ::= { siteV1ConfigList 27}
siteV1CfgWebServerMinimalTLSVersion     OBJECT-TYPE
              SYNTAX          DisplayString
              MAX-ACCESS      read-write
              STATUS          current
              DESCRIPTION    "NA"
              ::= { siteV1ConfigList 28}
siteV1CfgWebServerDefaultPage     OBJECT-TYPE
              SYNTAX          DisplayString
              MAX-ACCESS      read-write
              STATUS          current
              DESCRIPTION    "The default page displayed on logon (dashboard, site, summary, alarm_event, ...)"
              ::= { siteV1ConfigList 31}
siteV1CfgWebServerLocalizationDatetimeFormat     OBJECT-TYPE
              SYNTAX          DisplayString
              MAX-ACCESS      read-write
              STATUS          current
              DESCRIPTION    "NA"
              ::= { siteV1ConfigList 35}
siteV1CfgWebServerLocalizationTempUnit     OBJECT-TYPE
              SYNTAX          DisplayString
              MAX-ACCESS      read-write
              STATUS          current
              DESCRIPTION    "NA"
              ::= { siteV1ConfigList 36}
siteV1CfgXMLEventPostingEnabled     OBJECT-TYPE
              SYNTAX          DisplayString
              MAX-ACCESS      read-write
              STATUS          current
              DESCRIPTION    "This is a True/False parameter used to activate or deactivate the XML event posting."
              ::= { siteV1ConfigList 41}
siteV1CfgXMLEventPostingRefreshPeriod     OBJECT-TYPE
              SYNTAX          DisplayString
              MAX-ACCESS      read-write
              STATUS          current
              DESCRIPTION    "The minimal time in second between to calculation of the XML events to send. By default, this is done every two seconds."
              ::= { siteV1ConfigList 42}
siteV1CfgXMLEventPostingTimeout     OBJECT-TYPE
              SYNTAX          DisplayString
              MAX-ACCESS      read-write
              STATUS          current
              DESCRIPTION    "The timeout in millisecond when trying to post XML data to a Web Server."
              ::= { siteV1ConfigList 43}
siteV1CfgXMLEventPostingPostToSecOnlyIfPrimFail     OBJECT-TYPE
              SYNTAX          DisplayString
              MAX-ACCESS      read-write
              STATUS          current
              DESCRIPTION    "If this parameter is set to true, the events will be sent to secondary only if primary server is not available. If this parameter is set to false, all the events will be sent to primary and secondary server"
              ::= { siteV1ConfigList 45}
siteV1CfgXMLEventPostingTablesToPostOnXMLEvent     OBJECT-TYPE
              SYNTAX          DisplayString
              MAX-ACCESS      read-write
              STATUS          current
              DESCRIPTION    "The list of the tables to send when an event is generated. (description,alarm,data,config,control). This allows to have armada database updated on event."
              ::= { siteV1ConfigList 46}
siteV1CfgXMLHeartbeatPeriod     OBJECT-TYPE
              SYNTAX          DisplayString
              MAX-ACCESS      read-write
              STATUS          current
              DESCRIPTION    "This is the time between 2 XML Post of heartbeat. If set to 0, no heartbeat."
              ::= { siteV1ConfigList 51}
siteV1CfgSNMPAgentGlobalEnabled     OBJECT-TYPE
              SYNTAX          DisplayString
              MAX-ACCESS      read-write
              STATUS          current
              DESCRIPTION    "This is a True/False parameter used to activate or deactivate the SNMP agent."
              ::= { siteV1ConfigList 61}
siteV1CfgSNMPAgentGlobalUdpPort     OBJECT-TYPE
              SYNTAX          DisplayString
              MAX-ACCESS      read-write
              STATUS          current
              DESCRIPTION    "Configure the port for SNMP Agent"
              ::= { siteV1ConfigList 62}
siteV1CfgSNMPAgentGlobalTrapVersion     OBJECT-TYPE
              SYNTAX          DisplayString
              MAX-ACCESS      read-write
              STATUS          current
              DESCRIPTION    "Traps/Notification can be sent with SNMP V1, V2c or V3 format."
              ::= { siteV1ConfigList 63}
siteV1CfgSNMPAgentGlobalGETMinSecurityLevel     OBJECT-TYPE
              SYNTAX          DisplayString
              MAX-ACCESS      read-write
              STATUS          current
              DESCRIPTION    "5 choices are available: Not Allowed, No Authentication, V1 Community, V2c Community or V3."
              ::= { siteV1ConfigList 64}
siteV1CfgSNMPAgentGlobalSETMinSecurityLevel     OBJECT-TYPE
              SYNTAX          DisplayString
              MAX-ACCESS      read-write
              STATUS          current
              DESCRIPTION    "5 choices are available: Not Allowed, No Authentication, V1 Community, V2c Community or V3."
              ::= { siteV1ConfigList 65}
siteV1CfgSNMPAgentV3AuthenticationAlgorithm     OBJECT-TYPE
              SYNTAX          DisplayString
              MAX-ACCESS      read-write
              STATUS          current
              DESCRIPTION    "3 choices are available: MD5, SHA, Any"
              ::= { siteV1ConfigList 66}
siteV1CfgSNMPAgentV3PrivacyAlgorithm     OBJECT-TYPE
              SYNTAX          DisplayString
              MAX-ACCESS      read-write
              STATUS          current
              DESCRIPTION    "3 choices are available: DES, AES (128 bits), 3DES"
              ::= { siteV1ConfigList 67}
siteV1CfgSNMPAgentV3PrivacyPassword     OBJECT-TYPE
              SYNTAX          DisplayString
              MAX-ACCESS      read-write
              STATUS          current
              DESCRIPTION    "The global SNMP V3 Encryption Password (Privacy key). This one is common for all the users to avoid complexity. If not define, privacy is not used. If set, privacy must be defined on NMS"
              ::= { siteV1ConfigList 68}
siteV1CfgSNMPAgentV3TrapAuthAlgorithm     OBJECT-TYPE
              SYNTAX          DisplayString
              MAX-ACCESS      read-write
              STATUS          current
              DESCRIPTION    "2 choices are available: MD5, SHA"
              ::= { siteV1ConfigList 72}
siteV1CfgSNMPAgentV3TrapPrivacyAlgorithm     OBJECT-TYPE
              SYNTAX          DisplayString
              MAX-ACCESS      read-write
              STATUS          current
              DESCRIPTION    "3 choices are available: DES, AES (128 bits), 3DES"
              ::= { siteV1ConfigList 73}
siteV1CfgSNMPAgentV3TrapUsername     OBJECT-TYPE
              SYNTAX          DisplayString
              MAX-ACCESS      read-write
              STATUS          current
              DESCRIPTION    "The SNMP V3 Trap UserName used for all the SNMP V3 traps"
              ::= { siteV1ConfigList 74}
siteV1CfgSNMPAgentV3TrapAuthPassword     OBJECT-TYPE
              SYNTAX          DisplayString
              MAX-ACCESS      read-write
              STATUS          current
              DESCRIPTION    "The SNMP V3 Trap Authentication Password"
              ::= { siteV1ConfigList 75}
siteV1CfgSNMPAgentV3TrapPrivacyPassword     OBJECT-TYPE
              SYNTAX          DisplayString
              MAX-ACCESS      read-write
              STATUS          current
              DESCRIPTION    "The SNMP V3 Trap Privacy Password"
              ::= { siteV1ConfigList 76}
siteV1CfgSNMPAgentGlobalSiteDescriptionIdsIncludedInTraps     OBJECT-TYPE
              SYNTAX          DisplayString
              MAX-ACCESS      read-write
              STATUS          current
              DESCRIPTION    "List of site Description Elements to send on traps. (to have the site reference and the city in each trap for example). The list is separated with ';'"
              ::= { siteV1ConfigList 77}
siteV1CfgSNMPAgentV1V2cReadCommunity     OBJECT-TYPE
              SYNTAX          DisplayString
              MAX-ACCESS      read-write
              STATUS          current
              DESCRIPTION    "If read community is defined, it bypass the user management for SNMP V1/V2c"
              ::= { siteV1ConfigList 79}
siteV1CfgGenericEventsGenerateEventOnConfChanges     OBJECT-TYPE
              SYNTAX          DisplayString
              MAX-ACCESS      read-write
              STATUS          current
              DESCRIPTION    "This is a True/False parameter used to activate or deactivate the tracking of configuration changes"
              ::= { siteV1ConfigList 81}
siteV1CfgDataRecordsAutoArchivePeriodDataRecord     OBJECT-TYPE
              SYNTAX          DisplayString
              MAX-ACCESS      read-write
              STATUS          current
              DESCRIPTION    "Period in hour to auto save records (when detailed and long duration records are needed). 0 means disabled."
              ::= { siteV1ConfigList 82}
siteV1CfgGenericEventsGenerateEventOnControlExecution     OBJECT-TYPE
              SYNTAX          DisplayString
              MAX-ACCESS      read-write
              STATUS          current
              DESCRIPTION    "This is a True/False parameter used to activate or deactivate the tracking of control execution"
              ::= { siteV1ConfigList 83}
siteV1CfgGenericEventsGenerateEventOnAlarmAcknowledge     OBJECT-TYPE
              SYNTAX          DisplayString
              MAX-ACCESS      read-write
              STATUS          current
              DESCRIPTION    "This is a True/False parameter used to activate or deactivate the tracking of alarm acknowledgment"
              ::= { siteV1ConfigList 84}
siteV1CfgInventoryCANBusCANOpenRequiredNodeIds     OBJECT-TYPE
              SYNTAX          DisplayString
              MAX-ACCESS      read-write
              STATUS          current
              DESCRIPTION    "This is a coma separated list with the required CAN bus node ids"
              ::= { siteV1ConfigList 91}
siteV1CfgInventoryCANBusCANOpenLSSIdRange     OBJECT-TYPE
              SYNTAX          DisplayString
              MAX-ACCESS      read-write
              STATUS          current
              DESCRIPTION    "By default 50-80, means up to 50 Can Nodes like rectifiers with CAN Id 50 to 80. To support up to 100 rectifiers, change it to 1-100."
              ::= { siteV1ConfigList 92}
siteV1CfgInventoryCANBusCANOpenSystemDefinition     OBJECT-TYPE
              SYNTAX          DisplayString
              MAX-ACCESS      read-write
              STATUS          current
              DESCRIPTION    "Used to define new systems with or without ADIO. Example: dc3(30-100) or es1_dc1(es1_inv1,111) to bind an sierra system with ADIO10. A reboot is required after change of value."
              ::= { siteV1ConfigList 93}
siteV1CfgInventoryCANBusCANOpenLSSSavedConf     OBJECT-TYPE
              SYNTAX          DisplayString
              MAX-ACCESS      read-write
              STATUS          current
              DESCRIPTION    "NA"
              ::= { siteV1ConfigList 95}
siteV1CfgUsersAdministratorLoginPassword     OBJECT-TYPE
              SYNTAX          DisplayString
              MAX-ACCESS      read-write
              STATUS          current
              DESCRIPTION    "This is the login and the password of the administrator. It is saved with a special syntax. First the login in clear, followed of 2 points, followed by encrypted or hashed password. If you change the login:password by entering a non hashed password, this last is automatically hashed."
              ::= { siteV1ConfigList 101}
siteV1CfgUsersUser1LoginPassword     OBJECT-TYPE
              SYNTAX          DisplayString
              MAX-ACCESS      read-write
              STATUS          current
              DESCRIPTION    "This is the login and the password of the user number 1."
              ::= { siteV1ConfigList 102}
siteV1CfgUsersUser2LoginPassword     OBJECT-TYPE
              SYNTAX          DisplayString
              MAX-ACCESS      read-write
              STATUS          current
              DESCRIPTION    "This is the login and the password of the user number 2."
              ::= { siteV1ConfigList 103}
siteV1CfgUsersUser3LoginPassword     OBJECT-TYPE
              SYNTAX          DisplayString
              MAX-ACCESS      read-write
              STATUS          current
              DESCRIPTION    "This is the login and the password of the user number 3."
              ::= { siteV1ConfigList 104}
siteV1CfgUsersUser4LoginPassword     OBJECT-TYPE
              SYNTAX          DisplayString
              MAX-ACCESS      read-write
              STATUS          current
              DESCRIPTION    "This is the login and the password of the user number 4."
              ::= { siteV1ConfigList 105}
siteV1CfgUsersUser5LoginPassword     OBJECT-TYPE
              SYNTAX          DisplayString
              MAX-ACCESS      read-write
              STATUS          current
              DESCRIPTION    "This is the login and the password of the user number 5."
              ::= { siteV1ConfigList 106}
siteV1CfgRadiusAuthenticationServer     OBJECT-TYPE
              SYNTAX          DisplayString
              MAX-ACCESS      read-write
              STATUS          current
              DESCRIPTION    "Radius Server address. If you have a secondary server, you could use a coma to separate it."
              ::= { siteV1ConfigList 111}
siteV1CfgRadiusAuthenticationPort     OBJECT-TYPE
              SYNTAX          DisplayString
              MAX-ACCESS      read-write
              STATUS          current
              DESCRIPTION    "Radius Port. If you have a secondary server, you could use a coma to separate it."
              ::= { siteV1ConfigList 112}
siteV1CfgRadiusAuthenticationSecret     OBJECT-TYPE
              SYNTAX          DisplayString
              MAX-ACCESS      read-write
              STATUS          current
              DESCRIPTION    "Radius PassPhrase"
              ::= { siteV1ConfigList 113}
siteV1CfgEmailEnabled     OBJECT-TYPE
              SYNTAX          DisplayString
              MAX-ACCESS      read-write
              STATUS          current
              DESCRIPTION    "Enable/Disable the email feature"
              ::= { siteV1ConfigList 120}
siteV1CfgEmailServer     OBJECT-TYPE
              SYNTAX          DisplayString
              MAX-ACCESS      read-write
              STATUS          current
              DESCRIPTION    "Smtp Server. If you are using a domain name, make sure you configured the network Dns (CF5)"
              ::= { siteV1ConfigList 121}
siteV1CfgEmailDomain     OBJECT-TYPE
              SYNTAX          DisplayString
              MAX-ACCESS      read-write
              STATUS          current
              DESCRIPTION    "Smtp Domain. (Required by some servers.)"
              ::= { siteV1ConfigList 122}
siteV1CfgEmailCredentials     OBJECT-TYPE
              SYNTAX          DisplayString
              MAX-ACCESS      read-write
              STATUS          current
              DESCRIPTION    "Smtp Login and Password. The password is encrypted. To enter a new login and password, enter login:password and validate, the password will be encrypted."
              ::= { siteV1ConfigList 123}
siteV1CfgEmailSender     OBJECT-TYPE
              SYNTAX          DisplayString
              MAX-ACCESS      read-write
              STATUS          current
              DESCRIPTION    "Mail Sender (The 'From' of the emails you will receive)"
              ::= { siteV1ConfigList 130}
siteV1CfgEmailRecipients     OBJECT-TYPE
              SYNTAX          DisplayString
              MAX-ACCESS      read-write
              STATUS          current
              DESCRIPTION    "Mail Recipients, separated with semicolon ';'"
              ::= { siteV1ConfigList 131}
siteV1CfgEmailMinimalEventSeverityForSending     OBJECT-TYPE
              SYNTAX          DisplayString
              MAX-ACCESS      read-write
              STATUS          current
              DESCRIPTION    "This is the minimal severity of the event to send a Summary Mail"
              ::= { siteV1ConfigList 135}
siteV1CfgControllerFeaturesExtensions     OBJECT-TYPE
              SYNTAX          DisplayString
              MAX-ACCESS      read-write
              STATUS          current
              DESCRIPTION    "NA"
              ::= { siteV1ConfigList 140}
siteV1CfgControllerRebootAutomaticReboot     OBJECT-TYPE
              SYNTAX          DisplayString
              MAX-ACCESS      read-write
              STATUS          current
              DESCRIPTION    "Cron rules used in order to restart automatically the controller. Before rebooting configuration, events and data records are saved."
              ::= { siteV1ConfigList 150}
siteV1CfgModbusTcpEnabled     OBJECT-TYPE
              SYNTAX          DisplayString
              MAX-ACCESS      read-write
              STATUS          current
              DESCRIPTION    "This is a True/False parameter used to activate or deactivate the modbus interface."
              ::= { siteV1ConfigList 155}
siteV1CfgModbusTcpPort     OBJECT-TYPE
              SYNTAX          DisplayString
              MAX-ACCESS      read-write
              STATUS          current
              DESCRIPTION    "Configure the TCP port for Modbus"
              ::= { siteV1ConfigList 156}
siteV1CfgModbusGlobalWriteEnabled     OBJECT-TYPE
              SYNTAX          DisplayString
              MAX-ACCESS      read-write
              STATUS          current
              DESCRIPTION    "Allow writing registers"
              ::= { siteV1ConfigList 157}
siteV1CfgIOTMQTTLinkEnabled     OBJECT-TYPE
              SYNTAX          DisplayString
              MAX-ACCESS      read-write
              STATUS          current
              DESCRIPTION    "Enable Cloud Connection"
              ::= { siteV1ConfigList 171}
siteV1CfgInventoryCANBusBitrate     OBJECT-TYPE
              SYNTAX          DisplayString
              MAX-ACCESS      read-write
              STATUS          current
              DESCRIPTION    "BitRate for CAN0: most common are 125,250,500,1000"
              ::= { siteV1ConfigList 190}
siteV1CfgInventoryRS485BusBaudRate     OBJECT-TYPE
              SYNTAX          DisplayString
              MAX-ACCESS      read-write
              STATUS          current
              DESCRIPTION    "Baudrate for RS485 : 9600,19200,38400,57600,115200,230400,1000000"
              ::= { siteV1ConfigList 205}
siteV1CfgInventoryRS485BusParity     OBJECT-TYPE
              SYNTAX          DisplayString
              MAX-ACCESS      read-write
              STATUS          current
              DESCRIPTION    "Parity for RS485 : None,Odd,Even,Mark,Space"
              ::= { siteV1ConfigList 206}
siteV1CfgInventoryRS485BusExtensionsConf     OBJECT-TYPE
              SYNTAX          DisplayString
              MAX-ACCESS      read-write
              STATUS          current
              DESCRIPTION    "The configuration string for RS485 Extensions. For enabling modbus RTU, set MODBUS_RTU_SLAVE. This mode do no allow monitoring and control of other devices."
              ::= { siteV1ConfigList 210}
siteV1CfgInventoryEthernetExtensionsConf     OBJECT-TYPE
              SYNTAX          DisplayString
              MAX-ACCESS      read-write
              STATUS          current
              DESCRIPTION    "The configuration string for Ethernet Extensions like the Inview Gateway, a list can be defined with semicolon separator"
              ::= { siteV1ConfigList 220}
siteV1CfgInventoryUSBExtensionsConf     OBJECT-TYPE
              SYNTAX          DisplayString
              MAX-ACCESS      read-write
              STATUS          current
              DESCRIPTION    "The configuration string for USB Extensions like interface with Victron, a list can be defined with semicolon separator"
              ::= { siteV1ConfigList 230}
siteV1CfgLedLedBehaviour     OBJECT-TYPE
              SYNTAX          DisplayString
              MAX-ACCESS      read-write
              STATUS          current
              DESCRIPTION    "You can control the behaviour of the led in the front of UCC. With Site Level Only, the led will reflect only the status of the Site without taking in account the state of Sensors and actuators or other. With global status, the led will show the highest level of severity found in all your devices"
              ::= { siteV1ConfigList 240}
siteV1CfgScriptingLuaEnabled     OBJECT-TYPE
              SYNTAX          DisplayString
              MAX-ACCESS      read-write
              STATUS          current
              DESCRIPTION    "This parameter enable all CompasLua Scripting capabilities. You can control scripts in Files -> Files manager > scripting tab."
              ::= { siteV1ConfigList 250}
siteV1CfgScriptingLuaNumberofErrorsBeforeTriggeringAlarm     OBJECT-TYPE
              SYNTAX          DisplayString
              MAX-ACCESS      read-write
              STATUS          current
              DESCRIPTION    "Number of errors before triggering the scripting error alarm. When number of error is higher than this parameter, the alarm is triggered. If 0 is set, the alarm is deactivated"
              ::= { siteV1ConfigList 251}
siteV1CfgScriptingPythonEnabled     OBJECT-TYPE
              SYNTAX          DisplayString
              MAX-ACCESS      read-write
              STATUS          current
              DESCRIPTION    "This parameter enable all CompasPython Scripting capabilities. You can control scripts in Files -> Files manager > scripting tab."
              ::= { siteV1ConfigList 260}
siteV1CfgScriptingPythonNumberofErrorsBeforeTriggeringAlarm     OBJECT-TYPE
              SYNTAX          DisplayString
              MAX-ACCESS      read-write
              STATUS          current
              DESCRIPTION    "Number of errors before triggering the scripting error alarm. When number of error is higher than this parameter, the alarm is triggered. If 0 is set, the alarm is deactivated"
              ::= { siteV1ConfigList 261}
siteV1CfgScriptingPythonEnabledScripts     OBJECT-TYPE
              SYNTAX          DisplayString
              MAX-ACCESS      read-write
              STATUS          current
              DESCRIPTION    "NA"
              ::= { siteV1ConfigList 262}
siteV1CfgBuzzerEnabled     OBJECT-TYPE
              SYNTAX          DisplayString
              MAX-ACCESS      read-write
              STATUS          current
              DESCRIPTION    "Enable / Disable Buzzer"
              ::= { siteV1ConfigList 270}
siteV1CfgBuzzerSoundNotificationforMajorAlarms     OBJECT-TYPE
              SYNTAX          DisplayString
              MAX-ACCESS      read-write
              STATUS          current
              DESCRIPTION    "You can control the behaviour of the Buzzer."
              ::= { siteV1ConfigList 271}
siteV1CfgBuzzerSoundNotificationforMinorAlarms     OBJECT-TYPE
              SYNTAX          DisplayString
              MAX-ACCESS      read-write
              STATUS          current
              DESCRIPTION    "You can control the behaviour of the Buzzer."
              ::= { siteV1ConfigList 272}
siteV1CfgDisplayGlobalEnabled     OBJECT-TYPE
              SYNTAX          DisplayString
              MAX-ACCESS      read-write
              STATUS          current
              DESCRIPTION    "Allow to disable the display service"
              ::= { siteV1ConfigList 279}
siteV1CfgDisplayCredentialsPinCode     OBJECT-TYPE
              SYNTAX          DisplayString
              MAX-ACCESS      read-write
              STATUS          current
              DESCRIPTION    "Pin code for actions on display"
              ::= { siteV1ConfigList 280}
siteV1CfgDisplayBacklightLevel     OBJECT-TYPE
              SYNTAX          DisplayString
              MAX-ACCESS      read-write
              STATUS          current
              DESCRIPTION    "Backlight level between 40 and 100%"
              ::= { siteV1ConfigList 281}
siteV1CfgDisplayBacklightTimeout     OBJECT-TYPE
              SYNTAX          DisplayString
              MAX-ACCESS      read-write
              STATUS          current
              DESCRIPTION    "Timeout in second, -1 to disable"
              ::= { siteV1ConfigList 282}
siteV1CfgNetworkFirewallAllowICMP     OBJECT-TYPE
              SYNTAX          DisplayString
              MAX-ACCESS      read-write
              STATUS          current
              DESCRIPTION    "Enable support for Ping and Traceroute"
              ::= { siteV1ConfigList 350}
siteV1CfgNetworkFirewallAllowDebugConnection     OBJECT-TYPE
              SYNTAX          DisplayString
              MAX-ACCESS      read-write
              STATUS          current
              DESCRIPTION    "Enable Secured Shell"
              ::= { siteV1ConfigList 351}
siteV1CfgNetworkFirewallAllowHttp     OBJECT-TYPE
              SYNTAX          DisplayString
              MAX-ACCESS      read-write
              STATUS          current
              DESCRIPTION    "Enable Http"
              ::= { siteV1ConfigList 352}
siteV1CfgNetworkFirewallAllowedIpSourcebyMqttBroker     OBJECT-TYPE
              SYNTAX          DisplayString
              MAX-ACCESS      read-write
              STATUS          current
              DESCRIPTION    "Allows MQTT connections to internal broker (unsecured). Can be used to connect Inview GW, or to test python scripting from a computer. This is an advanced feature"
              ::= { siteV1ConfigList 353}
siteV1CfgNetworkWifiActivation     OBJECT-TYPE
              SYNTAX          DisplayString
              MAX-ACCESS      read-write
              STATUS          current
              DESCRIPTION    "NA"
              ::= { siteV1ConfigList 390}
siteV1CfgRelK1Mode     OBJECT-TYPE
              SYNTAX          DisplayString
              MAX-ACCESS      read-write
              STATUS          current
              DESCRIPTION    "Mode of the relay"
              ::= { siteV1ConfigList 401}
siteV1CfgRelK1DefaultState     OBJECT-TYPE
              SYNTAX          DisplayString
              MAX-ACCESS      read-write
              STATUS          current
              DESCRIPTION    "Relay 1 Normal State"
              ::= { siteV1ConfigList 402}
siteV1CfgRelK2Mode     OBJECT-TYPE
              SYNTAX          DisplayString
              MAX-ACCESS      read-write
              STATUS          current
              DESCRIPTION    "Mode of the relay"
              ::= { siteV1ConfigList 406}
siteV1CfgRelK2DefaultState     OBJECT-TYPE
              SYNTAX          DisplayString
              MAX-ACCESS      read-write
              STATUS          current
              DESCRIPTION    "Relay 2 Normal State"
              ::= { siteV1ConfigList 407}
siteV1CfgDigInputD1Mode     OBJECT-TYPE
              SYNTAX          DisplayString
              MAX-ACCESS      read-write
              STATUS          current
              DESCRIPTION    "The mode of the digital input"
              ::= { siteV1ConfigList 501}
siteV1CfgDigInputD1NormallyClosed     OBJECT-TYPE
              SYNTAX          DisplayString
              MAX-ACCESS      read-write
              STATUS          current
              DESCRIPTION    "Define if normally closed is the default state"
              ::= { siteV1ConfigList 502}
siteV1CfgDigInputD2Mode     OBJECT-TYPE
              SYNTAX          DisplayString
              MAX-ACCESS      read-write
              STATUS          current
              DESCRIPTION    "The mode of the digital input"
              ::= { siteV1ConfigList 506}
siteV1CfgDigInputD2NormallyClosed     OBJECT-TYPE
              SYNTAX          DisplayString
              MAX-ACCESS      read-write
              STATUS          current
              DESCRIPTION    "Define if normally closed is the default state"
              ::= { siteV1ConfigList 507}
siteV1CfgGenericEventsEventTableLength     OBJECT-TYPE
              SYNTAX          DisplayString
              MAX-ACCESS      read-write
              STATUS          current
              DESCRIPTION    "The maximum length of the table. The value must be comprised between 10 and 4000"
              ::= { siteV1ConfigList 601}
siteV1CfgSNMPAgentGlobalTrapTargetsIP     OBJECT-TYPE
              SYNTAX          DisplayString
              MAX-ACCESS      read-write
              STATUS          current
              DESCRIPTION    "One or multiple target IP to send traps, coma separated. Ex: 130.145.23.1, 130.23.12.45"
              ::= { siteV1ConfigList 611}
siteV1CfgSNMPAgentTrapsMinimalEventSeverityForSending     OBJECT-TYPE
              SYNTAX          DisplayString
              MAX-ACCESS      read-write
              STATUS          current
              DESCRIPTION    "This is the minimal severity of the event to send a SNMP trap"
              ::= { siteV1ConfigList 612}
siteV1CfgXMLEventPostingPrimPostURL     OBJECT-TYPE
              SYNTAX          DisplayString
              MAX-ACCESS      read-write
              STATUS          current
              DESCRIPTION    "This is the first URL at which the events related to this equipment must be posted. The XML ETSI standard is used in the posted data content."
              ::= { siteV1ConfigList 651}
siteV1CfgXMLEventPostingPrimPostLogin     OBJECT-TYPE
              SYNTAX          DisplayString
              MAX-ACCESS      read-write
              STATUS          current
              DESCRIPTION    "The login which must be used when posting events to the primary server"
              ::= { siteV1ConfigList 652}
siteV1CfgXMLEventPostingPrimPostPassword     OBJECT-TYPE
              SYNTAX          DisplayString
              MAX-ACCESS      read-write
              STATUS          current
              DESCRIPTION    "The password which must be used when posting events to the primary server"
              ::= { siteV1ConfigList 653}
siteV1CfgXMLEventPostingSecPostURL     OBJECT-TYPE
              SYNTAX          DisplayString
              MAX-ACCESS      read-write
              STATUS          current
              DESCRIPTION    "This is the second URL at which the events related to this equipment must be posted. The XML ETSI standard is used in the posted data content. This allows having redundancy with the management server."
              ::= { siteV1ConfigList 661}
siteV1CfgXMLEventPostingSecPostLogin     OBJECT-TYPE
              SYNTAX          DisplayString
              MAX-ACCESS      read-write
              STATUS          current
              DESCRIPTION    "The login which must be used when posting events to the secondary server"
              ::= { siteV1ConfigList 662}
siteV1CfgXMLEventPostingSecPostPassword     OBJECT-TYPE
              SYNTAX          DisplayString
              MAX-ACCESS      read-write
              STATUS          current
              DESCRIPTION    "The password which must be used when posting events to the secondary server"
              ::= { siteV1ConfigList 663}
siteV1CfgPLCGlobalNumberOfCustomData     OBJECT-TYPE
              SYNTAX          DisplayString
              MAX-ACCESS      read-write
              STATUS          current
              DESCRIPTION    "The number of PLC data. Every equipment can manage up to 30 user programmable data. Data elements are automatically added in the data table. Configuration parameters are added to set the PLC Data Name and the PLC Data Mathematical calculation. In order to use these functionalities, you need a license with the 'PLC' module"
              ::= { siteV1ConfigList 901}
siteV1CfgPLCGlobalNumberOfCustomAlarm     OBJECT-TYPE
              SYNTAX          DisplayString
              MAX-ACCESS      read-write
              STATUS          current
              DESCRIPTION    "The number of PLC alarm. Every equipment can manage up to 30 user programmable alarms. Alarm elements are automatically added in the alarm table. The alarm parameters are added to set the PLC Alarm Name and the PLC Alarm Boolean condition. In order to use these functionalities, you need a licence with the 'PLC' module"
              ::= { siteV1ConfigList 902}
siteV1Control          OBJECT IDENTIFIER ::= { siteV1 16 }
siteV1ControlNumber      OBJECT-TYPE
              SYNTAX          Integer32
              MAX-ACCESS      read-only
              STATUS          current
              DESCRIPTION    "The number of entries in the Control table related to the Site" 
              ::= { siteV1Control 1 }
siteV1ControlTable      OBJECT-TYPE
              SYNTAX          SEQUENCE OF SiteV1ControlEntry
              MAX-ACCESS      not-accessible
              STATUS          current
              DESCRIPTION    "The table of Control entries related to the Site" 
              ::= { siteV1Control 2 }
siteV1ControlEntry      OBJECT-TYPE
              SYNTAX          SiteV1ControlEntry
              MAX-ACCESS      not-accessible
              STATUS          current
              DESCRIPTION    "A Control entry"
              INDEX {siteV1ControlIndex}
              ::= { siteV1ControlTable 1 }
SiteV1ControlEntry ::= 
             SEQUENCE{ 
             siteV1ControlIndex       Unsigned32,  
             siteV1ControlName        DisplayString,
             siteV1ControlValue       DisplayString, 
              siteV1ControlEntryStatus  RowStatus 
             }
siteV1ControlIndex      OBJECT-TYPE
              SYNTAX          Unsigned32
              MAX-ACCESS      not-accessible
              STATUS          current
              DESCRIPTION    "The Control entry Index"
              ::= { siteV1ControlEntry 1 }
siteV1ControlName      OBJECT-TYPE
              SYNTAX          DisplayString
              MAX-ACCESS      read-only
              STATUS          current
              DESCRIPTION    "The Control entry name"
              ::= { siteV1ControlEntry 2 }
siteV1ControlValue     OBJECT-TYPE
              SYNTAX          DisplayString
              MAX-ACCESS      read-write
              STATUS          current
              DESCRIPTION    "The Control entry value"
              ::= { siteV1ControlEntry 3 }
siteV1ControlEntryStatus      OBJECT-TYPE
              SYNTAX          RowStatus
              MAX-ACCESS      read-create
              STATUS          current
              DESCRIPTION    "The status of this table entry - not used, only for compliance"
              ::= { siteV1ControlEntry 4 }
siteV1ControlList         OBJECT IDENTIFIER ::= { siteV1Control 3 }
siteV1CtrlControllerRebootRebootController     OBJECT-TYPE
              SYNTAX          DisplayString
              MAX-ACCESS      read-write
              STATUS          current
              DESCRIPTION    "Writing a '1' to this control element will reboot the monitoring. Events and Records will be saved."
              ::= { siteV1ControlList 1}
siteV1CtrlControllerRebootSaveConfAndRebootController     OBJECT-TYPE
              SYNTAX          DisplayString
              MAX-ACCESS      read-write
              STATUS          current
              DESCRIPTION    "Writing a '1' to this control element will first save the actual configuration and will reboot the monitoring after."
              ::= { siteV1ControlList 2}
siteV1CtrlControllerRebootRebootControllerWithoutSavingRecords     OBJECT-TYPE
              SYNTAX          DisplayString
              MAX-ACCESS      read-write
              STATUS          current
              DESCRIPTION    "Writing a '1' to this control element will reboot the monitoring without saving records"
              ::= { siteV1ControlList 3}
siteV1CtrlNetworkApplyNetworkConf     OBJECT-TYPE
              SYNTAX          DisplayString
              MAX-ACCESS      read-write
              STATUS          current
              DESCRIPTION    "Writing a '1' to this control element will reconfigure the ethernet according to the Network Configuration. If you change the IP address in the config table without using this command after, the configuration is not applied."
              ::= { siteV1ControlList 6}
siteV1CtrlTimeForceSNTPTimeRefresh     OBJECT-TYPE
              SYNTAX          DisplayString
              MAX-ACCESS      read-write
              STATUS          current
              DESCRIPTION    "Writing a '1' to this control element will force the monitoring to try to refresh his time with the configured SNTP Time Server."
              ::= { siteV1ControlList 11}
siteV1CtrlTimeSetLocalTime     OBJECT-TYPE
              SYNTAX          DisplayString
              MAX-ACCESS      read-write
              STATUS          current
              DESCRIPTION    "Writing a date and time to this control element allows to manually change the local time of the monitoring. The syntax of the date and the time is: 2007-11-19T13:02:34"
              ::= { siteV1ControlList 12}
siteV1CtrlTimeSetUTCTime     OBJECT-TYPE
              SYNTAX          DisplayString
              MAX-ACCESS      read-write
              STATUS          current
              DESCRIPTION    "Writing a date and time to this control element allows to manually change the UTC time of the monitoring. The syntax of the date and the time is: 2007-11-19T13:02:34"
              ::= { siteV1ControlList 13}
siteV1CtrlTimeResetUptime     OBJECT-TYPE
              SYNTAX          DisplayString
              MAX-ACCESS      read-write
              STATUS          current
              DESCRIPTION    "Writing a '1' to this control element will reset the uptime of the monitoring."
              ::= { siteV1ControlList 14}
siteV1CtrlControllerSaveCleanandSaveXMLUserConf     OBJECT-TYPE
              SYNTAX          DisplayString
              MAX-ACCESS      read-write
              STATUS          current
              DESCRIPTION    "Writing a '1' to this control element will remove the configuration sections related to missing equipments, than save all the configuration of all the connected equipment in a XML format. This file is read when the monitoring is starting in order to configure the monitoring. This file is also accessible trough the FTP server or can be downloaded trough the web interface."
              ::= { siteV1ControlList 20}
siteV1CtrlControllerSaveSaveXMLUserConf     OBJECT-TYPE
              SYNTAX          DisplayString
              MAX-ACCESS      read-write
              STATUS          current
              DESCRIPTION    "Writing a '1' to this control element will save all the configuration of all the connected (or previously connected) equipment in a XML format. This file is read when the monitoring is starting in order to configure the monitoring. This file is also accessible trough the FTP server or can be downloaded trough the web interface."
              ::= { siteV1ControlList 21}
siteV1CtrlDataRecordsSaveDataRecords     OBJECT-TYPE
              SYNTAX          DisplayString
              MAX-ACCESS      read-write
              STATUS          current
              DESCRIPTION    "Writing a '1' to this control element will force the monitoring to save all the data records. This is useful if you want to un-power the Compas monitoring. This function is called automatically everyday."
              ::= { siteV1ControlList 33}
siteV1CtrlDataRecordsExportDataRecordsinCSV     OBJECT-TYPE
              SYNTAX          DisplayString
              MAX-ACCESS      read-write
              STATUS          current
              DESCRIPTION    "Writing a '1' to this control element will force the monitoring to save all the CVS records files. The CSV files are stored in the records folder."
              ::= { siteV1ControlList 34}
siteV1CtrlDataRecordsArchiveDataRecords     OBJECT-TYPE
              SYNTAX          DisplayString
              MAX-ACCESS      read-write
              STATUS          current
              DESCRIPTION    "Writing a '1' to this control element will force the monitoring to archive in CSV all the data records."
              ::= { siteV1ControlList 35}
siteV1CtrlDataRecordsDeleteAllDataRecords     OBJECT-TYPE
              SYNTAX          DisplayString
              MAX-ACCESS      read-write
              STATUS          current
              DESCRIPTION    "Writing a '1' to this control element will force the monitoring to delete all the data records."
              ::= { siteV1ControlList 36}
siteV1CtrlControllerTranslationReloadTranslationFiles     OBJECT-TYPE
              SYNTAX          DisplayString
              MAX-ACCESS      read-write
              STATUS          current
              DESCRIPTION    "Writing a '1' to this control element will reload all the csv translation files"
              ::= { siteV1ControlList 41}
siteV1CtrlControllerLicenseReloadLicense     OBJECT-TYPE
              SYNTAX          DisplayString
              MAX-ACCESS      read-write
              STATUS          current
              DESCRIPTION    "Writing a '1' to this control element will reload the license file"
              ::= { siteV1ControlList 51}
siteV1CtrlInventoryGeneralSave     OBJECT-TYPE
              SYNTAX          DisplayString
              MAX-ACCESS      read-write
              STATUS          current
              DESCRIPTION    "Writing a '1' to this control element will save save the inventory in a XML format. This file is read when the monitoring is starting in order to configure the monitoring. This file is also accessible trough the FTP server or can be downloaded trough the web interface."
              ::= { siteV1ControlList 60}
siteV1CtrlInventoryGeneralCleanEquipmentInventory     OBJECT-TYPE
              SYNTAX          DisplayString
              MAX-ACCESS      read-write
              STATUS          current
              DESCRIPTION    "NA"
              ::= { siteV1ControlList 61}
siteV1CtrlInventoryCANBusResetCANBusNode     OBJECT-TYPE
              SYNTAX          DisplayString
              MAX-ACCESS      read-write
              STATUS          current
              DESCRIPTION    "Writing a valid CAN bus node id to this control element will reset the correspondent device."
              ::= { siteV1ControlList 81}
siteV1CtrlInventoryCANBusSaveCANOpenLSSConf     OBJECT-TYPE
              SYNTAX          DisplayString
              MAX-ACCESS      read-write
              STATUS          current
              DESCRIPTION    "NA"
              ::= { siteV1ControlList 82}
siteV1CtrlInventoryCANBusStartNewLSSInventory     OBJECT-TYPE
              SYNTAX          DisplayString
              MAX-ACCESS      read-write
              STATUS          current
              DESCRIPTION    "NA"
              ::= { siteV1ControlList 83}
siteV1CtrlInventoryCANBusUpgradeNodeFirmware     OBJECT-TYPE
              SYNTAX          DisplayString
              MAX-ACCESS      read-write
              STATUS          current
              DESCRIPTION    "This control element is used to start the firmware upgrade of a CAN bus Node. You need to upload first the firmware trough ftp in the /user/firmware path. Then you need to write the id number of the CAN Node, followed by a coma, followed by the file name. Example : '101,SOFT_0000030_01.txt'."
              ::= { siteV1ControlList 91}
siteV1CtrlInventoryCANBusCancelFirmwareUpgrade     OBJECT-TYPE
              SYNTAX          DisplayString
              MAX-ACCESS      read-write
              STATUS          current
              DESCRIPTION    "This control element is used to cancel the running firmware upgrade of a CAN bus Node."
              ::= { siteV1ControlList 92}
siteV1CtrlFilesFlashBinary     OBJECT-TYPE
              SYNTAX          DisplayString
              MAX-ACCESS      read-write
              STATUS          current
              DESCRIPTION    "This control element is used to start a binary flash update of the operating system. You need to upload first the firmware trough ftp in the /user/firmware path."
              ::= { siteV1ControlList 103}
siteV1CtrlFilesDownloadFileFromUrl     OBJECT-TYPE
              SYNTAX          DisplayString
              MAX-ACCESS      read-write
              STATUS          current
              DESCRIPTION    "This control element is used to download a file with HTTP get, the argument is an url. The file is saved in the upload folder"
              ::= { siteV1ControlList 110}
siteV1CtrlFilesDeleteUserUploadedFile     OBJECT-TYPE
              SYNTAX          DisplayString
              MAX-ACCESS      read-write
              STATUS          current
              DESCRIPTION    "This control element is used to delete a file in the user-upload folder. This is riskless as these files are not used, they are temporary files. "
              ::= { siteV1ControlList 111}
siteV1CtrlFilesMoveUserUploadedFile     OBJECT-TYPE
              SYNTAX          DisplayString
              MAX-ACCESS      read-write
              STATUS          current
              DESCRIPTION    "This control element is used to copy a file from the user-upload folder to another one. Be aware of what your are doing !"
              ::= { siteV1ControlList 112}
siteV1CtrlFilesExtractZipFileinuserupload     OBJECT-TYPE
              SYNTAX          DisplayString
              MAX-ACCESS      read-write
              STATUS          current
              DESCRIPTION    "This control element is used to delete a file in the user-upload folder. This is risk-less as these files are not used, they are temporary files. "
              ::= { siteV1ControlList 113}
siteV1CtrlEmailSendReport     OBJECT-TYPE
              SYNTAX          DisplayString
              MAX-ACCESS      read-write
              STATUS          current
              DESCRIPTION    "This control element is used to force the sending of a summary to the configured mail address"
              ::= { siteV1ControlList 120}
siteV1CtrlInventoryEthernetUpgradeNodeFirmware     OBJECT-TYPE
              SYNTAX          DisplayString
              MAX-ACCESS      read-write
              STATUS          current
              DESCRIPTION    "This control element is used to start the firmware upgrade of an ethernet device. You need to upload first the firmware in /user/firmware path. Then you need to write the ip address, followed by a coma, followed by the file name. Example : '10.250.251.1,ninja_ext.zip'."
              ::= { siteV1ControlList 220}
siteV1CtrlScriptingLuaCommand     OBJECT-TYPE
              SYNTAX          DisplayString
              MAX-ACCESS      read-write
              STATUS          current
              DESCRIPTION    "This control element is used to control the lua scripting system. Available command are: enable[Enable Lua Capabilities], disable[Disable Lua Capabilities], restart[Restart All Lua Capabilities], refresh[Read the folder script (if you added a file when system is running)], enable filename[enable filename.lua located in folder user/scripts], disable filename[disable filename.lua located in folder user/scripts], restart filename : Restart fileName[file must be enabled], reseterrors[Reset all errors counters], reseterrors filename[Reset errors from filename"
              ::= { siteV1ControlList 250}
siteV1CtrlScriptingPythonCommand     OBJECT-TYPE
              SYNTAX          DisplayString
              MAX-ACCESS      read-write
              STATUS          current
              DESCRIPTION    "This control element is used to control the python scripting system. Available command are: enable[Enable Python Capabilities], disable[Disable Python Capabilities], restart[Restart All Python Capabilities], refresh[Read the folder script (if you added a file when system is running)], enable filename[enable filename.py located in folder user/scripts], disable filename[disable filename.py located in folder user/scripts], restart filename : Restart fileName[file must be enabled], reseterrors[Reset all errors counters], reseterrors filename[Reset errors from filename"
              ::= { siteV1ControlList 260}
siteV1CtrlControllerAdvGenericCommandExecution     OBJECT-TYPE
              SYNTAX          DisplayString
              MAX-ACCESS      read-write
              STATUS          current
              DESCRIPTION    "This control is used to perform advanced operation."
              ::= { siteV1ControlList 300}
siteV1CtrlNetworkWifiEnableforXMinutes     OBJECT-TYPE
              SYNTAX          DisplayString
              MAX-ACCESS      read-write
              STATUS          current
              DESCRIPTION    "NA"
              ::= { siteV1ControlList 390}
siteV1CtrlRelK1InvertStateForXSeconds     OBJECT-TYPE
              SYNTAX          DisplayString
              MAX-ACCESS      read-write
              STATUS          current
              DESCRIPTION    "Generate Pulse on relay"
              ::= { siteV1ControlList 401}
siteV1CtrlRelK2InvertStateForXSeconds     OBJECT-TYPE
              SYNTAX          DisplayString
              MAX-ACCESS      read-write
              STATUS          current
              DESCRIPTION    "Generate Pulse on relay"
              ::= { siteV1ControlList 406}
siteV1CtrlGenericEventsClearMyEvents     OBJECT-TYPE
              SYNTAX          DisplayString
              MAX-ACCESS      read-write
              STATUS          current
              DESCRIPTION    "By writing '1' to this control element, all the events of this equipment will be cleared."
              ::= { siteV1ControlList 501}
siteV1CtrlGenericEventsClearAllEvents     OBJECT-TYPE
              SYNTAX          DisplayString
              MAX-ACCESS      read-write
              STATUS          current
              DESCRIPTION    "By writing '1' to this control element, all the events of this equipment and all the events of all the sub-equipments will be cleared."
              ::= { siteV1ControlList 502}
siteV1CtrlGenericEventsAddEvent     OBJECT-TYPE
              SYNTAX          DisplayString
              MAX-ACCESS      read-write
              STATUS          current
              DESCRIPTION    "This control element adds an event of severity none. The event name is the text written to this control element"
              ::= { siteV1ControlList 511}
siteV1CtrlGenericEventsAddMajorEvent     OBJECT-TYPE
              SYNTAX          DisplayString
              MAX-ACCESS      read-write
              STATUS          current
              DESCRIPTION    "This control element adds an event of severity major. The event name is the text written to this control element"
              ::= { siteV1ControlList 512}
siteV1CtrlGenericRenamingResetDefaultNamesAndGroups     OBJECT-TYPE
              SYNTAX          DisplayString
              MAX-ACCESS      read-write
              STATUS          current
              DESCRIPTION    "This control element resets all the element Names, Groups and Subgroups to default values for this equipment"
              ::= { siteV1ControlList 521}
siteV1CtrlGenericRenamingResetNameGroupRecursive     OBJECT-TYPE
              SYNTAX          DisplayString
              MAX-ACCESS      read-write
              STATUS          current
              DESCRIPTION    "This control element resets all the element Names, Groups and Subgroups to default values for this equipment and all sub equipments"
              ::= { siteV1ControlList 522}
siteV1Notifications           OBJECT IDENTIFIER ::= { siteV1 18 }
siteV1NotificationPrefix      OBJECT IDENTIFIER ::= { siteV1Notifications 0 }
siteV1NotificationOfEvent NOTIFICATION-TYPE
          OBJECTS {
          siteV1EventId,
          siteV1EventName,
          siteV1EventDateTime,
          siteV1EventSeverityType,
          siteV1EventSeverityLevel,
          siteV1AlarmSummary
          }
          STATUS current
          DESCRIPTION  "Notification generated when a new event appears"
          ::= { siteV1NotificationPrefix 1 }

siteV1Compliance OBJECT IDENTIFIER ::= { siteV1 19}
siteV1ComplianceGroups OBJECT IDENTIFIER ::={ siteV1Compliance 1}
siteV1FullCompliance MODULE-COMPLIANCE
    STATUS current
    DESCRIPTION " The compliance statement for SNMPV2 entities which implement the SNMPV2 MIB. "
    MODULE
        MANDATORY-GROUPS { siteV1GlobalGroup, siteV1NotificationGroup }
    ::= { siteV1Compliance 2 }

siteV1GlobalGroup OBJECT-GROUP
     OBJECTS{siteV1GlobalStatus, siteV1GlobalAlarmSeverityType, siteV1GlobalAlarmSeverityLevel, siteV1GlobalAlarmSeverityTypeInt, siteV1DescriptionNumber, siteV1DescriptionName, siteV1DescriptionValue, siteV1DescriptionEntryStatus, siteV1DescDescriptionSiteInformationSiteNumber, siteV1DescDescriptionSiteInformationSiteName, siteV1DescDescriptionSiteInformationShortDescription, siteV1DescDescriptionSiteInformationInfo, siteV1DescDescriptionCustomDescriptionDescription, siteV1DescDescriptionCustomDescriptionReference, siteV1DescDescriptionContactContactName, siteV1DescDescriptionContactPhoneNumber, siteV1DescDescriptionAddressLocation, siteV1DescDescriptionAddressStreet, siteV1DescDescriptionAddressCity, siteV1DescDescriptionAddressProvince, siteV1DescDescriptionAddressPostalCode, siteV1DescDescriptionAddressRegion, siteV1DescDescriptionAddressCountry, siteV1DescDescriptionClusteringGroup1, siteV1DescDescriptionClusteringGroup2, siteV1DescDescriptionClusteringGroup3, siteV1DescDescriptionClusteringGroup4, siteV1DescDescriptionClusteringGroup5, siteV1DescDescriptionGPSPositionLatitude, siteV1DescDescriptionGPSPositionLongitude, siteV1DescDescriptionGPSPositionAltitude, siteV1DescControllerSoftwareRunningCompasInformationalVersion, siteV1DescControllerSoftwareRunningCompasVersion, siteV1DescControllerSoftwarePlatformVersion, siteV1DescControllerHardwareCPU, siteV1DescControllerHardwarePlatform, siteV1DescControllerHardwarePartNumber, siteV1DescControllerHardwareSerialNumber, siteV1DescControllerSoftwareFactoryCompasVersion, siteV1DescControllerSoftwareUserCompasVersion, siteV1AlarmNumber, siteV1AlarmName, siteV1AlarmActive, siteV1AlarmSeverityType, siteV1AlarmSeverityLevel, siteV1AlarmStartTime, siteV1AlarmStopTime, siteV1AlarmEntryStatus, siteV1AlarmSummary, siteV1EventNumber, siteV1EventId, siteV1EventName, siteV1EventDateTime, siteV1EventSeverityType, siteV1EventSeverityLevel, siteV1EventEntryStatus, siteV1DataNumber, siteV1DataName, siteV1DataValue, siteV1DataEntryStatus, siteV1DataNetworkIPv4Address, siteV1DataNetworkIPv4Mask, siteV1DataNetworkMACAddress, siteV1DataNetworkIPv6SiteLocalAddress, siteV1DataNetworkIPv6LinkLocalAddress, siteV1DataControllerLicenseLicensedOptions, siteV1DataNetworkMegabytesReceived, siteV1DataNetworkMegabytesSent, siteV1DataTimeLocalDateAndTime, siteV1DataTimeUTCDateAndTime, siteV1DataControllerOperatingSystemInfoMonitoringMemoryUsed, siteV1DataControllerOperatingSystemInfoCPUPercentageUsage, siteV1DataControllerOperatingSystemInfoFreeFlashMemorySpace, siteV1DataDataRecordsTotalFifoSizeOfSecondRecords, siteV1DataDataRecordsTotalFifoSizeOfMinuteRecords, siteV1DataDataRecordsTotalFifoSizeOfHourRecords, siteV1DataDataRecordsTotalFifoSizeOfDayRecords, siteV1DataAlarmsNumberOfActiveMajor, siteV1DataAlarmsNumberOfActiveMinor, siteV1DataAlarmsNumberOfActiveWarning, siteV1DataInventoryCANBusCANOpenBusNodeIDs, siteV1DataSNMPAgentCounterAuthenticationFail, siteV1DataSNMPAgentCounterReadRequest, siteV1DataSNMPAgentCounterWriteRequest, siteV1DataModbusCounterReadRequest, siteV1DataModbusCounterWriteRequest, siteV1DataBuzzerState, siteV1DataNetworkFirewallListeningTcpPorts, siteV1DataNetworkFirewallListeningUdpPorts, siteV1DataNetworkWifiEnabled, siteV1DataNetworkWifiRemainingMinutes, siteV1DataRelK1State, siteV1DataRelK2State, siteV1DataDigInputD1State, siteV1DataDigInputD1Counter, siteV1DataDigInputD2State, siteV1DataDigInputD2Counter, siteV1ConfigNumber, siteV1ConfigName, siteV1ConfigValue, siteV1ConfigEntryStatus, siteV1CfgNetworkDHCPEnabled, siteV1CfgNetworkIPAddressIfStatic, siteV1CfgNetworkSubnetMaskIfStatic, siteV1CfgNetworkDefaultGatewayIfStatic, siteV1CfgNetworkDNSIfStatic, siteV1CfgNetworkDNS2IfStatic, siteV1CfgTimeNTPTimeServer, siteV1CfgTimeTimeZoneName, siteV1CfgWebServerAuthenticationEnabled, siteV1CfgWebServerHttpPort, siteV1CfgWebServerAuthenticationMethod, siteV1CfgWebServerSessionTimeout, siteV1CfgWebServerHttpsPort, siteV1CfgWebServerRedirectHttptoHttps, siteV1CfgWebServerMinimalTLSVersion, siteV1CfgWebServerDefaultPage, siteV1CfgWebServerLocalizationDatetimeFormat, siteV1CfgWebServerLocalizationTempUnit, siteV1CfgXMLEventPostingEnabled, siteV1CfgXMLEventPostingRefreshPeriod, siteV1CfgXMLEventPostingTimeout, siteV1CfgXMLEventPostingPostToSecOnlyIfPrimFail, siteV1CfgXMLEventPostingTablesToPostOnXMLEvent, siteV1CfgXMLHeartbeatPeriod, siteV1CfgSNMPAgentGlobalEnabled, siteV1CfgSNMPAgentGlobalUdpPort, siteV1CfgSNMPAgentGlobalTrapVersion, siteV1CfgSNMPAgentGlobalGETMinSecurityLevel, siteV1CfgSNMPAgentGlobalSETMinSecurityLevel, siteV1CfgSNMPAgentV3AuthenticationAlgorithm, siteV1CfgSNMPAgentV3PrivacyAlgorithm, siteV1CfgSNMPAgentV3PrivacyPassword, siteV1CfgSNMPAgentV3TrapAuthAlgorithm, siteV1CfgSNMPAgentV3TrapPrivacyAlgorithm, siteV1CfgSNMPAgentV3TrapUsername, siteV1CfgSNMPAgentV3TrapAuthPassword, siteV1CfgSNMPAgentV3TrapPrivacyPassword, siteV1CfgSNMPAgentGlobalSiteDescriptionIdsIncludedInTraps, siteV1CfgSNMPAgentV1V2cReadCommunity, siteV1CfgGenericEventsGenerateEventOnConfChanges, siteV1CfgDataRecordsAutoArchivePeriodDataRecord, siteV1CfgGenericEventsGenerateEventOnControlExecution, siteV1CfgGenericEventsGenerateEventOnAlarmAcknowledge, siteV1CfgInventoryCANBusCANOpenRequiredNodeIds, siteV1CfgInventoryCANBusCANOpenLSSIdRange, siteV1CfgInventoryCANBusCANOpenSystemDefinition, siteV1CfgInventoryCANBusCANOpenLSSSavedConf, siteV1CfgUsersAdministratorLoginPassword, siteV1CfgUsersUser1LoginPassword, siteV1CfgUsersUser2LoginPassword, siteV1CfgUsersUser3LoginPassword, siteV1CfgUsersUser4LoginPassword, siteV1CfgUsersUser5LoginPassword, siteV1CfgRadiusAuthenticationServer, siteV1CfgRadiusAuthenticationPort, siteV1CfgRadiusAuthenticationSecret, siteV1CfgEmailEnabled, siteV1CfgEmailServer, siteV1CfgEmailDomain, siteV1CfgEmailCredentials, siteV1CfgEmailSender, siteV1CfgEmailRecipients, siteV1CfgEmailMinimalEventSeverityForSending, siteV1CfgControllerFeaturesExtensions, siteV1CfgControllerRebootAutomaticReboot, siteV1CfgModbusTcpEnabled, siteV1CfgModbusTcpPort, siteV1CfgModbusGlobalWriteEnabled, siteV1CfgIOTMQTTLinkEnabled, siteV1CfgInventoryCANBusBitrate, siteV1CfgInventoryRS485BusBaudRate, siteV1CfgInventoryRS485BusParity, siteV1CfgInventoryRS485BusExtensionsConf, siteV1CfgInventoryEthernetExtensionsConf, siteV1CfgInventoryUSBExtensionsConf, siteV1CfgLedLedBehaviour, siteV1CfgScriptingLuaEnabled, siteV1CfgScriptingLuaNumberofErrorsBeforeTriggeringAlarm, siteV1CfgScriptingPythonEnabled, siteV1CfgScriptingPythonNumberofErrorsBeforeTriggeringAlarm, siteV1CfgScriptingPythonEnabledScripts, siteV1CfgBuzzerEnabled, siteV1CfgBuzzerSoundNotificationforMajorAlarms, siteV1CfgBuzzerSoundNotificationforMinorAlarms, siteV1CfgDisplayGlobalEnabled, siteV1CfgDisplayCredentialsPinCode, siteV1CfgDisplayBacklightLevel, siteV1CfgDisplayBacklightTimeout, siteV1CfgNetworkFirewallAllowICMP, siteV1CfgNetworkFirewallAllowDebugConnection, siteV1CfgNetworkFirewallAllowHttp, siteV1CfgNetworkFirewallAllowedIpSourcebyMqttBroker, siteV1CfgNetworkWifiActivation, siteV1CfgRelK1Mode, siteV1CfgRelK1DefaultState, siteV1CfgRelK2Mode, siteV1CfgRelK2DefaultState, siteV1CfgDigInputD1Mode, siteV1CfgDigInputD1NormallyClosed, siteV1CfgDigInputD2Mode, siteV1CfgDigInputD2NormallyClosed, siteV1CfgGenericEventsEventTableLength, siteV1CfgSNMPAgentGlobalTrapTargetsIP, siteV1CfgSNMPAgentTrapsMinimalEventSeverityForSending, siteV1CfgXMLEventPostingPrimPostURL, siteV1CfgXMLEventPostingPrimPostLogin, siteV1CfgXMLEventPostingPrimPostPassword, siteV1CfgXMLEventPostingSecPostURL, siteV1CfgXMLEventPostingSecPostLogin, siteV1CfgXMLEventPostingSecPostPassword, siteV1CfgPLCGlobalNumberOfCustomData, siteV1CfgPLCGlobalNumberOfCustomAlarm, siteV1ControlNumber, siteV1ControlName, siteV1ControlValue, siteV1ControlEntryStatus, siteV1CtrlControllerRebootRebootController, siteV1CtrlControllerRebootSaveConfAndRebootController, siteV1CtrlControllerRebootRebootControllerWithoutSavingRecords, siteV1CtrlNetworkApplyNetworkConf, siteV1CtrlTimeForceSNTPTimeRefresh, siteV1CtrlTimeSetLocalTime, siteV1CtrlTimeSetUTCTime, siteV1CtrlTimeResetUptime, siteV1CtrlControllerSaveCleanandSaveXMLUserConf, siteV1CtrlControllerSaveSaveXMLUserConf, siteV1CtrlDataRecordsSaveDataRecords, siteV1CtrlDataRecordsExportDataRecordsinCSV, siteV1CtrlDataRecordsArchiveDataRecords, siteV1CtrlDataRecordsDeleteAllDataRecords, siteV1CtrlControllerTranslationReloadTranslationFiles, siteV1CtrlControllerLicenseReloadLicense, siteV1CtrlInventoryGeneralSave, siteV1CtrlInventoryGeneralCleanEquipmentInventory, siteV1CtrlInventoryCANBusResetCANBusNode, siteV1CtrlInventoryCANBusSaveCANOpenLSSConf, siteV1CtrlInventoryCANBusStartNewLSSInventory, siteV1CtrlInventoryCANBusUpgradeNodeFirmware, siteV1CtrlInventoryCANBusCancelFirmwareUpgrade, siteV1CtrlFilesFlashBinary, siteV1CtrlFilesDownloadFileFromUrl, siteV1CtrlFilesDeleteUserUploadedFile, siteV1CtrlFilesMoveUserUploadedFile, siteV1CtrlFilesExtractZipFileinuserupload, siteV1CtrlEmailSendReport, siteV1CtrlInventoryEthernetUpgradeNodeFirmware, siteV1CtrlScriptingLuaCommand, siteV1CtrlScriptingPythonCommand, siteV1CtrlControllerAdvGenericCommandExecution, siteV1CtrlNetworkWifiEnableforXMinutes, siteV1CtrlRelK1InvertStateForXSeconds, siteV1CtrlRelK2InvertStateForXSeconds, siteV1CtrlGenericEventsClearMyEvents, siteV1CtrlGenericEventsClearAllEvents, siteV1CtrlGenericEventsAddEvent, siteV1CtrlGenericEventsAddMajorEvent, siteV1CtrlGenericRenamingResetDefaultNamesAndGroups, siteV1CtrlGenericRenamingResetNameGroupRecursive}
     STATUS       current
     DESCRIPTION  "text"
     ::= { siteV1ComplianceGroups 1 }

siteV1NotificationGroup NOTIFICATION-GROUP
     NOTIFICATIONS {siteV1NotificationOfEvent}
     STATUS       current
     DESCRIPTION  "text"
     ::= { siteV1ComplianceGroups 2 }



energySystems   OBJECT IDENTIFIER ::= { siteV1 20 }
es1   OBJECT IDENTIFIER ::= {energySystems 1}
es1GlobalStatus      OBJECT-TYPE 
              SYNTAX  DisplayString (SIZE (0..255)) 
              MAX-ACCESS  read-only 
              STATUS  current 
              DESCRIPTION "A textual string (alarms, normal or unknown) containing the status of the Energy System" 
              ::={es1 1 } 

es1GlobalAlarmSeverityType  OBJECT-TYPE 
              SYNTAX DisplayString
              MAX-ACCESS  read-only 
              STATUS  current 
              DESCRIPTION "The alarm severity type (critical, major, minor, warning, none, disabled) of the Energy System" 
              ::= { es1 2 }

es1GlobalAlarmSeverityLevel  OBJECT-TYPE 
              SYNTAX Integer32
              MAX-ACCESS  read-only 
              STATUS  current 
              DESCRIPTION "The alarm severity level (0-9) of the Energy System" 
              ::= { es1 3 }

es1GlobalAlarmSeverityTypeInt  OBJECT-TYPE 
              SYNTAX Integer32
              MAX-ACCESS  read-only 
              STATUS  current 
              DESCRIPTION "The alarm severity type as integer (critical=4, major=3, minor=2, warning=1, none=0) of the Energy System" 
              ::= { es1 4 }

es1Description     OBJECT IDENTIFIER ::= { es1 10 }
es1DescriptionNumber      OBJECT-TYPE
              SYNTAX          Integer32
              MAX-ACCESS      read-only
              STATUS          current
              DESCRIPTION    "The number of entries in the Energy System Description table"
              ::= { es1Description 1 }
es1DescriptionTable      OBJECT-TYPE
              SYNTAX          SEQUENCE OF Es1DescriptionEntry
              MAX-ACCESS      not-accessible
              STATUS          current
              DESCRIPTION    "The Description table of the Energy System" 
              ::= { es1Description 2 }
es1DescriptionEntry      OBJECT-TYPE
              SYNTAX          Es1DescriptionEntry
              MAX-ACCESS      not-accessible
              STATUS          current
              DESCRIPTION    "A Description entry"
              INDEX {es1DescriptionIndex}
              ::= { es1DescriptionTable 1 }
Es1DescriptionEntry ::= 
              SEQUENCE{ 
              es1DescriptionIndex    Unsigned32,  
              es1DescriptionName     DisplayString,
              es1DescriptionValue    DisplayString, 
              es1DescriptionEntryStatus RowStatus 
              }
es1DescriptionIndex      OBJECT-TYPE
              SYNTAX          Unsigned32
              MAX-ACCESS      not-accessible
              STATUS          current
              DESCRIPTION    "Description Index"
              ::= { es1DescriptionEntry 1 }
es1DescriptionName      OBJECT-TYPE
              SYNTAX          DisplayString
              MAX-ACCESS      read-only
              STATUS          current
              DESCRIPTION    "Description Name"
              ::= { es1DescriptionEntry 2 }
es1DescriptionValue      OBJECT-TYPE
              SYNTAX          DisplayString
              MAX-ACCESS      read-create
              STATUS          current
              DESCRIPTION    "Description Value"
              ::= { es1DescriptionEntry 3 }
es1DescriptionEntryStatus      OBJECT-TYPE
              SYNTAX          RowStatus
              MAX-ACCESS      read-create
              STATUS          current
              DESCRIPTION    "The status of this table entry"
              ::= { es1DescriptionEntry 4 }
es1DescriptionList         OBJECT IDENTIFIER ::= { es1Description 3 }
es1DescDescriptionCustomDescriptionDescription     OBJECT-TYPE
              SYNTAX          DisplayString
              MAX-ACCESS      read-write
              STATUS          current
              DESCRIPTION    "A free text zone to write a system description"
              ::= { es1DescriptionList 1}
es1DescDescriptionCustomDescriptionReference     OBJECT-TYPE
              SYNTAX          DisplayString
              MAX-ACCESS      read-write
              STATUS          current
              DESCRIPTION    "A free text zone to write the customer reference of the system"
              ::= { es1DescriptionList 2}
es1Alarm          OBJECT IDENTIFIER ::= { es1 11 }
es1AlarmNumber      OBJECT-TYPE
              SYNTAX          Integer32
              MAX-ACCESS      read-only
              STATUS          current
              DESCRIPTION    "The number of entries in the Energy System Alarm table"
              ::= { es1Alarm 1 }
es1AlarmTable      OBJECT-TYPE
              SYNTAX          SEQUENCE OF Es1AlarmEntry
              MAX-ACCESS      not-accessible
              STATUS          current
              DESCRIPTION    "The table of Alarm entries"
              ::= { es1Alarm 2 }
es1AlarmEntry      OBJECT-TYPE
              SYNTAX          Es1AlarmEntry
              MAX-ACCESS      not-accessible
              STATUS          current
              DESCRIPTION    "An alarm entry"
              INDEX {es1AlarmIndex}
              ::= { es1AlarmTable 1 }
Es1AlarmEntry ::= 
             SEQUENCE{ 
             es1AlarmIndex         Unsigned32,  
             es1AlarmName          DisplayString,
             es1AlarmActive        DisplayString, 
             es1AlarmSeverityType  DisplayString, 
             es1AlarmSeverityLevel DisplayString, 
             es1AlarmStartTime      DisplayString, 
             es1AlarmStopTime       DisplayString, 
              es1AlarmEntryStatus  RowStatus 
             }
es1AlarmIndex      OBJECT-TYPE
              SYNTAX          Unsigned32
              MAX-ACCESS      not-accessible
              STATUS          current
              DESCRIPTION    "Alarm Index"
              ::= { es1AlarmEntry 1 }
es1AlarmName      OBJECT-TYPE
              SYNTAX          DisplayString
              MAX-ACCESS      read-only
              STATUS          current
              DESCRIPTION    "Alarm Name"
              ::= { es1AlarmEntry 2 }
es1AlarmActive   OBJECT-TYPE
              SYNTAX          DisplayString
              MAX-ACCESS      read-only
              STATUS          current
              DESCRIPTION    "Is the Alarm active ? 'true' for active, 'false' for not-active"
              ::= { es1AlarmEntry 3 }
es1AlarmSeverityType      OBJECT-TYPE
              SYNTAX          DisplayString
              MAX-ACCESS      read-write
              STATUS          current
              DESCRIPTION    "The alarm severity type (major, minor, warning, none, disabled) of this alarm entry" 
              ::= { es1AlarmEntry 4 }
es1AlarmSeverityLevel      OBJECT-TYPE
              SYNTAX          DisplayString
              MAX-ACCESS      read-write
              STATUS          current
              DESCRIPTION    "The alarm severity level (0-9) of this alarm entry" 
              ::= { es1AlarmEntry 5 }
es1AlarmStartTime      OBJECT-TYPE
              SYNTAX          DisplayString
              MAX-ACCESS      read-only
              STATUS          current
              DESCRIPTION    "The last start time of this alarm entry (null if never active)"
              ::= { es1AlarmEntry 6 }
es1AlarmStopTime      OBJECT-TYPE
              SYNTAX          DisplayString
              MAX-ACCESS      read-only
              STATUS          current
              DESCRIPTION    "The last stop time of this alarm entry (null if alarm active)"
              ::= { es1AlarmEntry 7 }
es1AlarmEntryStatus      OBJECT-TYPE
              SYNTAX          RowStatus
              MAX-ACCESS      read-create
              STATUS          current
              DESCRIPTION    "The status of this table entry - not used, only for MIB compliance "
              ::= { es1AlarmEntry 8 }
es1AlarmSummary      OBJECT-TYPE
              SYNTAX BITS{
                  none (0)
              }
              MAX-ACCESS      read-only
              STATUS          current
              DESCRIPTION    "Summary bit vector with all the alarms state of the Energy System. A '1' means alarm active, '0' means not active. Unimplemented alarms are always '0'." 
              ::= { es1Alarm 3 }
es1Event          OBJECT IDENTIFIER ::= { es1 12 }
es1EventNumber      OBJECT-TYPE
              SYNTAX          Integer32
              MAX-ACCESS      read-only
              STATUS          current
              DESCRIPTION    "The number of entries in the Event Table related to the Energy System" 
              ::= { es1Event 1 }
es1EventTable      OBJECT-TYPE
              SYNTAX          SEQUENCE OF Es1EventEntry
              MAX-ACCESS      not-accessible
              STATUS          current
              DESCRIPTION    "The Event table related to the Energy System" 
              ::= { es1Event 2 }
es1EventEntry      OBJECT-TYPE
              SYNTAX          Es1EventEntry
              MAX-ACCESS      not-accessible
              STATUS          current
              DESCRIPTION    "."
              INDEX {es1EventIndex}
              ::= { es1EventTable 1 }
Es1EventEntry ::= 
             SEQUENCE{ 
             es1EventIndex           Unsigned32,  
             es1EventId              Unsigned32,  
             es1EventName            DisplayString,
             es1EventDateTime        DisplayString, 
             es1EventSeverityType    DisplayString, 
             es1EventSeverityLevel   DisplayString,
              es1EventEntryStatus    RowStatus 
             }
es1EventIndex      OBJECT-TYPE
              SYNTAX          Unsigned32
              MAX-ACCESS      not-accessible
              STATUS          current
              DESCRIPTION    "Event Index"
              ::= { es1EventEntry 1 }
es1EventId      OBJECT-TYPE
              SYNTAX          Unsigned32
              MAX-ACCESS      read-only
              STATUS          current
              DESCRIPTION    "Event Index"
              ::= { es1EventEntry 2 }
es1EventName      OBJECT-TYPE
              SYNTAX          DisplayString
              MAX-ACCESS      read-only
              STATUS          current
              DESCRIPTION    "Event Name"
              ::= { es1EventEntry 3 }
es1EventDateTime      OBJECT-TYPE
              SYNTAX          DisplayString
              MAX-ACCESS      read-only
              STATUS          current
              DESCRIPTION    "The date and time of the event"
              ::= { es1EventEntry 4 }
es1EventSeverityType      OBJECT-TYPE
              SYNTAX          DisplayString
              MAX-ACCESS      read-only
              STATUS          current
              DESCRIPTION    "The event severity type ('major', 'minor', 'warning' or 'none')"
              ::= { es1EventEntry 5 }
es1EventSeverityLevel      OBJECT-TYPE
              SYNTAX          DisplayString
              MAX-ACCESS      read-only
              STATUS          current
              DESCRIPTION    "The event severity level (0-9)"
              ::= { es1EventEntry 6 }
es1EventEntryStatus      OBJECT-TYPE
              SYNTAX          RowStatus
              MAX-ACCESS      read-create
              STATUS          current
              DESCRIPTION    "The status of this table entry"
              ::= { es1EventEntry 7 }
es1Data            OBJECT IDENTIFIER ::= { es1 13 }
es1DataNumber      OBJECT-TYPE
              SYNTAX          Integer32
              MAX-ACCESS      read-only
              STATUS          current
              DESCRIPTION    "The number of entries in the Data Table related to the Energy System" 
              ::= { es1Data 1 }
es1Config          OBJECT IDENTIFIER ::= { es1 15 }
es1ConfigNumber      OBJECT-TYPE
              SYNTAX          Integer32
              MAX-ACCESS      read-only
              STATUS          current
              DESCRIPTION    "The number of entries in the Config table related to the Energy System" 
              ::= { es1Config 1 }
es1ConfigTable      OBJECT-TYPE
              SYNTAX          SEQUENCE OF Es1ConfigEntry
              MAX-ACCESS      not-accessible
              STATUS          current
              DESCRIPTION    "The table of Config entries related to the Energy System" 
              ::= { es1Config 2 }
es1ConfigEntry      OBJECT-TYPE
              SYNTAX          Es1ConfigEntry
              MAX-ACCESS      not-accessible
              STATUS          current
              DESCRIPTION    "A Config entry"
              INDEX {es1ConfigIndex}
              ::= { es1ConfigTable 1 }
Es1ConfigEntry ::= 
             SEQUENCE{ 
             es1ConfigIndex       Unsigned32,  
             es1ConfigName        DisplayString,
             es1ConfigValue       DisplayString, 
              es1ConfigEntryStatus  RowStatus 
             }
es1ConfigIndex      OBJECT-TYPE
              SYNTAX          Unsigned32
              MAX-ACCESS      not-accessible
              STATUS          current
              DESCRIPTION    "The Config entry Index"
              ::= { es1ConfigEntry 1 }
es1ConfigName      OBJECT-TYPE
              SYNTAX          DisplayString
              MAX-ACCESS      read-only
              STATUS          current
              DESCRIPTION    "The Config entry name"
              ::= { es1ConfigEntry 2 }
es1ConfigValue     OBJECT-TYPE
              SYNTAX          DisplayString
              MAX-ACCESS      read-write
              STATUS          current
              DESCRIPTION    "The Config entry value"
              ::= { es1ConfigEntry 3 }
es1ConfigEntryStatus      OBJECT-TYPE
              SYNTAX          RowStatus
              MAX-ACCESS      read-create
              STATUS          current
              DESCRIPTION    "The status of this table entry - not used, only for compliance"
              ::= { es1ConfigEntry 4 }
es1ConfigList         OBJECT IDENTIFIER ::= { es1Config 3 }
es1CfgPowerManagementPlugin     OBJECT-TYPE
              SYNTAX          DisplayString
              MAX-ACCESS      read-write
              STATUS          current
              DESCRIPTION    "Power management plugins provide dedicated infrastructure monitoring and control generally-available capabilities. The remote DC distribution plugin enables to monitor and control a remote DC power distribution system supplying distributed telecommunication equipment and capable of fault isolation. Among others, such a system consists of a Sierra converter system configured in a rectifier topology, an Iris DC converter system and remote DC systems."
              ::= { es1ConfigList 9}
es1CfgPowerManagementEnabledFeatures     OBJECT-TYPE
              SYNTAX          DisplayString
              MAX-ACCESS      read-write
              STATUS          current
              DESCRIPTION    "Power management features provide dedicated infrastructure monitoring and control selectively-available capabilities."
              ::= { es1ConfigList 10}
es1CfgGenericEventsEventTableLength     OBJECT-TYPE
              SYNTAX          DisplayString
              MAX-ACCESS      read-write
              STATUS          current
              DESCRIPTION    "The maximum length of the table. The value must be comprised between 10 and 4000"
              ::= { es1ConfigList 601}
es1CfgPLCGlobalNumberOfCustomData     OBJECT-TYPE
              SYNTAX          DisplayString
              MAX-ACCESS      read-write
              STATUS          current
              DESCRIPTION    "The number of PLC data. Every equipment can manage up to 30 user programmable data. Data elements are automatically added in the data table. Configuration parameters are added to set the PLC Data Name and the PLC Data Mathematical calculation. In order to use these functionalities, you need a license with the 'PLC' module"
              ::= { es1ConfigList 901}
es1CfgPLCGlobalNumberOfCustomAlarm     OBJECT-TYPE
              SYNTAX          DisplayString
              MAX-ACCESS      read-write
              STATUS          current
              DESCRIPTION    "The number of PLC alarm. Every equipment can manage up to 30 user programmable alarms. Alarm elements are automatically added in the alarm table. The alarm parameters are added to set the PLC Alarm Name and the PLC Alarm Boolean condition. In order to use these functionalities, you need a licence with the 'PLC' module"
              ::= { es1ConfigList 902}
es1Control          OBJECT IDENTIFIER ::= { es1 16 }
es1ControlNumber      OBJECT-TYPE
              SYNTAX          Integer32
              MAX-ACCESS      read-only
              STATUS          current
              DESCRIPTION    "The number of entries in the Control table related to the Energy System" 
              ::= { es1Control 1 }
es1ControlTable      OBJECT-TYPE
              SYNTAX          SEQUENCE OF Es1ControlEntry
              MAX-ACCESS      not-accessible
              STATUS          current
              DESCRIPTION    "The table of Control entries related to the Energy System" 
              ::= { es1Control 2 }
es1ControlEntry      OBJECT-TYPE
              SYNTAX          Es1ControlEntry
              MAX-ACCESS      not-accessible
              STATUS          current
              DESCRIPTION    "A Control entry"
              INDEX {es1ControlIndex}
              ::= { es1ControlTable 1 }
Es1ControlEntry ::= 
             SEQUENCE{ 
             es1ControlIndex       Unsigned32,  
             es1ControlName        DisplayString,
             es1ControlValue       DisplayString, 
              es1ControlEntryStatus  RowStatus 
             }
es1ControlIndex      OBJECT-TYPE
              SYNTAX          Unsigned32
              MAX-ACCESS      not-accessible
              STATUS          current
              DESCRIPTION    "The Control entry Index"
              ::= { es1ControlEntry 1 }
es1ControlName      OBJECT-TYPE
              SYNTAX          DisplayString
              MAX-ACCESS      read-only
              STATUS          current
              DESCRIPTION    "The Control entry name"
              ::= { es1ControlEntry 2 }
es1ControlValue     OBJECT-TYPE
              SYNTAX          DisplayString
              MAX-ACCESS      read-write
              STATUS          current
              DESCRIPTION    "The Control entry value"
              ::= { es1ControlEntry 3 }
es1ControlEntryStatus      OBJECT-TYPE
              SYNTAX          RowStatus
              MAX-ACCESS      read-create
              STATUS          current
              DESCRIPTION    "The status of this table entry - not used, only for compliance"
              ::= { es1ControlEntry 4 }
es1ControlList         OBJECT IDENTIFIER ::= { es1Control 3 }
es1CtrlGenericEventsClearMyEvents     OBJECT-TYPE
              SYNTAX          DisplayString
              MAX-ACCESS      read-write
              STATUS          current
              DESCRIPTION    "By writing '1' to this control element, all the events of this equipment will be cleared."
              ::= { es1ControlList 501}
es1CtrlGenericEventsClearAllEvents     OBJECT-TYPE
              SYNTAX          DisplayString
              MAX-ACCESS      read-write
              STATUS          current
              DESCRIPTION    "By writing '1' to this control element, all the events of this equipment and all the events of all the sub-equipments will be cleared."
              ::= { es1ControlList 502}
es1CtrlGenericEventsAddEvent     OBJECT-TYPE
              SYNTAX          DisplayString
              MAX-ACCESS      read-write
              STATUS          current
              DESCRIPTION    "This control element adds an event of severity none. The event name is the text written to this control element"
              ::= { es1ControlList 511}
es1CtrlGenericEventsAddMajorEvent     OBJECT-TYPE
              SYNTAX          DisplayString
              MAX-ACCESS      read-write
              STATUS          current
              DESCRIPTION    "This control element adds an event of severity major. The event name is the text written to this control element"
              ::= { es1ControlList 512}
es1CtrlGenericRenamingResetDefaultNamesAndGroups     OBJECT-TYPE
              SYNTAX          DisplayString
              MAX-ACCESS      read-write
              STATUS          current
              DESCRIPTION    "This control element resets all the element Names, Groups and Subgroups to default values for this equipment"
              ::= { es1ControlList 521}
es1CtrlGenericRenamingResetNameGroupRecursive     OBJECT-TYPE
              SYNTAX          DisplayString
              MAX-ACCESS      read-write
              STATUS          current
              DESCRIPTION    "This control element resets all the element Names, Groups and Subgroups to default values for this equipment and all sub equipments"
              ::= { es1ControlList 522}
es1Notifications           OBJECT IDENTIFIER ::= { es1 18 }
es1NotificationPrefix      OBJECT IDENTIFIER ::= { es1Notifications 0 }
es1NotificationOfEvent NOTIFICATION-TYPE
          OBJECTS {
          es1EventId,
          es1EventName,
          es1EventDateTime,
          es1EventSeverityType,
          es1EventSeverityLevel,
          es1AlarmSummary
          }
          STATUS current
          DESCRIPTION  "Notification generated when a new event appears"
          ::= { es1NotificationPrefix 1 }

es1Compliance OBJECT IDENTIFIER ::= { es1 19}
es1ComplianceGroups OBJECT IDENTIFIER ::={ es1Compliance 1}
es1FullCompliance MODULE-COMPLIANCE
    STATUS current
    DESCRIPTION " The compliance statement for SNMPV2 entities which implement the SNMPV2 MIB. "
    MODULE
        MANDATORY-GROUPS { es1GlobalGroup, es1NotificationGroup }
    ::= { es1Compliance 2 }

es1GlobalGroup OBJECT-GROUP
     OBJECTS{es1GlobalStatus, es1GlobalAlarmSeverityType, es1GlobalAlarmSeverityLevel, es1GlobalAlarmSeverityTypeInt, es1DescriptionNumber, es1DescriptionName, es1DescriptionValue, es1DescriptionEntryStatus, es1DescDescriptionCustomDescriptionDescription, es1DescDescriptionCustomDescriptionReference, es1AlarmNumber, es1AlarmName, es1AlarmActive, es1AlarmSeverityType, es1AlarmSeverityLevel, es1AlarmStartTime, es1AlarmStopTime, es1AlarmEntryStatus, es1AlarmSummary, es1EventNumber, es1EventId, es1EventName, es1EventDateTime, es1EventSeverityType, es1EventSeverityLevel, es1EventEntryStatus, es1DataNumber, es1ConfigNumber, es1ConfigName, es1ConfigValue, es1ConfigEntryStatus, es1CfgPowerManagementPlugin, es1CfgPowerManagementEnabledFeatures, es1CfgGenericEventsEventTableLength, es1CfgPLCGlobalNumberOfCustomData, es1CfgPLCGlobalNumberOfCustomAlarm, es1ControlNumber, es1ControlName, es1ControlValue, es1ControlEntryStatus, es1CtrlGenericEventsClearMyEvents, es1CtrlGenericEventsClearAllEvents, es1CtrlGenericEventsAddEvent, es1CtrlGenericEventsAddMajorEvent, es1CtrlGenericRenamingResetDefaultNamesAndGroups, es1CtrlGenericRenamingResetNameGroupRecursive}
     STATUS       current
     DESCRIPTION  "text"
     ::= { es1ComplianceGroups 1 }

es1NotificationGroup NOTIFICATION-GROUP
     NOTIFICATIONS {es1NotificationOfEvent}
     STATUS       current
     DESCRIPTION  "text"
     ::= { es1ComplianceGroups 2 }



es1DcSystems   OBJECT IDENTIFIER ::= { es1 20 }
es1DcSys1   OBJECT IDENTIFIER ::= {es1DcSystems 1}
es1DcSys1GlobalStatus      OBJECT-TYPE 
              SYNTAX  DisplayString (SIZE (0..255)) 
              MAX-ACCESS  read-only 
              STATUS  current 
              DESCRIPTION "A textual string (alarms, normal or unknown) containing the status of the DC System" 
              ::={es1DcSys1 1 } 

es1DcSys1GlobalAlarmSeverityType  OBJECT-TYPE 
              SYNTAX DisplayString
              MAX-ACCESS  read-only 
              STATUS  current 
              DESCRIPTION "The alarm severity type (critical, major, minor, warning, none, disabled) of the DC System" 
              ::= { es1DcSys1 2 }

es1DcSys1GlobalAlarmSeverityLevel  OBJECT-TYPE 
              SYNTAX Integer32
              MAX-ACCESS  read-only 
              STATUS  current 
              DESCRIPTION "The alarm severity level (0-9) of the DC System" 
              ::= { es1DcSys1 3 }

es1DcSys1GlobalAlarmSeverityTypeInt  OBJECT-TYPE 
              SYNTAX Integer32
              MAX-ACCESS  read-only 
              STATUS  current 
              DESCRIPTION "The alarm severity type as integer (critical=4, major=3, minor=2, warning=1, none=0) of the DC System" 
              ::= { es1DcSys1 4 }

es1DcSys1Description     OBJECT IDENTIFIER ::= { es1DcSys1 10 }
es1DcSys1DescriptionNumber      OBJECT-TYPE
              SYNTAX          Integer32
              MAX-ACCESS      read-only
              STATUS          current
              DESCRIPTION    "The number of entries in the DC System Description table"
              ::= { es1DcSys1Description 1 }
es1DcSys1DescriptionTable      OBJECT-TYPE
              SYNTAX          SEQUENCE OF Es1DcSys1DescriptionEntry
              MAX-ACCESS      not-accessible
              STATUS          current
              DESCRIPTION    "The Description table of the DC System" 
              ::= { es1DcSys1Description 2 }
es1DcSys1DescriptionEntry      OBJECT-TYPE
              SYNTAX          Es1DcSys1DescriptionEntry
              MAX-ACCESS      not-accessible
              STATUS          current
              DESCRIPTION    "A Description entry"
              INDEX {es1DcSys1DescriptionIndex}
              ::= { es1DcSys1DescriptionTable 1 }
Es1DcSys1DescriptionEntry ::= 
              SEQUENCE{ 
              es1DcSys1DescriptionIndex    Unsigned32,  
              es1DcSys1DescriptionName     DisplayString,
              es1DcSys1DescriptionValue    DisplayString, 
              es1DcSys1DescriptionEntryStatus RowStatus 
              }
es1DcSys1DescriptionIndex      OBJECT-TYPE
              SYNTAX          Unsigned32
              MAX-ACCESS      not-accessible
              STATUS          current
              DESCRIPTION    "Description Index"
              ::= { es1DcSys1DescriptionEntry 1 }
es1DcSys1DescriptionName      OBJECT-TYPE
              SYNTAX          DisplayString
              MAX-ACCESS      read-only
              STATUS          current
              DESCRIPTION    "Description Name"
              ::= { es1DcSys1DescriptionEntry 2 }
es1DcSys1DescriptionValue      OBJECT-TYPE
              SYNTAX          DisplayString
              MAX-ACCESS      read-create
              STATUS          current
              DESCRIPTION    "Description Value"
              ::= { es1DcSys1DescriptionEntry 3 }
es1DcSys1DescriptionEntryStatus      OBJECT-TYPE
              SYNTAX          RowStatus
              MAX-ACCESS      read-create
              STATUS          current
              DESCRIPTION    "The status of this table entry"
              ::= { es1DcSys1DescriptionEntry 4 }
es1DcSys1DescriptionList         OBJECT IDENTIFIER ::= { es1DcSys1Description 3 }
es1DcSys1DescDescriptionCustomDescriptionDescription     OBJECT-TYPE
              SYNTAX          DisplayString
              MAX-ACCESS      read-write
              STATUS          current
              DESCRIPTION    "A free text zone to write a system description"
              ::= { es1DcSys1DescriptionList 1}
es1DcSys1DescDescriptionCustomDescriptionReference     OBJECT-TYPE
              SYNTAX          DisplayString
              MAX-ACCESS      read-write
              STATUS          current
              DESCRIPTION    "A free text zone to write the customer reference of the system"
              ::= { es1DcSys1DescriptionList 2}
es1DcSys1Alarm          OBJECT IDENTIFIER ::= { es1DcSys1 11 }
es1DcSys1AlarmNumber      OBJECT-TYPE
              SYNTAX          Integer32
              MAX-ACCESS      read-only
              STATUS          current
              DESCRIPTION    "The number of entries in the DC System Alarm table"
              ::= { es1DcSys1Alarm 1 }
es1DcSys1AlarmTable      OBJECT-TYPE
              SYNTAX          SEQUENCE OF Es1DcSys1AlarmEntry
              MAX-ACCESS      not-accessible
              STATUS          current
              DESCRIPTION    "The table of Alarm entries"
              ::= { es1DcSys1Alarm 2 }
es1DcSys1AlarmEntry      OBJECT-TYPE
              SYNTAX          Es1DcSys1AlarmEntry
              MAX-ACCESS      not-accessible
              STATUS          current
              DESCRIPTION    "An alarm entry"
              INDEX {es1DcSys1AlarmIndex}
              ::= { es1DcSys1AlarmTable 1 }
Es1DcSys1AlarmEntry ::= 
             SEQUENCE{ 
             es1DcSys1AlarmIndex         Unsigned32,  
             es1DcSys1AlarmName          DisplayString,
             es1DcSys1AlarmActive        DisplayString, 
             es1DcSys1AlarmSeverityType  DisplayString, 
             es1DcSys1AlarmSeverityLevel DisplayString, 
             es1DcSys1AlarmStartTime      DisplayString, 
             es1DcSys1AlarmStopTime       DisplayString, 
              es1DcSys1AlarmEntryStatus  RowStatus 
             }
es1DcSys1AlarmIndex      OBJECT-TYPE
              SYNTAX          Unsigned32
              MAX-ACCESS      not-accessible
              STATUS          current
              DESCRIPTION    "Alarm Index"
              ::= { es1DcSys1AlarmEntry 1 }
es1DcSys1AlarmName      OBJECT-TYPE
              SYNTAX          DisplayString
              MAX-ACCESS      read-only
              STATUS          current
              DESCRIPTION    "Alarm Name"
              ::= { es1DcSys1AlarmEntry 2 }
es1DcSys1AlarmActive   OBJECT-TYPE
              SYNTAX          DisplayString
              MAX-ACCESS      read-only
              STATUS          current
              DESCRIPTION    "Is the Alarm active ? 'true' for active, 'false' for not-active"
              ::= { es1DcSys1AlarmEntry 3 }
es1DcSys1AlarmSeverityType      OBJECT-TYPE
              SYNTAX          DisplayString
              MAX-ACCESS      read-write
              STATUS          current
              DESCRIPTION    "The alarm severity type (major, minor, warning, none, disabled) of this alarm entry" 
              ::= { es1DcSys1AlarmEntry 4 }
es1DcSys1AlarmSeverityLevel      OBJECT-TYPE
              SYNTAX          DisplayString
              MAX-ACCESS      read-write
              STATUS          current
              DESCRIPTION    "The alarm severity level (0-9) of this alarm entry" 
              ::= { es1DcSys1AlarmEntry 5 }
es1DcSys1AlarmStartTime      OBJECT-TYPE
              SYNTAX          DisplayString
              MAX-ACCESS      read-only
              STATUS          current
              DESCRIPTION    "The last start time of this alarm entry (null if never active)"
              ::= { es1DcSys1AlarmEntry 6 }
es1DcSys1AlarmStopTime      OBJECT-TYPE
              SYNTAX          DisplayString
              MAX-ACCESS      read-only
              STATUS          current
              DESCRIPTION    "The last stop time of this alarm entry (null if alarm active)"
              ::= { es1DcSys1AlarmEntry 7 }
es1DcSys1AlarmEntryStatus      OBJECT-TYPE
              SYNTAX          RowStatus
              MAX-ACCESS      read-create
              STATUS          current
              DESCRIPTION    "The status of this table entry - not used, only for MIB compliance "
              ::= { es1DcSys1AlarmEntry 8 }
es1DcSys1AlarmSummary      OBJECT-TYPE
              SYNTAX BITS{
                  systemMeasurementsMissing (0),          -- Alarm : System Measurements Missing
                  dCBusVoltageTooLow (50),          -- Alarm : DC Bus Voltage Too Low
                  dCBusVoltageTooHigh (51),          -- Alarm : DC Bus Voltage Too High
                  batTempTooHigh (100),          -- Alarm : Battery Temperature Too High
                  batTempTooLow (101),          -- Alarm : Battery Temperature Too Low
                  batTempSensorFail (102),          -- Alarm : Battery Temperature Sensor Failure
                  batChargeChargingDisabled (109),          -- Alarm : Battery Charge Charging Disabled
                  batChargeChargingDisabledByExternalCommand (110),          -- Alarm : Battery Charge Charging Disabled By External Command
                  batTestCanceled (250),          -- Alarm : Battery Test Canceled
                  batTestFail (251),          -- Alarm : Battery Test Failure
                  batTestOngoing (252),          -- Alarm : Battery Test Ongoing
                  batDisconnectGlobalOpeningSoon (300),          -- Alarm : Battery Disconnect Global Opening Soon
                  batDisconnectGlobalOpen (301),          -- Alarm : Battery Disconnect Global Open
                  batDisconnectGlobalFeedbackFail (302),          -- Alarm : Battery Disconnect Global Feedback Failure
                  batDisconnectGlobalCommandRelConfMissing (303),          -- Alarm : Battery Disconnect Global Command Relay Configuration Missing
                  batStringsMidpointUnbalance (349),          -- Alarm : Battery Strings Midpoint Unbalance
                  batStringsStringDisconnected (350),          -- Alarm : Battery Strings String Disconnected
                  loadDisconnected (400),          -- Alarm : Load Disconnected
                  loadSaturated (401)          -- Alarm : Load Saturated
              }
              MAX-ACCESS      read-only
              STATUS          current
              DESCRIPTION    "Summary bit vector with all the alarms state of the DC System. A '1' means alarm active, '0' means not active. Unimplemented alarms are always '0'." 
              ::= { es1DcSys1Alarm 3 }
es1DcSys1Event          OBJECT IDENTIFIER ::= { es1DcSys1 12 }
es1DcSys1EventNumber      OBJECT-TYPE
              SYNTAX          Integer32
              MAX-ACCESS      read-only
              STATUS          current
              DESCRIPTION    "The number of entries in the Event Table related to the DC System" 
              ::= { es1DcSys1Event 1 }
es1DcSys1EventTable      OBJECT-TYPE
              SYNTAX          SEQUENCE OF Es1DcSys1EventEntry
              MAX-ACCESS      not-accessible
              STATUS          current
              DESCRIPTION    "The Event table related to the DC System" 
              ::= { es1DcSys1Event 2 }
es1DcSys1EventEntry      OBJECT-TYPE
              SYNTAX          Es1DcSys1EventEntry
              MAX-ACCESS      not-accessible
              STATUS          current
              DESCRIPTION    "."
              INDEX {es1DcSys1EventIndex}
              ::= { es1DcSys1EventTable 1 }
Es1DcSys1EventEntry ::= 
             SEQUENCE{ 
             es1DcSys1EventIndex           Unsigned32,  
             es1DcSys1EventId              Unsigned32,  
             es1DcSys1EventName            DisplayString,
             es1DcSys1EventDateTime        DisplayString, 
             es1DcSys1EventSeverityType    DisplayString, 
             es1DcSys1EventSeverityLevel   DisplayString,
              es1DcSys1EventEntryStatus    RowStatus 
             }
es1DcSys1EventIndex      OBJECT-TYPE
              SYNTAX          Unsigned32
              MAX-ACCESS      not-accessible
              STATUS          current
              DESCRIPTION    "Event Index"
              ::= { es1DcSys1EventEntry 1 }
es1DcSys1EventId      OBJECT-TYPE
              SYNTAX          Unsigned32
              MAX-ACCESS      read-only
              STATUS          current
              DESCRIPTION    "Event Index"
              ::= { es1DcSys1EventEntry 2 }
es1DcSys1EventName      OBJECT-TYPE
              SYNTAX          DisplayString
              MAX-ACCESS      read-only
              STATUS          current
              DESCRIPTION    "Event Name"
              ::= { es1DcSys1EventEntry 3 }
es1DcSys1EventDateTime      OBJECT-TYPE
              SYNTAX          DisplayString
              MAX-ACCESS      read-only
              STATUS          current
              DESCRIPTION    "The date and time of the event"
              ::= { es1DcSys1EventEntry 4 }
es1DcSys1EventSeverityType      OBJECT-TYPE
              SYNTAX          DisplayString
              MAX-ACCESS      read-only
              STATUS          current
              DESCRIPTION    "The event severity type ('major', 'minor', 'warning' or 'none')"
              ::= { es1DcSys1EventEntry 5 }
es1DcSys1EventSeverityLevel      OBJECT-TYPE
              SYNTAX          DisplayString
              MAX-ACCESS      read-only
              STATUS          current
              DESCRIPTION    "The event severity level (0-9)"
              ::= { es1DcSys1EventEntry 6 }
es1DcSys1EventEntryStatus      OBJECT-TYPE
              SYNTAX          RowStatus
              MAX-ACCESS      read-create
              STATUS          current
              DESCRIPTION    "The status of this table entry"
              ::= { es1DcSys1EventEntry 7 }
es1DcSys1Data            OBJECT IDENTIFIER ::= { es1DcSys1 13 }
es1DcSys1DataNumber      OBJECT-TYPE
              SYNTAX          Integer32
              MAX-ACCESS      read-only
              STATUS          current
              DESCRIPTION    "The number of entries in the Data Table related to the DC System" 
              ::= { es1DcSys1Data 1 }
es1DcSys1DataTable      OBJECT-TYPE
              SYNTAX          SEQUENCE OF Es1DcSys1DataEntry
              MAX-ACCESS      not-accessible
              STATUS          current
              DESCRIPTION    "The table of Data entries"
              ::= { es1DcSys1Data 2 }
es1DcSys1DataEntry      OBJECT-TYPE
              SYNTAX          Es1DcSys1DataEntry
              MAX-ACCESS      not-accessible
              STATUS          current
              DESCRIPTION    "A data entry"
              INDEX {es1DcSys1DataIndex}
              ::= { es1DcSys1DataTable 1 }
Es1DcSys1DataEntry ::= 
             SEQUENCE{ 
             es1DcSys1DataIndex       Unsigned32,  
             es1DcSys1DataName        DisplayString,
             es1DcSys1DataValue       DisplayString, 
              es1DcSys1DataEntryStatus  RowStatus 
             }
es1DcSys1DataIndex      OBJECT-TYPE
              SYNTAX          Unsigned32
              MAX-ACCESS      not-accessible
              STATUS          current
              DESCRIPTION    "The data index"
              ::= { es1DcSys1DataEntry 1 }

es1DcSys1DataName      OBJECT-TYPE
              SYNTAX          DisplayString
              MAX-ACCESS      read-only
              STATUS          current
              DESCRIPTION    "The data name"
              ::= { es1DcSys1DataEntry 2 }
es1DcSys1DataValue     OBJECT-TYPE
              SYNTAX          DisplayString
              MAX-ACCESS      read-only
              STATUS          current
              DESCRIPTION    "The data value"
              ::= { es1DcSys1DataEntry 3 }
es1DcSys1DataEntryStatus      OBJECT-TYPE
              SYNTAX          RowStatus
              MAX-ACCESS      read-create
              STATUS          current
              DESCRIPTION    "The status of this table entry - not used, only present for compliance"
              ::= { es1DcSys1DataEntry 4 }
es1DcSys1DataList         OBJECT IDENTIFIER ::= { es1DcSys1Data 3 }
es1DcSys1DataBatGlobalState     OBJECT-TYPE
              SYNTAX          Integer32
              MAX-ACCESS      read-only
              STATUS          current
              DESCRIPTION    "NA"
              ::= { es1DcSys1DataList 1}
es1DcSys1DataConvertersVoltage     OBJECT-TYPE
              SYNTAX          Integer32
              MAX-ACCESS      read-only
              STATUS          current
              DESCRIPTION    "The DC bus voltage in volt, given by modules."
              ::= { es1DcSys1DataList 11}
es1DcSys1DataBatRegOperatingMode     OBJECT-TYPE
              SYNTAX          Integer32
              MAX-ACCESS      read-only
              STATUS          current
              DESCRIPTION    "The DC system can have 3 values: 'Float'(0), 'Boost'(1), 'Battery Test'(2)"
              ::= { es1DcSys1DataList 16}
es1DcSys1DataBatRegPreviousDCOperatingMode     OBJECT-TYPE
              SYNTAX          Integer32
              MAX-ACCESS      read-only
              STATUS          current
              DESCRIPTION    "The previous value of the DC Mode : 'Float'(0), 'Boost'(1), 'Battery Test'(2)"
              ::= { es1DcSys1DataList 17}
es1DcSys1DataBatRegTargetVoltage     OBJECT-TYPE
              SYNTAX          Integer32
              MAX-ACCESS      read-only
              STATUS          current
              DESCRIPTION    "NA"
              ::= { es1DcSys1DataList 18}
es1DcSys1DataBatRegMaxChargeCurrent     OBJECT-TYPE
              SYNTAX          Integer32
              MAX-ACCESS      read-only
              STATUS          current
              DESCRIPTION    "NA"
              ::= { es1DcSys1DataList 19}
es1DcSys1DataConvertersPower     OBJECT-TYPE
              SYNTAX          Integer32
              MAX-ACCESS      read-only
              STATUS          current
              DESCRIPTION    "The sum of the delivered dc power"
              ::= { es1DcSys1DataList 21}
es1DcSys1DataConvertersCurrent     OBJECT-TYPE
              SYNTAX          Integer32
              MAX-ACCESS      read-only
              STATUS          current
              DESCRIPTION    "The sum of the delivered dc current"
              ::= { es1DcSys1DataList 22}
es1DcSys1DataConvertersInstalledPower     OBJECT-TYPE
              SYNTAX          Integer32
              MAX-ACCESS      read-only
              STATUS          current
              DESCRIPTION    "Installed power value in watts for dc system "
              ::= { es1DcSys1DataList 23}
es1DcSys1DataConvertersCountMembers     OBJECT-TYPE
              SYNTAX          Integer32
              MAX-ACCESS      read-only
              STATUS          current
              DESCRIPTION    "The actual number of member modules in this dc system"
              ::= { es1DcSys1DataList 32}
es1DcSys1DataConvertersCountOK     OBJECT-TYPE
              SYNTAX          Integer32
              MAX-ACCESS      read-only
              STATUS          current
              DESCRIPTION    "The actual number of working modules in this dc system"
              ::= { es1DcSys1DataList 33}
es1DcSys1DataLoadGlobalPower     OBJECT-TYPE
              SYNTAX          Integer32
              MAX-ACCESS      read-only
              STATUS          current
              DESCRIPTION    "Estimation of the load power consumption"
              ::= { es1DcSys1DataList 51}
es1DcSys1DataLoadGlobalCurrent     OBJECT-TYPE
              SYNTAX          Integer32
              MAX-ACCESS      read-only
              STATUS          current
              DESCRIPTION    "Estimation of the load current consumption"
              ::= { es1DcSys1DataList 52}
es1DcSys1DataBatMeasurementsVoltage     OBJECT-TYPE
              SYNTAX          Integer32
              MAX-ACCESS      read-only
              STATUS          current
              DESCRIPTION    "Measurement of the battery voltage"
              ::= { es1DcSys1DataList 60}
es1DcSys1DataBatMeasurementsInputCurrent     OBJECT-TYPE
              SYNTAX          Integer32
              MAX-ACCESS      read-only
              STATUS          current
              DESCRIPTION    "The current flowing to battery"
              ::= { es1DcSys1DataList 61}
es1DcSys1DataBatMeasurementsInputPower     OBJECT-TYPE
              SYNTAX          Integer32
              MAX-ACCESS      read-only
              STATUS          current
              DESCRIPTION    "The power flowing to battery"
              ::= { es1DcSys1DataList 62}
es1DcSys1DataBatMeasurementsTemp     OBJECT-TYPE
              SYNTAX          Integer32
              MAX-ACCESS      read-only
              STATUS          current
              DESCRIPTION    "Measurement of the battery voltage"
              ::= { es1DcSys1DataList 71}
es1DcSys1DataBatEstimatesResistance     OBJECT-TYPE
              SYNTAX          Integer32
              MAX-ACCESS      read-only
              STATUS          current
              DESCRIPTION    "Estimation of Battery Resistance"
              ::= { es1DcSys1DataList 81}
es1DcSys1DataBatCapacityNominal     OBJECT-TYPE
              SYNTAX          Integer32
              MAX-ACCESS      read-only
              STATUS          current
              DESCRIPTION    "NA"
              ::= { es1DcSys1DataList 90}
es1DcSys1DataBatAutonomyStateOfCharge     OBJECT-TYPE
              SYNTAX          Integer32
              MAX-ACCESS      read-only
              STATUS          current
              DESCRIPTION    "The battery charge capacity, calculated by integration of the current, or coming from BMS."
              ::= { es1DcSys1DataList 91}
es1DcSys1DataBatAutonomyCalculatedAutonomy     OBJECT-TYPE
              SYNTAX          Integer32
              MAX-ACCESS      read-only
              STATUS          current
              DESCRIPTION    "Calculation of the remaining autonomy. This value can change following the load of your system and the maximal depth of discharge configuration (CF39)."
              ::= { es1DcSys1DataList 92}
es1DcSys1DataBatCapacityRemaining     OBJECT-TYPE
              SYNTAX          Integer32
              MAX-ACCESS      read-only
              STATUS          current
              DESCRIPTION    "NA"
              ::= { es1DcSys1DataList 93}
es1DcSys1DataBatAutonomyBatCurrentIntegration     OBJECT-TYPE
              SYNTAX          Integer32
              MAX-ACCESS      read-only
              STATUS          current
              DESCRIPTION    "Actual value of the integration of the current, in Ampere * hour"
              ::= { es1DcSys1DataList 94}
es1DcSys1DataBatCapacityStateOfHealth     OBJECT-TYPE
              SYNTAX          Integer32
              MAX-ACCESS      read-only
              STATUS          current
              DESCRIPTION    "NA"
              ::= { es1DcSys1DataList 95}
es1DcSys1DataBatBoostLastStartTrigger     OBJECT-TYPE
              SYNTAX          Integer32
              MAX-ACCESS      read-only
              STATUS          current
              DESCRIPTION    "The reason why the boost will start when possible"
              ::= { es1DcSys1DataList 202}
es1DcSys1DataBatBoostLastStopTrigger     OBJECT-TYPE
              SYNTAX          Integer32
              MAX-ACCESS      read-only
              STATUS          current
              DESCRIPTION    "The reason why the last boost ended"
              ::= { es1DcSys1DataList 203}
es1DcSys1DataBatBoostDuration     OBJECT-TYPE
              SYNTAX          Integer32
              MAX-ACCESS      read-only
              STATUS          current
              DESCRIPTION    "The duration of the last or ongoing boost."
              ::= { es1DcSys1DataList 205}
es1DcSys1DataBatBoostStartTime     OBJECT-TYPE
              SYNTAX          DisplayString
              MAX-ACCESS      read-only
              STATUS          current
              DESCRIPTION    "The datetime of the last battery boost start."
              ::= { es1DcSys1DataList 206}
es1DcSys1DataBatTestResult     OBJECT-TYPE
              SYNTAX          Integer32
              MAX-ACCESS      read-only
              STATUS          current
              DESCRIPTION    "This is about the result of the last battery test. 9 values are possible : NEVER_TESTED, SUCCESS, ON_GOING, FAILED_TIMEOUT, FAILED_VBUS_TOO_LOW, FAILED_LOAD_TOO_LOW, FAILED_AC_FAILURE, FAILED_CANCELED, FAILED_LVD_OPENED"
              ::= { es1DcSys1DataList 251}
es1DcSys1DataBatTestDischargedCapacityRatio     OBJECT-TYPE
              SYNTAX          Integer32
              MAX-ACCESS      read-only
              STATUS          current
              DESCRIPTION    "This is the battery capacity, in percent, discharged during the last battery test. This value is updated at the end of the battery test."
              ::= { es1DcSys1DataList 252}
es1DcSys1DataBatTestDischargedCapacity     OBJECT-TYPE
              SYNTAX          Integer32
              MAX-ACCESS      read-only
              STATUS          current
              DESCRIPTION    "This is the battery capacity, in ampere hour, discharged during the last battery test. This value is updated at the end of the battery test."
              ::= { es1DcSys1DataList 253}
es1DcSys1DataBatTestFinalVoltage     OBJECT-TYPE
              SYNTAX          Integer32
              MAX-ACCESS      read-only
              STATUS          current
              DESCRIPTION    "This is the bus voltage at the end of the last battery test. This value is updated at the end of the battery test."
              ::= { es1DcSys1DataList 254}
es1DcSys1DataBatTestDuration     OBJECT-TYPE
              SYNTAX          Integer32
              MAX-ACCESS      read-only
              STATUS          current
              DESCRIPTION    "The duration of the last battery test. This value is updated at the end of the battery test. This value can't be higher than 1440 minutes (24 hours)."
              ::= { es1DcSys1DataList 255}
es1DcSys1DataBatTestStartTime     OBJECT-TYPE
              SYNTAX          DisplayString
              MAX-ACCESS      read-only
              STATUS          current
              DESCRIPTION    "The datetime of the last battery test start."
              ::= { es1DcSys1DataList 256}
es1DcSys1DataBatTestPreviousResult     OBJECT-TYPE
              SYNTAX          Integer32
              MAX-ACCESS      read-only
              STATUS          current
              DESCRIPTION    "The result of the previous battery test"
              ::= { es1DcSys1DataList 261}
es1DcSys1DataBatTestPreviousDischargedCapacityRatio     OBJECT-TYPE
              SYNTAX          Integer32
              MAX-ACCESS      read-only
              STATUS          current
              DESCRIPTION    "This is the battery capacity, in percent, discharged during the previous battery test. This value is shifted at the end of the battery test."
              ::= { es1DcSys1DataList 262}
es1DcSys1DataBatTestPreviousDischargedCapacity     OBJECT-TYPE
              SYNTAX          Integer32
              MAX-ACCESS      read-only
              STATUS          current
              DESCRIPTION    "This is the battery capacity, in ampere hour, discharged during the previous battery test. This value is shifted at the end of the battery test."
              ::= { es1DcSys1DataList 263}
es1DcSys1DataBatTestPreviousFinalVoltage     OBJECT-TYPE
              SYNTAX          Integer32
              MAX-ACCESS      read-only
              STATUS          current
              DESCRIPTION    "This is the bus voltage at the end of the previous battery test. This value is shifted at the end of the battery test."
              ::= { es1DcSys1DataList 264}
es1DcSys1DataBatTestPreviousDuration     OBJECT-TYPE
              SYNTAX          Integer32
              MAX-ACCESS      read-only
              STATUS          current
              DESCRIPTION    "The duration of the previous battery test. This value is shifted at the end of the battery test. This value can't be higher than 1440 minutes (24 hours)."
              ::= { es1DcSys1DataList 265}
es1DcSys1DataBatTestPreviousStartTime     OBJECT-TYPE
              SYNTAX          DisplayString
              MAX-ACCESS      read-only
              STATUS          current
              DESCRIPTION    "The datetime of the previous battery test start."
              ::= { es1DcSys1DataList 266}
es1DcSys1DataBatTestNextScheduledBatTest     OBJECT-TYPE
              SYNTAX          Integer32
              MAX-ACCESS      read-only
              STATUS          current
              DESCRIPTION    "The date and time of the next time the scheduled battery test will run"
              ::= { es1DcSys1DataList 271}
es1DcSys1DataBatDisconnectGlobalState     OBJECT-TYPE
              SYNTAX          Integer32
              MAX-ACCESS      read-only
              STATUS          current
              DESCRIPTION    "Contactor State"
              ::= { es1DcSys1DataList 301}
es1DcSys1DataBatDisconnectGlobalReason     OBJECT-TYPE
              SYNTAX          Integer32
              MAX-ACCESS      read-only
              STATUS          current
              DESCRIPTION    "Reason why LVD is open or having invalid feedback"
              ::= { es1DcSys1DataList 302}
es1DcSys1DataBatDisconnectGlobalFeedbackState     OBJECT-TYPE
              SYNTAX          Integer32
              MAX-ACCESS      read-only
              STATUS          current
              DESCRIPTION    "Contactor Wanted State"
              ::= { es1DcSys1DataList 303}
es1DcSys1Config          OBJECT IDENTIFIER ::= { es1DcSys1 15 }
es1DcSys1ConfigNumber      OBJECT-TYPE
              SYNTAX          Integer32
              MAX-ACCESS      read-only
              STATUS          current
              DESCRIPTION    "The number of entries in the Config table related to the DC System" 
              ::= { es1DcSys1Config 1 }
es1DcSys1ConfigTable      OBJECT-TYPE
              SYNTAX          SEQUENCE OF Es1DcSys1ConfigEntry
              MAX-ACCESS      not-accessible
              STATUS          current
              DESCRIPTION    "The table of Config entries related to the DC System" 
              ::= { es1DcSys1Config 2 }
es1DcSys1ConfigEntry      OBJECT-TYPE
              SYNTAX          Es1DcSys1ConfigEntry
              MAX-ACCESS      not-accessible
              STATUS          current
              DESCRIPTION    "A Config entry"
              INDEX {es1DcSys1ConfigIndex}
              ::= { es1DcSys1ConfigTable 1 }
Es1DcSys1ConfigEntry ::= 
             SEQUENCE{ 
             es1DcSys1ConfigIndex       Unsigned32,  
             es1DcSys1ConfigName        DisplayString,
             es1DcSys1ConfigValue       DisplayString, 
              es1DcSys1ConfigEntryStatus  RowStatus 
             }
es1DcSys1ConfigIndex      OBJECT-TYPE
              SYNTAX          Unsigned32
              MAX-ACCESS      not-accessible
              STATUS          current
              DESCRIPTION    "The Config entry Index"
              ::= { es1DcSys1ConfigEntry 1 }
es1DcSys1ConfigName      OBJECT-TYPE
              SYNTAX          DisplayString
              MAX-ACCESS      read-only
              STATUS          current
              DESCRIPTION    "The Config entry name"
              ::= { es1DcSys1ConfigEntry 2 }
es1DcSys1ConfigValue     OBJECT-TYPE
              SYNTAX          DisplayString
              MAX-ACCESS      read-write
              STATUS          current
              DESCRIPTION    "The Config entry value"
              ::= { es1DcSys1ConfigEntry 3 }
es1DcSys1ConfigEntryStatus      OBJECT-TYPE
              SYNTAX          RowStatus
              MAX-ACCESS      read-create
              STATUS          current
              DESCRIPTION    "The status of this table entry - not used, only for compliance"
              ::= { es1DcSys1ConfigEntry 4 }
es1DcSys1ConfigList         OBJECT IDENTIFIER ::= { es1DcSys1Config 3 }
es1DcSys1CfgDCBusVoltageAlarmLowThreshold     OBJECT-TYPE
              SYNTAX          DisplayString
              MAX-ACCESS      read-write
              STATUS          current
              DESCRIPTION    "The bus voltage under which the alarm 'DC Bus Voltage Low' is set."
              ::= { es1DcSys1ConfigList 50}
es1DcSys1CfgDCBusVoltageAlarmLowClearThreshold     OBJECT-TYPE
              SYNTAX          DisplayString
              MAX-ACCESS      read-write
              STATUS          current
              DESCRIPTION    "The bus voltage over which the alarm 'DC Bus Voltage Low' is unset."
              ::= { es1DcSys1ConfigList 51}
es1DcSys1CfgDCBusVoltageAlarmHighThreshold     OBJECT-TYPE
              SYNTAX          DisplayString
              MAX-ACCESS      read-write
              STATUS          current
              DESCRIPTION    "The bus voltage under which the alarm 'DC Bus Voltage Low' is set."
              ::= { es1DcSys1ConfigList 52}
es1DcSys1CfgDCBusVoltageAlarmHighClearThreshold     OBJECT-TYPE
              SYNTAX          DisplayString
              MAX-ACCESS      read-write
              STATUS          current
              DESCRIPTION    "The bus voltage over which the alarm 'DC Bus Voltage Low' is unset."
              ::= { es1DcSys1ConfigList 53}
es1DcSys1CfgBatGlobalPresence     OBJECT-TYPE
              SYNTAX          DisplayString
              MAX-ACCESS      read-write
              STATUS          current
              DESCRIPTION    "NA"
              ::= { es1DcSys1ConfigList 90}
es1DcSys1CfgBatMeasurementSourceVoltage     OBJECT-TYPE
              SYNTAX          DisplayString
              MAX-ACCESS      read-write
              STATUS          current
              DESCRIPTION    "NA"
              ::= { es1DcSys1ConfigList 100}
es1DcSys1CfgBatMeasurementSourceCurrent     OBJECT-TYPE
              SYNTAX          DisplayString
              MAX-ACCESS      read-write
              STATUS          current
              DESCRIPTION    "NA"
              ::= { es1DcSys1ConfigList 101}
es1DcSys1CfgBatCharacteristicsType     OBJECT-TYPE
              SYNTAX          DisplayString
              MAX-ACCESS      read-write
              STATUS          current
              DESCRIPTION    "The chemistry of the installed battery."
              ::= { es1DcSys1ConfigList 102}
es1DcSys1CfgBatCharacteristicsNumberOfCells     OBJECT-TYPE
              SYNTAX          DisplayString
              MAX-ACCESS      read-write
              STATUS          current
              DESCRIPTION    "Number of cells in each string. This is also valid if there is only one string"
              ::= { es1DcSys1ConfigList 103}
es1DcSys1CfgBatCharacteristicsStringCapacity     OBJECT-TYPE
              SYNTAX          DisplayString
              MAX-ACCESS      read-write
              STATUS          current
              DESCRIPTION    "The capacity of each string in Ah"
              ::= { es1DcSys1ConfigList 104}
es1DcSys1CfgBatCharacteristicsNumberOfString     OBJECT-TYPE
              SYNTAX          DisplayString
              MAX-ACCESS      read-write
              STATUS          current
              DESCRIPTION    "Number of string"
              ::= { es1DcSys1ConfigList 105}
es1DcSys1CfgBatAutonomyPeukertNumber     OBJECT-TYPE
              SYNTAX          DisplayString
              MAX-ACCESS      read-write
              STATUS          current
              DESCRIPTION    "The Peukert number relates to the internal resistance of a battery and provides an indication of the expected capacity. The ideal number is 1. This value can be calculated with the formula: (ln(t2)-ln(t1))/(ln(i1)-ln(i2)) where tx is the autonomy in hours at a constant discharge current of ix Amps. Often, we use t1 = 1h and t2 = 10h"
              ::= { es1DcSys1ConfigList 106}
es1DcSys1CfgBatAutonomyMaxDepthOfDischargeforEstimation     OBJECT-TYPE
              SYNTAX          DisplayString
              MAX-ACCESS      read-write
              STATUS          current
              DESCRIPTION    "It is generally recommended to discharge maximum 60% of the battery capacity to enhance battery lifetime. By default, 100% is used for autonomy calculation. This parameter can also be used to take into account the age of the battery"
              ::= { es1DcSys1ConfigList 107}
es1DcSys1CfgBatFloatVoltagePerCell     OBJECT-TYPE
              SYNTAX          DisplayString
              MAX-ACCESS      read-write
              STATUS          current
              DESCRIPTION    "Value is in Volts with 2 decimals. This value should be found in battery's data sheet."
              ::= { es1DcSys1ConfigList 111}
es1DcSys1CfgBatFloatSource     OBJECT-TYPE
              SYNTAX          DisplayString
              MAX-ACCESS      read-write
              STATUS          current
              DESCRIPTION    "NA"
              ::= { es1DcSys1ConfigList 112}
es1DcSys1CfgBatCurrentLimitationEnabled     OBJECT-TYPE
              SYNTAX          DisplayString
              MAX-ACCESS      read-write
              STATUS          current
              DESCRIPTION    "This allows to enable or disable the charging current limitation. It is highly recommended to leave this parameter by default (enabled) in order to avoid severe damages."
              ::= { es1DcSys1ConfigList 113}
es1DcSys1CfgBatCurrentLimitationCurrentLimit     OBJECT-TYPE
              SYNTAX          DisplayString
              MAX-ACCESS      read-write
              STATUS          current
              DESCRIPTION    "The max charging current can be computed using the installed capacity times the wished C rate. For the specific case of NiZn battery, the recommended standard charging current limitation is C/4 while fast charging is C/2."
              ::= { es1DcSys1ConfigList 114}
es1DcSys1CfgBatCurrentLimitationSource     OBJECT-TYPE
              SYNTAX          DisplayString
              MAX-ACCESS      read-write
              STATUS          current
              DESCRIPTION    "NA"
              ::= { es1DcSys1ConfigList 115}
es1DcSys1CfgBatTempAlarmLowThreshold     OBJECT-TYPE
              SYNTAX          DisplayString
              MAX-ACCESS      read-write
              STATUS          current
              DESCRIPTION    "The temperature under which the alarm 'Battery Temperature Too Low' must be set."
              ::= { es1DcSys1ConfigList 121}
es1DcSys1CfgBatTempAlarmHighThreshold     OBJECT-TYPE
              SYNTAX          DisplayString
              MAX-ACCESS      read-write
              STATUS          current
              DESCRIPTION    "The temperature over which the alarm 'Battery Temperature Too High' must be set."
              ::= { es1DcSys1ConfigList 122}
es1DcSys1CfgBatTempAlarmHighHysteresis     OBJECT-TYPE
              SYNTAX          DisplayString
              MAX-ACCESS      read-write
              STATUS          current
              DESCRIPTION    "NA"
              ::= { es1DcSys1ConfigList 123}
es1DcSys1CfgBatTempDisableChargeWhenTooHigh     OBJECT-TYPE
              SYNTAX          DisplayString
              MAX-ACCESS      read-write
              STATUS          current
              DESCRIPTION    "Disable the charge when related alarm is set"
              ::= { es1DcSys1ConfigList 126}
es1DcSys1CfgBatTempCompensationEnabled     OBJECT-TYPE
              SYNTAX          DisplayString
              MAX-ACCESS      read-write
              STATUS          current
              DESCRIPTION    "Temperature compensation configuration"
              ::= { es1DcSys1ConfigList 151}
es1DcSys1CfgBatTempCompensationCellCoefficient     OBJECT-TYPE
              SYNTAX          DisplayString
              MAX-ACCESS      read-write
              STATUS          current
              DESCRIPTION    "Coefficient for temperature compensation per cell (in mV/degreeCelsius/cell)"
              ::= { es1DcSys1ConfigList 152}
es1DcSys1CfgBatTempCompensationReferenceTemp     OBJECT-TYPE
              SYNTAX          DisplayString
              MAX-ACCESS      read-write
              STATUS          current
              DESCRIPTION    "Reference temperature for temperature compensation (in degree Celsius)"
              ::= { es1DcSys1ConfigList 153}
es1DcSys1CfgBatTempCompensationMinTemp     OBJECT-TYPE
              SYNTAX          DisplayString
              MAX-ACCESS      read-write
              STATUS          current
              DESCRIPTION    "Below this temperature (in degree Celsius), the voltage corresponding to this threshold is applied continuously"
              ::= { es1DcSys1ConfigList 154}
es1DcSys1CfgBatTempCompensationMaxTemp     OBJECT-TYPE
              SYNTAX          DisplayString
              MAX-ACCESS      read-write
              STATUS          current
              DESCRIPTION    "Above this temperature (in degree Celsius), the voltage corresponding to this threshold is applied continuously"
              ::= { es1DcSys1ConfigList 155}
es1DcSys1CfgBatBoostEnabled     OBJECT-TYPE
              SYNTAX          DisplayString
              MAX-ACCESS      read-write
              STATUS          current
              DESCRIPTION    "Tick to enable boost charging"
              ::= { es1DcSys1ConfigList 201}
es1DcSys1CfgBatBoostVoltagePerCell     OBJECT-TYPE
              SYNTAX          DisplayString
              MAX-ACCESS      read-write
              STATUS          current
              DESCRIPTION    "Boost charging voltage per cell (0,01V precision)"
              ::= { es1DcSys1ConfigList 202}
es1DcSys1CfgBatBoostTimeoutEnabled     OBJECT-TYPE
              SYNTAX          DisplayString
              MAX-ACCESS      read-write
              STATUS          current
              DESCRIPTION    "Tick to enable an automatic stop after the configured delay"
              ::= { es1DcSys1ConfigList 203}
es1DcSys1CfgBatBoostTimeoutDuration     OBJECT-TYPE
              SYNTAX          DisplayString
              MAX-ACCESS      read-write
              STATUS          current
              DESCRIPTION    "Delay before an automatic stop (in seconds)"
              ::= { es1DcSys1ConfigList 204}
es1DcSys1CfgBatBoostStopOnLowCurrentEnabled     OBJECT-TYPE
              SYNTAX          DisplayString
              MAX-ACCESS      read-write
              STATUS          current
              DESCRIPTION    "Tick to enable an automatic stop if the current goes below the configured threshold"
              ::= { es1DcSys1ConfigList 205}
es1DcSys1CfgBatBoostStopOnLowCurrentThreshold     OBJECT-TYPE
              SYNTAX          DisplayString
              MAX-ACCESS      read-write
              STATUS          current
              DESCRIPTION    "Low current threshold for automatic stop (0,1A precision))"
              ::= { es1DcSys1ConfigList 206}
es1DcSys1CfgBatBoostStartOnLowCellVoltageEnabled     OBJECT-TYPE
              SYNTAX          DisplayString
              MAX-ACCESS      read-write
              STATUS          current
              DESCRIPTION    "Tick to enable a boost if cell voltage drops below the configured threshold voltage"
              ::= { es1DcSys1ConfigList 207}
es1DcSys1CfgBatBoostStartOnLowCellVoltageThreshold     OBJECT-TYPE
              SYNTAX          DisplayString
              MAX-ACCESS      read-write
              STATUS          current
              DESCRIPTION    "Low cell voltage start threshold (0,01V precision)"
              ::= { es1DcSys1ConfigList 208}
es1DcSys1CfgBatBoostStopOnTempHighEnabled     OBJECT-TYPE
              SYNTAX          DisplayString
              MAX-ACCESS      read-write
              STATUS          current
              DESCRIPTION    "Tick to enable an automatic stop of the boost if the battery temperature exceeds the specified threshold"
              ::= { es1DcSys1ConfigList 209}
es1DcSys1CfgBatBoostStartOnLongDischargeEnabled     OBJECT-TYPE
              SYNTAX          DisplayString
              MAX-ACCESS      read-write
              STATUS          current
              DESCRIPTION    "Tick to enable a boost if the discharge exceeds the configured duration"
              ::= { es1DcSys1ConfigList 211}
es1DcSys1CfgBatBoostStartOnLongDischargeThreshold     OBJECT-TYPE
              SYNTAX          DisplayString
              MAX-ACCESS      read-write
              STATUS          current
              DESCRIPTION    "Minimal discharge duration for an automated boost (in seconds)"
              ::= { es1DcSys1ConfigList 212}
es1DcSys1CfgBatTestEnabled     OBJECT-TYPE
              SYNTAX          DisplayString
              MAX-ACCESS      read-write
              STATUS          current
              DESCRIPTION    "Tick to enable battery testing"
              ::= { es1DcSys1ConfigList 251}
es1DcSys1CfgBatTestType     OBJECT-TYPE
              SYNTAX          DisplayString
              MAX-ACCESS      read-write
              STATUS          current
              DESCRIPTION    "In DC + AC type, the system will discharge the battery at the configured constant power using AC and DC.
 In DC only mode, the converter will set its DC output voltage to the configured voltage and let the battery discharge in the loads (not a constant power)."
              ::= { es1DcSys1ConfigList 252}
es1DcSys1CfgBatTestPowerSetpoint     OBJECT-TYPE
              SYNTAX          DisplayString
              MAX-ACCESS      read-write
              STATUS          current
              DESCRIPTION    "If AC input reinjection is disabled, test power set point should be lower than AC output power. Set point is in Watts"
              ::= { es1DcSys1ConfigList 253}
es1DcSys1CfgBatTestTimeoutDuration     OBJECT-TYPE
              SYNTAX          DisplayString
              MAX-ACCESS      read-write
              STATUS          current
              DESCRIPTION    "Duration timeout value"
              ::= { es1DcSys1ConfigList 254}
es1DcSys1CfgBatTestLowStop     OBJECT-TYPE
              SYNTAX          DisplayString
              MAX-ACCESS      read-write
              STATUS          current
              DESCRIPTION    "Low voltage stop threshold per cell (0,01V precision)"
              ::= { es1DcSys1ConfigList 255}
es1DcSys1CfgBatTestScheduling     OBJECT-TYPE
              SYNTAX          DisplayString
              MAX-ACCESS      read-write
              STATUS          current
              DESCRIPTION    "Scheduling enabled"
              ::= { es1DcSys1ConfigList 261}
es1DcSys1CfgBatTestSchedulerCronRule     OBJECT-TYPE
              SYNTAX          DisplayString
              MAX-ACCESS      read-write
              STATUS          current
              DESCRIPTION    "NA"
              ::= { es1DcSys1ConfigList 262}
es1DcSys1CfgBatTestGuardTime     OBJECT-TYPE
              SYNTAX          DisplayString
              MAX-ACCESS      read-write
              STATUS          current
              DESCRIPTION    "This parameter lets the user enable a minimum amount of time between two tests or between a discharge and a test"
              ::= { es1DcSys1ConfigList 271}
es1DcSys1CfgBatTestGuardTimeduration     OBJECT-TYPE
              SYNTAX          DisplayString
              MAX-ACCESS      read-write
              STATUS          current
              DESCRIPTION    "Guard time duration in hours"
              ::= { es1DcSys1ConfigList 272}
es1DcSys1CfgBatTestEnableACLossGuard     OBJECT-TYPE
              SYNTAX          DisplayString
              MAX-ACCESS      read-write
              STATUS          current
              DESCRIPTION    "When enabled, automated test will fail if the last ac loss occured to close to the test."
              ::= { es1DcSys1ConfigList 273}
es1DcSys1CfgBatTestAcLossGuardValue     OBJECT-TYPE
              SYNTAX          DisplayString
              MAX-ACCESS      read-write
              STATUS          current
              DESCRIPTION    "Minimal time (in hours) between a loss of ac and the start of an automated test."
              ::= { es1DcSys1ConfigList 274}
es1DcSys1CfgBatDisconnectGlobalPresence     OBJECT-TYPE
              SYNTAX          DisplayString
              MAX-ACCESS      read-write
              STATUS          current
              DESCRIPTION    "Low Voltage Disconnect settings"
              ::= { es1DcSys1ConfigList 301}
es1DcSys1CfgBatDisconnectGlobalInhibit     OBJECT-TYPE
              SYNTAX          DisplayString
              MAX-ACCESS      read-write
              STATUS          current
              DESCRIPTION    "This setting allows the user to inhibit LVD operation and therefore to maintain LVD closed. "
              ::= { es1DcSys1ConfigList 302}
es1DcSys1CfgBatDisconnectVoltageTooLowEnabled     OBJECT-TYPE
              SYNTAX          DisplayString
              MAX-ACCESS      read-write
              STATUS          current
              DESCRIPTION    "Low Voltage Disconnect settings"
              ::= { es1DcSys1ConfigList 310}
es1DcSys1CfgBatDisconnectVoltageTooLowThreshold     OBJECT-TYPE
              SYNTAX          DisplayString
              MAX-ACCESS      read-write
              STATUS          current
              DESCRIPTION    "Threshold voltage for opening (0,1V precision)"
              ::= { es1DcSys1ConfigList 311}
es1DcSys1CfgBatDisconnectGlobalClosingDelay     OBJECT-TYPE
              SYNTAX          DisplayString
              MAX-ACCESS      read-write
              STATUS          current
              DESCRIPTION    "Delay before LVD closing"
              ::= { es1DcSys1ConfigList 312}
es1DcSys1CfgBatDisconnectGlobalOpeningDelay     OBJECT-TYPE
              SYNTAX          DisplayString
              MAX-ACCESS      read-write
              STATUS          current
              DESCRIPTION    "Shutdown sequence duration (in seconds)"
              ::= { es1DcSys1ConfigList 313}
es1DcSys1CfgBatDisconnectTempTooHighEnabled     OBJECT-TYPE
              SYNTAX          DisplayString
              MAX-ACCESS      read-write
              STATUS          current
              DESCRIPTION    "NA"
              ::= { es1DcSys1ConfigList 321}
es1DcSys1CfgBatDisconnectTempTooHighDisconnectThreshold     OBJECT-TYPE
              SYNTAX          DisplayString
              MAX-ACCESS      read-write
              STATUS          current
              DESCRIPTION    "NA"
              ::= { es1DcSys1ConfigList 322}
es1DcSys1CfgBatDisconnectTempTooHighReconnectThreshold     OBJECT-TYPE
              SYNTAX          DisplayString
              MAX-ACCESS      read-write
              STATUS          current
              DESCRIPTION    "NA"
              ::= { es1DcSys1ConfigList 323}
es1DcSys1CfgBatStringsMidpointUnbalanceAlarmThreshold     OBJECT-TYPE
              SYNTAX          DisplayString
              MAX-ACCESS      read-write
              STATUS          current
              DESCRIPTION    "NA"
              ::= { es1DcSys1ConfigList 350}
es1DcSys1CfgBatStringsMidpointUnbalanceAlarmHysteresis     OBJECT-TYPE
              SYNTAX          DisplayString
              MAX-ACCESS      read-write
              STATUS          current
              DESCRIPTION    "NA"
              ::= { es1DcSys1ConfigList 351}
es1DcSys1CfgLoadNumberofLoads     OBJECT-TYPE
              SYNTAX          DisplayString
              MAX-ACCESS      read-write
              STATUS          current
              DESCRIPTION    "Number of independent load"
              ::= { es1DcSys1ConfigList 401}
es1DcSys1CfgGenericEventsEventTableLength     OBJECT-TYPE
              SYNTAX          DisplayString
              MAX-ACCESS      read-write
              STATUS          current
              DESCRIPTION    "The maximum length of the table. The value must be comprised between 10 and 4000"
              ::= { es1DcSys1ConfigList 601}
es1DcSys1CfgPLCGlobalNumberOfCustomData     OBJECT-TYPE
              SYNTAX          DisplayString
              MAX-ACCESS      read-write
              STATUS          current
              DESCRIPTION    "The number of PLC data. Every equipment can manage up to 30 user programmable data. Data elements are automatically added in the data table. Configuration parameters are added to set the PLC Data Name and the PLC Data Mathematical calculation. In order to use these functionalities, you need a license with the 'PLC' module"
              ::= { es1DcSys1ConfigList 901}
es1DcSys1CfgPLCGlobalNumberOfCustomAlarm     OBJECT-TYPE
              SYNTAX          DisplayString
              MAX-ACCESS      read-write
              STATUS          current
              DESCRIPTION    "The number of PLC alarm. Every equipment can manage up to 30 user programmable alarms. Alarm elements are automatically added in the alarm table. The alarm parameters are added to set the PLC Alarm Name and the PLC Alarm Boolean condition. In order to use these functionalities, you need a licence with the 'PLC' module"
              ::= { es1DcSys1ConfigList 902}
es1DcSys1Control          OBJECT IDENTIFIER ::= { es1DcSys1 16 }
es1DcSys1ControlNumber      OBJECT-TYPE
              SYNTAX          Integer32
              MAX-ACCESS      read-only
              STATUS          current
              DESCRIPTION    "The number of entries in the Control table related to the DC System" 
              ::= { es1DcSys1Control 1 }
es1DcSys1ControlTable      OBJECT-TYPE
              SYNTAX          SEQUENCE OF Es1DcSys1ControlEntry
              MAX-ACCESS      not-accessible
              STATUS          current
              DESCRIPTION    "The table of Control entries related to the DC System" 
              ::= { es1DcSys1Control 2 }
es1DcSys1ControlEntry      OBJECT-TYPE
              SYNTAX          Es1DcSys1ControlEntry
              MAX-ACCESS      not-accessible
              STATUS          current
              DESCRIPTION    "A Control entry"
              INDEX {es1DcSys1ControlIndex}
              ::= { es1DcSys1ControlTable 1 }
Es1DcSys1ControlEntry ::= 
             SEQUENCE{ 
             es1DcSys1ControlIndex       Unsigned32,  
             es1DcSys1ControlName        DisplayString,
             es1DcSys1ControlValue       DisplayString, 
              es1DcSys1ControlEntryStatus  RowStatus 
             }
es1DcSys1ControlIndex      OBJECT-TYPE
              SYNTAX          Unsigned32
              MAX-ACCESS      not-accessible
              STATUS          current
              DESCRIPTION    "The Control entry Index"
              ::= { es1DcSys1ControlEntry 1 }
es1DcSys1ControlName      OBJECT-TYPE
              SYNTAX          DisplayString
              MAX-ACCESS      read-only
              STATUS          current
              DESCRIPTION    "The Control entry name"
              ::= { es1DcSys1ControlEntry 2 }
es1DcSys1ControlValue     OBJECT-TYPE
              SYNTAX          DisplayString
              MAX-ACCESS      read-write
              STATUS          current
              DESCRIPTION    "The Control entry value"
              ::= { es1DcSys1ControlEntry 3 }
es1DcSys1ControlEntryStatus      OBJECT-TYPE
              SYNTAX          RowStatus
              MAX-ACCESS      read-create
              STATUS          current
              DESCRIPTION    "The status of this table entry - not used, only for compliance"
              ::= { es1DcSys1ControlEntry 4 }
es1DcSys1ControlList         OBJECT IDENTIFIER ::= { es1DcSys1Control 3 }
es1DcSys1CtrlBatFloatBackToFloat     OBJECT-TYPE
              SYNTAX          DisplayString
              MAX-ACCESS      read-write
              STATUS          current
              DESCRIPTION    "The dc system must go back in floating mode."
              ::= { es1DcSys1ControlList 1}
es1DcSys1CtrlBatBoostStartBoostMode     OBJECT-TYPE
              SYNTAX          DisplayString
              MAX-ACCESS      read-write
              STATUS          current
              DESCRIPTION    "The dc system must go in boost mode."
              ::= { es1DcSys1ControlList 201}
es1DcSys1CtrlBatTestStartBatTest     OBJECT-TYPE
              SYNTAX          DisplayString
              MAX-ACCESS      read-write
              STATUS          current
              DESCRIPTION    "The dc system must start a battery test."
              ::= { es1DcSys1ControlList 251}
es1DcSys1CtrlBatTestForceBatTest     OBJECT-TYPE
              SYNTAX          DisplayString
              MAX-ACCESS      read-write
              STATUS          current
              DESCRIPTION    "The dc system must force a battery test."
              ::= { es1DcSys1ControlList 252}
es1DcSys1CtrlBatTestResetLastBatTestState     OBJECT-TYPE
              SYNTAX          DisplayString
              MAX-ACCESS      read-write
              STATUS          current
              DESCRIPTION    "Reset the state of the last battery test. If an alarm 'Battery Last Test Failed' is set, the alarm will be cleared."
              ::= { es1DcSys1ControlList 253}
es1DcSys1CtrlBatDisconnectGlobalOpen     OBJECT-TYPE
              SYNTAX          DisplayString
              MAX-ACCESS      read-write
              STATUS          current
              DESCRIPTION    "NA"
              ::= { es1DcSys1ControlList 301}
es1DcSys1CtrlBatDisconnectGlobalClose     OBJECT-TYPE
              SYNTAX          DisplayString
              MAX-ACCESS      read-write
              STATUS          current
              DESCRIPTION    "NA"
              ::= { es1DcSys1ControlList 302}
es1DcSys1CtrlGenericEventsClearMyEvents     OBJECT-TYPE
              SYNTAX          DisplayString
              MAX-ACCESS      read-write
              STATUS          current
              DESCRIPTION    "By writing '1' to this control element, all the events of this equipment will be cleared."
              ::= { es1DcSys1ControlList 501}
es1DcSys1CtrlGenericEventsClearAllEvents     OBJECT-TYPE
              SYNTAX          DisplayString
              MAX-ACCESS      read-write
              STATUS          current
              DESCRIPTION    "By writing '1' to this control element, all the events of this equipment and all the events of all the sub-equipments will be cleared."
              ::= { es1DcSys1ControlList 502}
es1DcSys1CtrlGenericEventsAddEvent     OBJECT-TYPE
              SYNTAX          DisplayString
              MAX-ACCESS      read-write
              STATUS          current
              DESCRIPTION    "This control element adds an event of severity none. The event name is the text written to this control element"
              ::= { es1DcSys1ControlList 511}
es1DcSys1CtrlGenericEventsAddMajorEvent     OBJECT-TYPE
              SYNTAX          DisplayString
              MAX-ACCESS      read-write
              STATUS          current
              DESCRIPTION    "This control element adds an event of severity major. The event name is the text written to this control element"
              ::= { es1DcSys1ControlList 512}
es1DcSys1CtrlGenericRenamingResetDefaultNamesAndGroups     OBJECT-TYPE
              SYNTAX          DisplayString
              MAX-ACCESS      read-write
              STATUS          current
              DESCRIPTION    "This control element resets all the element Names, Groups and Subgroups to default values for this equipment"
              ::= { es1DcSys1ControlList 521}
es1DcSys1CtrlGenericRenamingResetNameGroupRecursive     OBJECT-TYPE
              SYNTAX          DisplayString
              MAX-ACCESS      read-write
              STATUS          current
              DESCRIPTION    "This control element resets all the element Names, Groups and Subgroups to default values for this equipment and all sub equipments"
              ::= { es1DcSys1ControlList 522}
es1DcSys1Notifications           OBJECT IDENTIFIER ::= { es1DcSys1 18 }
es1DcSys1NotificationPrefix      OBJECT IDENTIFIER ::= { es1DcSys1Notifications 0 }
es1DcSys1NotificationOfEvent NOTIFICATION-TYPE
          OBJECTS {
          es1DcSys1EventId,
          es1DcSys1EventName,
          es1DcSys1EventDateTime,
          es1DcSys1EventSeverityType,
          es1DcSys1EventSeverityLevel,
          es1DcSys1AlarmSummary
          }
          STATUS current
          DESCRIPTION  "Notification generated when a new event appears"
          ::= { es1DcSys1NotificationPrefix 1 }

es1DcSys1Compliance OBJECT IDENTIFIER ::= { es1DcSys1 19}
es1DcSys1ComplianceGroups OBJECT IDENTIFIER ::={ es1DcSys1Compliance 1}
es1DcSys1FullCompliance MODULE-COMPLIANCE
    STATUS current
    DESCRIPTION " The compliance statement for SNMPV2 entities which implement the SNMPV2 MIB. "
    MODULE
        MANDATORY-GROUPS { es1DcSys1GlobalGroup, es1DcSys1NotificationGroup }
    ::= { es1DcSys1Compliance 2 }

es1DcSys1GlobalGroup OBJECT-GROUP
     OBJECTS{es1DcSys1GlobalStatus, es1DcSys1GlobalAlarmSeverityType, es1DcSys1GlobalAlarmSeverityLevel, es1DcSys1GlobalAlarmSeverityTypeInt, es1DcSys1DescriptionNumber, es1DcSys1DescriptionName, es1DcSys1DescriptionValue, es1DcSys1DescriptionEntryStatus, es1DcSys1DescDescriptionCustomDescriptionDescription, es1DcSys1DescDescriptionCustomDescriptionReference, es1DcSys1AlarmNumber, es1DcSys1AlarmName, es1DcSys1AlarmActive, es1DcSys1AlarmSeverityType, es1DcSys1AlarmSeverityLevel, es1DcSys1AlarmStartTime, es1DcSys1AlarmStopTime, es1DcSys1AlarmEntryStatus, es1DcSys1AlarmSummary, es1DcSys1EventNumber, es1DcSys1EventId, es1DcSys1EventName, es1DcSys1EventDateTime, es1DcSys1EventSeverityType, es1DcSys1EventSeverityLevel, es1DcSys1EventEntryStatus, es1DcSys1DataNumber, es1DcSys1DataName, es1DcSys1DataValue, es1DcSys1DataEntryStatus, es1DcSys1DataBatGlobalState, es1DcSys1DataConvertersVoltage, es1DcSys1DataBatRegOperatingMode, es1DcSys1DataBatRegPreviousDCOperatingMode, es1DcSys1DataBatRegTargetVoltage, es1DcSys1DataBatRegMaxChargeCurrent, es1DcSys1DataConvertersPower, es1DcSys1DataConvertersCurrent, es1DcSys1DataConvertersInstalledPower, es1DcSys1DataConvertersCountMembers, es1DcSys1DataConvertersCountOK, es1DcSys1DataLoadGlobalPower, es1DcSys1DataLoadGlobalCurrent, es1DcSys1DataBatMeasurementsVoltage, es1DcSys1DataBatMeasurementsInputCurrent, es1DcSys1DataBatMeasurementsInputPower, es1DcSys1DataBatMeasurementsTemp, es1DcSys1DataBatEstimatesResistance, es1DcSys1DataBatCapacityNominal, es1DcSys1DataBatAutonomyStateOfCharge, es1DcSys1DataBatAutonomyCalculatedAutonomy, es1DcSys1DataBatCapacityRemaining, es1DcSys1DataBatAutonomyBatCurrentIntegration, es1DcSys1DataBatCapacityStateOfHealth, es1DcSys1DataBatBoostLastStartTrigger, es1DcSys1DataBatBoostLastStopTrigger, es1DcSys1DataBatBoostDuration, es1DcSys1DataBatBoostStartTime, es1DcSys1DataBatTestResult, es1DcSys1DataBatTestDischargedCapacityRatio, es1DcSys1DataBatTestDischargedCapacity, es1DcSys1DataBatTestFinalVoltage, es1DcSys1DataBatTestDuration, es1DcSys1DataBatTestStartTime, es1DcSys1DataBatTestPreviousResult, es1DcSys1DataBatTestPreviousDischargedCapacityRatio, es1DcSys1DataBatTestPreviousDischargedCapacity, es1DcSys1DataBatTestPreviousFinalVoltage, es1DcSys1DataBatTestPreviousDuration, es1DcSys1DataBatTestPreviousStartTime, es1DcSys1DataBatTestNextScheduledBatTest, es1DcSys1DataBatDisconnectGlobalState, es1DcSys1DataBatDisconnectGlobalReason, es1DcSys1DataBatDisconnectGlobalFeedbackState, es1DcSys1ConfigNumber, es1DcSys1ConfigName, es1DcSys1ConfigValue, es1DcSys1ConfigEntryStatus, es1DcSys1CfgDCBusVoltageAlarmLowThreshold, es1DcSys1CfgDCBusVoltageAlarmLowClearThreshold, es1DcSys1CfgDCBusVoltageAlarmHighThreshold, es1DcSys1CfgDCBusVoltageAlarmHighClearThreshold, es1DcSys1CfgBatGlobalPresence, es1DcSys1CfgBatMeasurementSourceVoltage, es1DcSys1CfgBatMeasurementSourceCurrent, es1DcSys1CfgBatCharacteristicsType, es1DcSys1CfgBatCharacteristicsNumberOfCells, es1DcSys1CfgBatCharacteristicsStringCapacity, es1DcSys1CfgBatCharacteristicsNumberOfString, es1DcSys1CfgBatAutonomyPeukertNumber, es1DcSys1CfgBatAutonomyMaxDepthOfDischargeforEstimation, es1DcSys1CfgBatFloatVoltagePerCell, es1DcSys1CfgBatFloatSource, es1DcSys1CfgBatCurrentLimitationEnabled, es1DcSys1CfgBatCurrentLimitationCurrentLimit, es1DcSys1CfgBatCurrentLimitationSource, es1DcSys1CfgBatTempAlarmLowThreshold, es1DcSys1CfgBatTempAlarmHighThreshold, es1DcSys1CfgBatTempAlarmHighHysteresis, es1DcSys1CfgBatTempDisableChargeWhenTooHigh, es1DcSys1CfgBatTempCompensationEnabled, es1DcSys1CfgBatTempCompensationCellCoefficient, es1DcSys1CfgBatTempCompensationReferenceTemp, es1DcSys1CfgBatTempCompensationMinTemp, es1DcSys1CfgBatTempCompensationMaxTemp, es1DcSys1CfgBatBoostEnabled, es1DcSys1CfgBatBoostVoltagePerCell, es1DcSys1CfgBatBoostTimeoutEnabled, es1DcSys1CfgBatBoostTimeoutDuration, es1DcSys1CfgBatBoostStopOnLowCurrentEnabled, es1DcSys1CfgBatBoostStopOnLowCurrentThreshold, es1DcSys1CfgBatBoostStartOnLowCellVoltageEnabled, es1DcSys1CfgBatBoostStartOnLowCellVoltageThreshold, es1DcSys1CfgBatBoostStopOnTempHighEnabled, es1DcSys1CfgBatBoostStartOnLongDischargeEnabled, es1DcSys1CfgBatBoostStartOnLongDischargeThreshold, es1DcSys1CfgBatTestEnabled, es1DcSys1CfgBatTestType, es1DcSys1CfgBatTestPowerSetpoint, es1DcSys1CfgBatTestTimeoutDuration, es1DcSys1CfgBatTestLowStop, es1DcSys1CfgBatTestScheduling, es1DcSys1CfgBatTestSchedulerCronRule, es1DcSys1CfgBatTestGuardTime, es1DcSys1CfgBatTestGuardTimeduration, es1DcSys1CfgBatTestEnableACLossGuard, es1DcSys1CfgBatTestAcLossGuardValue, es1DcSys1CfgBatDisconnectGlobalPresence, es1DcSys1CfgBatDisconnectGlobalInhibit, es1DcSys1CfgBatDisconnectVoltageTooLowEnabled, es1DcSys1CfgBatDisconnectVoltageTooLowThreshold, es1DcSys1CfgBatDisconnectGlobalClosingDelay, es1DcSys1CfgBatDisconnectGlobalOpeningDelay, es1DcSys1CfgBatDisconnectTempTooHighEnabled, es1DcSys1CfgBatDisconnectTempTooHighDisconnectThreshold, es1DcSys1CfgBatDisconnectTempTooHighReconnectThreshold, es1DcSys1CfgBatStringsMidpointUnbalanceAlarmThreshold, es1DcSys1CfgBatStringsMidpointUnbalanceAlarmHysteresis, es1DcSys1CfgLoadNumberofLoads, es1DcSys1CfgGenericEventsEventTableLength, es1DcSys1CfgPLCGlobalNumberOfCustomData, es1DcSys1CfgPLCGlobalNumberOfCustomAlarm, es1DcSys1ControlNumber, es1DcSys1ControlName, es1DcSys1ControlValue, es1DcSys1ControlEntryStatus, es1DcSys1CtrlBatFloatBackToFloat, es1DcSys1CtrlBatBoostStartBoostMode, es1DcSys1CtrlBatTestStartBatTest, es1DcSys1CtrlBatTestForceBatTest, es1DcSys1CtrlBatTestResetLastBatTestState, es1DcSys1CtrlBatDisconnectGlobalOpen, es1DcSys1CtrlBatDisconnectGlobalClose, es1DcSys1CtrlGenericEventsClearMyEvents, es1DcSys1CtrlGenericEventsClearAllEvents, es1DcSys1CtrlGenericEventsAddEvent, es1DcSys1CtrlGenericEventsAddMajorEvent, es1DcSys1CtrlGenericRenamingResetDefaultNamesAndGroups, es1DcSys1CtrlGenericRenamingResetNameGroupRecursive}
     STATUS       current
     DESCRIPTION  "text"
     ::= { es1DcSys1ComplianceGroups 1 }

es1DcSys1NotificationGroup NOTIFICATION-GROUP
     NOTIFICATIONS {es1DcSys1NotificationOfEvent}
     STATUS       current
     DESCRIPTION  "text"
     ::= { es1DcSys1ComplianceGroups 2 }



extensions   OBJECT IDENTIFIER ::= { siteV1 21 }
es1DcConvSystems   OBJECT IDENTIFIER ::= { es1 23 }
es1ConverterSystems  OBJECT IDENTIFIER ::= { es1 24 }
es1ConvSys1   OBJECT IDENTIFIER ::= {es1ConverterSystems 1}
es1ConvSys1GlobalStatus      OBJECT-TYPE 
              SYNTAX  DisplayString (SIZE (0..255)) 
              MAX-ACCESS  read-only 
              STATUS  current 
              DESCRIPTION "A textual string (alarms, normal or unknown) containing the status of the Converter System" 
              ::={es1ConvSys1 1 } 

es1ConvSys1GlobalAlarmSeverityType  OBJECT-TYPE 
              SYNTAX DisplayString
              MAX-ACCESS  read-only 
              STATUS  current 
              DESCRIPTION "The alarm severity type (critical, major, minor, warning, none, disabled) of the Converter System" 
              ::= { es1ConvSys1 2 }

es1ConvSys1GlobalAlarmSeverityLevel  OBJECT-TYPE 
              SYNTAX Integer32
              MAX-ACCESS  read-only 
              STATUS  current 
              DESCRIPTION "The alarm severity level (0-9) of the Converter System" 
              ::= { es1ConvSys1 3 }

es1ConvSys1GlobalAlarmSeverityTypeInt  OBJECT-TYPE 
              SYNTAX Integer32
              MAX-ACCESS  read-only 
              STATUS  current 
              DESCRIPTION "The alarm severity type as integer (critical=4, major=3, minor=2, warning=1, none=0) of the Converter System" 
              ::= { es1ConvSys1 4 }

es1ConvSys1Description     OBJECT IDENTIFIER ::= { es1ConvSys1 10 }
es1ConvSys1DescriptionNumber      OBJECT-TYPE
              SYNTAX          Integer32
              MAX-ACCESS      read-only
              STATUS          current
              DESCRIPTION    "The number of entries in the Converter System Description table"
              ::= { es1ConvSys1Description 1 }
es1ConvSys1DescriptionTable      OBJECT-TYPE
              SYNTAX          SEQUENCE OF Es1ConvSys1DescriptionEntry
              MAX-ACCESS      not-accessible
              STATUS          current
              DESCRIPTION    "The Description table of the Converter System" 
              ::= { es1ConvSys1Description 2 }
es1ConvSys1DescriptionEntry      OBJECT-TYPE
              SYNTAX          Es1ConvSys1DescriptionEntry
              MAX-ACCESS      not-accessible
              STATUS          current
              DESCRIPTION    "A Description entry"
              INDEX {es1ConvSys1DescriptionIndex}
              ::= { es1ConvSys1DescriptionTable 1 }
Es1ConvSys1DescriptionEntry ::= 
              SEQUENCE{ 
              es1ConvSys1DescriptionIndex    Unsigned32,  
              es1ConvSys1DescriptionName     DisplayString,
              es1ConvSys1DescriptionValue    DisplayString, 
              es1ConvSys1DescriptionEntryStatus RowStatus 
              }
es1ConvSys1DescriptionIndex      OBJECT-TYPE
              SYNTAX          Unsigned32
              MAX-ACCESS      not-accessible
              STATUS          current
              DESCRIPTION    "Description Index"
              ::= { es1ConvSys1DescriptionEntry 1 }
es1ConvSys1DescriptionName      OBJECT-TYPE
              SYNTAX          DisplayString
              MAX-ACCESS      read-only
              STATUS          current
              DESCRIPTION    "Description Name"
              ::= { es1ConvSys1DescriptionEntry 2 }
es1ConvSys1DescriptionValue      OBJECT-TYPE
              SYNTAX          DisplayString
              MAX-ACCESS      read-create
              STATUS          current
              DESCRIPTION    "Description Value"
              ::= { es1ConvSys1DescriptionEntry 3 }
es1ConvSys1DescriptionEntryStatus      OBJECT-TYPE
              SYNTAX          RowStatus
              MAX-ACCESS      read-create
              STATUS          current
              DESCRIPTION    "The status of this table entry"
              ::= { es1ConvSys1DescriptionEntry 4 }
es1ConvSys1DescriptionList         OBJECT IDENTIFIER ::= { es1ConvSys1Description 3 }
es1ConvSys1DescDescriptionCustomDescriptionDescription     OBJECT-TYPE
              SYNTAX          DisplayString
              MAX-ACCESS      read-write
              STATUS          current
              DESCRIPTION    "A free text zone to write a system description"
              ::= { es1ConvSys1DescriptionList 1}
es1ConvSys1DescDescriptionCustomDescriptionReference     OBJECT-TYPE
              SYNTAX          DisplayString
              MAX-ACCESS      read-write
              STATUS          current
              DESCRIPTION    "A free text zone to write the customer reference of the system"
              ::= { es1ConvSys1DescriptionList 2}
es1ConvSys1DescConvertersModel     OBJECT-TYPE
              SYNTAX          DisplayString
              MAX-ACCESS      read-only
              STATUS          current
              DESCRIPTION    "The model of module"
              ::= { es1ConvSys1DescriptionList 21}
es1ConvSys1DescACInputsGlobalSourceType     OBJECT-TYPE
              SYNTAX          DisplayString
              MAX-ACCESS      read-write
              STATUS          current
              DESCRIPTION    "The type of Ac Input Source"
              ::= { es1ConvSys1DescriptionList 301}
es1ConvSys1DescACInputsGlobalSourceName     OBJECT-TYPE
              SYNTAX          DisplayString
              MAX-ACCESS      read-write
              STATUS          current
              DESCRIPTION    "The name of Ac Input Source"
              ::= { es1ConvSys1DescriptionList 302}
es1ConvSys1DescGatewayGW1SerialNumber     OBJECT-TYPE
              SYNTAX          DisplayString
              MAX-ACCESS      read-only
              STATUS          current
              DESCRIPTION    "Gateway Serial Number"
              ::= { es1ConvSys1DescriptionList 611}
es1ConvSys1DescGatewayGW1SoftwareVersion     OBJECT-TYPE
              SYNTAX          DisplayString
              MAX-ACCESS      read-only
              STATUS          current
              DESCRIPTION    "Gateway Software Version"
              ::= { es1ConvSys1DescriptionList 612}
es1ConvSys1DescGatewayGW1HardwareReference     OBJECT-TYPE
              SYNTAX          DisplayString
              MAX-ACCESS      read-only
              STATUS          current
              DESCRIPTION    "Gateway HW Type"
              ::= { es1ConvSys1DescriptionList 613}
es1ConvSys1DescGatewayGW1IPAddress     OBJECT-TYPE
              SYNTAX          DisplayString
              MAX-ACCESS      read-only
              STATUS          current
              DESCRIPTION    "Inview Ip Address"
              ::= { es1ConvSys1DescriptionList 614}
es1ConvSys1Alarm          OBJECT IDENTIFIER ::= { es1ConvSys1 11 }
es1ConvSys1AlarmNumber      OBJECT-TYPE
              SYNTAX          Integer32
              MAX-ACCESS      read-only
              STATUS          current
              DESCRIPTION    "The number of entries in the Converter System Alarm table"
              ::= { es1ConvSys1Alarm 1 }
es1ConvSys1AlarmTable      OBJECT-TYPE
              SYNTAX          SEQUENCE OF Es1ConvSys1AlarmEntry
              MAX-ACCESS      not-accessible
              STATUS          current
              DESCRIPTION    "The table of Alarm entries"
              ::= { es1ConvSys1Alarm 2 }
es1ConvSys1AlarmEntry      OBJECT-TYPE
              SYNTAX          Es1ConvSys1AlarmEntry
              MAX-ACCESS      not-accessible
              STATUS          current
              DESCRIPTION    "An alarm entry"
              INDEX {es1ConvSys1AlarmIndex}
              ::= { es1ConvSys1AlarmTable 1 }
Es1ConvSys1AlarmEntry ::= 
             SEQUENCE{ 
             es1ConvSys1AlarmIndex         Unsigned32,  
             es1ConvSys1AlarmName          DisplayString,
             es1ConvSys1AlarmActive        DisplayString, 
             es1ConvSys1AlarmSeverityType  DisplayString, 
             es1ConvSys1AlarmSeverityLevel DisplayString, 
             es1ConvSys1AlarmStartTime      DisplayString, 
             es1ConvSys1AlarmStopTime       DisplayString, 
              es1ConvSys1AlarmEntryStatus  RowStatus 
             }
es1ConvSys1AlarmIndex      OBJECT-TYPE
              SYNTAX          Unsigned32
              MAX-ACCESS      not-accessible
              STATUS          current
              DESCRIPTION    "Alarm Index"
              ::= { es1ConvSys1AlarmEntry 1 }
es1ConvSys1AlarmName      OBJECT-TYPE
              SYNTAX          DisplayString
              MAX-ACCESS      read-only
              STATUS          current
              DESCRIPTION    "Alarm Name"
              ::= { es1ConvSys1AlarmEntry 2 }
es1ConvSys1AlarmActive   OBJECT-TYPE
              SYNTAX          DisplayString
              MAX-ACCESS      read-only
              STATUS          current
              DESCRIPTION    "Is the Alarm active ? 'true' for active, 'false' for not-active"
              ::= { es1ConvSys1AlarmEntry 3 }
es1ConvSys1AlarmSeverityType      OBJECT-TYPE
              SYNTAX          DisplayString
              MAX-ACCESS      read-write
              STATUS          current
              DESCRIPTION    "The alarm severity type (major, minor, warning, none, disabled) of this alarm entry" 
              ::= { es1ConvSys1AlarmEntry 4 }
es1ConvSys1AlarmSeverityLevel      OBJECT-TYPE
              SYNTAX          DisplayString
              MAX-ACCESS      read-write
              STATUS          current
              DESCRIPTION    "The alarm severity level (0-9) of this alarm entry" 
              ::= { es1ConvSys1AlarmEntry 5 }
es1ConvSys1AlarmStartTime      OBJECT-TYPE
              SYNTAX          DisplayString
              MAX-ACCESS      read-only
              STATUS          current
              DESCRIPTION    "The last start time of this alarm entry (null if never active)"
              ::= { es1ConvSys1AlarmEntry 6 }
es1ConvSys1AlarmStopTime      OBJECT-TYPE
              SYNTAX          DisplayString
              MAX-ACCESS      read-only
              STATUS          current
              DESCRIPTION    "The last stop time of this alarm entry (null if alarm active)"
              ::= { es1ConvSys1AlarmEntry 7 }
es1ConvSys1AlarmEntryStatus      OBJECT-TYPE
              SYNTAX          RowStatus
              MAX-ACCESS      read-create
              STATUS          current
              DESCRIPTION    "The status of this table entry - not used, only for MIB compliance "
              ::= { es1ConvSys1AlarmEntry 8 }
es1ConvSys1AlarmSummary      OBJECT-TYPE
              SYNTAX BITS{
                  systemGlobalTopologyInconsistentWithDCSystemConf (0),          -- Alarm : System Global Topology Inconsistent With DC System Configuration
                  convertersGlobalBackfeedDetected (20),          -- Alarm : Converters Global Backfeed Detected
                  convertersBypassReady (30),          -- Alarm : Converters Bypass Ready
                  aCOutsGlobalFail (100),          -- Alarm : AC Outputs Global Failure
                  aCOutsGlobalSaturated (101),          -- Alarm : AC Outputs Global Saturated
                  aCOutsGlobalRedundancyLost (102),          -- Alarm : AC Outputs Global Redundancy Lost
                  aCOutsGlobalRedundancyPlusOneLost (103),          -- Alarm : AC Outputs Global Redundancy Plus One Lost
                  aCOutsGlobalLessConvertersThanConfigured (104),          -- Alarm : AC Outputs Global Less Converters Than Configured
                  aCOutsPhase1Fail (120),          -- Alarm : AC Outputs Phase 1 Failure
                  aCOutsPhase1Saturated (121),          -- Alarm : AC Outputs Phase 1 Saturated
                  aCOutsPhase1RedundancyLost (122),          -- Alarm : AC Outputs Phase 1 Redundancy Lost
                  aCOutsPhase1RedundancyPlusOneLost (123),          -- Alarm : AC Outputs Phase 1 Redundancy Plus One Lost
                  aCOutsPhase1LessConvertersThanConfigured (124),          -- Alarm : AC Outputs Phase 1 Less Converters Than Configured
                  aCInputsGlobalSourceFail (300),          -- Alarm : AC Inputs Global Source Failure
                  aCInputsGlobalSaturated (301),          -- Alarm : AC Inputs Global Saturated
                  aCInputsPhase1SourceFail (320),          -- Alarm : AC Inputs Phase 1 Source Failure
                  aCInputsPhase1Saturated (321),          -- Alarm : AC Inputs Phase 1 Saturated
                  dCBus1Fail (500),          -- Alarm : DC Bus 1 Failure
                  dCBus1Saturated (501),          -- Alarm : DC Bus 1 Saturated
                  gatewayGW1CommunicationFail (610),          -- Alarm : Gateway GW1 Communication Failure
                  gatewayGW1SystemParallelizationBusIssue (611),          -- Alarm : Gateway GW1 System Parallelization Bus Issue
                  gatewayGW1WrongConf (612),          -- Alarm : Gateway GW1 Wrong Configuration
                  gatewayGW1LastConfSendingFail (613),          -- Alarm : Gateway GW1 Last Configuration Sending Failure
                  synchronizerGlobalFail (700),          -- Alarm : Synchronizer Global Failure
                  synchronizerGlobalRedundancyLost (701),          -- Alarm : Synchronizer Global Redundancy Lost
                  synchronizerPhase1Fail (720),          -- Alarm : Synchronizer Phase 1 Failure
                  synchronizerPhase1RedundancyLost (721)          -- Alarm : Synchronizer Phase 1 Redundancy Lost
              }
              MAX-ACCESS      read-only
              STATUS          current
              DESCRIPTION    "Summary bit vector with all the alarms state of the Converter System. A '1' means alarm active, '0' means not active. Unimplemented alarms are always '0'." 
              ::= { es1ConvSys1Alarm 3 }
es1ConvSys1Event          OBJECT IDENTIFIER ::= { es1ConvSys1 12 }
es1ConvSys1EventNumber      OBJECT-TYPE
              SYNTAX          Integer32
              MAX-ACCESS      read-only
              STATUS          current
              DESCRIPTION    "The number of entries in the Event Table related to the Converter System" 
              ::= { es1ConvSys1Event 1 }
es1ConvSys1EventTable      OBJECT-TYPE
              SYNTAX          SEQUENCE OF Es1ConvSys1EventEntry
              MAX-ACCESS      not-accessible
              STATUS          current
              DESCRIPTION    "The Event table related to the Converter System" 
              ::= { es1ConvSys1Event 2 }
es1ConvSys1EventEntry      OBJECT-TYPE
              SYNTAX          Es1ConvSys1EventEntry
              MAX-ACCESS      not-accessible
              STATUS          current
              DESCRIPTION    "."
              INDEX {es1ConvSys1EventIndex}
              ::= { es1ConvSys1EventTable 1 }
Es1ConvSys1EventEntry ::= 
             SEQUENCE{ 
             es1ConvSys1EventIndex           Unsigned32,  
             es1ConvSys1EventId              Unsigned32,  
             es1ConvSys1EventName            DisplayString,
             es1ConvSys1EventDateTime        DisplayString, 
             es1ConvSys1EventSeverityType    DisplayString, 
             es1ConvSys1EventSeverityLevel   DisplayString,
              es1ConvSys1EventEntryStatus    RowStatus 
             }
es1ConvSys1EventIndex      OBJECT-TYPE
              SYNTAX          Unsigned32
              MAX-ACCESS      not-accessible
              STATUS          current
              DESCRIPTION    "Event Index"
              ::= { es1ConvSys1EventEntry 1 }
es1ConvSys1EventId      OBJECT-TYPE
              SYNTAX          Unsigned32
              MAX-ACCESS      read-only
              STATUS          current
              DESCRIPTION    "Event Index"
              ::= { es1ConvSys1EventEntry 2 }
es1ConvSys1EventName      OBJECT-TYPE
              SYNTAX          DisplayString
              MAX-ACCESS      read-only
              STATUS          current
              DESCRIPTION    "Event Name"
              ::= { es1ConvSys1EventEntry 3 }
es1ConvSys1EventDateTime      OBJECT-TYPE
              SYNTAX          DisplayString
              MAX-ACCESS      read-only
              STATUS          current
              DESCRIPTION    "The date and time of the event"
              ::= { es1ConvSys1EventEntry 4 }
es1ConvSys1EventSeverityType      OBJECT-TYPE
              SYNTAX          DisplayString
              MAX-ACCESS      read-only
              STATUS          current
              DESCRIPTION    "The event severity type ('major', 'minor', 'warning' or 'none')"
              ::= { es1ConvSys1EventEntry 5 }
es1ConvSys1EventSeverityLevel      OBJECT-TYPE
              SYNTAX          DisplayString
              MAX-ACCESS      read-only
              STATUS          current
              DESCRIPTION    "The event severity level (0-9)"
              ::= { es1ConvSys1EventEntry 6 }
es1ConvSys1EventEntryStatus      OBJECT-TYPE
              SYNTAX          RowStatus
              MAX-ACCESS      read-create
              STATUS          current
              DESCRIPTION    "The status of this table entry"
              ::= { es1ConvSys1EventEntry 7 }
es1ConvSys1Data            OBJECT IDENTIFIER ::= { es1ConvSys1 13 }
es1ConvSys1DataNumber      OBJECT-TYPE
              SYNTAX          Integer32
              MAX-ACCESS      read-only
              STATUS          current
              DESCRIPTION    "The number of entries in the Data Table related to the Converter System" 
              ::= { es1ConvSys1Data 1 }
es1ConvSys1DataTable      OBJECT-TYPE
              SYNTAX          SEQUENCE OF Es1ConvSys1DataEntry
              MAX-ACCESS      not-accessible
              STATUS          current
              DESCRIPTION    "The table of Data entries"
              ::= { es1ConvSys1Data 2 }
es1ConvSys1DataEntry      OBJECT-TYPE
              SYNTAX          Es1ConvSys1DataEntry
              MAX-ACCESS      not-accessible
              STATUS          current
              DESCRIPTION    "A data entry"
              INDEX {es1ConvSys1DataIndex}
              ::= { es1ConvSys1DataTable 1 }
Es1ConvSys1DataEntry ::= 
             SEQUENCE{ 
             es1ConvSys1DataIndex       Unsigned32,  
             es1ConvSys1DataName        DisplayString,
             es1ConvSys1DataValue       DisplayString, 
              es1ConvSys1DataEntryStatus  RowStatus 
             }
es1ConvSys1DataIndex      OBJECT-TYPE
              SYNTAX          Unsigned32
              MAX-ACCESS      not-accessible
              STATUS          current
              DESCRIPTION    "The data index"
              ::= { es1ConvSys1DataEntry 1 }

es1ConvSys1DataName      OBJECT-TYPE
              SYNTAX          DisplayString
              MAX-ACCESS      read-only
              STATUS          current
              DESCRIPTION    "The data name"
              ::= { es1ConvSys1DataEntry 2 }
es1ConvSys1DataValue     OBJECT-TYPE
              SYNTAX          DisplayString
              MAX-ACCESS      read-only
              STATUS          current
              DESCRIPTION    "The data value"
              ::= { es1ConvSys1DataEntry 3 }
es1ConvSys1DataEntryStatus      OBJECT-TYPE
              SYNTAX          RowStatus
              MAX-ACCESS      read-create
              STATUS          current
              DESCRIPTION    "The status of this table entry - not used, only present for compliance"
              ::= { es1ConvSys1DataEntry 4 }
es1ConvSys1DataList         OBJECT IDENTIFIER ::= { es1ConvSys1Data 3 }
es1ConvSys1DataConvertersBypassState     OBJECT-TYPE
              SYNTAX          DisplayString
              MAX-ACCESS      read-only
              STATUS          current
              DESCRIPTION    "State of converters with respect to Manual Bypass (MBP)"
              ::= { es1ConvSys1DataList 31}
es1ConvSys1DataACOutsGlobalCurrent     OBJECT-TYPE
              SYNTAX          Integer32
              MAX-ACCESS      read-only
              STATUS          current
              DESCRIPTION    "Current in amperes group 0"
              ::= { es1ConvSys1DataList 102}
es1ConvSys1DataACOutsGlobalActivePower     OBJECT-TYPE
              SYNTAX          Integer32
              MAX-ACCESS      read-only
              STATUS          current
              DESCRIPTION    "Power in watts group 0"
              ::= { es1ConvSys1DataList 103}
es1ConvSys1DataACOutsGlobalApparentPower     OBJECT-TYPE
              SYNTAX          Integer32
              MAX-ACCESS      read-only
              STATUS          current
              DESCRIPTION    "Apparent power in VA group 0"
              ::= { es1ConvSys1DataList 104}
es1ConvSys1DataACOutsGlobalStatus     OBJECT-TYPE
              SYNTAX          Integer32
              MAX-ACCESS      read-only
              STATUS          current
              DESCRIPTION    "NA"
              ::= { es1ConvSys1DataList 106}
es1ConvSys1DataACOutsGlobalMembers     OBJECT-TYPE
              SYNTAX          Integer32
              MAX-ACCESS      read-only
              STATUS          current
              DESCRIPTION    "The number of module"
              ::= { es1ConvSys1DataList 107}
es1ConvSys1DataACOutsGlobalInstalledActivePower     OBJECT-TYPE
              SYNTAX          Integer32
              MAX-ACCESS      read-only
              STATUS          current
              DESCRIPTION    "Installed power value in watts for group 0"
              ::= { es1ConvSys1DataList 111}
es1ConvSys1DataACOutsGlobalInstalledApparentPower     OBJECT-TYPE
              SYNTAX          Integer32
              MAX-ACCESS      read-only
              STATUS          current
              DESCRIPTION    "Installed power value in VA for group 0"
              ::= { es1ConvSys1DataList 112}
es1ConvSys1DataACOutsGlobalAvailableActivePower     OBJECT-TYPE
              SYNTAX          Integer32
              MAX-ACCESS      read-only
              STATUS          current
              DESCRIPTION    "Available power value in watts for group 0"
              ::= { es1ConvSys1DataList 113}
es1ConvSys1DataACOutsGlobalAvailableApparentPower     OBJECT-TYPE
              SYNTAX          Integer32
              MAX-ACCESS      read-only
              STATUS          current
              DESCRIPTION    "Available power value in VA for group 0"
              ::= { es1ConvSys1DataList 114}
es1ConvSys1DataACOutsGlobalPowerFactor     OBJECT-TYPE
              SYNTAX          Integer32
              MAX-ACCESS      read-only
              STATUS          current
              DESCRIPTION    "Power Factor Phase 0"
              ::= { es1ConvSys1DataList 115}
es1ConvSys1DataACOutsGlobalSaturationLevel     OBJECT-TYPE
              SYNTAX          Integer32
              MAX-ACCESS      read-only
              STATUS          current
              DESCRIPTION    "The max of the ratio Used Power/Installed Power in VA and W"
              ::= { es1ConvSys1DataList 117}
es1ConvSys1DataACOutsPhase1Voltage     OBJECT-TYPE
              SYNTAX          Integer32
              MAX-ACCESS      read-only
              STATUS          current
              DESCRIPTION    "Voltage in volts group 1"
              ::= { es1ConvSys1DataList 121}
es1ConvSys1DataACOutsPhase1Current     OBJECT-TYPE
              SYNTAX          Integer32
              MAX-ACCESS      read-only
              STATUS          current
              DESCRIPTION    "Current in amperes group 1"
              ::= { es1ConvSys1DataList 122}
es1ConvSys1DataACOutsPhase1ActivePower     OBJECT-TYPE
              SYNTAX          Integer32
              MAX-ACCESS      read-only
              STATUS          current
              DESCRIPTION    "Power in watts group 1"
              ::= { es1ConvSys1DataList 123}
es1ConvSys1DataACOutsPhase1ApparentPower     OBJECT-TYPE
              SYNTAX          Integer32
              MAX-ACCESS      read-only
              STATUS          current
              DESCRIPTION    "Apparent power in VA group 1"
              ::= { es1ConvSys1DataList 124}
es1ConvSys1DataACOutsPhase1Frequency     OBJECT-TYPE
              SYNTAX          Integer32
              MAX-ACCESS      read-only
              STATUS          current
              DESCRIPTION    "Output Frequency in hertz group 1"
              ::= { es1ConvSys1DataList 125}
es1ConvSys1DataACOutsPhase1Status     OBJECT-TYPE
              SYNTAX          Integer32
              MAX-ACCESS      read-only
              STATUS          current
              DESCRIPTION    "NA"
              ::= { es1ConvSys1DataList 126}
es1ConvSys1DataACOutsPhase1Members     OBJECT-TYPE
              SYNTAX          Integer32
              MAX-ACCESS      read-only
              STATUS          current
              DESCRIPTION    "The number of module"
              ::= { es1ConvSys1DataList 127}
es1ConvSys1DataACOutsPhase1InstalledActivePower     OBJECT-TYPE
              SYNTAX          Integer32
              MAX-ACCESS      read-only
              STATUS          current
              DESCRIPTION    "Installed power value in watts for group 1"
              ::= { es1ConvSys1DataList 131}
es1ConvSys1DataACOutsPhase1InstalledApparentPower     OBJECT-TYPE
              SYNTAX          Integer32
              MAX-ACCESS      read-only
              STATUS          current
              DESCRIPTION    "Installed power value in VA for group 1"
              ::= { es1ConvSys1DataList 132}
es1ConvSys1DataACOutsPhase1AvailableActivePower     OBJECT-TYPE
              SYNTAX          Integer32
              MAX-ACCESS      read-only
              STATUS          current
              DESCRIPTION    "Available power value in watts for group 1"
              ::= { es1ConvSys1DataList 133}
es1ConvSys1DataACOutsPhase1AvailableApparentPower     OBJECT-TYPE
              SYNTAX          Integer32
              MAX-ACCESS      read-only
              STATUS          current
              DESCRIPTION    "Available power value in VA for group 1"
              ::= { es1ConvSys1DataList 134}
es1ConvSys1DataACOutsPhase1PowerFactor     OBJECT-TYPE
              SYNTAX          Integer32
              MAX-ACCESS      read-only
              STATUS          current
              DESCRIPTION    "Power Factor Phase 1"
              ::= { es1ConvSys1DataList 135}
es1ConvSys1DataACOutsPhase1SaturationLevel     OBJECT-TYPE
              SYNTAX          Integer32
              MAX-ACCESS      read-only
              STATUS          current
              DESCRIPTION    "The max of the ratio Used Power/Installed Power in VA and W"
              ::= { es1ConvSys1DataList 137}
es1ConvSys1DataACInputsGlobalCurrent     OBJECT-TYPE
              SYNTAX          Integer32
              MAX-ACCESS      read-only
              STATUS          current
              DESCRIPTION    "Current in amperes group 0"
              ::= { es1ConvSys1DataList 302}
es1ConvSys1DataACInputsGlobalActivePower     OBJECT-TYPE
              SYNTAX          Integer32
              MAX-ACCESS      read-only
              STATUS          current
              DESCRIPTION    "Power in watts group 0"
              ::= { es1ConvSys1DataList 303}
es1ConvSys1DataACInputsGlobalApparentPower     OBJECT-TYPE
              SYNTAX          Integer32
              MAX-ACCESS      read-only
              STATUS          current
              DESCRIPTION    "Apparent power in VA group 0"
              ::= { es1ConvSys1DataList 304}
es1ConvSys1DataACInputsGlobalStatus     OBJECT-TYPE
              SYNTAX          Integer32
              MAX-ACCESS      read-only
              STATUS          current
              DESCRIPTION    "NA"
              ::= { es1ConvSys1DataList 310}
es1ConvSys1DataACInputsGlobalInstalledActivePower     OBJECT-TYPE
              SYNTAX          Integer32
              MAX-ACCESS      read-only
              STATUS          current
              DESCRIPTION    "Installed power value in watts for group 0"
              ::= { es1ConvSys1DataList 311}
es1ConvSys1DataACInputsGlobalInstalledApparentPower     OBJECT-TYPE
              SYNTAX          Integer32
              MAX-ACCESS      read-only
              STATUS          current
              DESCRIPTION    "Installed power value in VA for group 0"
              ::= { es1ConvSys1DataList 312}
es1ConvSys1DataACInputsGlobalAvailableActivePower     OBJECT-TYPE
              SYNTAX          Integer32
              MAX-ACCESS      read-only
              STATUS          current
              DESCRIPTION    "Available power value in watts for group 0"
              ::= { es1ConvSys1DataList 313}
es1ConvSys1DataACInputsGlobalAvailableApparentPower     OBJECT-TYPE
              SYNTAX          Integer32
              MAX-ACCESS      read-only
              STATUS          current
              DESCRIPTION    "Available power value in VA for group 0"
              ::= { es1ConvSys1DataList 314}
es1ConvSys1DataACInputsGlobalSaturationLevel     OBJECT-TYPE
              SYNTAX          Integer32
              MAX-ACCESS      read-only
              STATUS          current
              DESCRIPTION    "The max of the ratio Used Power/Installed Power in VA and W"
              ::= { es1ConvSys1DataList 317}
es1ConvSys1DataACInputsPhase1Voltage     OBJECT-TYPE
              SYNTAX          Integer32
              MAX-ACCESS      read-only
              STATUS          current
              DESCRIPTION    "Voltage in volts group 1"
              ::= { es1ConvSys1DataList 321}
es1ConvSys1DataACInputsPhase1Current     OBJECT-TYPE
              SYNTAX          Integer32
              MAX-ACCESS      read-only
              STATUS          current
              DESCRIPTION    "Current in amperes group 1"
              ::= { es1ConvSys1DataList 322}
es1ConvSys1DataACInputsPhase1ActivePower     OBJECT-TYPE
              SYNTAX          Integer32
              MAX-ACCESS      read-only
              STATUS          current
              DESCRIPTION    "Power in watts group 1"
              ::= { es1ConvSys1DataList 323}
es1ConvSys1DataACInputsPhase1ApparentPower     OBJECT-TYPE
              SYNTAX          Integer32
              MAX-ACCESS      read-only
              STATUS          current
              DESCRIPTION    "Apparent power in VA group 1"
              ::= { es1ConvSys1DataList 324}
es1ConvSys1DataACInputsPhase1Frequency     OBJECT-TYPE
              SYNTAX          Integer32
              MAX-ACCESS      read-only
              STATUS          current
              DESCRIPTION    "Output Frequency in hertz group 1"
              ::= { es1ConvSys1DataList 325}
es1ConvSys1DataACInputsPhase1Status     OBJECT-TYPE
              SYNTAX          Integer32
              MAX-ACCESS      read-only
              STATUS          current
              DESCRIPTION    "NA"
              ::= { es1ConvSys1DataList 330}
es1ConvSys1DataACInputsPhase1InstalledActivePower     OBJECT-TYPE
              SYNTAX          Integer32
              MAX-ACCESS      read-only
              STATUS          current
              DESCRIPTION    "Installed power value in watts for group 1"
              ::= { es1ConvSys1DataList 331}
es1ConvSys1DataACInputsPhase1InstalledApparentPower     OBJECT-TYPE
              SYNTAX          Integer32
              MAX-ACCESS      read-only
              STATUS          current
              DESCRIPTION    "Installed power value in VA for group 1"
              ::= { es1ConvSys1DataList 332}
es1ConvSys1DataACInputsPhase1AvailableActivePower     OBJECT-TYPE
              SYNTAX          Integer32
              MAX-ACCESS      read-only
              STATUS          current
              DESCRIPTION    "Available power value in watts for group 1"
              ::= { es1ConvSys1DataList 333}
es1ConvSys1DataACInputsPhase1AvailableApparentPower     OBJECT-TYPE
              SYNTAX          Integer32
              MAX-ACCESS      read-only
              STATUS          current
              DESCRIPTION    "Available power value in VA for group 1"
              ::= { es1ConvSys1DataList 334}
es1ConvSys1DataACInputsPhase1SaturationLevel     OBJECT-TYPE
              SYNTAX          Integer32
              MAX-ACCESS      read-only
              STATUS          current
              DESCRIPTION    "The max of the ratio Used Power/Installed Power in VA and W"
              ::= { es1ConvSys1DataList 337}
es1ConvSys1DataDCBus1Voltage     OBJECT-TYPE
              SYNTAX          Integer32
              MAX-ACCESS      read-only
              STATUS          current
              DESCRIPTION    "DC voltage value in volt group 1"
              ::= { es1ConvSys1DataList 501}
es1ConvSys1DataDCBus1Current     OBJECT-TYPE
              SYNTAX          Integer32
              MAX-ACCESS      read-only
              STATUS          current
              DESCRIPTION    "DC current value in amperes group 1"
              ::= { es1ConvSys1DataList 502}
es1ConvSys1DataDCBus1Power     OBJECT-TYPE
              SYNTAX          Integer32
              MAX-ACCESS      read-only
              STATUS          current
              DESCRIPTION    "DC power value in watts group 1"
              ::= { es1ConvSys1DataList 503}
es1ConvSys1DataDCBus1VoltageSetPoint     OBJECT-TYPE
              SYNTAX          Integer32
              MAX-ACCESS      read-only
              STATUS          current
              DESCRIPTION    "The Live Setpoint of DC Bus 1 Voltage"
              ::= { es1ConvSys1DataList 504}
es1ConvSys1DataDCBus1PowerSetpoint     OBJECT-TYPE
              SYNTAX          Integer32
              MAX-ACCESS      read-only
              STATUS          current
              DESCRIPTION    "The Live Setpoint of DC Bus 1 Power"
              ::= { es1ConvSys1DataList 505}
es1ConvSys1DataDCBus1Status     OBJECT-TYPE
              SYNTAX          Integer32
              MAX-ACCESS      read-only
              STATUS          current
              DESCRIPTION    "NA"
              ::= { es1ConvSys1DataList 506}
es1ConvSys1DataDCBus1Members     OBJECT-TYPE
              SYNTAX          Integer32
              MAX-ACCESS      read-only
              STATUS          current
              DESCRIPTION    "Number of members"
              ::= { es1ConvSys1DataList 507}
es1ConvSys1DataDCBus1InstalledPower     OBJECT-TYPE
              SYNTAX          Integer32
              MAX-ACCESS      read-only
              STATUS          current
              DESCRIPTION    "Installed power value in watts for group 1"
              ::= { es1ConvSys1DataList 511}
es1ConvSys1DataDCBus1AvailablePower     OBJECT-TYPE
              SYNTAX          Integer32
              MAX-ACCESS      read-only
              STATUS          current
              DESCRIPTION    "Available power value in watts for group 1"
              ::= { es1ConvSys1DataList 512}
es1ConvSys1DataDCBus1StatusCharger     OBJECT-TYPE
              SYNTAX          Integer32
              MAX-ACCESS      read-only
              STATUS          current
              DESCRIPTION    "NA"
              ::= { es1ConvSys1DataList 516}
es1ConvSys1DataDCBus1SaturationLevel     OBJECT-TYPE
              SYNTAX          Integer32
              MAX-ACCESS      read-only
              STATUS          current
              DESCRIPTION    "The max of the ratio Used Power/Installed Power in VA and W"
              ::= { es1ConvSys1DataList 517}
es1ConvSys1DataGatewayGW1BusStatus     OBJECT-TYPE
              SYNTAX          Integer32
              MAX-ACCESS      read-only
              STATUS          current
              DESCRIPTION    "The State of the bus"
              ::= { es1ConvSys1DataList 611}
es1ConvSys1DataGatewayGW1ConfStatus     OBJECT-TYPE
              SYNTAX          Integer32
              MAX-ACCESS      read-only
              STATUS          current
              DESCRIPTION    "The state of the configuration"
              ::= { es1ConvSys1DataList 612}
es1ConvSys1DataGatewayGW1LastConfSendingState     OBJECT-TYPE
              SYNTAX          DisplayString
              MAX-ACCESS      read-only
              STATUS          current
              DESCRIPTION    "The state of the configuration"
              ::= { es1ConvSys1DataList 613}
es1ConvSys1DataGatewayGW1LastConfSendingMessage     OBJECT-TYPE
              SYNTAX          DisplayString
              MAX-ACCESS      read-only
              STATUS          current
              DESCRIPTION    "The state of the configuration"
              ::= { es1ConvSys1DataList 614}
es1ConvSys1DataGatewayGW1LastConfSendingDetails     OBJECT-TYPE
              SYNTAX          DisplayString
              MAX-ACCESS      read-only
              STATUS          current
              DESCRIPTION    "The state of the configuration"
              ::= { es1ConvSys1DataList 615}
es1ConvSys1DataSynchronizerGlobalStatus     OBJECT-TYPE
              SYNTAX          Integer32
              MAX-ACCESS      read-only
              STATUS          current
              DESCRIPTION    "NA"
              ::= { es1ConvSys1DataList 706}
es1ConvSys1DataSynchronizerGlobalMembers     OBJECT-TYPE
              SYNTAX          Integer32
              MAX-ACCESS      read-only
              STATUS          current
              DESCRIPTION    "The number of TUS"
              ::= { es1ConvSys1DataList 707}
es1ConvSys1DataSynchronizerGlobalOK     OBJECT-TYPE
              SYNTAX          Integer32
              MAX-ACCESS      read-only
              STATUS          current
              DESCRIPTION    "The number of TUS OK"
              ::= { es1ConvSys1DataList 708}
es1ConvSys1DataSynchronizerPhase1Status     OBJECT-TYPE
              SYNTAX          Integer32
              MAX-ACCESS      read-only
              STATUS          current
              DESCRIPTION    "NA"
              ::= { es1ConvSys1DataList 726}
es1ConvSys1DataSynchronizerPhase1Members     OBJECT-TYPE
              SYNTAX          Integer32
              MAX-ACCESS      read-only
              STATUS          current
              DESCRIPTION    "The number of TUS"
              ::= { es1ConvSys1DataList 727}
es1ConvSys1DataSynchronizerPhase1OK     OBJECT-TYPE
              SYNTAX          Integer32
              MAX-ACCESS      read-only
              STATUS          current
              DESCRIPTION    "The number of TUS OK"
              ::= { es1ConvSys1DataList 728}
es1ConvSys1Config          OBJECT IDENTIFIER ::= { es1ConvSys1 15 }
es1ConvSys1ConfigNumber      OBJECT-TYPE
              SYNTAX          Integer32
              MAX-ACCESS      read-only
              STATUS          current
              DESCRIPTION    "The number of entries in the Config table related to the Converter System" 
              ::= { es1ConvSys1Config 1 }
es1ConvSys1ConfigTable      OBJECT-TYPE
              SYNTAX          SEQUENCE OF Es1ConvSys1ConfigEntry
              MAX-ACCESS      not-accessible
              STATUS          current
              DESCRIPTION    "The table of Config entries related to the Converter System" 
              ::= { es1ConvSys1Config 2 }
es1ConvSys1ConfigEntry      OBJECT-TYPE
              SYNTAX          Es1ConvSys1ConfigEntry
              MAX-ACCESS      not-accessible
              STATUS          current
              DESCRIPTION    "A Config entry"
              INDEX {es1ConvSys1ConfigIndex}
              ::= { es1ConvSys1ConfigTable 1 }
Es1ConvSys1ConfigEntry ::= 
             SEQUENCE{ 
             es1ConvSys1ConfigIndex       Unsigned32,  
             es1ConvSys1ConfigName        DisplayString,
             es1ConvSys1ConfigValue       DisplayString, 
              es1ConvSys1ConfigEntryStatus  RowStatus 
             }
es1ConvSys1ConfigIndex      OBJECT-TYPE
              SYNTAX          Unsigned32
              MAX-ACCESS      not-accessible
              STATUS          current
              DESCRIPTION    "The Config entry Index"
              ::= { es1ConvSys1ConfigEntry 1 }
es1ConvSys1ConfigName      OBJECT-TYPE
              SYNTAX          DisplayString
              MAX-ACCESS      read-only
              STATUS          current
              DESCRIPTION    "The Config entry name"
              ::= { es1ConvSys1ConfigEntry 2 }
es1ConvSys1ConfigValue     OBJECT-TYPE
              SYNTAX          DisplayString
              MAX-ACCESS      read-write
              STATUS          current
              DESCRIPTION    "The Config entry value"
              ::= { es1ConvSys1ConfigEntry 3 }
es1ConvSys1ConfigEntryStatus      OBJECT-TYPE
              SYNTAX          RowStatus
              MAX-ACCESS      read-create
              STATUS          current
              DESCRIPTION    "The status of this table entry - not used, only for compliance"
              ::= { es1ConvSys1ConfigEntry 4 }
es1ConvSys1ConfigList         OBJECT IDENTIFIER ::= { es1ConvSys1Config 3 }
es1ConvSys1CfgSystemGlobalTopology     OBJECT-TYPE
              SYNTAX          DisplayString
              MAX-ACCESS      read-write
              STATUS          current
              DESCRIPTION    "NA"
              ::= { es1ConvSys1ConfigList 1}
es1ConvSys1CfgSystemACNumberOfPhases     OBJECT-TYPE
              SYNTAX          DisplayString
              MAX-ACCESS      read-write
              STATUS          current
              DESCRIPTION    "Number of AC output Phase"
              ::= { es1ConvSys1ConfigList 6}
es1ConvSys1CfgConvertersAllowFullRemoteControl     OBJECT-TYPE
              SYNTAX          DisplayString
              MAX-ACCESS      read-write
              STATUS          current
              DESCRIPTION    "By default set to false, this parameters allows to shut down all modules with all API"
              ::= { es1ConvSys1ConfigList 41}
es1ConvSys1CfgACOutsGlobalSaturationLevelAlarmSet     OBJECT-TYPE
              SYNTAX          DisplayString
              MAX-ACCESS      read-write
              STATUS          current
              DESCRIPTION    "NA"
              ::= { es1ConvSys1ConfigList 111}
es1ConvSys1CfgACOutsGlobalSaturationLevelAlarmClear     OBJECT-TYPE
              SYNTAX          DisplayString
              MAX-ACCESS      read-write
              STATUS          current
              DESCRIPTION    "NA"
              ::= { es1ConvSys1ConfigList 112}
es1ConvSys1CfgACOutsPhase1ConfiguredConverters     OBJECT-TYPE
              SYNTAX          DisplayString
              MAX-ACCESS      read-write
              STATUS          current
              DESCRIPTION    "Number of modules configured for the phase 1"
              ::= { es1ConvSys1ConfigList 121}
es1ConvSys1CfgACOutsPhase1RedundantConverters     OBJECT-TYPE
              SYNTAX          DisplayString
              MAX-ACCESS      read-write
              STATUS          current
              DESCRIPTION    "Amount of redundancy configured in the phase 1"
              ::= { es1ConvSys1ConfigList 122}
es1ConvSys1CfgACOutsPhase1NominalPhaseShift     OBJECT-TYPE
              SYNTAX          DisplayString
              MAX-ACCESS      read-write
              STATUS          current
              DESCRIPTION    "The phase shift in degrees in phase"
              ::= { es1ConvSys1ConfigList 123}
es1ConvSys1CfgACOutsPhase1NominalVoltage     OBJECT-TYPE
              SYNTAX          DisplayString
              MAX-ACCESS      read-write
              STATUS          current
              DESCRIPTION    "The nominal voltage in phase"
              ::= { es1ConvSys1ConfigList 124}
es1ConvSys1CfgACInputsPeakShavingOverridePowerLimitationTimeout     OBJECT-TYPE
              SYNTAX          DisplayString
              MAX-ACCESS      read-write
              STATUS          current
              DESCRIPTION    "NA"
              ::= { es1ConvSys1ConfigList 301}
es1ConvSys1CfgACInputsGlobalSaturationLevelAlarmSet     OBJECT-TYPE
              SYNTAX          DisplayString
              MAX-ACCESS      read-write
              STATUS          current
              DESCRIPTION    "NA"
              ::= { es1ConvSys1ConfigList 311}
es1ConvSys1CfgACInputsGlobalSaturationLevelAlarmClear     OBJECT-TYPE
              SYNTAX          DisplayString
              MAX-ACCESS      read-write
              STATUS          current
              DESCRIPTION    "NA"
              ::= { es1ConvSys1ConfigList 312}
es1ConvSys1CfgDCBus1OverrideVoltageSetPointTimeout     OBJECT-TYPE
              SYNTAX          DisplayString
              MAX-ACCESS      read-write
              STATUS          current
              DESCRIPTION    "NA"
              ::= { es1ConvSys1ConfigList 501}
es1ConvSys1CfgDCBus1OverridePowerSetPointTimeout     OBJECT-TYPE
              SYNTAX          DisplayString
              MAX-ACCESS      read-write
              STATUS          current
              DESCRIPTION    "NA"
              ::= { es1ConvSys1ConfigList 503}
es1ConvSys1CfgDCGlobalSaturationLevelAlarmSet     OBJECT-TYPE
              SYNTAX          DisplayString
              MAX-ACCESS      read-write
              STATUS          current
              DESCRIPTION    "NA"
              ::= { es1ConvSys1ConfigList 511}
es1ConvSys1CfgDCGlobalSaturationLevelAlarmClear     OBJECT-TYPE
              SYNTAX          DisplayString
              MAX-ACCESS      read-write
              STATUS          current
              DESCRIPTION    "NA"
              ::= { es1ConvSys1ConfigList 512}
es1ConvSys1CfgDCVoltageLowStart     OBJECT-TYPE
              SYNTAX          DisplayString
              MAX-ACCESS      read-write
              STATUS          current
              DESCRIPTION    "The DC input low start in volts"
              ::= { es1ConvSys1ConfigList 1000}
es1ConvSys1CfgDCVoltageLowTransfer     OBJECT-TYPE
              SYNTAX          DisplayString
              MAX-ACCESS      read-write
              STATUS          current
              DESCRIPTION    "The DC input low transfer in volts"
              ::= { es1ConvSys1ConfigList 1001}
es1ConvSys1CfgDCVoltageLowStop     OBJECT-TYPE
              SYNTAX          DisplayString
              MAX-ACCESS      read-write
              STATUS          current
              DESCRIPTION    "The DC input low stop in volts"
              ::= { es1ConvSys1ConfigList 1002}
es1ConvSys1CfgDCVoltageHighStart     OBJECT-TYPE
              SYNTAX          DisplayString
              MAX-ACCESS      read-write
              STATUS          current
              DESCRIPTION    "The DC input high start in volts"
              ::= { es1ConvSys1ConfigList 1003}
es1ConvSys1CfgDCVoltageHighTransfer     OBJECT-TYPE
              SYNTAX          DisplayString
              MAX-ACCESS      read-write
              STATUS          current
              DESCRIPTION    "The DC input high transfer in volts"
              ::= { es1ConvSys1ConfigList 1004}
es1ConvSys1CfgDCVoltageHighStop     OBJECT-TYPE
              SYNTAX          DisplayString
              MAX-ACCESS      read-write
              STATUS          current
              DESCRIPTION    "The DC input high stop in volts"
              ::= { es1ConvSys1ConfigList 1005}
es1ConvSys1CfgACInputsVoltageLowStart     OBJECT-TYPE
              SYNTAX          DisplayString
              MAX-ACCESS      read-write
              STATUS          current
              DESCRIPTION    "The AC input low start in volts"
              ::= { es1ConvSys1ConfigList 1006}
es1ConvSys1CfgACInputsVoltageLowTransfer     OBJECT-TYPE
              SYNTAX          DisplayString
              MAX-ACCESS      read-write
              STATUS          current
              DESCRIPTION    "The AC input low transfer in volts"
              ::= { es1ConvSys1ConfigList 1007}
es1ConvSys1CfgACInputsVoltageLowStop     OBJECT-TYPE
              SYNTAX          DisplayString
              MAX-ACCESS      read-write
              STATUS          current
              DESCRIPTION    "The AC input low stop in volts"
              ::= { es1ConvSys1ConfigList 1008}
es1ConvSys1CfgACInputsVoltageHighStart     OBJECT-TYPE
              SYNTAX          DisplayString
              MAX-ACCESS      read-write
              STATUS          current
              DESCRIPTION    "The AC input high start in volts"
              ::= { es1ConvSys1ConfigList 1009}
es1ConvSys1CfgACInputsVoltageHighTransfer     OBJECT-TYPE
              SYNTAX          DisplayString
              MAX-ACCESS      read-write
              STATUS          current
              DESCRIPTION    "The AC input high transfer in volts"
              ::= { es1ConvSys1ConfigList 1010}
es1ConvSys1CfgACInputsVoltageHighStop     OBJECT-TYPE
              SYNTAX          DisplayString
              MAX-ACCESS      read-write
              STATUS          current
              DESCRIPTION    "The AC input high stop in volts"
              ::= { es1ConvSys1ConfigList 1011}
es1ConvSys1CfgACInputsFrequencyLowStart     OBJECT-TYPE
              SYNTAX          DisplayString
              MAX-ACCESS      read-write
              STATUS          current
              DESCRIPTION    "The AC frequency low start in hertz"
              ::= { es1ConvSys1ConfigList 1012}
es1ConvSys1CfgACInputsFrequencyLowStop     OBJECT-TYPE
              SYNTAX          DisplayString
              MAX-ACCESS      read-write
              STATUS          current
              DESCRIPTION    "The AC frequency low stop in hertz."
              ::= { es1ConvSys1ConfigList 1013}
es1ConvSys1CfgACInputsFrequencyHighStart     OBJECT-TYPE
              SYNTAX          DisplayString
              MAX-ACCESS      read-write
              STATUS          current
              DESCRIPTION    "The AC frequency high start in hertz"
              ::= { es1ConvSys1ConfigList 1014}
es1ConvSys1CfgACInputsFrequencyHighStop     OBJECT-TYPE
              SYNTAX          DisplayString
              MAX-ACCESS      read-write
              STATUS          current
              DESCRIPTION    "The AC frequency high stop in hertz."
              ::= { es1ConvSys1ConfigList 1015}
es1ConvSys1CfgACOutsFrequencyNominal     OBJECT-TYPE
              SYNTAX          DisplayString
              MAX-ACCESS      read-write
              STATUS          current
              DESCRIPTION    "The free running frequency."
              ::= { es1ConvSys1ConfigList 1016}
es1ConvSys1CfgConverterConfAdvShortcircuitthresholdvoltage     OBJECT-TYPE
              SYNTAX          DisplayString
              MAX-ACCESS      read-write
              STATUS          current
              DESCRIPTION    "Short circuit threshold voltage"
              ::= { es1ConvSys1ConfigList 1034}
es1ConvSys1CfgConverterConfAdvShortcircuitholdtime     OBJECT-TYPE
              SYNTAX          DisplayString
              MAX-ACCESS      read-write
              STATUS          current
              DESCRIPTION    "Short circuit hold time"
              ::= { es1ConvSys1ConfigList 1035}
es1ConvSys1CfgConverterConfAdvInputsourceinPercent     OBJECT-TYPE
              SYNTAX          DisplayString
              MAX-ACCESS      read-write
              STATUS          current
              DESCRIPTION    "Input source in Percent"
              ::= { es1ConvSys1ConfigList 1036}
es1ConvSys1CfgConverterConfAdvSynchronizationtrackingspeed     OBJECT-TYPE
              SYNTAX          DisplayString
              MAX-ACCESS      read-write
              STATUS          current
              DESCRIPTION    "Synchronization tracking speed"
              ::= { es1ConvSys1ConfigList 1037}
es1ConvSys1CfgConverterConfAdvMaxcurrentPercent     OBJECT-TYPE
              SYNTAX          DisplayString
              MAX-ACCESS      read-write
              STATUS          current
              DESCRIPTION    "Max current Percent"
              ::= { es1ConvSys1ConfigList 1038}
es1ConvSys1CfgConverterConfAdvMaxpowerPercent     OBJECT-TYPE
              SYNTAX          DisplayString
              MAX-ACCESS      read-write
              STATUS          current
              DESCRIPTION    "Max power Percent"
              ::= { es1ConvSys1ConfigList 1039}
es1ConvSys1CfgConverterConfAdvMaxOverloadDuration     OBJECT-TYPE
              SYNTAX          DisplayString
              MAX-ACCESS      read-write
              STATUS          current
              DESCRIPTION    "Max Overload Duration"
              ::= { es1ConvSys1ConfigList 1040}
es1ConvSys1CfgConverterConfAdvACinmode     OBJECT-TYPE
              SYNTAX          DisplayString
              MAX-ACCESS      read-write
              STATUS          current
              DESCRIPTION    "AC in mode"
              ::= { es1ConvSys1ConfigList 1041}
es1ConvSys1CfgConverterConfAdvBooster10xIin     OBJECT-TYPE
              SYNTAX          DisplayString
              MAX-ACCESS      read-write
              STATUS          current
              DESCRIPTION    "Booster 10x I in"
              ::= { es1ConvSys1ConfigList 1042}
es1ConvSys1CfgConverterConfAdvRemoteOffDisableACInPower     OBJECT-TYPE
              SYNTAX          DisplayString
              MAX-ACCESS      read-write
              STATUS          current
              DESCRIPTION    "Remote Off Disable AC InPower"
              ::= { es1ConvSys1ConfigList 1043}
es1ConvSys1CfgConverterConfAdvReinjectionallowed     OBJECT-TYPE
              SYNTAX          DisplayString
              MAX-ACCESS      read-write
              STATUS          current
              DESCRIPTION    "Reinjection allowed"
              ::= { es1ConvSys1ConfigList 1044}
es1ConvSys1CfgConverterConfAdvExternalclock     OBJECT-TYPE
              SYNTAX          DisplayString
              MAX-ACCESS      read-write
              STATUS          current
              DESCRIPTION    "External clock"
              ::= { es1ConvSys1ConfigList 1045}
es1ConvSys1CfgConverterConfAdvWalkinmode     OBJECT-TYPE
              SYNTAX          DisplayString
              MAX-ACCESS      read-write
              STATUS          current
              DESCRIPTION    "Walk in mode"
              ::= { es1ConvSys1ConfigList 1046}
es1ConvSys1CfgConverterConfAdvTrianglemode     OBJECT-TYPE
              SYNTAX          DisplayString
              MAX-ACCESS      read-write
              STATUS          current
              DESCRIPTION    "Triangle mode"
              ::= { es1ConvSys1ConfigList 1047}
es1ConvSys1CfgConverterConfAdvAircoMode     OBJECT-TYPE
              SYNTAX          DisplayString
              MAX-ACCESS      read-write
              STATUS          current
              DESCRIPTION    "Airco Mode"
              ::= { es1ConvSys1ConfigList 1048}
es1ConvSys1CfgConverterConfAdvStartwithoutsupervision     OBJECT-TYPE
              SYNTAX          DisplayString
              MAX-ACCESS      read-write
              STATUS          current
              DESCRIPTION    "Start without supervision"
              ::= { es1ConvSys1ConfigList 1049}
es1ConvSys1CfgConverterConfAdvPDCMax     OBJECT-TYPE
              SYNTAX          DisplayString
              MAX-ACCESS      read-write
              STATUS          current
              DESCRIPTION    "P DC Max"
              ::= { es1ConvSys1ConfigList 1050}
es1ConvSys1CfgConverterConfAdvAC1stoppower     OBJECT-TYPE
              SYNTAX          DisplayString
              MAX-ACCESS      read-write
              STATUS          current
              DESCRIPTION    "AC 1 stop power"
              ::= { es1ConvSys1ConfigList 1051}
es1ConvSys1CfgConverterConfAdvAC2stoppower     OBJECT-TYPE
              SYNTAX          DisplayString
              MAX-ACCESS      read-write
              STATUS          current
              DESCRIPTION    "AC 2 stop power"
              ::= { es1ConvSys1ConfigList 1052}
es1ConvSys1CfgConverterConfAdvAC3stoppower     OBJECT-TYPE
              SYNTAX          DisplayString
              MAX-ACCESS      read-write
              STATUS          current
              DESCRIPTION    "AC 3 stop power"
              ::= { es1ConvSys1ConfigList 1053}
es1ConvSys1CfgConverterConfAdvAC4stoppower     OBJECT-TYPE
              SYNTAX          DisplayString
              MAX-ACCESS      read-write
              STATUS          current
              DESCRIPTION    "AC 4 stop power"
              ::= { es1ConvSys1ConfigList 1054}
es1ConvSys1CfgConverterConfAdvStmoduleNumber     OBJECT-TYPE
              SYNTAX          DisplayString
              MAX-ACCESS      read-write
              STATUS          current
              DESCRIPTION    "St module Number"
              ::= { es1ConvSys1ConfigList 1055}
es1ConvSys1CfgConverterConfAdvStmoduleRedundancy     OBJECT-TYPE
              SYNTAX          DisplayString
              MAX-ACCESS      read-write
              STATUS          current
              DESCRIPTION    "St module Redundancy"
              ::= { es1ConvSys1ConfigList 1056}
es1ConvSys1CfgConverterConfAdvTus     OBJECT-TYPE
              SYNTAX          DisplayString
              MAX-ACCESS      read-write
              STATUS          current
              DESCRIPTION    "Tus"
              ::= { es1ConvSys1ConfigList 1057}
es1ConvSys1CfgConverterConfAdvTusmodulesnumber     OBJECT-TYPE
              SYNTAX          DisplayString
              MAX-ACCESS      read-write
              STATUS          current
              DESCRIPTION    "Tus modules number"
              ::= { es1ConvSys1ConfigList 1058}
es1ConvSys1CfgConverterConfAdvTussubsubsystemaddress     OBJECT-TYPE
              SYNTAX          DisplayString
              MAX-ACCESS      read-write
              STATUS          current
              DESCRIPTION    "Tus sub sub system address"
              ::= { es1ConvSys1ConfigList 1059}
es1ConvSys1CfgConverterConfAdvTussubsubsystemoutputphase     OBJECT-TYPE
              SYNTAX          DisplayString
              MAX-ACCESS      read-write
              STATUS          current
              DESCRIPTION    "Tus sub sub system output phase"
              ::= { es1ConvSys1ConfigList 1060}
es1ConvSys1CfgConverterConfAdvTussubsystemindex     OBJECT-TYPE
              SYNTAX          DisplayString
              MAX-ACCESS      read-write
              STATUS          current
              DESCRIPTION    "Tus sub system index"
              ::= { es1ConvSys1ConfigList 1061}
es1ConvSys1CfgConverterConfAdvNumberoftussubsubsystem     OBJECT-TYPE
              SYNTAX          DisplayString
              MAX-ACCESS      read-write
              STATUS          current
              DESCRIPTION    "Number of tus sub sub system"
              ::= { es1ConvSys1ConfigList 1062}
es1ConvSys1CfgConverterConfAdvXTussupplySource     OBJECT-TYPE
              SYNTAX          DisplayString
              MAX-ACCESS      read-write
              STATUS          current
              DESCRIPTION    "X Tus supply Source"
              ::= { es1ConvSys1ConfigList 1063}
es1ConvSys1CfgConverterConfAdvYTussupplySource     OBJECT-TYPE
              SYNTAX          DisplayString
              MAX-ACCESS      read-write
              STATUS          current
              DESCRIPTION    "Y Tus supply Source"
              ::= { es1ConvSys1ConfigList 1064}
es1ConvSys1CfgConverterConfAdvTussubsubsystemdcgroup     OBJECT-TYPE
              SYNTAX          DisplayString
              MAX-ACCESS      read-write
              STATUS          current
              DESCRIPTION    "Tus sub sub system dc group"
              ::= { es1ConvSys1ConfigList 1065}
es1ConvSys1CfgDCSafeChargingVoltage     OBJECT-TYPE
              SYNTAX          DisplayString
              MAX-ACCESS      read-write
              STATUS          current
              DESCRIPTION    "V DC charger safe mode"
              ::= { es1ConvSys1ConfigList 1066}
es1ConvSys1CfgDCSafeDischargingPower     OBJECT-TYPE
              SYNTAX          DisplayString
              MAX-ACCESS      read-write
              STATUS          current
              DESCRIPTION    "DC power setpoint in sierra mode:
Value > 0 - mode discharge battery (if the discharge setpoint is > than the asked output power, remaining DC power is injected into the AC input port, provided it is allowed by param 044)
Value < 0 - mode charge battery"
              ::= { es1ConvSys1ConfigList 1067}
es1ConvSys1CfgACInputsPeakShavingDefaultPowerLimitation     OBJECT-TYPE
              SYNTAX          DisplayString
              MAX-ACCESS      read-write
              STATUS          current
              DESCRIPTION    "P AC peak shaving safe mode"
              ::= { es1ConvSys1ConfigList 1068}
es1ConvSys1CfgConverterConfAdvPACmaxperphasesafemode     OBJECT-TYPE
              SYNTAX          DisplayString
              MAX-ACCESS      read-write
              STATUS          current
              DESCRIPTION    "P AC max per phase safe mode"
              ::= { es1ConvSys1ConfigList 1069}
es1ConvSys1CfgConverterConfAdvPhasecompensation     OBJECT-TYPE
              SYNTAX          DisplayString
              MAX-ACCESS      read-write
              STATUS          current
              DESCRIPTION    "Phase compensation"
              ::= { es1ConvSys1ConfigList 1070}
es1ConvSys1CfgConverterConfAdvSierramode     OBJECT-TYPE
              SYNTAX          DisplayString
              MAX-ACCESS      read-write
              STATUS          current
              DESCRIPTION    "Sierra mode"
              ::= { es1ConvSys1ConfigList 1071}
es1ConvSys1CfgConverterConfAdvVDClowstopcharger     OBJECT-TYPE
              SYNTAX          DisplayString
              MAX-ACCESS      read-write
              STATUS          current
              DESCRIPTION    "V DC low stop charger"
              ::= { es1ConvSys1ConfigList 1072}
es1ConvSys1CfgConverterConfAdvLvdmode     OBJECT-TYPE
              SYNTAX          DisplayString
              MAX-ACCESS      read-write
              STATUS          current
              DESCRIPTION    "Lvd mode"
              ::= { es1ConvSys1ConfigList 1073}
es1ConvSys1CfgConverterConfAdvMaxVDCincrementsafemode     OBJECT-TYPE
              SYNTAX          DisplayString
              MAX-ACCESS      read-write
              STATUS          current
              DESCRIPTION    "Max V DC increment safe mode"
              ::= { es1ConvSys1ConfigList 1074}
es1ConvSys1CfgConverterConfAdvOutSync1     OBJECT-TYPE
              SYNTAX          DisplayString
              MAX-ACCESS      read-write
              STATUS          current
              DESCRIPTION    "Out Sync 1"
              ::= { es1ConvSys1ConfigList 1075}
es1ConvSys1CfgConverterConfAdvOutSync2     OBJECT-TYPE
              SYNTAX          DisplayString
              MAX-ACCESS      read-write
              STATUS          current
              DESCRIPTION    "Out Sync 2"
              ::= { es1ConvSys1ConfigList 1076}
es1ConvSys1CfgConverterConfAdvOutSync3     OBJECT-TYPE
              SYNTAX          DisplayString
              MAX-ACCESS      read-write
              STATUS          current
              DESCRIPTION    "Out Sync 3"
              ::= { es1ConvSys1ConfigList 1077}
es1ConvSys1CfgConverterConfAdvOutSync4     OBJECT-TYPE
              SYNTAX          DisplayString
              MAX-ACCESS      read-write
              STATUS          current
              DESCRIPTION    "Out Sync 4"
              ::= { es1ConvSys1ConfigList 1078}
es1ConvSys1CfgConverterConfAdvOutSync5     OBJECT-TYPE
              SYNTAX          DisplayString
              MAX-ACCESS      read-write
              STATUS          current
              DESCRIPTION    "Out Sync 5"
              ::= { es1ConvSys1ConfigList 1079}
es1ConvSys1CfgConverterConfAdvOutSync6     OBJECT-TYPE
              SYNTAX          DisplayString
              MAX-ACCESS      read-write
              STATUS          current
              DESCRIPTION    "Out Sync 6"
              ::= { es1ConvSys1ConfigList 1080}
es1ConvSys1CfgConverterConfAdvOutSync7     OBJECT-TYPE
              SYNTAX          DisplayString
              MAX-ACCESS      read-write
              STATUS          current
              DESCRIPTION    "Out Sync 7"
              ::= { es1ConvSys1ConfigList 1081}
es1ConvSys1CfgConverterConfAdvOutSync8     OBJECT-TYPE
              SYNTAX          DisplayString
              MAX-ACCESS      read-write
              STATUS          current
              DESCRIPTION    "Out Sync 8"
              ::= { es1ConvSys1ConfigList 1082}
es1ConvSys1CfgConverterConfAdvScalingFactor     OBJECT-TYPE
              SYNTAX          DisplayString
              MAX-ACCESS      read-write
              STATUS          current
              DESCRIPTION    "Scaling Factor"
              ::= { es1ConvSys1ConfigList 1083}
es1ConvSys1CfgConverterConfAdvTempDeratingMode     OBJECT-TYPE
              SYNTAX          DisplayString
              MAX-ACCESS      read-write
              STATUS          current
              DESCRIPTION    "Temperature Derating Mode"
              ::= { es1ConvSys1ConfigList 1084}
es1ConvSys1CfgDCInternalRegSlope     OBJECT-TYPE
              SYNTAX          DisplayString
              MAX-ACCESS      read-write
              STATUS          current
              DESCRIPTION    "NA"
              ::= { es1ConvSys1ConfigList 1087}
es1ConvSys1CfgConverterConfAdvBackFeedDetectionMode     OBJECT-TYPE
              SYNTAX          DisplayString
              MAX-ACCESS      read-write
              STATUS          current
              DESCRIPTION    "BackFeedDetectionMode"
              ::= { es1ConvSys1ConfigList 1097}
es1ConvSys1CfgConverterConfAdvSleepMode     OBJECT-TYPE
              SYNTAX          DisplayString
              MAX-ACCESS      read-write
              STATUS          current
              DESCRIPTION    "SleepMode"
              ::= { es1ConvSys1ConfigList 1098}
es1ConvSys1Control          OBJECT IDENTIFIER ::= { es1ConvSys1 16 }
es1ConvSys1ControlNumber      OBJECT-TYPE
              SYNTAX          Integer32
              MAX-ACCESS      read-only
              STATUS          current
              DESCRIPTION    "The number of entries in the Control table related to the Converter System" 
              ::= { es1ConvSys1Control 1 }
es1ConvSys1ControlTable      OBJECT-TYPE
              SYNTAX          SEQUENCE OF Es1ConvSys1ControlEntry
              MAX-ACCESS      not-accessible
              STATUS          current
              DESCRIPTION    "The table of Control entries related to the Converter System" 
              ::= { es1ConvSys1Control 2 }
es1ConvSys1ControlEntry      OBJECT-TYPE
              SYNTAX          Es1ConvSys1ControlEntry
              MAX-ACCESS      not-accessible
              STATUS          current
              DESCRIPTION    "A Control entry"
              INDEX {es1ConvSys1ControlIndex}
              ::= { es1ConvSys1ControlTable 1 }
Es1ConvSys1ControlEntry ::= 
             SEQUENCE{ 
             es1ConvSys1ControlIndex       Unsigned32,  
             es1ConvSys1ControlName        DisplayString,
             es1ConvSys1ControlValue       DisplayString, 
              es1ConvSys1ControlEntryStatus  RowStatus 
             }
es1ConvSys1ControlIndex      OBJECT-TYPE
              SYNTAX          Unsigned32
              MAX-ACCESS      not-accessible
              STATUS          current
              DESCRIPTION    "The Control entry Index"
              ::= { es1ConvSys1ControlEntry 1 }
es1ConvSys1ControlName      OBJECT-TYPE
              SYNTAX          DisplayString
              MAX-ACCESS      read-only
              STATUS          current
              DESCRIPTION    "The Control entry name"
              ::= { es1ConvSys1ControlEntry 2 }
es1ConvSys1ControlValue     OBJECT-TYPE
              SYNTAX          DisplayString
              MAX-ACCESS      read-write
              STATUS          current
              DESCRIPTION    "The Control entry value"
              ::= { es1ConvSys1ControlEntry 3 }
es1ConvSys1ControlEntryStatus      OBJECT-TYPE
              SYNTAX          RowStatus
              MAX-ACCESS      read-create
              STATUS          current
              DESCRIPTION    "The status of this table entry - not used, only for compliance"
              ::= { es1ConvSys1ControlEntry 4 }
es1ConvSys1ControlList         OBJECT IDENTIFIER ::= { es1ConvSys1Control 3 }
es1ConvSys1CtrlConvertersInventoryCleanConverterInventory     OBJECT-TYPE
              SYNTAX          DisplayString
              MAX-ACCESS      read-write
              STATUS          current
              DESCRIPTION    "Force the removal of absent modules"
              ::= { es1ConvSys1ControlList 21}
es1ConvSys1CtrlConvertersBlinkStartBlinkSequenceById     OBJECT-TYPE
              SYNTAX          DisplayString
              MAX-ACCESS      read-write
              STATUS          current
              DESCRIPTION    "NA"
              ::= { es1ConvSys1ControlList 26}
es1ConvSys1CtrlConvertersBypassSetReady     OBJECT-TYPE
              SYNTAX          DisplayString
              MAX-ACCESS      read-write
              STATUS          current
              DESCRIPTION    "NA"
              ::= { es1ConvSys1ControlList 31}
es1ConvSys1CtrlConvertersBypassReset     OBJECT-TYPE
              SYNTAX          DisplayString
              MAX-ACCESS      read-write
              STATUS          current
              DESCRIPTION    "NA"
              ::= { es1ConvSys1ControlList 36}
es1ConvSys1CtrlConvertersControlTurnAllConvertersOn     OBJECT-TYPE
              SYNTAX          DisplayString
              MAX-ACCESS      read-write
              STATUS          current
              DESCRIPTION    "NA"
              ::= { es1ConvSys1ControlList 41}
es1ConvSys1CtrlConvertersControlTurnAllConvertersOff     OBJECT-TYPE
              SYNTAX          DisplayString
              MAX-ACCESS      read-write
              STATUS          current
              DESCRIPTION    "NA"
              ::= { es1ConvSys1ControlList 42}
es1ConvSys1CtrlACOutsGlobalTurnAllConvertersOn     OBJECT-TYPE
              SYNTAX          DisplayString
              MAX-ACCESS      read-write
              STATUS          current
              DESCRIPTION    "NA"
              ::= { es1ConvSys1ControlList 101}
es1ConvSys1CtrlACOutsGlobalTurnAllConvertersOff     OBJECT-TYPE
              SYNTAX          DisplayString
              MAX-ACCESS      read-write
              STATUS          current
              DESCRIPTION    "NA"
              ::= { es1ConvSys1ControlList 102}
es1ConvSys1CtrlACInputsPeakShavingOverridePowerLimitation     OBJECT-TYPE
              SYNTAX          DisplayString
              MAX-ACCESS      read-write
              STATUS          current
              DESCRIPTION    "Set Peak Shaving Value for all phases"
              ::= { es1ConvSys1ControlList 301}
es1ConvSys1CtrlDCBus1OverrideVoltageSetPoint     OBJECT-TYPE
              SYNTAX          DisplayString
              MAX-ACCESS      read-write
              STATUS          current
              DESCRIPTION    "Set DC regulation voltage"
              ::= { es1ConvSys1ControlList 501}
es1ConvSys1CtrlDCBus1OverridePowerSetPoint     OBJECT-TYPE
              SYNTAX          DisplayString
              MAX-ACCESS      read-write
              STATUS          current
              DESCRIPTION    "Set DC regulation power"
              ::= { es1ConvSys1ControlList 503}
es1ConvSys1CtrlDCBus1TurnAllConvertersOn     OBJECT-TYPE
              SYNTAX          DisplayString
              MAX-ACCESS      read-write
              STATUS          current
              DESCRIPTION    "NA"
              ::= { es1ConvSys1ControlList 511}
es1ConvSys1CtrlDCBus1TurnAllConvertersOff     OBJECT-TYPE
              SYNTAX          DisplayString
              MAX-ACCESS      read-write
              STATUS          current
              DESCRIPTION    "NA"
              ::= { es1ConvSys1ControlList 512}
es1ConvSys1CtrlGatewayGlobalApplyConf     OBJECT-TYPE
              SYNTAX          DisplayString
              MAX-ACCESS      read-write
              STATUS          current
              DESCRIPTION    "Force send of parameters"
              ::= { es1ConvSys1ControlList 601}
es1ConvSys1CtrlGatewayGlobalReadConf     OBJECT-TYPE
              SYNTAX          DisplayString
              MAX-ACCESS      read-write
              STATUS          current
              DESCRIPTION    "Force send of parameters"
              ::= { es1ConvSys1ControlList 602}
es1ConvSys1CtrlGatewayGlobalResetDefaultConf     OBJECT-TYPE
              SYNTAX          DisplayString
              MAX-ACCESS      read-write
              STATUS          current
              DESCRIPTION    "Restore the default module configuration"
              ::= { es1ConvSys1ControlList 603}
es1ConvSys1CtrlGatewayGlobalOverwriteConf     OBJECT-TYPE
              SYNTAX          DisplayString
              MAX-ACCESS      read-write
              STATUS          current
              DESCRIPTION    "Send manual module configuration array, comma separated"
              ::= { es1ConvSys1ControlList 604}
es1ConvSys1CtrlGenericEventsClearMyEvents     OBJECT-TYPE
              SYNTAX          DisplayString
              MAX-ACCESS      read-write
              STATUS          current
              DESCRIPTION    "By writing '1' to this control element, all the events of this equipment will be cleared."
              ::= { es1ConvSys1ControlList 1001}
es1ConvSys1CtrlGenericEventsClearAllEvents     OBJECT-TYPE
              SYNTAX          DisplayString
              MAX-ACCESS      read-write
              STATUS          current
              DESCRIPTION    "By writing '1' to this control element, all the events of this equipment and all the events of all the sub-equipments will be cleared."
              ::= { es1ConvSys1ControlList 1002}
es1ConvSys1CtrlGenericEventsAddEvent     OBJECT-TYPE
              SYNTAX          DisplayString
              MAX-ACCESS      read-write
              STATUS          current
              DESCRIPTION    "This control element adds an event of severity none. The event name is the text written to this control element"
              ::= { es1ConvSys1ControlList 1011}
es1ConvSys1CtrlGenericEventsAddMajorEvent     OBJECT-TYPE
              SYNTAX          DisplayString
              MAX-ACCESS      read-write
              STATUS          current
              DESCRIPTION    "This control element adds an event of severity major. The event name is the text written to this control element"
              ::= { es1ConvSys1ControlList 1012}
es1ConvSys1CtrlGenericRenamingResetDefaultNamesAndGroups     OBJECT-TYPE
              SYNTAX          DisplayString
              MAX-ACCESS      read-write
              STATUS          current
              DESCRIPTION    "This control element resets all the element Names, Groups and Subgroups to default values for this equipment"
              ::= { es1ConvSys1ControlList 1021}
es1ConvSys1CtrlGenericRenamingResetNameGroupRecursive     OBJECT-TYPE
              SYNTAX          DisplayString
              MAX-ACCESS      read-write
              STATUS          current
              DESCRIPTION    "This control element resets all the element Names, Groups and Subgroups to default values for this equipment and all sub equipments"
              ::= { es1ConvSys1ControlList 1022}
es1ConvSys1Notifications           OBJECT IDENTIFIER ::= { es1ConvSys1 18 }
es1ConvSys1NotificationPrefix      OBJECT IDENTIFIER ::= { es1ConvSys1Notifications 0 }
es1ConvSys1NotificationOfEvent NOTIFICATION-TYPE
          OBJECTS {
          es1ConvSys1EventId,
          es1ConvSys1EventName,
          es1ConvSys1EventDateTime,
          es1ConvSys1EventSeverityType,
          es1ConvSys1EventSeverityLevel,
          es1ConvSys1AlarmSummary
          }
          STATUS current
          DESCRIPTION  "Notification generated when a new event appears"
          ::= { es1ConvSys1NotificationPrefix 1 }

es1ConvSys1Compliance OBJECT IDENTIFIER ::= { es1ConvSys1 19}
es1ConvSys1ComplianceGroups OBJECT IDENTIFIER ::={ es1ConvSys1Compliance 1}
es1ConvSys1FullCompliance MODULE-COMPLIANCE
    STATUS current
    DESCRIPTION " The compliance statement for SNMPV2 entities which implement the SNMPV2 MIB. "
    MODULE
        MANDATORY-GROUPS { es1ConvSys1GlobalGroup, es1ConvSys1NotificationGroup }
    ::= { es1ConvSys1Compliance 2 }

es1ConvSys1GlobalGroup OBJECT-GROUP
     OBJECTS{es1ConvSys1GlobalStatus, es1ConvSys1GlobalAlarmSeverityType, es1ConvSys1GlobalAlarmSeverityLevel, es1ConvSys1GlobalAlarmSeverityTypeInt, es1ConvSys1DescriptionNumber, es1ConvSys1DescriptionName, es1ConvSys1DescriptionValue, es1ConvSys1DescriptionEntryStatus, es1ConvSys1DescDescriptionCustomDescriptionDescription, es1ConvSys1DescDescriptionCustomDescriptionReference, es1ConvSys1DescConvertersModel, es1ConvSys1DescACInputsGlobalSourceType, es1ConvSys1DescACInputsGlobalSourceName, es1ConvSys1DescGatewayGW1SerialNumber, es1ConvSys1DescGatewayGW1SoftwareVersion, es1ConvSys1DescGatewayGW1HardwareReference, es1ConvSys1DescGatewayGW1IPAddress, es1ConvSys1AlarmNumber, es1ConvSys1AlarmName, es1ConvSys1AlarmActive, es1ConvSys1AlarmSeverityType, es1ConvSys1AlarmSeverityLevel, es1ConvSys1AlarmStartTime, es1ConvSys1AlarmStopTime, es1ConvSys1AlarmEntryStatus, es1ConvSys1AlarmSummary, es1ConvSys1EventNumber, es1ConvSys1EventId, es1ConvSys1EventName, es1ConvSys1EventDateTime, es1ConvSys1EventSeverityType, es1ConvSys1EventSeverityLevel, es1ConvSys1EventEntryStatus, es1ConvSys1DataNumber, es1ConvSys1DataName, es1ConvSys1DataValue, es1ConvSys1DataEntryStatus, es1ConvSys1DataConvertersBypassState, es1ConvSys1DataACOutsGlobalCurrent, es1ConvSys1DataACOutsGlobalActivePower, es1ConvSys1DataACOutsGlobalApparentPower, es1ConvSys1DataACOutsGlobalStatus, es1ConvSys1DataACOutsGlobalMembers, es1ConvSys1DataACOutsGlobalInstalledActivePower, es1ConvSys1DataACOutsGlobalInstalledApparentPower, es1ConvSys1DataACOutsGlobalAvailableActivePower, es1ConvSys1DataACOutsGlobalAvailableApparentPower, es1ConvSys1DataACOutsGlobalPowerFactor, es1ConvSys1DataACOutsGlobalSaturationLevel, es1ConvSys1DataACOutsPhase1Voltage, es1ConvSys1DataACOutsPhase1Current, es1ConvSys1DataACOutsPhase1ActivePower, es1ConvSys1DataACOutsPhase1ApparentPower, es1ConvSys1DataACOutsPhase1Frequency, es1ConvSys1DataACOutsPhase1Status, es1ConvSys1DataACOutsPhase1Members, es1ConvSys1DataACOutsPhase1InstalledActivePower, es1ConvSys1DataACOutsPhase1InstalledApparentPower, es1ConvSys1DataACOutsPhase1AvailableActivePower, es1ConvSys1DataACOutsPhase1AvailableApparentPower, es1ConvSys1DataACOutsPhase1PowerFactor, es1ConvSys1DataACOutsPhase1SaturationLevel, es1ConvSys1DataACInputsGlobalCurrent, es1ConvSys1DataACInputsGlobalActivePower, es1ConvSys1DataACInputsGlobalApparentPower, es1ConvSys1DataACInputsGlobalStatus, es1ConvSys1DataACInputsGlobalInstalledActivePower, es1ConvSys1DataACInputsGlobalInstalledApparentPower, es1ConvSys1DataACInputsGlobalAvailableActivePower, es1ConvSys1DataACInputsGlobalAvailableApparentPower, es1ConvSys1DataACInputsGlobalSaturationLevel, es1ConvSys1DataACInputsPhase1Voltage, es1ConvSys1DataACInputsPhase1Current, es1ConvSys1DataACInputsPhase1ActivePower, es1ConvSys1DataACInputsPhase1ApparentPower, es1ConvSys1DataACInputsPhase1Frequency, es1ConvSys1DataACInputsPhase1Status, es1ConvSys1DataACInputsPhase1InstalledActivePower, es1ConvSys1DataACInputsPhase1InstalledApparentPower, es1ConvSys1DataACInputsPhase1AvailableActivePower, es1ConvSys1DataACInputsPhase1AvailableApparentPower, es1ConvSys1DataACInputsPhase1SaturationLevel, es1ConvSys1DataDCBus1Voltage, es1ConvSys1DataDCBus1Current, es1ConvSys1DataDCBus1Power, es1ConvSys1DataDCBus1VoltageSetPoint, es1ConvSys1DataDCBus1PowerSetpoint, es1ConvSys1DataDCBus1Status, es1ConvSys1DataDCBus1Members, es1ConvSys1DataDCBus1InstalledPower, es1ConvSys1DataDCBus1AvailablePower, es1ConvSys1DataDCBus1StatusCharger, es1ConvSys1DataDCBus1SaturationLevel, es1ConvSys1DataGatewayGW1BusStatus, es1ConvSys1DataGatewayGW1ConfStatus, es1ConvSys1DataGatewayGW1LastConfSendingState, es1ConvSys1DataGatewayGW1LastConfSendingMessage, es1ConvSys1DataGatewayGW1LastConfSendingDetails, es1ConvSys1DataSynchronizerGlobalStatus, es1ConvSys1DataSynchronizerGlobalMembers, es1ConvSys1DataSynchronizerGlobalOK, es1ConvSys1DataSynchronizerPhase1Status, es1ConvSys1DataSynchronizerPhase1Members, es1ConvSys1DataSynchronizerPhase1OK, es1ConvSys1ConfigNumber, es1ConvSys1ConfigName, es1ConvSys1ConfigValue, es1ConvSys1ConfigEntryStatus, es1ConvSys1CfgSystemGlobalTopology, es1ConvSys1CfgSystemACNumberOfPhases, es1ConvSys1CfgConvertersAllowFullRemoteControl, es1ConvSys1CfgACOutsGlobalSaturationLevelAlarmSet, es1ConvSys1CfgACOutsGlobalSaturationLevelAlarmClear, es1ConvSys1CfgACOutsPhase1ConfiguredConverters, es1ConvSys1CfgACOutsPhase1RedundantConverters, es1ConvSys1CfgACOutsPhase1NominalPhaseShift, es1ConvSys1CfgACOutsPhase1NominalVoltage, es1ConvSys1CfgACInputsPeakShavingOverridePowerLimitationTimeout, es1ConvSys1CfgACInputsGlobalSaturationLevelAlarmSet, es1ConvSys1CfgACInputsGlobalSaturationLevelAlarmClear, es1ConvSys1CfgDCBus1OverrideVoltageSetPointTimeout, es1ConvSys1CfgDCBus1OverridePowerSetPointTimeout, es1ConvSys1CfgDCGlobalSaturationLevelAlarmSet, es1ConvSys1CfgDCGlobalSaturationLevelAlarmClear, es1ConvSys1CfgDCVoltageLowStart, es1ConvSys1CfgDCVoltageLowTransfer, es1ConvSys1CfgDCVoltageLowStop, es1ConvSys1CfgDCVoltageHighStart, es1ConvSys1CfgDCVoltageHighTransfer, es1ConvSys1CfgDCVoltageHighStop, es1ConvSys1CfgACInputsVoltageLowStart, es1ConvSys1CfgACInputsVoltageLowTransfer, es1ConvSys1CfgACInputsVoltageLowStop, es1ConvSys1CfgACInputsVoltageHighStart, es1ConvSys1CfgACInputsVoltageHighTransfer, es1ConvSys1CfgACInputsVoltageHighStop, es1ConvSys1CfgACInputsFrequencyLowStart, es1ConvSys1CfgACInputsFrequencyLowStop, es1ConvSys1CfgACInputsFrequencyHighStart, es1ConvSys1CfgACInputsFrequencyHighStop, es1ConvSys1CfgACOutsFrequencyNominal, es1ConvSys1CfgConverterConfAdvShortcircuitthresholdvoltage, es1ConvSys1CfgConverterConfAdvShortcircuitholdtime, es1ConvSys1CfgConverterConfAdvInputsourceinPercent, es1ConvSys1CfgConverterConfAdvSynchronizationtrackingspeed, es1ConvSys1CfgConverterConfAdvMaxcurrentPercent, es1ConvSys1CfgConverterConfAdvMaxpowerPercent, es1ConvSys1CfgConverterConfAdvMaxOverloadDuration, es1ConvSys1CfgConverterConfAdvACinmode, es1ConvSys1CfgConverterConfAdvBooster10xIin, es1ConvSys1CfgConverterConfAdvRemoteOffDisableACInPower, es1ConvSys1CfgConverterConfAdvReinjectionallowed, es1ConvSys1CfgConverterConfAdvExternalclock, es1ConvSys1CfgConverterConfAdvWalkinmode, es1ConvSys1CfgConverterConfAdvTrianglemode, es1ConvSys1CfgConverterConfAdvAircoMode, es1ConvSys1CfgConverterConfAdvStartwithoutsupervision, es1ConvSys1CfgConverterConfAdvPDCMax, es1ConvSys1CfgConverterConfAdvAC1stoppower, es1ConvSys1CfgConverterConfAdvAC2stoppower, es1ConvSys1CfgConverterConfAdvAC3stoppower, es1ConvSys1CfgConverterConfAdvAC4stoppower, es1ConvSys1CfgConverterConfAdvStmoduleNumber, es1ConvSys1CfgConverterConfAdvStmoduleRedundancy, es1ConvSys1CfgConverterConfAdvTus, es1ConvSys1CfgConverterConfAdvTusmodulesnumber, es1ConvSys1CfgConverterConfAdvTussubsubsystemaddress, es1ConvSys1CfgConverterConfAdvTussubsubsystemoutputphase, es1ConvSys1CfgConverterConfAdvTussubsystemindex, es1ConvSys1CfgConverterConfAdvNumberoftussubsubsystem, es1ConvSys1CfgConverterConfAdvXTussupplySource, es1ConvSys1CfgConverterConfAdvYTussupplySource, es1ConvSys1CfgConverterConfAdvTussubsubsystemdcgroup, es1ConvSys1CfgDCSafeChargingVoltage, es1ConvSys1CfgDCSafeDischargingPower, es1ConvSys1CfgACInputsPeakShavingDefaultPowerLimitation, es1ConvSys1CfgConverterConfAdvPACmaxperphasesafemode, es1ConvSys1CfgConverterConfAdvPhasecompensation, es1ConvSys1CfgConverterConfAdvSierramode, es1ConvSys1CfgConverterConfAdvVDClowstopcharger, es1ConvSys1CfgConverterConfAdvLvdmode, es1ConvSys1CfgConverterConfAdvMaxVDCincrementsafemode, es1ConvSys1CfgConverterConfAdvOutSync1, es1ConvSys1CfgConverterConfAdvOutSync2, es1ConvSys1CfgConverterConfAdvOutSync3, es1ConvSys1CfgConverterConfAdvOutSync4, es1ConvSys1CfgConverterConfAdvOutSync5, es1ConvSys1CfgConverterConfAdvOutSync6, es1ConvSys1CfgConverterConfAdvOutSync7, es1ConvSys1CfgConverterConfAdvOutSync8, es1ConvSys1CfgConverterConfAdvScalingFactor, es1ConvSys1CfgConverterConfAdvTempDeratingMode, es1ConvSys1CfgDCInternalRegSlope, es1ConvSys1CfgConverterConfAdvBackFeedDetectionMode, es1ConvSys1CfgConverterConfAdvSleepMode, es1ConvSys1ControlNumber, es1ConvSys1ControlName, es1ConvSys1ControlValue, es1ConvSys1ControlEntryStatus, es1ConvSys1CtrlConvertersInventoryCleanConverterInventory, es1ConvSys1CtrlConvertersBlinkStartBlinkSequenceById, es1ConvSys1CtrlConvertersBypassSetReady, es1ConvSys1CtrlConvertersBypassReset, es1ConvSys1CtrlConvertersControlTurnAllConvertersOn, es1ConvSys1CtrlConvertersControlTurnAllConvertersOff, es1ConvSys1CtrlACOutsGlobalTurnAllConvertersOn, es1ConvSys1CtrlACOutsGlobalTurnAllConvertersOff, es1ConvSys1CtrlACInputsPeakShavingOverridePowerLimitation, es1ConvSys1CtrlDCBus1OverrideVoltageSetPoint, es1ConvSys1CtrlDCBus1OverridePowerSetPoint, es1ConvSys1CtrlDCBus1TurnAllConvertersOn, es1ConvSys1CtrlDCBus1TurnAllConvertersOff, es1ConvSys1CtrlGatewayGlobalApplyConf, es1ConvSys1CtrlGatewayGlobalReadConf, es1ConvSys1CtrlGatewayGlobalResetDefaultConf, es1ConvSys1CtrlGatewayGlobalOverwriteConf, es1ConvSys1CtrlGenericEventsClearMyEvents, es1ConvSys1CtrlGenericEventsClearAllEvents, es1ConvSys1CtrlGenericEventsAddEvent, es1ConvSys1CtrlGenericEventsAddMajorEvent, es1ConvSys1CtrlGenericRenamingResetDefaultNamesAndGroups, es1ConvSys1CtrlGenericRenamingResetNameGroupRecursive}
     STATUS       current
     DESCRIPTION  "text"
     ::= { es1ConvSys1ComplianceGroups 1 }

es1ConvSys1NotificationGroup NOTIFICATION-GROUP
     NOTIFICATIONS {es1ConvSys1NotificationOfEvent}
     STATUS       current
     DESCRIPTION  "text"
     ::= { es1ConvSys1ComplianceGroups 2 }



es1InverterSystems   OBJECT IDENTIFIER ::= { es1 25 }
es1RemoteDcSystems   OBJECT IDENTIFIER ::= { es1 27 }
es1RemotePowerFeedingSystems   OBJECT IDENTIFIER ::= { es1 28 }


 END
